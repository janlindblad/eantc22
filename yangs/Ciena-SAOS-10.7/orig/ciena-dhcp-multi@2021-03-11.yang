module ciena-dhcp-multi {
  namespace "http://www.ciena.com/ns/yang/ciena-dhcp-multi";
  prefix dhcp-multi;

  import ietf-inet-types {
    prefix inet;
  }

  import openconfig-interfaces {
    prefix "oc-if";
  }

  import ciena-dhcp {
    prefix dhcp;
  }

  organization
    "Ciena Corporation";

  contact
    "Web URL: http://www.ciena.com/
     E-mail:  yang@ciena.com
     Postal:  7035 Ridge Road
              Hanover, Maryland 21076
              U.S.A.
     Phone:   +1 800-921-1144
     Fax:     +1 410-694-5750";

  description
    "This YANG module defines Ciena's augmentations to the ciena-dhcp
     model for the purpose of adding support for DHCP clients on
     multiple interfaces.

     Copyright (c) 2016 Ciena Corporation.  All rights reserved.

     All information contained herein is, and remains the property of
     Ciena Corporation. Dissemination of this information or
     reproduction of this material is strictly forbidden unless prior
     written permission is obtained from Ciena Corporation.";

  revision 2021-03-11 {
    description
       "Added client identifier option";
    reference
       "RFC 4361 for DHCPv4";
  }

  revision 2019-09-05 {
    description
       "Added default value for subnet-mask option.";
    reference
       "Ciena Functional Specification.";
  }

  revision 2018-06-28 {
    description
      "Initial revision.";
    reference
      "RFC 2131, Dynamic Host Configuration Protocol
       RFC 2132, DHCP Options and BOOTP Vendor Extensions
       RFC 3046, DHCP Relay Agent Information Option
       RFC 3925, Vendor-Identifying Vendor Options for
                 Dynamic Host Configuration Protocol version 4
                 (DHCPv4)";
  }

  augment "/dhcp:dhcp-client" {
    description
      "Augmentation of dhcp-client to include multiple instances, one
       per interface.";

    list client {
      key interface-name;
      description
        "A client may have several interfaces, it is more reasonable
         to configure and manage parameters on the interface-level.
         The list defines specific client interfaces and their data.
         Different interfaces are distinguished by the key which is
         a configurable string value.";
      leaf interface-name {
        type oc-if:base-interface-ref;
        mandatory true;
        description
          "Interface name";
      }

      leaf admin-enable {
        type boolean;
        description
          "The administrative state of this DHCP client.";
      }

      leaf requested-lease-time {
        type uint32 {
          range "45..4294967294";
        }
        units seconds;
        description
          "The lease time requested from the server, in seconds.  Uses
           the IP Address Lease Time option, option 51.";
        reference
          "RFC 2132, Section 9.2";
      }

      leaf client-identifier {
        type enumeration {
          enum chassis-id {
            description
              "The value chassis-id indicates that the DHCP
               client-identifier will contain chassis serial number." ;
          }
          enum mac-address {
            description
              "The value mac-address indicates that the DHCP
               client-identifier will contain interface mac-address." ;
          }
          enum IAID-DUID {
            description
              "The value IAID followed by DUID-EN as defined RFC4361
               that the IAID will be derived from interface mac-address
               and DUID will contain chassis-id." ;
          }
        }
        default chassis-id;
        description
          "This option is used by DHCP clients to specify their unique
           identifier. This value is expected to be unique for all
           clients in an administrative domain.";
        reference
          "RFC 2132, RFC 4361";
      }

      container option-enable {
        description
          "Specifies the option codes to be included in the Parameter
           Request List option, option 55, and to be used if received.
           (An option may be included in the Parameter Request List even
           if not enabled, but it will be ignored if received if it is
           not enabled.)";
        reference
          "RFC 2132, Section 9.8";

        leaf subnet-mask {
          type boolean;
            default true;
          description
            "Subnet Mask option, option 1";
          reference
            "RFC 2132, Section 3.3";
        }

        leaf time-offset {
          type boolean;
          description
            "Time Offset option, option 2";
          reference
            "RFC 2132, Section 3.4";
        }

        leaf router {
          type boolean;
          description
            "Router Option, option 3";
          reference
            "RFC 2132, Section 3.5";
        }

        leaf domain-name-server {
          type boolean;
          description
            "Domain Name Server Option, option 6";
          reference
            "RFC 2132, Section 3.8";
        }

        leaf log-server {
          type boolean;
          description
            "Log Server Option, option 7";
          reference
            "RFC 2132, Section 3.9";
        }

        leaf host-name {
          type boolean;
          description
            "Host Name Option, option 12";
          reference
            "RFC 2132, Section 3.14";
        }

        leaf domain-name {
          type boolean;
          description
            "Domain Name option, option 15";
          reference
            "RFC 2132, Section 3.17";
        }

        leaf ntp-servers {
          type boolean;
          description
            "Network Time Protocol (NTP) Servers Option, option 42";
          reference
            "RFC 2132, Section 8.3";
        }

        leaf lease-time {
          type boolean;
          description
            "IP Address Lease Time, option 51";
          reference
            "RFC 2132, Section 9.2";
        }

        leaf tftp-server-name {
          type boolean;
          description
            "TFTP Server Name option, option 66";
          reference
            "RFC 2132, Section 9.4";
        }

        leaf bootfile-name {
          type boolean;
          description
            "Bootfile Name option, option 67";
          reference
            "RFC 2132, Section 9.5";
        }

        leaf vivsi {
          type boolean;
          description
            "Vendor-Identifying Vendor-Specific Information Option,
             option 125";
          reference
            "RFC 3925, Section 4";
        }
      }
    }
  }

  augment "/dhcp:dhcp-client-state" {
    description
      "Augmentation of dhcp-client-state to include multiple instances,
       one per interface.";

    list client {
      key interface-name;
      description
        "A client may have several interfaces, it is more reasonable
         to configure and manage parameters on the interface-level.
         The list defines specific client interfaces and their data.
         Different interfaces are distinguished by the key which is
         a configurable string value.";
      leaf interface-name {
        type oc-if:base-interface-ref;
        mandatory true;
        description
          "Interface name";
      }

      leaf oper-enabled {
        type boolean;
        description
          "The global operational state of this DHCP client.";
      }

      leaf dhcp-state {
        type string;
        description
          "The state of this DHCP client, as described in RFC 2131.";
      }

      leaf lease-time {
        type uint32;
        units seconds;
        description
          "The duration of the current lease in seconds.  The received
           value of the IP Address Least Time option, option 51.";
        reference
          "RFC 2132, Section 9.2";
      }

      leaf lease-time-remaining {
        type uint32;
        units seconds;
        description
          "The remaining time of the current lease in seconds.";
      }

      leaf renewal-time {
        type uint32;
        units seconds;
        description
          "The initial time before the current lease is renewed (T1), in
           seconds.";
      }

      leaf renewal-time-remaining {
        type uint32;
        units seconds;
        description
          "The remaining time before the current lease is renewed (T1),
           in seconds.";
      }

      leaf rebinding-time {
        type uint32;
        units seconds;
        description
          "The initial time before the current lease is rebound (T2), in
           seconds.";
      }

      leaf rebinding-time-remaining {
        type uint32;
        units seconds;
        description
          "The remaining time before the current lease is rebound (T2),
           in seconds.";
      }

      leaf dhcp-server-identifier {
        type inet:ipv4-address;
        description
          "The IP address of the server providing the current lease.
           The received value of the Server Identifier option, option
           54.";
        reference
          "RFC 2132, Section 9.7";
      }

      container option-value {
        description
          "Contains the values of options received.";

        leaf subnet-mask {
          type inet:ipv4-address;
          description
            "Subnet Mask option, option 1";
          reference
            "RFC 2132, Section 3.3";
        }

        leaf time-offset {
          type int32;
          units seconds;
          description
            "Time Offset option, option 2.  Offset from Coordinated
             Universal Time (UTC), in seconds.";
          reference
            "RFC 2132, Section 3.4";
        }

        leaf-list router {
          type inet:ipv4-address;
          max-elements 63;
          description
            "Router Option, option 3";
          reference
            "RFC 2132, Section 3.5";
        }
  
        leaf-list domain-name-server {
          type inet:ipv4-address;
          max-elements 63;
          description
            "Domain Name Server Option, option 6";
          reference
            "RFC 2132, Section 3.8";
        }
  
        leaf-list log-server {
          type inet:ipv4-address;
          max-elements 63;
          description
            "Log Server Option, option 7";
          reference
            "RFC 2132, Section 3.9";
        }

        leaf host-name {
          type string;
          description
            "Host Name Option, option 12";
          reference
            "RFC 2132, Section 3.14";
        }

        leaf domain-name {
          type string;
          description
            "Domain Name option, option 15";
          reference
            "RFC 2132, Section 3.17";
        }

        leaf-list ntp-servers {
          type inet:ipv4-address;
          max-elements 63;
          description
            "Network Time Protocol (NTP) Servers Option, option 42";
          reference
            "RFC 2132, Section 8.3";
        }

        leaf lease-time {
          type uint32;
          units seconds;
          description
            "IP Address Lease Time, option 51, in seconds";
          reference
            "RFC 2132, Section 9.2";
        }

        leaf tftp-server-name {
          type string;
          description
            "TFTP Server Name option, option 66";
          reference
            "RFC 2132, Section 9.4";
        }

        leaf bootfile-name {
          type string;
          description
            "Bootfile Name option, option 67";
          reference
            "RFC 2132, Section 9.5";
        }

        leaf bootfile-uri {
          type string;
          description
            "Ciena Bootfile URI Sub-Option (16) of the
             Vendor-Identifying Vendor-Specific Information Option,
             option 125";
          reference
            "RFC 3925, Section 4";
        }
      }
    }
  }

  augment "/dhcp:dhcp-client-lease-renew/dhcp:input" {
    description
      "Augmentation of dhcp-client-lease-renew to include the interface
       name.";
  
    leaf interface-name {
      type oc-if:base-interface-ref;
      description
        "Interface name.  This must be optional because it was not part
         of earlier revisions.  If no interface-name is given, all
         operationally-enabled clients are told to renew their leases.";
    }
  }
}
