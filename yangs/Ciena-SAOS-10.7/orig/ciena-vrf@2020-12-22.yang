module ciena-vrf {
    namespace   "urn:ciena:params:xml:ns:yang:ciena:ciena-vrf";
    prefix "vrf";

    organization
        "Ciena Corporation";

    contact
        "Web URL: http://www.ciena.com/
         E-mail:  yang@ciena.com
         Postal:  7035 Ridge Road
                  Hanover, Maryland 21076
                      U.S.A.
         Phone:   +1 800-921-1144
         Fax:     +1 410-694-5750";

    description
        "This YANG module defines Ciena's VPN Routing/Forwarding model.

         Copyright (c) 2018  Ciena Corporation.  All rights
         reserved.

         All information contained herein is, and remains the
         property of Ciena Corporation. Dissemination of this
         information or reproduction of this material is strictly
         forbidden unless prior written permission is obtained
         from Ciena Corporation.";


    revision "2020-12-22" {
        description "Added color and fallback for SR policy.";
    }

    revision "2016-10-29" {
        description "Modifications to auto-generate clis.";
    }

    grouping vrf-grouping {
         list vrf {
            key "vrfName";
            max-elements 129;
            description
               "Virtual Routing Forwarding (VRF) Instance";
            leaf vrfName  {
               type  string {
                  length "1..15";
               }
               description "Routing Forwarding Instance Name";
            }

            leaf description  {
               type  string {
                  length "0..255";
               }
               description 
                "Description of VRF";
            }

            container sr-policy {
              description
                "Segment Routing (SR) Policy";
              leaf color {
                type uint32;
                description
                  "Color associated with the SR policy";
              }

              leaf fallback {
                type enumeration {
                  enum enable {
                    description
                      "Specifies fallback as enable";
                  }
                  enum disable {
                    description
                      "Specifies fallback as disable";
                  }
                }
                default "enable";
                description
                  "Fallback enable is used when the SR policy is down.
                   The service will still continue to be UP, but
                   will fall back to labeled IGP shortest path.";
              }
            }
        }
    }

    uses vrf-grouping;
}
