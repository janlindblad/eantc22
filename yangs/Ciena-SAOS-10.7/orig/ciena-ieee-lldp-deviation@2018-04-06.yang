module ciena-ieee-lldp-deviation {

  namespace "http://www.ciena.com/ns/yang/ciena-ieee-lag-dev";
  prefix ciena-ieee-lldp-dev;

  import ciena-ieee-lldp {
    prefix ciena-ieee-lldp;
  }
 
  import openconfig-interfaces { prefix oc-if; }
 
  revision 2018-04-06 {
    description
     "Initial Revision";
  }

  deviation /oc-if:interfaces/oc-if:interface/oc-if:config/ciena-ieee-lldp:dot1-port-config {
    deviate not-supported;
  }
  
  deviation /oc-if:interfaces/oc-if:interface/oc-if:state/ciena-ieee-lldp:lldp-dot1-port-operational {
    deviate not-supported;
  }
  
  deviation /oc-if:interfaces/oc-if:interface/oc-if:state/ciena-ieee-lldp:lldp-remote-port-operational/ciena-ieee-lldp:dot1-remote-entry {
    deviate not-supported;
  }
}
