module ciena-sync-external {
  namespace "http://www.ciena.com/ns/yang/ciena-sync-external";
  prefix "ext";

  import ciena-sync {
    prefix sync;
  }

  organization
    "Ciena Corporation";

  contact
    "Web URL: http://www.ciena.com/
     E-mail:  yang@ciena.com
     Postal:  7035 Ridge Road
     Hanover, Maryland 21076
     U.S.A.
     Phone:   +1 800-921-1144
     Fax:     +1 410-694-5750";

  description
    "This YANG module defines Ciena's data model for the management of clock
     synchronization in packet networks specific to External timing references.

     Copyright (c) 2018 Ciena Corporation. All rights reserved.

     All information contained herein is, and remains the property of Ciena
     Corporation. Dissemination of this information or reproduction of this
     material is strictly forbidden unless prior written permission is obtained
     from Ciena Corporation.";

  revision "2020-02-18" {
    description
      "Change pulse-width default value, range and yang model support for PPS input references.
       Add SMB-1 to external timing interface types.";
    reference
      "ITU-T G.703: Physical/electrical characteristics of hierarchical digital
      interfaces.";
  }

  revision "2018-10-10" {
    description
      "Support CLK interface.";
    reference
      "ITU-T G.703: Physical/electrical characteristics of hierarchical digital
                    interfaces.";
  }

  revision "2018-09-10" {
    description
      "Initial version.";
    reference
      "ITU-T G.703: Physical/electrical characteristics of hierarchical digital
                    interfaces.";
  }

  /*
   * Identities
   */

  identity sync-external-timing-interface-identity {
    description
      "Base identity from which specific external timing interface types are
       derived.";
  }

  identity smb-clk-1 {
    base ext:sync-external-timing-interface-identity;
    description
      "CLK (1) SMB interface.";
  }

  identity smb-1pps-1 {
    base ext:sync-external-timing-interface-identity;
    description
      "1PPS (1) SMB interface.";
  }

  identity rj45-sync-1 {
    base ext:sync-external-timing-interface-identity;
    description
      "SYNC (1) RJ45 interface.";
  }

  identity smb-1 {
    base ext:sync-external-timing-interface-identity;
    description
      "CLK or 1PPS (1) SMB interface.";
  }

  /*
   * Typedefs
   */

  typedef interface-type {
    type identityref {
      base ext:sync-external-timing-interface-identity;
    }
    description
      "External timing interface type.";
  }

  typedef clk-input-reference-leafref-type {
    type leafref {
      path "/sync:sync" + 
           "/sync:input-references" + 
           "/ext:clk-input-reference" + 
           "/ext:name";
    }
    description
      "CLK input reference leafref type.";
  }

  typedef clk-output-reference-leafref-type {
    type leafref {
      path "/sync:sync" + 
           "/sync:output-references" + 
           "/ext:clk-output-reference" + 
           "/ext:name";
    }
    description
      "CLK output reference leafref type.";
  }

  typedef pps-input-reference-leafref-type {
    type leafref {
      path "/sync:sync" +
           "/sync:input-references" +
           "/ext:pps-input-reference" +
           "/ext:name";
    }
    description
      "1PPS input reference leafref type.";
  }

  typedef pps-output-reference-leafref-type {
    type leafref {
      path "/sync:sync" + 
           "/sync:output-references" + 
           "/ext:pps-output-reference" + 
           "/ext:name";
    }
    description
      "1PPS output reference leafref type.";
  }

  typedef clk-input-reference-interface-leafref-type {
    type leafref {
      path "/sync:sync" +
           "/sync:input-references" +
           "/ext:clk-input-reference" +
           "/ext:interface";
    }
    description
      "CLK input reference interface leafref type.";
  }

  typedef clk-output-reference-interface-leafref-type {
    type leafref {
      path "/sync:sync" +
           "/sync:output-references" +
           "/ext:clk-output-reference" +
           "/ext:interface";
    }
    description
      "CLK output reference interface leafref type.";
  }

  typedef pps-input-reference-interface-leafref-type {
    type leafref {
      path "/sync:sync" +
           "/sync:input-references" +
           "/ext:pps-input-reference" +
           "/ext:interface";
    }
    description
      "1PPS input reference interface leafref type.";
  }

  typedef pps-output-reference-interface-leafref-type {
    type leafref {
      path "/sync:sync" +
           "/sync:output-references" +
           "/ext:pps-output-reference" +
           "/ext:interface";
    }
    description
      "1PPS output reference interface leafref type.";
  }

  typedef clk-input-reference-oper-state-leafref-type {
    type leafref {
      path "/sync:sync-state" +
           "/sync:input-references" +
           "/ext:clk-input-reference" +
           "/ext:oper-state";
    }
    description
      "CLK input reference operational state leafref type.";
  }

  typedef clk-output-reference-oper-state-leafref-type {
    type leafref {
      path "/sync:sync-state" +
           "/sync:output-references" +
           "/ext:clk-output-reference" +
           "/ext:oper-state";
    }
    description
      "CLK output reference operational state leafref type.";
  }

  typedef pps-input-reference-oper-state-leafref-type {
    type leafref {
      path "/sync:sync-state" +
           "/sync:input-references" +
           "/ext:pps-input-reference" +
           "/ext:oper-state";
    }
    description
      "1PPS input reference operational state leafref type.";
  }

  typedef pps-output-reference-oper-state-leafref-type {
    type leafref {
      path "/sync:sync-state" +
           "/sync:output-references" +
           "/ext:pps-output-reference" +
           "/ext:oper-state";
    }
    description
      "1PPS output reference operational state leafref type.";
  }

  typedef clock-frequency-type {
    type enumeration {
      enum 10-mhz {
        description
          "10 MHz clock.
           Applies to all network-option configuration.";
      }
      enum 2048-khz {
        description
          "2048 kHz clock. 
           Applies to Option-1 only.";
      }
      enum 1544-khz {
        description
          "1544 kHz clock. 
           Applies to Option-2 only.";
      }
    }
    description
      "Clock frequency enumeration type.";
  }

  /*
   * Groupings
   */

  grouping clk-input-reference-config-grouping {
    description
      "CLK input reference configuration attributes.";
    leaf interface {
      type ext:interface-type;
      mandatory true;
      description
        "Interface used by a CLK input reference.";
    }
    uses sync:sync-input-reference-config-grouping;
    uses sync:sync-frequency-input-reference-config-grouping;
    leaf clock-frequency {
      type ext:clock-frequency-type;
      mandatory true;
      description
        "Frequency of input clock.";
    }
  }

  grouping clk-output-reference-config-grouping {
    description
      "CLK output reference configuration attributes.";
    leaf interface {
      type ext:interface-type;
      mandatory true;
      description
        "Interface used by a CLK output reference.";
    }
    leaf clock-frequency {
      type ext:clock-frequency-type;
      mandatory true;
      description
        "Frequency of output clock.";
    }
  }

  grouping pps-input-reference-config-grouping {
    description
      "1PPS input reference configuration attributes.";
    leaf interface {
      type ext:interface-type;
      mandatory true;
      description
        "Interface used by a 1PPS input reference.";
    }

    uses sync:sync-input-reference-config-grouping;

    leaf forced-quality-level {
      type sync:quality-level-type;
      description
        "Configuration to ignore/override the RX quality-level of an input
         reference.";
    }
  }

  grouping pps-output-reference-config-grouping {
    description
      "1PPS output reference configuration attributes.";
    leaf interface {
      type ext:interface-type;
      mandatory true;
      description
        "Interface used by a 1PPS output reference.";
    }
  }

  grouping clk-input-reference-state-grouping {
    description
      "CLK input reference state attributes.";
    uses sync:sync-input-reference-state-grouping;
    uses sync:sync-frequency-input-reference-state-grouping;
  }

  grouping clk-output-reference-state-grouping {
    description
      "CLK output reference state attributes.";
    uses sync:sync-output-reference-state-grouping;
    uses sync:sync-frequency-output-reference-state-grouping;
  }

  grouping pps-input-reference-state-grouping {
    description
      "1PPS input reference state attributes.";
    uses sync:sync-input-reference-state-grouping;
  }

  grouping pps-output-reference-state-grouping {
    description
      "1PPS output reference state attributes.";
    uses sync:sync-output-reference-state-grouping;
  }

  /*
   * Configuration data
   */

  augment "/sync:sync" {
    description
      "1PPS configuration.";
    container pps-global {
      description
        "1PPS global configuration.";
      leaf pulse-width {
        type uint32 {
          range "100..500000000";
        }
        units "nanoseconds";
        default 100000000;
        description
          "pulse-width of 1PPS output references in 100 ns increments.";
      }
    }
  }

  augment "/sync:sync" + 
          "/sync:input-references" {
    description
      "CLK input reference configuration.";
    list clk-input-reference {
      key "name";
      description
        "A list of all CLK input configuration entries.";
      leaf name {
        type sync:name-string-type;
        description
          "Name of CLK input reference.";
      }
      uses ext:clk-input-reference-config-grouping;
    }
  }

  augment "/sync:sync" +
          "/sync:input-references" {
    description
      "1PPS input reference configuration.";
    list pps-input-reference {
      key "name";
      description
        "A list of all 1PPS input configuration entries.";
      leaf name {
        type sync:name-string-type;
        description
          "Name of 1PPS input reference.";
      }
      uses ext:pps-input-reference-config-grouping;
    }
  }

  augment "/sync:sync" + 
          "/sync:output-references" {
    description
      "CLK output reference configuration.";
    list clk-output-reference {
      key "name";
      description
        "A list of all CLK output configuration entries.";
      leaf name {
        type sync:name-string-type;
        description
          "Name of CLK output reference.";
      }
      uses ext:clk-output-reference-config-grouping;
    }
  }

  augment "/sync:sync" + 
          "/sync:output-references" {
    description
      "1PPS output reference configuration.";
    list pps-output-reference {
      key "name";
      description
        "A list of all 1PPS output configuration entries.";
      leaf name {
        type sync:name-string-type;
        description
          "Name of 1PPS output reference.";
      }
      uses ext:pps-output-reference-config-grouping;
    }
  }

  augment "/sync:sync" + 
          "/sync:protection-groups" + 
          "/sync:frequency-protection-group" {
    description
      "CLK input reference configuration in frequency protection-group.";
    leaf-list clk-input-reference {
      type ext:clk-input-reference-leafref-type;
      description
        "List of CLK input references that shall be considered as candidates
         for clock selection in frequency protection-group.";
    }
  }

  augment "/sync:sync" +
          "/sync:protection-groups" +
          "/sync:phase-protection-group" {
    description
      "1PPS input reference configuration in phase protection-group.";
    leaf-list pps-input-reference {
      type ext:pps-input-reference-leafref-type;
      description
        "List of 1PPS input references that shall be considered as candidates
         for clock selection in phase protection-group.";
    }
  }

  /*
   * State data
   */

  augment "/sync:sync-state" + 
          "/sync:input-references" {
    description
      "CLK input reference state.";
    list clk-input-reference {
      key "name";
      description
        "A list of all CLK input state entries.";
      leaf name {
         type ext:clk-input-reference-leafref-type;
         description
           "Name of CLK input reference.";
      }
      uses ext:clk-input-reference-state-grouping;
    }
  }

  augment "/sync:sync-state" +
          "/sync:input-references" {
    description
      "1PPS input reference state.";
    list pps-input-reference {
      key "name";
      description
        "A list of all 1PPS input state entries.";
      leaf name {
         type ext:pps-input-reference-leafref-type;
         description
           "Name of 1PPS input reference.";
      }
      uses ext:pps-input-reference-state-grouping;
    }
  }

  augment "/sync:sync-state" + 
          "/sync:output-references" {
    description
      "CLK output reference state.";
    list clk-output-reference {
      key "name";
      description
        "A list of all CLK output state entries.";
      leaf name {
         type ext:clk-output-reference-leafref-type;
         description
           "Name of CLK output reference.";
      }
      uses ext:clk-output-reference-state-grouping;
    }
  }

  augment "/sync:sync-state" + 
          "/sync:output-references" {
    description
      "1PPS output reference state.";
    list pps-output-reference {
      key "name";
      description
        "A list of all 1PPS output state entries.";
      leaf name {
         type ext:pps-output-reference-leafref-type;
         description
           "Name of 1PPS output reference.";
      }
      uses ext:pps-output-reference-state-grouping;
    }
  }

  augment "/sync:sync-state" + 
          "/sync:protection-groups" + 
          "/sync:frequency-protection-group" {
    description
      "CLK input reference selected in frequency protection-group.";
    leaf selected-clk-input-reference-name {
      type ext:clk-input-reference-leafref-type;
      description
        "CLK input reference name.";
    }
  }

  augment "/sync:sync-state" +
          "/sync:protection-groups" +
          "/sync:phase-protection-group" {
    description
      "1PPS input reference selected in phase protection-group.";
    leaf selected-pps-input-reference-name {
      type ext:pps-input-reference-leafref-type;
      description
        "1PPS input reference name.";
    }
  }

  /*
   * RPC Operations
   */

  augment "/sync:sync-protection-group-selection-force-switch" +
          "/sync:input" {
    description
      "Force-switch a CLK input reference selection on protection-group.";
    leaf clk-input-reference-name {
      type ext:clk-input-reference-leafref-type;
      description
        "Name of CLK input reference.";
    }
  }

  augment "/sync:sync-protection-group-selection-force-switch" +
          "/sync:input" {
    description
      "Force-switch a PPS input reference selection on protection-group.";
    leaf pps-input-reference-name {
      type ext:pps-input-reference-leafref-type;
      description
        "Name of PPS input reference.";
    }
  }


  /*
   * Notifications
   */

  notification clk-input-reference-oper-state-change {
    description
      "Generated when the operational state of a CLK input reference changes.";
    leaf clk-input-reference-name {
      type ext:clk-input-reference-leafref-type;
      description
        "Name of CLK input reference.";
    }
    leaf interface {
      type ext:clk-input-reference-interface-leafref-type;
      description
        "Interface of CLK input reference.";
    }
    leaf oper-state {
      type ext:clk-input-reference-oper-state-leafref-type;
      description
        "Operational state of CLK input reference.";
    }
  }

  notification clk-output-reference-oper-state-change {
    description
      "Generated when the operational state of a CLK output reference changes.";
    leaf clk-output-reference-name {
      type ext:clk-output-reference-leafref-type;
      description
        "Name of CLK output reference.";
    }
    leaf interface {
      type ext:clk-output-reference-interface-leafref-type;
      description
        "Interface of CLK output reference.";
    }
    leaf oper-state {
      type ext:clk-output-reference-oper-state-leafref-type;
      description
        "Operational state of CLK output reference.";
    }
  }

  notification pps-input-reference-oper-state-change {
    description
      "Generated when the operational state of a 1PPS input reference changes.";
    leaf pps-input-reference-name {
      type ext:pps-input-reference-leafref-type;
      description
        "Name of 1PPS input reference.";
    }
    leaf interface {
      type ext:pps-input-reference-interface-leafref-type;
      description
        "Interface of 1PPS input reference.";
    }
    leaf oper-state {
      type ext:pps-input-reference-oper-state-leafref-type;
      description
        "Operational state of 1PPS input reference.";
    }
  }

  notification pps-output-reference-oper-state-change {
    description
      "Generated when the operational state of a 1PPS output reference changes.";
    leaf pps-output-reference-name {
      type ext:pps-output-reference-leafref-type;
      description
        "Name of 1PPS output reference.";
    }
    leaf interface {
      type ext:pps-output-reference-interface-leafref-type;
      description
        "Interface of 1PPS output reference.";
    }
    leaf oper-state {
      type ext:pps-output-reference-oper-state-leafref-type;
      description
        "Operational state of 1PPS output reference.";
    }
  }

  augment "/sync:frequency-protection-group-oper-state-change" {
    description
      "CLK input reference selected in frequency protection-group.";
    leaf selected-clk-input-reference-name {
      type ext:clk-input-reference-leafref-type;
      description
        "CLK input reference name.";
    }
  }

  augment "/sync:phase-protection-group-oper-state-change" {
    description
      "1PPS input reference selected in phase protection-group.";
    leaf selected-pps-input-reference-name {
      type ext:pps-input-reference-leafref-type;
      description
        "PPS input reference name.";
    }
  }
}
