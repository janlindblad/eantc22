module ieee-types {

  namespace "urn:ieee:params:xml:ns:yang:ieee-types";
  prefix "ieee";
  
  organization
      "Institute of Electrical and Electronics Engineers";

    contact
      "Web URL: http://www.ieee802.org
    	
       Editor: 
    	   Marc Holness
    	   mholness@ciena.com";

  description
	  "This module contains a collection of generally useful derived
	  data types for IEEE YANG models.";

  revision 2015-09-10 {
	  description
		  "Initial revision.";
      reference
          "IEEE 802";
  }

  /*
   * Collection of IEEE address type definitions
   */

  typedef mac-address {
	  type string {
		  pattern '[0-9a-fA-F]{2}(:[0-9a-fA-F]{2}){5}';
      }
	  description
		  "The mac-address type represents an 802 MAC address 
		  represented in the canonical order defined by
		  IEEE 802.";
	  reference
		  "IEEE 802.3-2012, Clause 3.2.3";
  }

  /*
   * Collection of IEEE 802 related identifier types 
   */

  typedef bridgeid {
	  type string {
		  pattern '[0-9a-fA-F]{4}(:[0-9a-fA-F]{2}){6}';
      }
	  description
		  "The bridgeid type represents identifiers that uniquely
		  identify a bridge.  Its first four hexadecimal digits
		  contain a priority value followed by a colon. The
		  remaining characters contain the MAC address used to
		  refer to a bridge in a unique fashion (typically, the
		  numerically smallest MAC address of all ports on the
		  bridge).
          This type is in the value set and its semantics equivalent
          to the BridgeId textual convention of the SMIv2. However, 
          since the BridgeId textual convention does not prescribe
          a lexical representation, the appearance might be different.";
      reference
    	  "TBD";
  }

  typedef vlanid {
	  type uint16 {
		  range "1..4094";
	  }
	  description
		  "The vlanid type uniquely identifies a VLAN. This is the
		  12-bit VLAN-ID used in the VLAN Tag header. The range is
		  defined by the referenced specification.
		  
		  This type is in the value set and its semantics equivalent
		  to the VlanId textual convention of the SMIv2.";
	  reference
		  "IEEE Std 802.1Q-2014: Virtual Bridged Local Area Networks."; 
  }

}
