module ciena-openconfig-telemetry {
  namespace "http://www.ciena.com/ns/yang/ciena-openconfig-telemetry";
  prefix "ciena-oc-tmet";

  import openconfig-telemetry {
    prefix oc-telemetry;
  }
  import ciena-tls-service-profile {
    prefix ciena-tsp;
  }
  import ietf-inet-types {
    prefix inet;
  }

  organization
    "Ciena Corporation";

  contact
    "Web URL: http://www.ciena.com/
    E-mail:  yang@ciena.com
    Postal:  7035 Ridge Road
             Hanover, Maryland 21076
             U.S.A.
    Phone:   +1 800-921-1144
    Fax:     +1 410-694-5750";

  description       
    "This YANG module defines Ciena's global
     configuration for telemetry.
    
    Copyright (c) 2018 Ciena Corporation.  All rights 
    reserved.

    All information contained herein is, and remains
    the property of Ciena Corporation. Dissemination of this 
    information or reproduction of this material is strictly 
    forbidden unless prior written permission is obtained from 
    Ciena Corporation.";  

  revision 2021-08-11 {
    description
      "Add sensor service mode.";
    reference
      "openconfig-telemetry.yang";
  }

  revision 2020-03-13 {
    description
      "Add sensor and subscription interfaces.";
    reference
      "openconfig-telemetry.yang";
  }

  revision 2018-03-26 {
    description
      "Initial version";
    reference
      "RFC 6020: YANG - A Data Modeling Language for
       the Network Configuration Protocol (NETCONF).
       No specific reference; standard not available.";
  }

//typedefs
  typedef tmet-sub-submode {
    description
      "This typedef defines submode of telemetry 
      stream subscription.";
    type enumeration {
      enum target-defined {
        description
          "gNMI telemetry subscription stream mode of
          sub mode as target-defined.";
      }
      enum onchange {
        description
          "gNMI telemetry subscription stream mode of
          sub mode as on-change.";
      }
      enum sample {
        description
          "gNMI telemetry subscription stream mode of
          sub mode as sample.";
      }
    }
  }

  typedef tmet-sensor-sub-svcmode {
    description
      "This typedef defines the sensor service mode to support
      telemetry stream subscription.";
    type enumeration {
      enum unavailable {
        description
          "Sensor registration for a gNMI telemetry subscription
          is unavailable.";
      }
      enum onchange {
        description
          "Sensor registration for a gNMI telemetry subscription
          is an onchange service.";
      }
      enum sample {
        description
          "Sensor registration for a gNMI telemetry subscription
          is a sample service.";
      }
    }
  }

  typedef tmet-sub-mode {
    description
      "This typedef defines telemetry subscription mode.";
    type enumeration {
      enum stream {
        description
          "gNMI telemetry subscription mode - stream.";
      }
    }
  }
  
  grouping telemetry-server-config {
    description
      "Configuration data for the
       telemetry server.";

    leaf enable {
      type boolean;
      default true;
      description
        "Enables the telemetry server.";
    }

    leaf tls-service-profile {
      type leafref {
        path "/ciena-tsp:tls-service-profiles/ciena-tsp:tls-service-profile-name";
      }
      description
        "The TLS Service Profile to be used when accepting
         TLS connections.";
    }
  }

  grouping telemetry-subscription-mode {
    description
      "Subscription mode settings.";
    leaf subscription-mode {
      type tmet-sub-mode;
      description
        "The subscription mode specified by
        a client in the subscription request.";
    }

    leaf update-only {
      type boolean;
      default false;
      description
        "The updates_only flag specified by a client in
        the subscription request.";
    }
  }

  grouping telemetry-subscription-stream-submode {
    description
      "Stream subscription submode.";
    leaf stream-sub-submode {
      type tmet-sub-submode;
      description
        "The sub-submode used within the subscription request
        of type stream mode.";
    }
  }

  grouping telemetry-sensor-subscription-svcmode {
    description
      "Sensor service mode for stream subscription.";
    leaf sensor-sub-svcmode {
      type tmet-sensor-sub-svcmode;
      description
        "The sensor service mode used for the subscription request
        of type stream mode.";
    }
  }

  grouping telemetry-sensor-supported-stream-submode {
    description
      "Grouping for sensor supported stream subscription submode.";
    leaf sensor-supported-stream-submode {
      type tmet-sub-submode;
      description
        "The sub-submode used within the subscription request
        of type stream mode.";
    }
  }

  grouping telemetry-sensor-path-element {
    description
      "Grouping for path elements.";
    list xpath-elements {
      key "path-element";
      config false;
      description
        "Path elements are tokens from the
        registered xpath.";

      leaf path-element {
        type string;
        description
          "Path tokens generated by a registered xpath.";
      }

      leaf filter-name {
        type string;
        description
          "Valid filter name used to filter response from
          Grpc server.";
      }

      leaf filter-value {
        type string;
        description
          "Filter value provided by the client.";
      }
    }
  }

  grouping telemetry-compound-key {
    description
      "Grouping for compound key support.";
    list compound-keys {
      key "compound-key";
      config false;
      description
        "List of compound keys and path elements that 
        generated them.";

      leaf compound-key {
        type string;
        description
          "Value of a compound key which is generated by
          its list of correlated path elements.";
      }

      uses telemetry-sensor-path-element;
    }
  }

  grouping telemetry-user-info {
    description
      "Grouping for user information";
    leaf user-name {
      type string;
      description
        "User name used for authentication to establish a gNMI 
        telemetry subscription session";
    }
    
    leaf telemetry-server-port {
      type inet:port-number;
      description
        "The port number of the device on which an external gNMI client 
        established a gNMI telemetry subscription session.";
    }

    leaf telemetry-client-ip-address {
      type inet:ip-address;
      description
        "The source IP address from which the external gNMI client 
        originates a gNMI telemetry subscription session.";
    }
  }

  grouping telemetry-sensor-id {
    description
      "A grouping to contain unique identifier 
      which is used to identify an internal sensor
      assocaited with subscription xpathtmet generates a 
      identifier that can uniquely identify a sensor.";
    leaf sensor-id {
      type uint64;
      description
        "A unique sensor id to identify a sensor.";
    }
  }

  grouping telemetry-subscriptions{
    description
      "Grouping for a list of subscriptions";
    list subscriptions {
      key "id";

      leaf id {
        type string;
        description
          "GRPC generated identifier to  uniquely identify a gNMI 
          telemetry subscription request";
      }

      container subscription-state {
        config false;
        description
          "State parameters relating to the telemetry
          subscriptions on the local device.";
        uses telemetry-user-info;
        uses telemetry-subscription-mode;
        uses oc-telemetry:telemetry-stream-frequency-config;
      }

      container subscription {
        config false;
        description
          "Describes a set of paths that is to be subscribed to by a 
          client.";
        list telemetry-sensor-paths {
          key "telemetry-sensor-path";
          description
            "A list of sensor paths and exclude filters which comprise
            a sensor grouping";

          leaf telemetry-sensor-path {
            type string;
            description
              "The sensor path is a path to a portion of operational
              state of interest in the data model";
          }

          uses telemetry-sensor-id;
          uses telemetry-subscription-stream-submode;
          uses telemetry-sensor-subscription-svcmode;
        }
      }
    }
  }

  grouping telemetry-sensors-top {
    description
      "Top level grouping for avaialbe sensors registered for the device.";
    container telemetry-registered-sensors {
      config false;
      container stream-sensors {
        description
          "List of stream sensors that are registered 
          for the device's telemetry system.";
        list telemetry-sensor-paths {
          key "telemetry-sensor-path";
          description
            "A list of sensor paths and exclude filters which comprise
            a sensor grouping";

          leaf telemetry-sensor-path {
            type string;
            description
              "The sensor path is a path to a portion of operational
              state of interest in the data model";
          }

          uses telemetry-sensor-id;
          uses telemetry-sensor-supported-stream-submode;
        }
      }
    }
  }

  grouping telemetry-subscriptions-top {
    description
        "Telemetry Subscription stats.";
      container telemetry-client-subscriptions {
        config false;
        uses telemetry-subscriptions;
      }
  }

  uses telemetry-sensors-top;
  uses telemetry-subscriptions-top;

//augment statments
  augment /oc-telemetry:telemetry-system {
    description
      "Addition for configuring the telemetry server";

    container server {
      description
        "Top-level container for telemetry server";

      container config {
        description
          "Configuration parameters for the 
           telemetry server.";

        uses telemetry-server-config;
        
      }
    }
  }

//rpc 
  rpc gnmi-subscribe {
    description
      "Represents the gNMI Subscribe RPC used by
       gNMI clients when requesting a subscription from
       telemetry. Clients may use this RPC to define NACM
       rules limiting access to the telemetry subscribe operation.
       Since telemetry subscriptions are only supported over
       telemetry connections, attempting to invoke it via NETCONF 
       will always return an error.";
  }
}
