module ciena-rstp {
  // Generated by yanger -t ncs
  tailf:mount-id "ciena107s3-nc-1.0:ciena107s3-nc-1.0";
  tailf:ncs-device-type "netconf";

  namespace "urn:ciena:params:xml:ns:yang:ciena-pn:ciena-rstp";
  prefix ciena-rstp;

  import ciena-ieee-rstp {
    prefix ieee-rstp;
  }
  import ietf-yang-types {
    prefix yang;
  }
  import ciena-mef-logical-port {
    prefix mef-logical-port;
  }
  import tailf-common {
    prefix tailf;
  }
  import tailf-ncs {
    prefix ncs;
  }

  organization
    "Ciena Corporation";
  contact
    "Web URL: http://www.ciena.com/
     E-mail:  yang@ciena.com
     Postal:  7035 Ridge Road
     Hanover, Maryland 21076
     U.S.A.
     Phone:   +1 800-921-1144
     Fax:     +1 410-694-5750";
  description
    "This YANG module defines Ciena's specific augmentations
     to the Rapid Spanning Tree Protocol yang model.

     Copyright (c) 2018 Ciena Corporation.  All rights
     reserved.

     All information contained herein is, and remains the
     property of Ciena Corporation. Dissemination of this
     information or reproduction of this material is strictly
     forbidden unless prior written permission is obtained
     from Ciena Corporation.";

  revision 2018-05-02 {
    description
      "Initial Version.";
    reference "IEEE-802.1D-2004";
  }

  typedef ncs_template_rstp-admin-state {
    type string;
    description
      "RSTP admininistrative state.";
  }

  typedef ncs_template_compliance-mode {
    type string;
    description
      "RSTP version running on the bridge.";
  }

  typedef ncs_rpc_notif_rstp-admin-state {
    type enumeration {
      enum "disable" {
        description
          "Administrative state is disabled.";
      }
      enum "enable" {
        description
          "Administrative state is enabled.";
      }
    }
    description
      "RSTP admininistrative state.";
  }

  typedef ncs_rpc_notif_compliance-mode {
    type enumeration {
      enum "ieee802.1w" {
        description
          "RSTP operate in as defined by the 802.1w standard.";
      }
      enum "ieee802.1D" {
        description
          "RSTP operate in as defined by the 802.1D standard.";
      }
      enum "ciena-enhanced" {
        description
          "Enables the use of Ciena-specific optimizations to the RSTP
           protocol. This compliance mode encompasses the operations
           available under the 802.1D mode too.";
      }
    }
    description
      "RSTP version running on the bridge.";
  }

  typedef live_ncs_rstp-admin-state {
    type enumeration {
      enum "disable" {
        description
          "Administrative state is disabled.";
      }
      enum "enable" {
        description
          "Administrative state is enabled.";
      }
    }
    description
      "RSTP admininistrative state.";
  }

  typedef live_ncs_compliance-mode {
    type enumeration {
      enum "ieee802.1w" {
        description
          "RSTP operate in as defined by the 802.1w standard.";
      }
      enum "ieee802.1D" {
        description
          "RSTP operate in as defined by the 802.1D standard.";
      }
      enum "ciena-enhanced" {
        description
          "Enables the use of Ciena-specific optimizations to the RSTP
           protocol. This compliance mode encompasses the operations
           available under the 802.1D mode too.";
      }
    }
    description
      "RSTP version running on the bridge.";
  }

  typedef rstp-admin-state {
    type enumeration {
      enum "disable" {
        description
          "Administrative state is disabled.";
      }
      enum "enable" {
        description
          "Administrative state is enabled.";
      }
    }
    description
      "RSTP admininistrative state.";
  }

  typedef compliance-mode {
    type enumeration {
      enum "ieee802.1w" {
        description
          "RSTP operate in as defined by the 802.1w standard.";
      }
      enum "ieee802.1D" {
        description
          "RSTP operate in as defined by the 802.1D standard.";
      }
      enum "ciena-enhanced" {
        description
          "Enables the use of Ciena-specific optimizations to the RSTP
           protocol. This compliance mode encompasses the operations
           available under the 802.1D mode too.";
      }
    }
    description
      "RSTP version running on the bridge.";
  }

  grouping ncs_template_domain-config {
    description
      "Grouping for RSTP domain config data";
    leaf domain-identifier {
      type string;
      // NCS drop mandatory statement
      description
        "Integer that identifies a domain on the device. By default,
         domain with identifier 0 and name 'default' is created and
         all ports are assigned to that domain.";
    }
    leaf priority {
      type string;
      description
        "Priority for the given domain. This value is used in the
         priority component of the Bridge Identifier of BPDUs
         transmitted from ports on this bridge that are part of this
         domain.";
    }
    leaf compliance {
      type ncs_template_compliance-mode;
      description
        "Determines which standard version the domain complies
         with - 802.1w/802.1D/ciena-enhanced.";
    }
  }

  grouping ncs_template_domain-oper-data {
    description
      "Grouping for RSTP domain operational data";
    leaf designated-root-address {
      type string;
      description
        "The designated root mac address for this domain.";
    }
    leaf designated-root-priority {
      type string;
      description
        "The designated root priority for this domain.";
    }
    leaf designated-root-cost {
      type string;
      description
        "The path cost to the root for this domain.";
    }
    leaf designated-bridge-priority {
      type string;
      description
        "The designated bridge priority for this domain.";
    }
    leaf designated-bridge-address {
      type string;
      description
        "The designated bridge MAC address for this domain.";
    }
    leaf root-port {
      type mef-logical-port:ncs_template_logical-port-ref;
      description
        "The port number of the port which offers the lowest cost
         path from this bridge to the root bridge of this domain.";
      reference "RFC4188 BRIDGE-MIB dot1dStpRootPort";
    }
    leaf-list port-list {
      // NCS patched for predictable order
      ordered-by user;
      type mef-logical-port:ncs_template_logical-port-ref;
      description
        "The list of ports mapped to this domain.";
    }
  }

  grouping ncs_rpc_notif_domain-config {
    description
      "Grouping for RSTP domain config data";
    leaf domain-identifier {
      type uint16 {
        range "0..255";
      }
      mandatory true;
      description
        "Integer that identifies a domain on the device. By default,
         domain with identifier 0 and name 'default' is created and
         all ports are assigned to that domain.";
    }
    leaf priority {
      type uint16 {
        range "0..15";
      }
      description
        "Priority for the given domain. This value is used in the
         priority component of the Bridge Identifier of BPDUs
         transmitted from ports on this bridge that are part of this
         domain.";
    }
    leaf compliance {
      type ncs_rpc_notif_compliance-mode;
      description
        "Determines which standard version the domain complies
         with - 802.1w/802.1D/ciena-enhanced.";
    }
  }

  grouping ncs_rpc_notif_domain-oper-data {
    description
      "Grouping for RSTP domain operational data";
    leaf designated-root-address {
      type yang:mac-address;
      description
        "The designated root mac address for this domain.";
    }
    leaf designated-root-priority {
      type uint16 {
        range "0..15";
      }
      description
        "The designated root priority for this domain.";
    }
    leaf designated-root-cost {
      type uint32;
      description
        "The path cost to the root for this domain.";
    }
    leaf designated-bridge-priority {
      type uint16;
      description
        "The designated bridge priority for this domain.";
    }
    leaf designated-bridge-address {
      type yang:mac-address;
      description
        "The designated bridge MAC address for this domain.";
    }
    leaf root-port {
      type mef-logical-port:ncs_rpc_notif_logical-port-ref;
      description
        "The port number of the port which offers the lowest cost
         path from this bridge to the root bridge of this domain.";
      reference "RFC4188 BRIDGE-MIB dot1dStpRootPort";
    }
    leaf-list port-list {
      type mef-logical-port:ncs_rpc_notif_logical-port-ref;
      description
        "The list of ports mapped to this domain.";
    }
  }

  grouping live_ncs_domain-config {
    description
      "Grouping for RSTP domain config data";
    leaf domain-identifier {
      type uint16 {
        range "0..255";
      }
      // NCS drop mandatory statement
      description
        "Integer that identifies a domain on the device. By default,
         domain with identifier 0 and name 'default' is created and
         all ports are assigned to that domain.";
    }
    leaf priority {
      type uint16 {
        range "0..15";
      }
      description
        "Priority for the given domain. This value is used in the
         priority component of the Bridge Identifier of BPDUs
         transmitted from ports on this bridge that are part of this
         domain.";
    }
    leaf compliance {
      type live_ncs_compliance-mode;
      description
        "Determines which standard version the domain complies
         with - 802.1w/802.1D/ciena-enhanced.";
    }
  }

  grouping live_ncs_domain-oper-data {
    description
      "Grouping for RSTP domain operational data";
    leaf designated-root-address {
      type yang:mac-address;
      description
        "The designated root mac address for this domain.";
    }
    leaf designated-root-priority {
      type uint16 {
        range "0..15";
      }
      description
        "The designated root priority for this domain.";
    }
    leaf designated-root-cost {
      type uint32;
      description
        "The path cost to the root for this domain.";
    }
    leaf designated-bridge-priority {
      type uint16;
      description
        "The designated bridge priority for this domain.";
    }
    leaf designated-bridge-address {
      type yang:mac-address;
      description
        "The designated bridge MAC address for this domain.";
    }
    leaf root-port {
      type mef-logical-port:live_ncs_logical-port-ref;
      description
        "The port number of the port which offers the lowest cost
         path from this bridge to the root bridge of this domain.";
      reference "RFC4188 BRIDGE-MIB dot1dStpRootPort";
    }
    leaf-list port-list {
      type mef-logical-port:live_ncs_logical-port-ref;
      description
        "The list of ports mapped to this domain.";
    }
  }

  grouping domain-config {
    description
      "Grouping for RSTP domain config data";
    leaf domain-identifier {
      type uint16 {
        range "0..255";
      }
      mandatory true;
      description
        "Integer that identifies a domain on the device. By default,
         domain with identifier 0 and name 'default' is created and
         all ports are assigned to that domain.";
    }
    leaf priority {
      type uint16 {
        range "0..15";
      }
      description
        "Priority for the given domain. This value is used in the
         priority component of the Bridge Identifier of BPDUs
         transmitted from ports on this bridge that are part of this
         domain.";
    }
    leaf compliance {
      type compliance-mode;
      description
        "Determines which standard version the domain complies
         with - 802.1w/802.1D/ciena-enhanced.";
    }
  }

  grouping domain-oper-data {
    description
      "Grouping for RSTP domain operational data";
    leaf designated-root-address {
      type yang:mac-address;
      description
        "The designated root mac address for this domain.";
    }
    leaf designated-root-priority {
      type uint16 {
        range "0..15";
      }
      description
        "The designated root priority for this domain.";
    }
    leaf designated-root-cost {
      type uint32;
      description
        "The path cost to the root for this domain.";
    }
    leaf designated-bridge-priority {
      type uint16;
      description
        "The designated bridge priority for this domain.";
    }
    leaf designated-bridge-address {
      type yang:mac-address;
      description
        "The designated bridge MAC address for this domain.";
    }
    leaf root-port {
      type mef-logical-port:logical-port-ref;
      description
        "The port number of the port which offers the lowest cost
         path from this bridge to the root bridge of this domain.";
      reference "RFC4188 BRIDGE-MIB dot1dStpRootPort";
    }
    leaf-list port-list {
      type mef-logical-port:logical-port-ref;
      description
        "The list of ports mapped to this domain.";
    }
  }

  augment "/ncs:devices/ncs:device/ncs:rpc" {
    container rpc-clear-rstp-statistics {
      tailf:ncs-device-type "netconf";
      tailf:display-when "not(../../ncs:module) or ../../ncs:module[ncs:name='ciena-rstp']";
      tailf:action clear-rstp-statistics {
        tailf:actionpoint ncsproxy {
          tailf:internal;
        }
        description
          "RPC to clear the RSTP statistics of a specific or all logical
           ports.";
        input {
          choice clear-scope {
            description
              "Clear statistics for all or for a specific logical port.";
            case logical-port {
              leaf logical-port {
                type mef-logical-port:ncs_rpc_notif_logical-port-ref;
                description
                  "Clear statistics for this logical port.";
              }
            }
            case all {
              leaf all {
                type empty;
                description
                  "Clear statistics for all logical ports.";
              }
            }
          }
        }
        output {
          leaf status {
            type string;
            description
              "Status of the clear statistics operation.";
          }
        }
      }
    }
  }
  augment "/ncs:devices/ncs:device-group/ncs:ned-id/ncs:rpc" {
    container rpc-clear-rstp-statistics {
      tailf:ncs-device-type "netconf";
      tailf:display-when "/ncs:devices/ncs:device[ncs:name=current()/../../../ncs:member]/ncs:module[ncs:name='ciena-rstp']";
      tailf:action clear-rstp-statistics {
        tailf:actionpoint ncsproxy {
          tailf:internal;
        }
        description
          "RPC to clear the RSTP statistics of a specific or all logical
           ports.";
        input {
          choice clear-scope {
            description
              "Clear statistics for all or for a specific logical port.";
            case logical-port {
              leaf logical-port {
                type mef-logical-port:ncs_rpc_notif_logical-port-ref;
                description
                  "Clear statistics for this logical port.";
              }
            }
            case all {
              leaf all {
                type empty;
                description
                  "Clear statistics for all logical ports.";
              }
            }
          }
        }
        output {
          container "device" {
            leaf "name" {
              type string;
            }
            leaf "info" {
              type string;
            }
            container "result" {
              leaf status {
                type string;
                description
                  "Status of the clear statistics operation.";
              }
            }
          }
        }
      }
    }
  }
  augment "/ncs:devices/ncs:device/ncs:notifications/ncs:received-notifications/ncs:notification/ncs:data" {
    container rstp-root-port-lost {
      presence "";
      config false;
      description
        "A notification is sent whenever the device detects that root
         port is lost. This notification indicates either the link failure
         or RSTP is disabled on the remote link.";
      leaf bridge-mac-address {
        type ieee-rstp:ncs_rpc_notif_bridge-mac-address-ref;
        description
          "MAC address of the device.";
      }
      leaf port {
        type mef-logical-port:ncs_rpc_notif_logical-port-ref;
        description
          "Root port.";
      }
    }
  }
  augment "/ncs:devices/ncs:device/ncs:notifications/ncs:received-notifications/ncs:notification/ncs:data" {
    container rstp-port-flap {
      presence "";
      config false;
      description
        "A notification is sent whenever the device detects a port
         flapping. Notification is generated under following criteria.
         If device detects port flapped more than once within 1 minute
         timer period and it has not sent a notification within last 5
         minutes then it will generate this notification.";
      leaf bridge-mac-address {
        type ieee-rstp:ncs_rpc_notif_bridge-mac-address-ref;
        description
          "MAC address of the device.";
      }
      leaf port {
        type mef-logical-port:ncs_rpc_notif_logical-port-ref;
        description
          "Port that has flapped.";
      }
    }
  }
  augment "/ncs:devices/ncs:device/ncs:notifications/ncs:received-notifications/ncs:notification/ncs:data" {
    container rstp-self-loop {
      presence "";
      config false;
      description
        "A notification is sent whenever device detects detects same cable
         connected to a port in a loop back.
         Also if loop-back blocking is enabled on the device then RSTP will
         block this port (self disable).";
      leaf bridge-mac-address {
        type ieee-rstp:ncs_rpc_notif_bridge-mac-address-ref;
        description
          "MAC address of the device.";
      }
      leaf port {
        type mef-logical-port:ncs_rpc_notif_logical-port-ref;
        description
          "Port on the device.";
      }
    }
  }
  augment "/ncs:devices/ncs:device/ncs:notifications/ncs:received-notifications/ncs:notification/ncs:data" {
    container rstp-oper-edge {
      presence "";
      config false;
      description
        "A notification is sent whenever the OperEdge value of the port
         changes.";
      leaf bridge-mac-address {
        type ieee-rstp:ncs_rpc_notif_bridge-mac-address-ref;
        description
          "MAC address of the device.";
      }
      leaf port {
        type mef-logical-port:ncs_rpc_notif_logical-port-ref;
        description
          "Port whose oper Edge has changed.";
      }
      leaf oper-edge-port {
        type boolean;
        description
          "The value of the operEdgePort parameter, as determined by the
           operation of the Bridge Detection state machine.";
      }
    }
  }
  augment "/ncs:devices/ncs:device/ncs:notifications/ncs:received-notifications/ncs:notification/ncs:data" {
    container rstp-port-backup {
      presence "";
      config false;
      description
        "A notification is sent whenever device detects self loop i.e.
         same cable connected to two ports on the same device.";
      leaf bridge-mac-address {
        type ieee-rstp:ncs_rpc_notif_bridge-mac-address-ref;
        description
          "MAC address of the device.";
      }
      leaf port {
        type mef-logical-port:ncs_rpc_notif_logical-port-ref;
        description
          "Ports that are connected back to back.";
      }
    }
  }
  augment "/ncs:devices/ncs:device/ncs:netconf-notifications/ncs:received-notifications/ncs:notification/ncs:data" {
    container rstp-root-port-lost {
      presence "";
      config false;
      description
        "A notification is sent whenever the device detects that root
         port is lost. This notification indicates either the link failure
         or RSTP is disabled on the remote link.";
      leaf bridge-mac-address {
        type ieee-rstp:ncs_rpc_notif_bridge-mac-address-ref;
        description
          "MAC address of the device.";
      }
      leaf port {
        type mef-logical-port:ncs_rpc_notif_logical-port-ref;
        description
          "Root port.";
      }
    }
  }
  augment "/ncs:devices/ncs:device/ncs:netconf-notifications/ncs:received-notifications/ncs:notification/ncs:data" {
    container rstp-port-flap {
      presence "";
      config false;
      description
        "A notification is sent whenever the device detects a port
         flapping. Notification is generated under following criteria.
         If device detects port flapped more than once within 1 minute
         timer period and it has not sent a notification within last 5
         minutes then it will generate this notification.";
      leaf bridge-mac-address {
        type ieee-rstp:ncs_rpc_notif_bridge-mac-address-ref;
        description
          "MAC address of the device.";
      }
      leaf port {
        type mef-logical-port:ncs_rpc_notif_logical-port-ref;
        description
          "Port that has flapped.";
      }
    }
  }
  augment "/ncs:devices/ncs:device/ncs:netconf-notifications/ncs:received-notifications/ncs:notification/ncs:data" {
    container rstp-self-loop {
      presence "";
      config false;
      description
        "A notification is sent whenever device detects detects same cable
         connected to a port in a loop back.
         Also if loop-back blocking is enabled on the device then RSTP will
         block this port (self disable).";
      leaf bridge-mac-address {
        type ieee-rstp:ncs_rpc_notif_bridge-mac-address-ref;
        description
          "MAC address of the device.";
      }
      leaf port {
        type mef-logical-port:ncs_rpc_notif_logical-port-ref;
        description
          "Port on the device.";
      }
    }
  }
  augment "/ncs:devices/ncs:device/ncs:netconf-notifications/ncs:received-notifications/ncs:notification/ncs:data" {
    container rstp-oper-edge {
      presence "";
      config false;
      description
        "A notification is sent whenever the OperEdge value of the port
         changes.";
      leaf bridge-mac-address {
        type ieee-rstp:ncs_rpc_notif_bridge-mac-address-ref;
        description
          "MAC address of the device.";
      }
      leaf port {
        type mef-logical-port:ncs_rpc_notif_logical-port-ref;
        description
          "Port whose oper Edge has changed.";
      }
      leaf oper-edge-port {
        type boolean;
        description
          "The value of the operEdgePort parameter, as determined by the
           operation of the Bridge Detection state machine.";
      }
    }
  }
  augment "/ncs:devices/ncs:device/ncs:netconf-notifications/ncs:received-notifications/ncs:notification/ncs:data" {
    container rstp-port-backup {
      presence "";
      config false;
      description
        "A notification is sent whenever device detects self loop i.e.
         same cable connected to two ports on the same device.";
      leaf bridge-mac-address {
        type ieee-rstp:ncs_rpc_notif_bridge-mac-address-ref;
        description
          "MAC address of the device.";
      }
      leaf port {
        type mef-logical-port:ncs_rpc_notif_logical-port-ref;
        description
          "Ports that are connected back to back.";
      }
    }
  }
  augment "/ncs:devices/ncs:template/ncs:ned-id/ncs:config/ieee-rstp:rstp/ieee-rstp:config" {
    description
      "Augmentation for configuration data.";
    leaf admin-state {
      type ncs_template_rstp-admin-state;
      // NCS drop default statement
      description
        "Enable or disable RSTP on this device.";
    }
    leaf mode {
      type string;
      // NCS drop default statement
      description
        "Sets the mode to RSTP or RSTP domain on this device.";
    }
    leaf compliance {
      type ncs_template_compliance-mode;
      // NCS drop default statement
      description
        "Determines which standard version the RSTP bridge complies
         with - 802.1w/802.1D/ciena-enhanced.";
    }
    leaf loopback-blocking {
      type ncs_template_rstp-admin-state;
      // NCS drop default statement
      description
        "This is configured to block a port that loops back its own
         BPDU.";
    }
  }
  augment "/ncs:devices/ncs:device/ncs:live-status/ieee-rstp:rstp/ieee-rstp:config" {
    description
      "Augmentation for configuration data.";
    leaf admin-state {
      tailf:ncs-device-type "netconf";
      tailf:display-when "not(../../../../ncs:module) or ../../../../ncs:module[ncs:name='ciena-rstp'] or (../../../../ncs:live-status-protocol[not(ncs:capability)]) or (../../../../ncs:live-status-protocol/ncs:capability/ncs:module[.='ciena-rstp'])";
      type live_ncs_rstp-admin-state;
      // NCS drop default statement
      description
        "Enable or disable RSTP on this device.";
    }
    leaf mode {
      tailf:ncs-device-type "netconf";
      tailf:display-when "not(../../../../ncs:module) or ../../../../ncs:module[ncs:name='ciena-rstp'] or (../../../../ncs:live-status-protocol[not(ncs:capability)]) or (../../../../ncs:live-status-protocol/ncs:capability/ncs:module[.='ciena-rstp'])";
      type enumeration {
        enum "rstp" {
          description
            "Rapid Spanning Tree Protocol.";
        }
        enum "rstp-domain" {
          description
            "RSTP Domain.";
        }
      }
      // NCS drop default statement
      description
        "Sets the mode to RSTP or RSTP domain on this device.";
    }
    leaf compliance {
      tailf:ncs-device-type "netconf";
      tailf:display-when "not(../../../../ncs:module) or ../../../../ncs:module[ncs:name='ciena-rstp'] or (../../../../ncs:live-status-protocol[not(ncs:capability)]) or (../../../../ncs:live-status-protocol/ncs:capability/ncs:module[.='ciena-rstp'])";
      type live_ncs_compliance-mode;
      // NCS drop default statement
      description
        "Determines which standard version the RSTP bridge complies
         with - 802.1w/802.1D/ciena-enhanced.";
    }
    leaf loopback-blocking {
      tailf:ncs-device-type "netconf";
      tailf:display-when "not(../../../../ncs:module) or ../../../../ncs:module[ncs:name='ciena-rstp'] or (../../../../ncs:live-status-protocol[not(ncs:capability)]) or (../../../../ncs:live-status-protocol/ncs:capability/ncs:module[.='ciena-rstp'])";
      type live_ncs_rstp-admin-state;
      // NCS drop default statement
      description
        "This is configured to block a port that loops back its own
         BPDU.";
    }
  }
  augment "/ncs:devices/ncs:device/ncs:config/ieee-rstp:rstp/ieee-rstp:config" {
    description
      "Augmentation for configuration data.";
    leaf admin-state {
      tailf:ncs-device-type "netconf";
      tailf:display-when "not(../../../../ncs:module) or ../../../../ncs:module[ncs:name='ciena-rstp']";
      type rstp-admin-state;
      default "disable";
      description
        "Enable or disable RSTP on this device.";
    }
    leaf mode {
      tailf:ncs-device-type "netconf";
      tailf:display-when "not(../../../../ncs:module) or ../../../../ncs:module[ncs:name='ciena-rstp']";
      type enumeration {
        enum "rstp" {
          description
            "Rapid Spanning Tree Protocol.";
        }
        enum "rstp-domain" {
          description
            "RSTP Domain.";
        }
      }
      default "rstp";
      description
        "Sets the mode to RSTP or RSTP domain on this device.";
    }
    leaf compliance {
      tailf:ncs-device-type "netconf";
      tailf:display-when "not(../../../../ncs:module) or ../../../../ncs:module[ncs:name='ciena-rstp']";
      type compliance-mode;
      default "ciena-enhanced";
      description
        "Determines which standard version the RSTP bridge complies
         with - 802.1w/802.1D/ciena-enhanced.";
    }
    leaf loopback-blocking {
      tailf:ncs-device-type "netconf";
      tailf:display-when "not(../../../../ncs:module) or ../../../../ncs:module[ncs:name='ciena-rstp']";
      type rstp-admin-state;
      default "enable";
      description
        "This is configured to block a port that loops back its own
         BPDU.";
    }
  }
  augment "/ncs:devices/ncs:template/ncs:ned-id/ncs:config/ieee-rstp:rstp" {
    description
      "Augmentation for RSTP domain.";
    container domains {
      description
        "RSTP Domain specific configuration and operational
         information.";
      list domain {
        // NCS patched for predictable order
        ordered-by user;
        // NCS drop must statement
        key "name";
        unique "config/domain-identifier";
        description
          "The list of domains on the device.";
        leaf name {
          type string;
          description
            "The name of the domain.";
        }
        container config {
          description
            "RSTP Domain configuration information.";
          uses ncs_template_domain-config;
        }
        // NCS drop config false container state
      }
    }
  }
  augment "/ncs:devices/ncs:device/ncs:live-status/ieee-rstp:rstp" {
    description
      "Augmentation for RSTP domain.";
    container domains {
      tailf:ncs-device-type "netconf";
      tailf:display-when "not(../../../ncs:module) or ../../../ncs:module[ncs:name='ciena-rstp'] or (../../../ncs:live-status-protocol[not(ncs:capability)]) or (../../../ncs:live-status-protocol/ncs:capability/ncs:module[.='ciena-rstp'])";
      description
        "RSTP Domain specific configuration and operational
         information.";
      list domain {
        // NCS drop must statement
        key "name";
        unique "config/domain-identifier";
        description
          "The list of domains on the device.";
        leaf name {
          type string {
            length "1..32";
          }
          description
            "The name of the domain.";
        }
        container config {
          description
            "RSTP Domain configuration information.";
          uses live_ncs_domain-config;
        }
        container state {
          description
            "Contains operational parameters for the domain.";
          uses live_ncs_domain-oper-data;
        }
      }
    }
  }
  augment "/ncs:devices/ncs:device/ncs:config/ieee-rstp:rstp" {
    description
      "Augmentation for RSTP domain.";
    container domains {
      tailf:ncs-device-type "netconf";
      tailf:display-when "not(../../../ncs:module) or ../../../ncs:module[ncs:name='ciena-rstp']";
      description
        "RSTP Domain specific configuration and operational
         information.";
      list domain {
        must "(config/domain-identifier != 0 and /ieee-rstp:rstp/ieee-rstp:config/ciena-rstp:mode = 'rstp-domain') or (config/domain-identifier = 0 and /ieee-rstp:rstp/ieee-rstp:config/ciena-rstp:mode[.='rstp-domain' or .='rstp'])" {
          tailf:xpath-root 3;
          error-message "For non-zero domain identifier, mode must be rstp-domain";
          description
            "Mode must be rstp-domain for non-zero domain identifiers.";
        }
        key "name";
        unique "config/domain-identifier";
        description
          "The list of domains on the device.";
        leaf name {
          type string {
            length "1..32";
          }
          description
            "The name of the domain.";
        }
        container config {
          description
            "RSTP Domain configuration information.";
          uses domain-config;
        }
        // NCS drop config false container state
      }
    }
  }
  augment "/ncs:devices/ncs:template/ncs:ned-id/ncs:config/mef-logical-port:logical-ports/mef-logical-port:logical-port/ieee-rstp:rstp-port-config" {
    description
      "Augmentation for port configuration data.";
    leaf admin-state {
      type ncs_template_rstp-admin-state;
      // NCS drop default statement
      description
        "Enable or disable RSTP on port.";
    }
    leaf domain {
      type string;
      description
        "RSTP domain to which this port belongs.";
    }
    leaf legacy-tx {
      type ncs_template_rstp-admin-state;
      // NCS drop default statement
      description
        "Enable or disable the transmission of 802.1w format RSTP BPDUs
         to enable interoperability with 802.1w devices under certain
         conditions.";
    }
  }
  augment "/ncs:devices/ncs:device/ncs:live-status/mef-logical-port:logical-ports/mef-logical-port:logical-port/ieee-rstp:rstp-port-config" {
    description
      "Augmentation for port configuration data.";
    leaf admin-state {
      tailf:ncs-device-type "netconf";
      tailf:display-when "not(../../../../../ncs:module) or ../../../../../ncs:module[ncs:name='ciena-rstp'] or (../../../../../ncs:live-status-protocol[not(ncs:capability)]) or (../../../../../ncs:live-status-protocol/ncs:capability/ncs:module[.='ciena-rstp'])";
      type live_ncs_rstp-admin-state;
      // NCS drop default statement
      description
        "Enable or disable RSTP on port.";
    }
    leaf domain {
      tailf:ncs-device-type "netconf";
      tailf:display-when "not(../../../../../ncs:module) or ../../../../../ncs:module[ncs:name='ciena-rstp'] or (../../../../../ncs:live-status-protocol[not(ncs:capability)]) or (../../../../../ncs:live-status-protocol/ncs:capability/ncs:module[.='ciena-rstp'])";
      type leafref {
        path "/ncs:devices/ncs:device/ncs:live-status/ieee-rstp:rstp/ciena-rstp:domains/ciena-rstp:domain/ciena-rstp:name" {
          tailf:xpath-root 3;
        }
      }
      description
        "RSTP domain to which this port belongs.";
    }
    leaf legacy-tx {
      tailf:ncs-device-type "netconf";
      tailf:display-when "not(../../../../../ncs:module) or ../../../../../ncs:module[ncs:name='ciena-rstp'] or (../../../../../ncs:live-status-protocol[not(ncs:capability)]) or (../../../../../ncs:live-status-protocol/ncs:capability/ncs:module[.='ciena-rstp'])";
      type live_ncs_rstp-admin-state;
      // NCS drop default statement
      description
        "Enable or disable the transmission of 802.1w format RSTP BPDUs
         to enable interoperability with 802.1w devices under certain
         conditions.";
    }
  }
  augment "/ncs:devices/ncs:device/ncs:config/mef-logical-port:logical-ports/mef-logical-port:logical-port/ieee-rstp:rstp-port-config" {
    description
      "Augmentation for port configuration data.";
    leaf admin-state {
      tailf:ncs-device-type "netconf";
      tailf:display-when "not(../../../../../ncs:module) or ../../../../../ncs:module[ncs:name='ciena-rstp']";
      type rstp-admin-state;
      default "enable";
      description
        "Enable or disable RSTP on port.";
    }
    leaf domain {
      tailf:ncs-device-type "netconf";
      tailf:display-when "not(../../../../../ncs:module) or ../../../../../ncs:module[ncs:name='ciena-rstp']";
      type leafref {
        path "/ncs:devices/ncs:device/ncs:config/ieee-rstp:rstp/ciena-rstp:domains/ciena-rstp:domain/ciena-rstp:name" {
          tailf:xpath-root 3;
        }
      }
      description
        "RSTP domain to which this port belongs.";
    }
    leaf legacy-tx {
      tailf:ncs-device-type "netconf";
      tailf:display-when "not(../../../../../ncs:module) or ../../../../../ncs:module[ncs:name='ciena-rstp']";
      type rstp-admin-state;
      default "disable";
      description
        "Enable or disable the transmission of 802.1w format RSTP BPDUs
         to enable interoperability with 802.1w devices under certain
         conditions.";
    }
  }
}
