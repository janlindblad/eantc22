module ciena-cfm {
  // Generated by yanger -t ncs
  tailf:mount-id "ciena107s3-nc-1.0:ciena107s3-nc-1.0";
  tailf:ncs-device-type "netconf";

  namespace "urn:ciena:params:xml:ns:yang:ciena-pn:ciena-cfm";
  prefix ciena-cfm;

  import mef-cfm {
    prefix mef-cfm;
  }
  import ciena-mef-fd {
    prefix ciena-mef-fd;
  }
  import ietf-yang-types {
    prefix yang;
  }
  import tailf-common {
    prefix tailf;
  }
  import tailf-ncs {
    prefix ncs;
  }

  organization
    "Ciena Corporation";
  contact
    "Web URL: http://www.ciena.com/
     E-mail:  yang@ciena.com
     Postal:  7035 Ridge Road
     Hanover, Maryland 21076
     U.S.A.
     Phone:   +1 800-921-1144
     Fax:     +1 410-694-5750";
  description
    "This YANG module defines Ciena's specific augmentations
     to the mef-cfm yang model.

     Copyright (c) 2016 Ciena Corporation.  All rights
     reserved.

     All information contained herein is, and remains the
     property of Ciena Corporation. Dissemination of this
     information or reproduction of this material is strictly
     forbidden unless prior written permission is obtained
     from Ciena Corporation.";

  revision 2021-09-06 {
    description
      "Added choice to provide single-tag or dual-tag l2-transform.
       Case vlan-stack contains a list vtags to support dual-tagged vlan's that can be applied on the CFM Frames.
       Enumerations in l2-transform are defined in typedef for reusability.";
  }
  revision 2020-10-08 {
    description
      "Added container l2-loop-config under maintenance-association-end-point list.
       Added leafs admin-state, reversion-mode, pdu-count, wtr-timer in l2-loop-config container.
       Added container l2-loop-oper-data under maintenance-association-end-point list.
       Added leafs loop-present, loop-blocked, rx-drop-loop-count, wtr-timer-running in l2-loop-oper-data container.
       Added RPC l2-loop-block-revert.
       Added notification l2-loop-alarm.
       Added types l2-loop-reversion-mode and cfm-alarm-state.
       Changed the description of typedef cfm-admin-state for a more generic utility.
       Added static RMEP parameters:
         - remote-mep-config list under maintenance-association.
         - static RMEP config parameters under newly added remote-mep-config list.
         - added parameter discovery-type under remote-mep operational data.
       Added leaf ccm-loss-num in maintenance-association configurational data.
       Added changes for L2-loop notification:
         -added list event-list and leaf event-type in cfm-event notification.
         -added identity cfm-event-type, l2-loop and any.
       Added feature condition l2-loop in container l2-loop-config and l2-loop-oper-data.";
    reference "IEEE-802.1Q-2011";
  }
  revision 2020-04-02 {
    description
      "Added leaf ppm-forced-ccm-off in maintenance-association-end-point operational data.";
    reference "IEEE-802.1Q-2011";
  }
  revision 2016-05-23 {
    description
      "Provides support for operational data.";
    reference "IEEE-802.1Q-2011";
  }
  revision 2015-10-20 {
    description
      "Initial version";
    reference "Enter a reference here";
  }

  typedef ncs_template_cfm-admin-state {
    type string;
    description
      "Admininistrative state enumeration";
  }

  typedef ncs_template_l2-loop-reversion-mode {
    type string;
    description
      "An enumeration indicating the reversion mode of the restriction placed
       due to detection of a loop.";
  }

  typedef ncs_template_cfm-alarm-status {
    type string;
    description
      "An enumeration indicating fault present or cleared in an alarm indication.";
  }

  typedef ncs_template_pcp-type {
    type string;
  }

  typedef ncs_template_tpid-type {
    type string;
  }

  typedef ncs_template_dei-type {
    type string;
  }

  typedef ncs_rpc_notif_cfm-admin-state {
    type enumeration {
      enum "disable" {
        description
          "Administrative state is disabled";
      }
      enum "enable" {
        description
          "Administrative state is enabled";
      }
    }
    description
      "Admininistrative state enumeration";
  }

  typedef ncs_rpc_notif_l2-loop-reversion-mode {
    type enumeration {
      enum "automatic" {
        description
          "Automatically unblock the restriction once the loop clears.";
      }
      enum "manual" {
        description
          "Restriction will be in place unless user manually triggers
           the clear.";
      }
    }
    description
      "An enumeration indicating the reversion mode of the restriction placed
       due to detection of a loop.";
  }

  typedef ncs_rpc_notif_cfm-alarm-status {
    type enumeration {
      enum "set" {
        description
          "When fault is present.";
      }
      enum "clear" {
        description
          "When fault is cleared.";
      }
    }
    description
      "An enumeration indicating fault present or cleared in an alarm indication.";
  }

  typedef ncs_rpc_notif_pcp-type {
    type enumeration {
      enum "pcp-0" {
        value 0;
        description
          "Frame priority value 0";
      }
      enum "pcp-1" {
        value 1;
        description
          "Frame priority value 1";
      }
      enum "pcp-2" {
        value 2;
        description
          "Frame priority value 2";
      }
      enum "pcp-3" {
        value 3;
        description
          "Frame priority value 3";
      }
      enum "pcp-4" {
        value 4;
        description
          "Frame priority value 4";
      }
      enum "pcp-5" {
        value 5;
        description
          "Frame priority value 5";
      }
      enum "pcp-6" {
        value 6;
        description
          "Frame priority value 6";
      }
      enum "pcp-7" {
        value 7;
        description
          "Frame priority value 7";
      }
    }
  }

  typedef ncs_rpc_notif_tpid-type {
    type enumeration {
      enum "tpid-8100" {
        value 33024;
        description
          "Identifies the frame as IEEE 802.1Q VLAN tagged";
      }
      enum "tpid-88a8" {
        value 34984;
        description
          "Identifies the frame as IEEE 802.1ad VLAN tagged";
      }
      enum "tpid-9100" {
        value 37120;
        description
          "Identifies the frame as IEEE 802.1QinQ VLAN tagged";
      }
    }
  }

  typedef ncs_rpc_notif_dei-type {
    type enumeration {
      enum "enabled" {
        description
          "Indicates DEI bit is set to 1 in the transmitted frame";
      }
      enum "disabled" {
        description
          "Indicates DEI bit is set to 0 in the transmitted frame";
      }
    }
  }

  typedef live_ncs_cfm-admin-state {
    type enumeration {
      enum "disable" {
        description
          "Administrative state is disabled";
      }
      enum "enable" {
        description
          "Administrative state is enabled";
      }
    }
    description
      "Admininistrative state enumeration";
  }

  typedef live_ncs_l2-loop-reversion-mode {
    type enumeration {
      enum "automatic" {
        description
          "Automatically unblock the restriction once the loop clears.";
      }
      enum "manual" {
        description
          "Restriction will be in place unless user manually triggers
           the clear.";
      }
    }
    description
      "An enumeration indicating the reversion mode of the restriction placed
       due to detection of a loop.";
  }

  typedef live_ncs_cfm-alarm-status {
    type enumeration {
      enum "set" {
        description
          "When fault is present.";
      }
      enum "clear" {
        description
          "When fault is cleared.";
      }
    }
    description
      "An enumeration indicating fault present or cleared in an alarm indication.";
  }

  typedef live_ncs_pcp-type {
    type enumeration {
      enum "pcp-0" {
        value 0;
        description
          "Frame priority value 0";
      }
      enum "pcp-1" {
        value 1;
        description
          "Frame priority value 1";
      }
      enum "pcp-2" {
        value 2;
        description
          "Frame priority value 2";
      }
      enum "pcp-3" {
        value 3;
        description
          "Frame priority value 3";
      }
      enum "pcp-4" {
        value 4;
        description
          "Frame priority value 4";
      }
      enum "pcp-5" {
        value 5;
        description
          "Frame priority value 5";
      }
      enum "pcp-6" {
        value 6;
        description
          "Frame priority value 6";
      }
      enum "pcp-7" {
        value 7;
        description
          "Frame priority value 7";
      }
    }
  }

  typedef live_ncs_tpid-type {
    type enumeration {
      enum "tpid-8100" {
        value 33024;
        description
          "Identifies the frame as IEEE 802.1Q VLAN tagged";
      }
      enum "tpid-88a8" {
        value 34984;
        description
          "Identifies the frame as IEEE 802.1ad VLAN tagged";
      }
      enum "tpid-9100" {
        value 37120;
        description
          "Identifies the frame as IEEE 802.1QinQ VLAN tagged";
      }
    }
  }

  typedef live_ncs_dei-type {
    type enumeration {
      enum "enabled" {
        description
          "Indicates DEI bit is set to 1 in the transmitted frame";
      }
      enum "disabled" {
        description
          "Indicates DEI bit is set to 0 in the transmitted frame";
      }
    }
  }

  typedef cfm-admin-state {
    type enumeration {
      enum "disable" {
        description
          "Administrative state is disabled";
      }
      enum "enable" {
        description
          "Administrative state is enabled";
      }
    }
    description
      "Admininistrative state enumeration";
  }

  typedef l2-loop-reversion-mode {
    type enumeration {
      enum "automatic" {
        description
          "Automatically unblock the restriction once the loop clears.";
      }
      enum "manual" {
        description
          "Restriction will be in place unless user manually triggers
           the clear.";
      }
    }
    description
      "An enumeration indicating the reversion mode of the restriction placed
       due to detection of a loop.";
  }

  typedef cfm-alarm-status {
    type enumeration {
      enum "set" {
        description
          "When fault is present.";
      }
      enum "clear" {
        description
          "When fault is cleared.";
      }
    }
    description
      "An enumeration indicating fault present or cleared in an alarm indication.";
  }

  typedef pcp-type {
    type enumeration {
      enum "pcp-0" {
        value 0;
        description
          "Frame priority value 0";
      }
      enum "pcp-1" {
        value 1;
        description
          "Frame priority value 1";
      }
      enum "pcp-2" {
        value 2;
        description
          "Frame priority value 2";
      }
      enum "pcp-3" {
        value 3;
        description
          "Frame priority value 3";
      }
      enum "pcp-4" {
        value 4;
        description
          "Frame priority value 4";
      }
      enum "pcp-5" {
        value 5;
        description
          "Frame priority value 5";
      }
      enum "pcp-6" {
        value 6;
        description
          "Frame priority value 6";
      }
      enum "pcp-7" {
        value 7;
        description
          "Frame priority value 7";
      }
    }
  }

  typedef tpid-type {
    type enumeration {
      enum "tpid-8100" {
        value 33024;
        description
          "Identifies the frame as IEEE 802.1Q VLAN tagged";
      }
      enum "tpid-88a8" {
        value 34984;
        description
          "Identifies the frame as IEEE 802.1ad VLAN tagged";
      }
      enum "tpid-9100" {
        value 37120;
        description
          "Identifies the frame as IEEE 802.1QinQ VLAN tagged";
      }
    }
  }

  typedef dei-type {
    type enumeration {
      enum "enabled" {
        description
          "Indicates DEI bit is set to 1 in the transmitted frame";
      }
      enum "disabled" {
        description
          "Indicates DEI bit is set to 0 in the transmitted frame";
      }
    }
  }

  augment "/ncs:devices/ncs:device/ncs:rpc" {
    container rpc-l2-loop-block-revert {
      tailf:ncs-device-type "netconf";
      tailf:display-when "not(../../ncs:module) or ../../ncs:module[ncs:name='ciena-cfm']";
      tailf:action l2-loop-block-revert {
        tailf:actionpoint ncsproxy {
          tailf:internal;
        }
        // NCS drop if-feature statement
        description
          "Revert the block on the flow-point.";
        input {
          leaf maintenance-domain {
            tailf:display-when "not(../../ncs:module) or boolean(/ncs:devices/ncs:device[ncs:name=current()/../../ncs:name]/capability/feature='l2-loop')";
            type string;
            mandatory true;
            description
              "A reference to a specific Maintenance Domain.";
          }
          leaf maintenance-association {
            tailf:display-when "not(../../ncs:module) or boolean(/ncs:devices/ncs:device[ncs:name=current()/../../ncs:name]/capability/feature='l2-loop')";
            type string;
            mandatory true;
            description
              "A reference to a specific Maintenance Association.";
          }
          leaf maintenance-association-end-point {
            tailf:display-when "not(../../ncs:module) or boolean(/ncs:devices/ncs:device[ncs:name=current()/../../ncs:name]/capability/feature='l2-loop')";
            type string;
            mandatory true;
            description
              "A reference to a specific Maintenance Association End Point.";
          }
        }
        output {
          leaf errstr {
            tailf:display-when "not(../../ncs:module) or boolean(/ncs:devices/ncs:device[ncs:name=current()/../../ncs:name]/capability/feature='l2-loop')";
            type string;
            description
              "Error message from the device if RPC failed.";
          }
        }
      }
    }
  }
  augment "/ncs:devices/ncs:device-group/ncs:ned-id/ncs:rpc" {
    container rpc-l2-loop-block-revert {
      tailf:ncs-device-type "netconf";
      tailf:display-when "/ncs:devices/ncs:device[ncs:name=current()/../../../ncs:member]/ncs:module[ncs:name='ciena-cfm']";
      tailf:action l2-loop-block-revert {
        tailf:actionpoint ncsproxy {
          tailf:internal;
        }
        // NCS drop if-feature statement
        description
          "Revert the block on the flow-point.";
        input {
          leaf maintenance-domain {
            tailf:display-when "not(../../ncs:module) or boolean(/ncs:devices/ncs:device[ncs:name=current()/../../ncs:name]/capability/feature='l2-loop')";
            type string;
            mandatory true;
            description
              "A reference to a specific Maintenance Domain.";
          }
          leaf maintenance-association {
            tailf:display-when "not(../../ncs:module) or boolean(/ncs:devices/ncs:device[ncs:name=current()/../../ncs:name]/capability/feature='l2-loop')";
            type string;
            mandatory true;
            description
              "A reference to a specific Maintenance Association.";
          }
          leaf maintenance-association-end-point {
            tailf:display-when "not(../../ncs:module) or boolean(/ncs:devices/ncs:device[ncs:name=current()/../../ncs:name]/capability/feature='l2-loop')";
            type string;
            mandatory true;
            description
              "A reference to a specific Maintenance Association End Point.";
          }
        }
        output {
          container "device" {
            leaf "name" {
              type string;
            }
            leaf "info" {
              type string;
            }
            container "result" {
              leaf errstr {
                tailf:display-when "not(../../../../ncs:module) or boolean(/ncs:devices/ncs:device[ncs:name=current()/../../../../ncs:name]/capability/feature='l2-loop')";
                type string;
                description
                  "Error message from the device if RPC failed.";
              }
            }
          }
        }
      }
    }
  }
  augment "/ncs:devices/ncs:device/ncs:rpc" {
    container rpc-clear-maintenance-association-end-point-frame-stats {
      tailf:ncs-device-type "netconf";
      tailf:display-when "not(../../ncs:module) or ../../ncs:module[ncs:name='ciena-cfm']";
      tailf:action clear-maintenance-association-end-point-frame-stats {
        tailf:actionpoint ncsproxy {
          tailf:internal;
        }
        description
          "Administratively clear frame statistics on a specific MEP";
        input {
          leaf maintenance-domain-id {
            type string;
            mandatory true;
            description
              "The ID of a Maintenance Domain of the MEP on which the
               statistics should be administratively cleared";
          }
          leaf maintenance-association-id {
            type string;
            mandatory true;
            description
              "The ID of a Maintenance Association of the MEP on which the
               statistics should be administratively cleared";
          }
          leaf mep-id {
            type mef-cfm:ncs_rpc_notif_mep-id-type;
            mandatory true;
            description
              "The ID of the MEP on which  the statistics should be
               administratively cleared";
          }
        }
      }
    }
  }
  augment "/ncs:devices/ncs:device-group/ncs:ned-id/ncs:rpc" {
    container rpc-clear-maintenance-association-end-point-frame-stats {
      tailf:ncs-device-type "netconf";
      tailf:display-when "/ncs:devices/ncs:device[ncs:name=current()/../../../ncs:member]/ncs:module[ncs:name='ciena-cfm']";
      tailf:action clear-maintenance-association-end-point-frame-stats {
        tailf:actionpoint ncsproxy {
          tailf:internal;
        }
        description
          "Administratively clear frame statistics on a specific MEP";
        input {
          leaf maintenance-domain-id {
            type string;
            mandatory true;
            description
              "The ID of a Maintenance Domain of the MEP on which the
               statistics should be administratively cleared";
          }
          leaf maintenance-association-id {
            type string;
            mandatory true;
            description
              "The ID of a Maintenance Association of the MEP on which the
               statistics should be administratively cleared";
          }
          leaf mep-id {
            type mef-cfm:ncs_rpc_notif_mep-id-type;
            mandatory true;
            description
              "The ID of the MEP on which  the statistics should be
               administratively cleared";
          }
        }
      }
    }
  }
  augment "/ncs:devices/ncs:device/ncs:rpc" {
    container rpc-clear-cfm-global-frame-statistics {
      tailf:ncs-device-type "netconf";
      tailf:display-when "not(../../ncs:module) or ../../ncs:module[ncs:name='ciena-cfm']";
      tailf:action clear-cfm-global-frame-statistics {
        tailf:actionpoint ncsproxy {
          tailf:internal;
        }
        description
          "Administratively clear global frame statistics";
      }
    }
  }
  augment "/ncs:devices/ncs:device-group/ncs:ned-id/ncs:rpc" {
    container rpc-clear-cfm-global-frame-statistics {
      tailf:ncs-device-type "netconf";
      tailf:display-when "/ncs:devices/ncs:device[ncs:name=current()/../../../ncs:member]/ncs:module[ncs:name='ciena-cfm']";
      tailf:action clear-cfm-global-frame-statistics {
        tailf:actionpoint ncsproxy {
          tailf:internal;
        }
        description
          "Administratively clear global frame statistics";
      }
    }
  }
  augment "/ncs:devices/ncs:device/ncs:notifications/ncs:received-notifications/ncs:notification/ncs:data" {
    container cfm-event {
      presence "";
      config false;
      description
        "A notification that a specific service has a loop present or clear condition.";
      list maintenance-domain {
        description
          "maintenance-domain of a specific MEP.";
        leaf id {
          type string;
          description
            "The ID of a Maintenance Domain of the MEP.";
        }
        list maintenance-association {
          description
            "maintenance-association of a specific MEP.";
          leaf id {
            type string;
            description
              "The ID of a Maintenance Association of the MEP.";
          }
          list maintenance-association-end-point {
            description
              "MEP for which a notification needs to be sent when a loop is present
               or when the loop gets cleared.";
            leaf id {
              type string;
              description
                "The ID of the MEP.";
            }
            list event-list {
              leaf event-type {
                type identityref {
                  base cfm-event-type;
                }
                description
                  "CFM event types.";
              }
              leaf status {
                type boolean;
                default "false";
                description
                  "Status of CFM event.";
              }
            }
          }
        }
      }
    }
  }
  augment "/ncs:devices/ncs:device/ncs:netconf-notifications/ncs:received-notifications/ncs:notification/ncs:data" {
    container cfm-event {
      presence "";
      config false;
      description
        "A notification that a specific service has a loop present or clear condition.";
      list maintenance-domain {
        description
          "maintenance-domain of a specific MEP.";
        leaf id {
          type string;
          description
            "The ID of a Maintenance Domain of the MEP.";
        }
        list maintenance-association {
          description
            "maintenance-association of a specific MEP.";
          leaf id {
            type string;
            description
              "The ID of a Maintenance Association of the MEP.";
          }
          list maintenance-association-end-point {
            description
              "MEP for which a notification needs to be sent when a loop is present
               or when the loop gets cleared.";
            leaf id {
              type string;
              description
                "The ID of the MEP.";
            }
            list event-list {
              leaf event-type {
                type identityref {
                  base cfm-event-type;
                }
                description
                  "CFM event types.";
              }
              leaf status {
                type boolean;
                default "false";
                description
                  "Status of CFM event.";
              }
            }
          }
        }
      }
    }
  }
  augment "/ncs:devices/ncs:device/ncs:config" {
    container cfm-global-config {
      tailf:ncs-device-type "netconf";
      tailf:display-when "not(../../ncs:module) or ../../ncs:module[ncs:name='ciena-cfm']";
      description
        "Contains configurable parameters applicable to all maintenance
         associations in the system";
      leaf admin-state {
        type cfm-admin-state;
        description
          "Enable or disable CFM on this device";
      }
    }
    // NCS drop config false container 'cfm-global-frame-statistics'
    // NCS drop config false container 'cfm-maintenance-domain-intermediate-point'
    // NCS drop config false list 'cfm-configuration-error-list'
  }
  augment "/ncs:devices/ncs:device/ncs:live-status" {
    container cfm-global-config {
      tailf:ncs-device-type "netconf";
      tailf:display-when "not(../../ncs:module) or ../../ncs:module[ncs:name='ciena-cfm'] or (../../ncs:live-status-protocol[not(ncs:capability)]) or (../../ncs:live-status-protocol/ncs:capability/ncs:module[.='ciena-cfm'])";
      description
        "Contains configurable parameters applicable to all maintenance
         associations in the system";
      leaf admin-state {
        type live_ncs_cfm-admin-state;
        description
          "Enable or disable CFM on this device";
      }
    }
    container cfm-global-frame-statistics {
      tailf:ncs-device-type "netconf";
      tailf:display-when "not(../../ncs:module) or ../../ncs:module[ncs:name='ciena-cfm'] or (../../ncs:live-status-protocol[not(ncs:capability)]) or (../../ncs:live-status-protocol/ncs:capability/ncs:module[.='ciena-cfm'])";
      description
        "Global statistics of CFM frames";
      leaf tx-cfm {
        type yang:counter32;
        description
          "Total number of CFM frames transmitted";
      }
      leaf rx-cfm {
        type yang:counter32;
        description
          "Total number of CFM frames received";
      }
      leaf rx-cfm-discarded-by-passive-side-mep {
        type yang:counter32;
        description
          "Total Rx CFM frames discarded by the passive side of a MEP";
      }
      leaf rx-cfm-drop-invalid-interface-status-tlv {
        type yang:counter32;
        description
          "Total number of frames dropped due to invalid interface status
           TLV";
      }
      leaf rx-cfm-drop-invalid-port-status-tlv {
        type yang:counter32;
        description
          "Total number of frames dropped due to invalid port status TLV";
      }
      leaf rx-cfm-drop-admin-disable {
        type yang:counter32;
        description
          "Total number of frames dropped due to CFM admin disable";
      }
      leaf rx-cfm-drop-l2loop {
        type yang:counter32;
        description
          "Total number of frames dropped due to l2 loop";
      }
      leaf tx-lbm {
        type yang:counter32;
        description
          "Total number of LBM frames transmitted";
      }
      leaf rx-lbm {
        type yang:counter32;
        description
          "Total number of LBM frames received";
      }
      leaf tx-lbr {
        type yang:counter32;
        description
          "Total number of LBR frames transmitted";
      }
      leaf rx-lbr {
        type yang:counter32;
        description
          "Total number of LBR frames received";
      }
      leaf tx-dmm {
        type yang:counter32;
        description
          "Total number of DMM frames transmitted";
      }
      leaf rx-dmm {
        type yang:counter32;
        description
          "Total number of DMM frames received";
      }
      leaf tx-dmr {
        type yang:counter32;
        description
          "Total number of DMR frames transmitted";
      }
      leaf rx-dmr {
        type yang:counter32;
        description
          "Total number of DMR frames received";
      }
      leaf tx-lmm {
        type yang:counter32;
        description
          "Total number of LMM frames transmitted";
      }
      leaf rx-lmm {
        type yang:counter32;
        description
          "Total number of LMM frames received";
      }
      leaf tx-lmr {
        type yang:counter32;
        description
          "Total number of LMR frames transmitted";
      }
      leaf rx-lmr {
        type yang:counter32;
        description
          "Total number of LMR frames received";
      }
      leaf tx-slm {
        type yang:counter32;
        description
          "Total number of SLM frames transmitted";
      }
      leaf rx-slm {
        type yang:counter32;
        description
          "Total number of SLM frames received";
      }
      leaf tx-slr {
        type yang:counter32;
        description
          "Total number of SLR frames transmitted";
      }
      leaf rx-slr {
        type yang:counter32;
        description
          "Total number of SLR frames received";
      }
      leaf tx-ccm {
        type yang:counter32;
        description
          "Total number of CCM frames transmitted on all MEPs";
      }
      leaf rx-ccm {
        type yang:counter32;
        description
          "Total number of valid CCM frames received";
      }
      leaf rx-ccm-interval-mismatch {
        type yang:counter32;
        description
          "Total number of CCM frames received with ccm-interval
           mismatch";
      }
      leaf rx-ccm-sequence-error {
        type yang:counter32;
        description
          "Total number of CCM frames received with sequence error";
      }
      leaf rx-ccm-cross-connect-maid {
        type yang:counter32;
        description
          "Total number of CCM frames received with invalid MAID
           encoding";
      }
      leaf rx-ccm-cross-connect-md-level {
        type yang:counter32;
        description
          "Total number of cross-connect CCM frames due to MD level";
      }
      leaf tx-ltm {
        type yang:counter32;
        description
          "Total number of LTM frames transmitted";
      }
      leaf rx-ltm {
        type yang:counter32;
        description
          "Total number of LTM frames received";
      }
      leaf tx-ltr {
        type yang:counter32;
        description
          "Total number of LTR frames transmitted";
      }
      leaf rx-ltm-invalid {
        type yang:counter32;
        description
          "Total number of invalid LTM frames received";
      }
      leaf rx-ltm-unresolved {
        type yang:counter32;
        description
          "Total number of received LTM with unresolved target MAC";
      }
      leaf rx-ltr {
        type yang:counter32;
        description
          "Total number of LTR frames received";
      }
      leaf rx-ltr-invalid {
        type yang:counter32;
        description
          "Total number of invalid LTR frames received";
      }
      leaf rx-ltr-invalid-relay-action {
        type yang:counter32;
        description
          "Total number of LTR frames received with invalid relay action
           rules";
      }
      leaf rx-ltr-unexpected {
        type yang:counter32;
        description
          "Total number of received LTR frames that does not match
           expected transaction ID";
      }
    }
    container cfm-maintenance-domain-intermediate-point {
      tailf:ncs-device-type "netconf";
      tailf:display-when "not(../../ncs:module) or ../../ncs:module[ncs:name='ciena-cfm'] or (../../ncs:live-status-protocol[not(ncs:capability)]) or (../../ncs:live-status-protocol/ncs:capability/ncs:module[.='ciena-cfm'])";
      description
        "Data definitions related to the Maintenance domain Intermediate
         Point";
      list maintenance-domain-intermediate-point {
        key "fp-name md-level";
        description
          "The list of Maintenance domain Intermediate Points";
        leaf fp-name {
          type string;
          description
            "The flow point on which MIP is created.";
        }
        leaf fd-name {
          type string;
          description
            "An administratively assigned string, which may be used
             to identify the forwarding domain.";
        }
        leaf md-level {
          type mef-cfm:live_ncs_md-level-type;
          description
            "The MD Level at which MIP is created.";
        }
        leaf mac-address {
          type yang:mac-address;
          description
            "The MAC address of the MIP.";
        }
      }
    }
    list cfm-configuration-error-list {
      tailf:ncs-device-type "netconf";
      tailf:display-when "not(../ncs:module) or ../ncs:module[ncs:name='ciena-cfm'] or (../ncs:live-status-protocol[not(ncs:capability)]) or (../ncs:live-status-protocol/ncs:capability/ncs:module[.='ciena-cfm'])";
      key "interface";
      description
        "The Configuration Error List managed object provides a list of
         flow points that are incorrectly configured.";
      leaf interface {
        type string;
        description
          "A flow point as defined in mef-fp. The value is expected to
           uniquely identify a single interface on the system. The
           structure of the identifier is implementation specific.";
      }
      leaf fd-name {
        type string;
        description
          "An administratively assigned string, which may be used to
           identify the forwarding domain.";
      }
      leaf error-conditions {
        type mef-cfm:live_ncs_error-conditions-type;
        // NCS drop mandatory statement
        description
          "A list of possible errors on a flow point.";
        reference "[802.1q] 12.14.4.1.3:b";
      }
    }
  }
  augment "/ncs:devices/ncs:template/ncs:ned-id/ncs:config" {
    container cfm-global-config {
      description
        "Contains configurable parameters applicable to all maintenance
         associations in the system";
      leaf admin-state {
        type ncs_template_cfm-admin-state;
        description
          "Enable or disable CFM on this device";
      }
    }
    // NCS drop config false container 'cfm-global-frame-statistics'
    // NCS drop config false container 'cfm-maintenance-domain-intermediate-point'
    // NCS drop config false list 'cfm-configuration-error-list'
  }
  augment "/ncs:devices/ncs:template/ncs:ned-id/ncs:config/mef-cfm:default-md-levels" {
    description
      "Augmentation for default-md-levels";
    list fd-default-md-level {
      // NCS patched for predictable order
      ordered-by user;
      key "fd-name";
      description
        "Data definitions related to the default MD level associated
         with specific flow domain";
      leaf fd-name {
        type string;
        description
          "An administratively assigned string, which may be used
           to identify the flow domain.";
      }
      // NCS drop config false leaf status
      uses mef-cfm:ncs_template_md-level-group;
    }
  }
  augment "/ncs:devices/ncs:device/ncs:live-status/mef-cfm:default-md-levels" {
    description
      "Augmentation for default-md-levels";
    list fd-default-md-level {
      tailf:ncs-device-type "netconf";
      tailf:display-when "not(../../ncs:module) or ../../ncs:module[ncs:name='ciena-cfm'] or (../../ncs:live-status-protocol[not(ncs:capability)]) or (../../ncs:live-status-protocol/ncs:capability/ncs:module[.='ciena-cfm'])";
      key "fd-name";
      description
        "Data definitions related to the default MD level associated
         with specific flow domain";
      leaf fd-name {
        type leafref {
          path "/ncs:devices/ncs:device/ncs:live-status/ciena-mef-fd:fds/ciena-mef-fd:fd/ciena-mef-fd:name" {
            tailf:xpath-root 3;
          }
        }
        description
          "An administratively assigned string, which may be used
           to identify the flow domain.";
      }
      leaf status {
        type boolean;
        description
          "State of this list entry. The value 'true' if there is no
           entry in the maintenance-assoication list entry defining an
           MA for the same flow domain and MD Level as this table's
           entry, and on which MA an Up MEP is defined, else 'false'.";
        reference "[802.1q] 12.14.3.1.3:b";
      }
      uses mef-cfm:live_ncs_md-level-group;
    }
  }
  augment "/ncs:devices/ncs:device/ncs:config/mef-cfm:default-md-levels" {
    description
      "Augmentation for default-md-levels";
    list fd-default-md-level {
      tailf:ncs-device-type "netconf";
      tailf:display-when "not(../../ncs:module) or ../../ncs:module[ncs:name='ciena-cfm']";
      key "fd-name";
      description
        "Data definitions related to the default MD level associated
         with specific flow domain";
      leaf fd-name {
        type leafref {
          path "/ncs:devices/ncs:device/ncs:config/ciena-mef-fd:fds/ciena-mef-fd:fd/ciena-mef-fd:name" {
            tailf:xpath-root 3;
          }
        }
        description
          "An administratively assigned string, which may be used
           to identify the flow domain.";
      }
      // NCS drop config false leaf status
      uses mef-cfm:md-level-group;
    }
  }
  augment "/ncs:devices/ncs:template/ncs:ned-id/ncs:config/mef-cfm:maintenance-domain/mef-cfm:maintenance-association" {
    description
      "Augmentation for RMEP config";
    list remote-mep-config {
      // NCS patched for predictable order
      ordered-by user;
      key "mep-id";
      description
        "RMEP configuration parameters.";
      leaf mep-id {
        type mef-cfm:ncs_template_mep-id-type;
        description
          "ID of a remote MEP";
      }
      leaf mac-address {
        type string;
        // NCS drop mandatory statement
        description
          "The MAC address of the remote MEP.";
      }
      leaf admin-state {
        type ncs_template_cfm-admin-state;
        // NCS drop default statement
        description
          "Enable or disable the RMEP admin state.";
      }
    }
  }
  augment "/ncs:devices/ncs:device/ncs:live-status/mef-cfm:maintenance-domain/mef-cfm:maintenance-association" {
    description
      "Augmentation for RMEP config";
    list remote-mep-config {
      tailf:ncs-device-type "netconf";
      tailf:display-when "not(../../../ncs:module) or ../../../ncs:module[ncs:name='ciena-cfm'] or (../../../ncs:live-status-protocol[not(ncs:capability)]) or (../../../ncs:live-status-protocol/ncs:capability/ncs:module[.='ciena-cfm'])";
      key "mep-id";
      description
        "RMEP configuration parameters.";
      leaf mep-id {
        type mef-cfm:live_ncs_mep-id-type;
        description
          "ID of a remote MEP";
      }
      leaf mac-address {
        type yang:mac-address;
        // NCS drop mandatory statement
        description
          "The MAC address of the remote MEP.";
      }
      leaf admin-state {
        type live_ncs_cfm-admin-state;
        // NCS drop default statement
        description
          "Enable or disable the RMEP admin state.";
      }
    }
  }
  augment "/ncs:devices/ncs:device/ncs:config/mef-cfm:maintenance-domain/mef-cfm:maintenance-association" {
    description
      "Augmentation for RMEP config";
    list remote-mep-config {
      tailf:ncs-device-type "netconf";
      tailf:display-when "not(../../../ncs:module) or ../../../ncs:module[ncs:name='ciena-cfm']";
      key "mep-id";
      description
        "RMEP configuration parameters.";
      leaf mep-id {
        type mef-cfm:mep-id-type;
        description
          "ID of a remote MEP";
      }
      leaf mac-address {
        type yang:mac-address;
        mandatory true;
        description
          "The MAC address of the remote MEP.";
      }
      leaf admin-state {
        type cfm-admin-state;
        default "disable";
        description
          "Enable or disable the RMEP admin state.";
      }
    }
  }
  augment "/ncs:devices/ncs:template/ncs:ned-id/ncs:config/mef-cfm:maintenance-domain/mef-cfm:maintenance-association" {
    description
      "Augmentation for CCM loss number";
    leaf ccm-loss-num {
      type string;
      // NCS drop default statement
      description
        "Indicates the CCM loss number, which may be used to
         detect CCM fault at local MEP.";
    }
  }
  augment "/ncs:devices/ncs:device/ncs:live-status/mef-cfm:maintenance-domain/mef-cfm:maintenance-association" {
    description
      "Augmentation for CCM loss number";
    leaf ccm-loss-num {
      tailf:ncs-device-type "netconf";
      tailf:display-when "not(../../../../ncs:module) or ../../../../ncs:module[ncs:name='ciena-cfm'] or (../../../../ncs:live-status-protocol[not(ncs:capability)]) or (../../../../ncs:live-status-protocol/ncs:capability/ncs:module[.='ciena-cfm'])";
      type uint8 {
        range "1..255";
      }
      // NCS drop default statement
      description
        "Indicates the CCM loss number, which may be used to
         detect CCM fault at local MEP.";
    }
  }
  augment "/ncs:devices/ncs:device/ncs:config/mef-cfm:maintenance-domain/mef-cfm:maintenance-association" {
    description
      "Augmentation for CCM loss number";
    leaf ccm-loss-num {
      tailf:ncs-device-type "netconf";
      tailf:display-when "not(../../../../ncs:module) or ../../../../ncs:module[ncs:name='ciena-cfm']";
      type uint8 {
        range "1..255";
      }
      default "3";
      description
        "Indicates the CCM loss number, which may be used to
         detect CCM fault at local MEP.";
    }
  }
  augment "/ncs:devices/ncs:template/ncs:ned-id/ncs:config/mef-cfm:maintenance-domain/mef-cfm:maintenance-association/mef-cfm:component-list" {
    description
      "Augmentation for fd name";
    leaf fd-name {
      type string;
      description
        "An administratively assigned string, which may be used
         to identify the forwarding domain.";
    }
  }
  augment "/ncs:devices/ncs:device/ncs:live-status/mef-cfm:maintenance-domain/mef-cfm:maintenance-association/mef-cfm:component-list" {
    description
      "Augmentation for fd name";
    leaf fd-name {
      tailf:ncs-device-type "netconf";
      tailf:display-when "not(../../../../../ncs:module) or ../../../../../ncs:module[ncs:name='ciena-cfm'] or (../../../../../ncs:live-status-protocol[not(ncs:capability)]) or (../../../../../ncs:live-status-protocol/ncs:capability/ncs:module[.='ciena-cfm'])";
      type leafref {
        path "/ncs:devices/ncs:device/ncs:live-status/ciena-mef-fd:fds/ciena-mef-fd:fd/ciena-mef-fd:name" {
          tailf:xpath-root 3;
        }
      }
      description
        "An administratively assigned string, which may be used
         to identify the forwarding domain.";
    }
  }
  augment "/ncs:devices/ncs:device/ncs:config/mef-cfm:maintenance-domain/mef-cfm:maintenance-association/mef-cfm:component-list" {
    description
      "Augmentation for fd name";
    leaf fd-name {
      tailf:ncs-device-type "netconf";
      tailf:display-when "not(../../../../../ncs:module) or ../../../../../ncs:module[ncs:name='ciena-cfm']";
      type leafref {
        path "/ncs:devices/ncs:device/ncs:config/ciena-mef-fd:fds/ciena-mef-fd:fd/ciena-mef-fd:name" {
          tailf:xpath-root 3;
        }
      }
      description
        "An administratively assigned string, which may be used
         to identify the forwarding domain.";
    }
  }
  augment "/ncs:devices/ncs:template/ncs:ned-id/ncs:config/mef-cfm:maintenance-domain/mef-cfm:maintenance-association/mef-cfm:maintenance-association-end-point" {
    description
      "Augments maintenance association end point for interface-type
       and operational data";
    leaf interface-type {
      type string;
      description
        "Lower layer interface type over which maintenance association
         end point is created";
    }
    container l2-transform {
      presence "Enable l2-transform";
      description
        "Specifies the l2-transform that is to be applied on the CFM
         frames";
      choice vlan-type {
        case vlan {
          leaf tpid {
            type ncs_template_tpid-type;
            // NCS drop default statement
            description
              "Tag protocol identifier, a 16-bit field set in order to
               identify the frame as tagged";
          }
          leaf pcp {
            type ncs_template_pcp-type;
            description
              "Priority code point, a 3-bit field that maps to the frame
               priority level. These values are used to prioritize different
               classes of traffic.";
          }
          leaf dei {
            type ncs_template_dei-type;
            description
              "Drop eligible indicator, a 1-bit field to indicate frames
               eligible to be dropped in the presence of congestion.";
          }
          leaf vlanid {
            type mef-cfm:ncs_template_vlan-id-type;
            // NCS drop mandatory statement
            description
              "VLAN ID that is transmitted in CCM";
          }
        }
        case vlan-stack {
          list vtags {
            // NCS patched for predictable order
            ordered-by user;
            key "tag";
            // NCS drop max-elements statement
            // NCS drop min-elements statement
            description
              "List to configure dual-tagged l2-transform applied on CFM frames.";
            leaf tag {
              // NCS drop mandatory statement
              type string;
              description
                "'1' represents outermost tag, '2' next outermost.";
            }
            leaf tpid {
              type ncs_template_tpid-type;
              // NCS drop default statement
              description
                "Tag protocol identifier, a 16-bit field set in order to
                 identify the frame as tagged";
            }
            leaf pcp {
              type ncs_template_pcp-type;
              description
                "Priority code point, a 3-bit field that maps to the frame
                 priority level. These values are used to prioritize different
                 classes of traffic.";
            }
            leaf dei {
              type ncs_template_dei-type;
              description
                "Drop eligible indicator, a 1-bit field to indicate frames
                 eligible to be dropped in the presence of congestion.";
            }
            leaf vlanid {
              type mef-cfm:ncs_template_vlan-id-type;
              // NCS drop mandatory statement
              description
                "VLAN ID that is transmitted in CCM";
            }
          }
        }
      }
    }
    // NCS drop config false container 'maintenance-association-end-point-oper-data'
    // NCS drop config false container 'maintenance-association-end-point-frame-stats'
  }
  augment "/ncs:devices/ncs:device/ncs:live-status/mef-cfm:maintenance-domain/mef-cfm:maintenance-association/mef-cfm:maintenance-association-end-point" {
    description
      "Augments maintenance association end point for interface-type
       and operational data";
    leaf interface-type {
      tailf:ncs-device-type "netconf";
      tailf:display-when "not(../../../../../ncs:module) or ../../../../../ncs:module[ncs:name='ciena-cfm'] or (../../../../../ncs:live-status-protocol[not(ncs:capability)]) or (../../../../../ncs:live-status-protocol/ncs:capability/ncs:module[.='ciena-cfm'])";
      type enumeration {
        enum "bridge-port" {
          description
            "An interface which is either a Bridge
             Port or an aggregated IEEE 802.3 port";
        }
        enum "fp" {
          description
            "A flow point as defined in mef-fp";
        }
      }
      description
        "Lower layer interface type over which maintenance association
         end point is created";
    }
    container l2-transform {
      tailf:ncs-device-type "netconf";
      tailf:display-when "not(../../../../../ncs:module) or ../../../../../ncs:module[ncs:name='ciena-cfm'] or (../../../../../ncs:live-status-protocol[not(ncs:capability)]) or (../../../../../ncs:live-status-protocol/ncs:capability/ncs:module[.='ciena-cfm'])";
      presence "Enable l2-transform";
      description
        "Specifies the l2-transform that is to be applied on the CFM
         frames";
      choice vlan-type {
        case vlan {
          leaf tpid {
            type live_ncs_tpid-type;
            // NCS drop default statement
            description
              "Tag protocol identifier, a 16-bit field set in order to
               identify the frame as tagged";
          }
          leaf pcp {
            type live_ncs_pcp-type;
            description
              "Priority code point, a 3-bit field that maps to the frame
               priority level. These values are used to prioritize different
               classes of traffic.";
          }
          leaf dei {
            type live_ncs_dei-type;
            description
              "Drop eligible indicator, a 1-bit field to indicate frames
               eligible to be dropped in the presence of congestion.";
          }
          leaf vlanid {
            type mef-cfm:live_ncs_vlan-id-type;
            // NCS drop mandatory statement
            description
              "VLAN ID that is transmitted in CCM";
          }
        }
        case vlan-stack {
          list vtags {
            key "tag";
            // NCS drop max-elements statement
            // NCS drop min-elements statement
            description
              "List to configure dual-tagged l2-transform applied on CFM frames.";
            leaf tag {
              // NCS drop mandatory statement
              type uint8;
              description
                "'1' represents outermost tag, '2' next outermost.";
            }
            leaf tpid {
              type live_ncs_tpid-type;
              // NCS drop default statement
              description
                "Tag protocol identifier, a 16-bit field set in order to
                 identify the frame as tagged";
            }
            leaf pcp {
              type live_ncs_pcp-type;
              description
                "Priority code point, a 3-bit field that maps to the frame
                 priority level. These values are used to prioritize different
                 classes of traffic.";
            }
            leaf dei {
              type live_ncs_dei-type;
              description
                "Drop eligible indicator, a 1-bit field to indicate frames
                 eligible to be dropped in the presence of congestion.";
            }
            leaf vlanid {
              type mef-cfm:live_ncs_vlan-id-type;
              // NCS drop mandatory statement
              description
                "VLAN ID that is transmitted in CCM";
            }
          }
        }
      }
    }
    container maintenance-association-end-point-oper-data {
      tailf:ncs-device-type "netconf";
      tailf:display-when "not(../../../../../ncs:module) or ../../../../../ncs:module[ncs:name='ciena-cfm'] or (../../../../../ncs:live-status-protocol[not(ncs:capability)]) or (../../../../../ncs:live-status-protocol/ncs:capability/ncs:module[.='ciena-cfm'])";
      description
        "The MEP Operational data";
      leaf error-ccm-defect-timeout {
        type yang:date-and-time;
        description
          "Time when invalid CCMs timeouts.";
      }
      leaf cross-connect-ccm-defect-timeout {
        type yang:date-and-time;
        description
          "Time when cross connect CCMs timouts.";
      }
      leaf next-ccm-transaction-id {
        type uint32;
        description
          "A  MEP  either  transmits a 0 in  this
           field  or  copies  to  it the contents
           of the CCIsentCCMs variable.";
      }
      leaf instability-defect {
        type boolean;
        description
          "The MEP has never established a stable
           CCM connection with any remote MEP";
      }
      leaf rdi-present {
        type boolean;
        description
          "A Boolean value indicating the state of
           the RDI bit in CCMs transmitted by this
           MEP. rdi-present is true if and only if
           one or more of the variables RMEPCCMdefect,
           MACstatusDefect, errorCCMdefect, or
           xconCCMdefect is true, and if the corresponding
           priority of that variable, from
           IEEE Std 802.1Q 2011 Table 20-1, is
           greater than or equal to the value of the
           variable lowestAlarmPri.";
      }
      leaf ppm-forced-ccm-off {
        type boolean;
        description
          "The status of CCM after PPM action on it.";
      }
    }
    container maintenance-association-end-point-frame-stats {
      tailf:ncs-device-type "netconf";
      tailf:display-when "not(../../../../../ncs:module) or ../../../../../ncs:module[ncs:name='ciena-cfm'] or (../../../../../ncs:live-status-protocol[not(ncs:capability)]) or (../../../../../ncs:live-status-protocol/ncs:capability/ncs:module[.='ciena-cfm'])";
      description
        "Frame stats on each MEP";
      leaf tx-ccm {
        type yang:counter32;
        description
          "Total number of CCM frames transmitted on the MEP";
      }
      leaf rx-ccm {
        type yang:counter32;
        description
          "Total number of CCM frames received on the MEP";
      }
      leaf tx-dmm {
        type yang:counter32;
        description
          "Total number of DMM frames transmitted on the MEP";
      }
      leaf rx-dmm {
        type yang:counter32;
        description
          "Total number of DMM frames received on the MEP";
      }
      leaf tx-dmr {
        type yang:counter32;
        description
          "Total number of DMR frames transmitted  on the MEP";
      }
      leaf rx-dmr {
        type yang:counter32;
        description
          "Total number of DMR frames received on the MEP";
      }
      leaf tx-slm {
        type yang:counter32;
        description
          "Total number of SLM frames transmitted on the MEP";
      }
      leaf rx-slm {
        type yang:counter32;
        description
          "Total number of SLM frames received on the MEP";
      }
      leaf tx-slr {
        type yang:counter32;
        description
          "Total number of SLR frames transmitted on the MEP";
      }
      leaf rx-slr {
        type yang:counter32;
        description
          "Total number of SLR frames received on the MEP";
      }
      leaf tx-lmm {
        type yang:counter32;
        description
          "Total number of LMM frames transmitted on the MEP";
      }
      leaf rx-lmm {
        type yang:counter32;
        description
          "Total number of LMM frames received on the MEP";
      }
      leaf tx-lmr {
        type yang:counter32;
        description
          "Total number of LMR frames transmitted on the MEP";
      }
      leaf rx-lmr {
        type yang:counter32;
        description
          "Total number of LMR frames received on the MEP";
      }
      leaf tx-lbm {
        type yang:counter32;
        description
          "Total number of LBM frames transmitted on the MEP";
      }
      leaf rx-lbm {
        type yang:counter32;
        description
          "Total number of LBM frames received on the MEP";
      }
      leaf tx-lbr {
        type yang:counter32;
        description
          "Total number of LBR frames transmitted on the MEP";
      }
      leaf rx-lbr {
        type yang:counter32;
        description
          "Total number of LBR frames received on the MEP";
      }
      leaf tx-ltm {
        type yang:counter32;
        description
          "Total number of LTM frames transmitted";
      }
      leaf rx-ltm {
        type yang:counter32;
        description
          "Total number of LTM frames received";
      }
      leaf tx-ltr {
        type yang:counter32;
        description
          "Total number of LTR frames transmitted";
      }
      leaf rx-ltr {
        type yang:counter32;
        description
          "Total number of LTR frames received";
      }
      leaf rx-ltm-invalid {
        type yang:counter32;
        description
          "Total number of invalid LTM frames received";
      }
      leaf rx-ltr-invalid {
        type yang:counter32;
        description
          "Total number of invalid LTR frames received";
      }
      leaf rx-ltr-unexpected {
        type yang:counter32;
        description
          "Total number of received LTR frames that does not match
           expected transaction ID";
      }
      leaf rx-ltr-invalid-relay-action {
        type yang:counter32;
        description
          "Total number of LTR frames received with invalid relay
           action rules";
      }
    }
  }
  augment "/ncs:devices/ncs:device/ncs:config/mef-cfm:maintenance-domain/mef-cfm:maintenance-association/mef-cfm:maintenance-association-end-point" {
    description
      "Augments maintenance association end point for interface-type
       and operational data";
    leaf interface-type {
      tailf:ncs-device-type "netconf";
      tailf:display-when "not(../../../../../ncs:module) or ../../../../../ncs:module[ncs:name='ciena-cfm']";
      type enumeration {
        enum "bridge-port" {
          description
            "An interface which is either a Bridge
             Port or an aggregated IEEE 802.3 port";
        }
        enum "fp" {
          description
            "A flow point as defined in mef-fp";
        }
      }
      description
        "Lower layer interface type over which maintenance association
         end point is created";
    }
    container l2-transform {
      tailf:ncs-device-type "netconf";
      tailf:display-when "not(../../../../../ncs:module) or ../../../../../ncs:module[ncs:name='ciena-cfm']";
      presence "Enable l2-transform";
      description
        "Specifies the l2-transform that is to be applied on the CFM
         frames";
      choice vlan-type {
        case vlan {
          leaf tpid {
            type tpid-type;
            default "tpid-8100";
            description
              "Tag protocol identifier, a 16-bit field set in order to
               identify the frame as tagged";
          }
          leaf pcp {
            type pcp-type;
            description
              "Priority code point, a 3-bit field that maps to the frame
               priority level. These values are used to prioritize different
               classes of traffic.";
          }
          leaf dei {
            type dei-type;
            description
              "Drop eligible indicator, a 1-bit field to indicate frames
               eligible to be dropped in the presence of congestion.";
          }
          leaf vlanid {
            type mef-cfm:vlan-id-type;
            mandatory true;
            description
              "VLAN ID that is transmitted in CCM";
          }
        }
        case vlan-stack {
          list vtags {
            key "tag";
            max-elements 2;
            min-elements 2;
            description
              "List to configure dual-tagged l2-transform applied on CFM frames.";
            leaf tag {
              mandatory true;
              type uint8;
              description
                "'1' represents outermost tag, '2' next outermost.";
            }
            leaf tpid {
              type tpid-type;
              default "tpid-8100";
              description
                "Tag protocol identifier, a 16-bit field set in order to
                 identify the frame as tagged";
            }
            leaf pcp {
              type pcp-type;
              description
                "Priority code point, a 3-bit field that maps to the frame
                 priority level. These values are used to prioritize different
                 classes of traffic.";
            }
            leaf dei {
              type dei-type;
              description
                "Drop eligible indicator, a 1-bit field to indicate frames
                 eligible to be dropped in the presence of congestion.";
            }
            leaf vlanid {
              type mef-cfm:vlan-id-type;
              mandatory true;
              description
                "VLAN ID that is transmitted in CCM";
            }
          }
        }
      }
    }
    // NCS drop config false container 'maintenance-association-end-point-oper-data'
    // NCS drop config false container 'maintenance-association-end-point-frame-stats'
  }
  augment "/ncs:devices/ncs:device/ncs:live-status/mef-cfm:maintenance-domain/mef-cfm:maintenance-association/mef-cfm:maintenance-association-end-point/mef-cfm:loopback" {
    description
      "Augments loopback for operational data";
    leaf loopback-session-active {
      tailf:ncs-device-type "netconf";
      tailf:display-when "not(../../../../../../ncs:module) or ../../../../../../ncs:module[ncs:name='ciena-cfm'] or (../../../../../../ncs:live-status-protocol[not(ncs:capability)]) or (../../../../../../ncs:live-status-protocol/ncs:capability/ncs:module[.='ciena-cfm'])";
      type boolean;
      description
        "A Boolean flag set to true to indicate that a loopback session
         is active. Reset to false by the MEP Loopback Initiator State
         Machine.";
    }
    leaf lbm-transmitted {
      tailf:ncs-device-type "netconf";
      tailf:display-when "not(../../../../../../ncs:module) or ../../../../../../ncs:module[ncs:name='ciena-cfm'] or (../../../../../../ncs:live-status-protocol[not(ncs:capability)]) or (../../../../../../ncs:live-status-protocol/ncs:capability/ncs:module[.='ciena-cfm'])";
      type yang:counter32;
      description
        "Total number of LBM frames transmitted by the MEP";
    }
    leaf lbm-received {
      tailf:ncs-device-type "netconf";
      tailf:display-when "not(../../../../../../ncs:module) or ../../../../../../ncs:module[ncs:name='ciena-cfm'] or (../../../../../../ncs:live-status-protocol[not(ncs:capability)]) or (../../../../../../ncs:live-status-protocol/ncs:capability/ncs:module[.='ciena-cfm'])";
      type yang:counter32;
      description
        "Total number of LBM frames received by the MEP";
    }
  }
  augment "/ncs:devices/ncs:device/ncs:live-status/mef-cfm:maintenance-domain/mef-cfm:maintenance-association/mef-cfm:maintenance-association-end-point/mef-cfm:remote-mep-database/mef-cfm:remote-mep" {
    description
      "Augments remote mep for operational data";
    container remote-mep-oper-data {
      tailf:ncs-device-type "netconf";
      tailf:display-when "not(../../../../../../../ncs:module) or ../../../../../../../ncs:module[ncs:name='ciena-cfm'] or (../../../../../../../ncs:live-status-protocol[not(ncs:capability)]) or (../../../../../../../ncs:live-status-protocol/ncs:capability/ncs:module[.='ciena-cfm'])";
      description
        "Remote mep operational data";
      leaf operational-state {
        type enumeration {
          enum "disabled" {
            description
              "Remote MEP is admin disabled";
          }
          enum "enabled" {
            description
              "Remote MEP is admin enabled and the remote MEP must be
               free of a CCM fault for rmep-hold-time before it
               transitions to oper enabled";
          }
          enum "holding" {
            description
              "Holding is an intermediate state between oper disabled
               and enabled";
          }
        }
        description
          "An enumeration indicating if defects associated
           with a remote MEP fault the service. Detected service
           defects can only trigger a fault when the remote MEP is
           oper enabled";
      }
      leaf last-state-change-time {
        type yang:date-and-time;
        description
          "Time that a remote MEP CCM defect was last detected or
           cleared";
      }
      leaf hold-state-timeout {
        type yang:date-and-time;
        description
          "Time until a remote MEP in hold state transitions to oper
           enabled";
      }
      leaf last-ccm-rx-time {
        type yang:date-and-time;
        description
          "Time that the last CCM was received from the remote MEP";
      }
      leaf total-rx-ccm {
        type yang:counter32;
        description
          "Total number of CCMs received from the remote MEP";
      }
      leaf rmep-ccm-defect {
        type boolean;
        description
          "Reports the state of the remote MEP. When true, no CCM has
           been received from the remote MEP for at least
           (3.25  CCMtime(CCMinterval)) seconds.";
      }
      leaf mac-status-defect {
        type boolean;
        description
          "A Boolean indicating that remote MEP is reporting a failure
           in its Port Status TLV or Interface Status TLV";
      }
      leaf ccm-timeout {
        type yang:date-and-time;
        description
          "Time when, timer counter for declaring mismatch defects based
           on the received traffic field, timeouts";
      }
      leaf rx-timeout-stamp {
        type yang:date-and-time;
        description
          "Time that the last CCM received from the remote MEP expires,
           triggering an RMEP CCM defect";
      }
      leaf discovery-type {
        type enumeration {
          enum "static" {
            description
              "RMEP is statically configured";
          }
          enum "dynamic" {
            description
              "RMEP is dynamically configured via CCMs learning";
          }
        }
        description
          "Indicate that remote MEP is created statically by user manually or
           is created dynamically via CCMs learning";
      }
    }
  }
  augment "/ncs:devices/ncs:device/ncs:rpc/mef-cfm:rpc-transmit-loopback/mef-cfm:transmit-loopback/mef-cfm:input" {
    description
      "Augments loopback RPC input.";
    leaf interval {
      type uint32 {
        range "0..60000";
      }
      units "milliseconds";
      default "1000";
      description
        "The interval between LBM transmissions by a MEP.";
    }
    leaf timeout {
      type yang:gauge32 {
        range "1..10000";
      }
      units "milliseconds";
      default "5000";
      description
        "The maximum amount of time to receive an LBR in response to a
         LBM. If a LBR is not received within the timeout value it is
         considered lost.";
    }
  }
  augment "/ncs:devices/ncs:template/ncs:ned-id/ncs:config/mef-cfm:maintenance-domain/mef-cfm:maintenance-association/mef-cfm:maintenance-association-end-point" {
    description
      "Augments maintenance-association-end-point list for l2 Loopback
       configurational data.";
    container l2-loop-config {
      // NCS drop if-feature statement
      presence "Enable l2-loop-config";
      description
        "Specifies the leafs for l2-loopback configuration data that
         has to be applied per MEP service.";
      leaf admin-state {
        // NCS drop if-feature statement
        type ncs_template_cfm-admin-state;
        // NCS drop default statement
        description
          "Enable or disable the loop detection for the MEP.";
      }
      leaf reversion-mode {
        // NCS drop if-feature statement
        type ncs_template_l2-loop-reversion-mode;
        // NCS drop default statement
        description
          "Reversion mode of the restriction placed due to detection of a
           loop.";
      }
      leaf prevention {
        // NCS drop if-feature statement
        type ncs_template_cfm-admin-state;
        // NCS drop default statement
        description
          "Enable or disable the loop prevention for the MEP.";
      }
      leaf pdu-count {
        // NCS drop if-feature statement
        type string;
        // NCS drop default statement
        description
          "Total number of CCM pdus to receive before raising a loop present notification.";
      }
      leaf wtr-timer {
        // NCS drop if-feature statement
        type string;
        units "minutes";
        // NCS drop default statement
        description
          "In reversion-mode as automatic, the wtr-timer is used to prevent frequent operation
           of the unblocking flow-point due to intermittent signal failure. When the loop is
           cleared, the timer must be long enough to allow the network to become stable.
           When WTR timer is expired the service will initiate the unblock request.";
      }
    }
  }
  augment "/ncs:devices/ncs:device/ncs:live-status/mef-cfm:maintenance-domain/mef-cfm:maintenance-association/mef-cfm:maintenance-association-end-point" {
    description
      "Augments maintenance-association-end-point list for l2 Loopback
       configurational data.";
    container l2-loop-config {
      tailf:ncs-device-type "netconf";
      tailf:display-when "not(../../../../../ncs:module) or ../../../../../ncs:module[ncs:name='ciena-cfm'] or (../../../../../ncs:live-status-protocol[not(ncs:capability)]) or (../../../../../ncs:live-status-protocol/ncs:capability/ncs:module[.='ciena-cfm'])";
      // NCS drop if-feature statement
      presence "Enable l2-loop-config";
      description
        "Specifies the leafs for l2-loopback configuration data that
         has to be applied per MEP service.";
      leaf admin-state {
        // NCS drop if-feature statement
        type live_ncs_cfm-admin-state;
        // NCS drop default statement
        description
          "Enable or disable the loop detection for the MEP.";
      }
      leaf reversion-mode {
        // NCS drop if-feature statement
        type live_ncs_l2-loop-reversion-mode;
        // NCS drop default statement
        description
          "Reversion mode of the restriction placed due to detection of a
           loop.";
      }
      leaf prevention {
        // NCS drop if-feature statement
        type live_ncs_cfm-admin-state;
        // NCS drop default statement
        description
          "Enable or disable the loop prevention for the MEP.";
      }
      leaf pdu-count {
        // NCS drop if-feature statement
        type yang:counter32 {
          range "3..30";
        }
        // NCS drop default statement
        description
          "Total number of CCM pdus to receive before raising a loop present notification.";
      }
      leaf wtr-timer {
        // NCS drop if-feature statement
        type uint8 {
          range "1..12";
        }
        units "minutes";
        // NCS drop default statement
        description
          "In reversion-mode as automatic, the wtr-timer is used to prevent frequent operation
           of the unblocking flow-point due to intermittent signal failure. When the loop is
           cleared, the timer must be long enough to allow the network to become stable.
           When WTR timer is expired the service will initiate the unblock request.";
      }
    }
  }
  augment "/ncs:devices/ncs:device/ncs:config/mef-cfm:maintenance-domain/mef-cfm:maintenance-association/mef-cfm:maintenance-association-end-point" {
    description
      "Augments maintenance-association-end-point list for l2 Loopback
       configurational data.";
    container l2-loop-config {
      tailf:ncs-device-type "netconf";
      tailf:display-when "not(../../../../../ncs:module) or ../../../../../ncs:module[ncs:name='ciena-cfm']";
      tailf:display-when "not(../../../../../ncs:module) or boolean(/ncs:devices/ncs:device[ncs:name=current()/../../../../../ncs:name]/capability/feature='l2-loop')";
      presence "Enable l2-loop-config";
      description
        "Specifies the leafs for l2-loopback configuration data that
         has to be applied per MEP service.";
      leaf admin-state {
        tailf:display-when "not(../../../../../../ncs:module) or boolean(/ncs:devices/ncs:device[ncs:name=current()/../../../../../../ncs:name]/capability/feature='l2-loop')";
        type cfm-admin-state;
        default "disable";
        description
          "Enable or disable the loop detection for the MEP.";
      }
      leaf reversion-mode {
        tailf:display-when "not(../../../../../../ncs:module) or boolean(/ncs:devices/ncs:device[ncs:name=current()/../../../../../../ncs:name]/capability/feature='l2-loop')";
        type l2-loop-reversion-mode;
        default "automatic";
        description
          "Reversion mode of the restriction placed due to detection of a
           loop.";
      }
      leaf prevention {
        tailf:display-when "not(../../../../../../ncs:module) or boolean(/ncs:devices/ncs:device[ncs:name=current()/../../../../../../ncs:name]/capability/feature='l2-loop')";
        type cfm-admin-state;
        default "disable";
        description
          "Enable or disable the loop prevention for the MEP.";
      }
      leaf pdu-count {
        tailf:display-when "not(../../../../../../ncs:module) or boolean(/ncs:devices/ncs:device[ncs:name=current()/../../../../../../ncs:name]/capability/feature='l2-loop')";
        type yang:counter32 {
          range "3..30";
        }
        default "3";
        description
          "Total number of CCM pdus to receive before raising a loop present notification.";
      }
      leaf wtr-timer {
        tailf:display-when "not(../../../../../../ncs:module) or boolean(/ncs:devices/ncs:device[ncs:name=current()/../../../../../../ncs:name]/capability/feature='l2-loop')";
        type uint8 {
          range "1..12";
        }
        units "minutes";
        default "1";
        description
          "In reversion-mode as automatic, the wtr-timer is used to prevent frequent operation
           of the unblocking flow-point due to intermittent signal failure. When the loop is
           cleared, the timer must be long enough to allow the network to become stable.
           When WTR timer is expired the service will initiate the unblock request.";
      }
    }
  }
  augment "/ncs:devices/ncs:template/ncs:ned-id/ncs:config/mef-cfm:maintenance-domain/mef-cfm:maintenance-association/mef-cfm:maintenance-association-end-point" {
    description
      "Augments maintenance-association-end-point-list for l2 Loopback
       operational data.";
    // NCS drop config false container 'l2-loop-oper-data'
  }
  augment "/ncs:devices/ncs:device/ncs:live-status/mef-cfm:maintenance-domain/mef-cfm:maintenance-association/mef-cfm:maintenance-association-end-point" {
    description
      "Augments maintenance-association-end-point-list for l2 Loopback
       operational data.";
    container l2-loop-oper-data {
      tailf:ncs-device-type "netconf";
      tailf:display-when "not(../../../../../ncs:module) or ../../../../../ncs:module[ncs:name='ciena-cfm'] or (../../../../../ncs:live-status-protocol[not(ncs:capability)]) or (../../../../../ncs:live-status-protocol/ncs:capability/ncs:module[.='ciena-cfm'])";
      // NCS drop if-feature statement
      description
        "Specifies the leafs for l2-loopback operational data per MEP service.";
      leaf loop-present {
        // NCS drop if-feature statement
        type boolean;
        // NCS drop default statement
        description
          "An boolean flag indicating the current state of the l2-loop in the service.";
      }
      leaf loop-blocked {
        // NCS drop if-feature statement
        type boolean;
        // NCS drop default statement
        description
          "An boolean flag indicating if the flow point on which the MEP resides,is blocked.";
      }
      leaf rx-drop-loop-count {
        // NCS drop if-feature statement
        type yang:counter32;
        description
          "Total number of loopback CCM pdus rxed.";
      }
      leaf wtr-timer-running {
        // NCS drop if-feature statement
        type boolean;
        // NCS drop default statement
        description
          "Boolean flag indicating if WTR timer is running for l2 loop flow point unblock.";
      }
    }
  }
  augment "/ncs:devices/ncs:device/ncs:config/mef-cfm:maintenance-domain/mef-cfm:maintenance-association/mef-cfm:maintenance-association-end-point" {
    description
      "Augments maintenance-association-end-point-list for l2 Loopback
       operational data.";
    // NCS drop config false container 'l2-loop-oper-data'
  }

  feature l2-loop {
    description
      "Support for L2-loop detection and prevention.";
  }

  identity any {
    base cfm-event-type;
    description
      "Used to represent any CFM event in telemetry framework";
  }

  identity l2-loop {
    base cfm-event-type;
    description
      "CFM l2-loop-detection event";
  }

  identity cfm-event-type {
    description
      "Represents CFM fault events";
  }
}
