module ciena-arp {
  // Generated by yanger -t ncs
  tailf:mount-id "ciena107s3-nc-1.0:ciena107s3-nc-1.0";
  tailf:ncs-device-type "netconf";

  namespace "http://ciena.com/ns/yang/ciena-arp";
  prefix arp;

  import ietf-inet-types {
    prefix inet;
  }
  import openconfig-interfaces {
    prefix oc-if;
  }
  import tailf-common {
    prefix tailf;
  }
  import tailf-ncs {
    prefix ncs;
  }

  organization
    "Ciena Corporation";
  contact
    "Web URL: http://www.ciena.com/
     E-mail:  yang@ciena.com
     Postal:  7035 Ridge Road
     Hanover, Maryland 21076
     U.S.A.
     Phone:   +1 800-921-1144
     Fax:     +1 410-694-5750";
  description
    "This YANG module defines Ciena's cli to manage arp

     Copyright (c) 2018  Ciena Corporation.  All rights
     reserved.

     All information contained herein is, and remains the
     property of Ciena Corporation. Dissemination of this
     information or reproduction of this material is strictly
     forbidden unless prior written permission is obtained
     from Ciena Corporation.";

  revision 2018-07-12 {
    description
      "Initial version of ciena-arp config, state and rpc yang model";
  }

  augment "/ncs:devices/ncs:device/ncs:rpc" {
    container rpc-arp-delete {
      tailf:ncs-device-type "netconf";
      tailf:display-when "not(../../ncs:module) or ../../ncs:module[ncs:name='ciena-arp']";
      tailf:action arp-delete {
        tailf:actionpoint ncsproxy {
          tailf:internal;
        }
        input {
          leaf ip-address {
            type inet:ipv4-address;
            description
              "delete arp entries for this ip address.";
          }
        }
        output {
          leaf response {
            type string;
            description
              "The response could be 'success', or the reason for arp-delete failure";
          }
        }
      }
    }
  }
  augment "/ncs:devices/ncs:device-group/ncs:ned-id/ncs:rpc" {
    container rpc-arp-delete {
      tailf:ncs-device-type "netconf";
      tailf:display-when "/ncs:devices/ncs:device[ncs:name=current()/../../../ncs:member]/ncs:module[ncs:name='ciena-arp']";
      tailf:action arp-delete {
        tailf:actionpoint ncsproxy {
          tailf:internal;
        }
        input {
          leaf ip-address {
            type inet:ipv4-address;
            description
              "delete arp entries for this ip address.";
          }
        }
        output {
          container "device" {
            leaf "name" {
              type string;
            }
            leaf "info" {
              type string;
            }
            container "result" {
              leaf response {
                type string;
                description
                  "The response could be 'success', or the reason for arp-delete failure";
              }
            }
          }
        }
      }
    }
  }
  augment "/ncs:devices/ncs:device/ncs:rpc" {
    container rpc-arp-flush {
      tailf:ncs-device-type "netconf";
      tailf:display-when "not(../../ncs:module) or ../../ncs:module[ncs:name='ciena-arp']";
      tailf:action arp-flush {
        tailf:actionpoint ncsproxy {
          tailf:internal;
        }
        input {
          leaf interface {
            type string;
            description
              "flush arp entries for this interface.";
          }
        }
        output {
          leaf response {
            type string;
            description
              "The response could be 'success', or the reason for arp-flush failure";
          }
        }
      }
    }
  }
  augment "/ncs:devices/ncs:device-group/ncs:ned-id/ncs:rpc" {
    container rpc-arp-flush {
      tailf:ncs-device-type "netconf";
      tailf:display-when "/ncs:devices/ncs:device[ncs:name=current()/../../../ncs:member]/ncs:module[ncs:name='ciena-arp']";
      tailf:action arp-flush {
        tailf:actionpoint ncsproxy {
          tailf:internal;
        }
        input {
          leaf interface {
            type string;
            description
              "flush arp entries for this interface.";
          }
        }
        output {
          container "device" {
            leaf "name" {
              type string;
            }
            leaf "info" {
              type string;
            }
            container "result" {
              leaf response {
                type string;
                description
                  "The response could be 'success', or the reason for arp-flush failure";
              }
            }
          }
        }
      }
    }
  }
}
