module ciena-vrf {
  // Generated by yanger -t ncs
  tailf:mount-id "ciena107s3-nc-1.0:ciena107s3-nc-1.0";
  tailf:ncs-device-type "netconf";

  namespace "urn:ciena:params:xml:ns:yang:ciena:ciena-vrf";
  prefix vrf;

  import tailf-common {
    prefix tailf;
  }
  import tailf-ncs {
    prefix ncs;
  }

  organization
    "Ciena Corporation";
  contact
    "Web URL: http://www.ciena.com/
     E-mail:  yang@ciena.com
     Postal:  7035 Ridge Road
              Hanover, Maryland 21076
                  U.S.A.
     Phone:   +1 800-921-1144
     Fax:     +1 410-694-5750";
  description
    "This YANG module defines Ciena's VPN Routing/Forwarding model.

     Copyright (c) 2018  Ciena Corporation.  All rights
     reserved.

     All information contained herein is, and remains the
     property of Ciena Corporation. Dissemination of this
     information or reproduction of this material is strictly
     forbidden unless prior written permission is obtained
     from Ciena Corporation.";

  revision 2020-12-22 {
    description
      "Added color and fallback for SR policy.";
  }
  revision 2016-10-29 {
    description
      "Modifications to auto-generate clis.";
  }

  grouping ncs_template_vrf-grouping {
    list vrf {
      // NCS patched for predictable order
      ordered-by user;
      key "vrfName";
      // NCS drop max-elements statement
      description
        "Virtual Routing Forwarding (VRF) Instance";
      leaf vrfName {
        type string;
        description
          "Routing Forwarding Instance Name";
      }
      leaf description {
        type string;
        description
          "Description of VRF";
      }
      container sr-policy {
        description
          "Segment Routing (SR) Policy";
        leaf color {
          type string;
          description
            "Color associated with the SR policy";
        }
        leaf fallback {
          type string;
          // NCS drop default statement
          description
            "Fallback enable is used when the SR policy is down.
             The service will still continue to be UP, but
             will fall back to labeled IGP shortest path.";
        }
      }
    }
  }

  grouping ncs_rpc_notif_vrf-grouping {
    list vrf {
      key "vrfName";
      max-elements 129;
      description
        "Virtual Routing Forwarding (VRF) Instance";
      leaf vrfName {
        type string {
          length "1..15";
        }
        description
          "Routing Forwarding Instance Name";
      }
      leaf description {
        type string {
          length "0..255";
        }
        description
          "Description of VRF";
      }
      container sr-policy {
        description
          "Segment Routing (SR) Policy";
        leaf color {
          type uint32;
          description
            "Color associated with the SR policy";
        }
        leaf fallback {
          type enumeration {
            enum "enable" {
              description
                "Specifies fallback as enable";
            }
            enum "disable" {
              description
                "Specifies fallback as disable";
            }
          }
          default "enable";
          description
            "Fallback enable is used when the SR policy is down.
             The service will still continue to be UP, but
             will fall back to labeled IGP shortest path.";
        }
      }
    }
  }

  grouping live_ncs_vrf-grouping {
    list vrf {
      key "vrfName";
      // NCS drop max-elements statement
      description
        "Virtual Routing Forwarding (VRF) Instance";
      leaf vrfName {
        type string {
          length "1..15";
        }
        description
          "Routing Forwarding Instance Name";
      }
      leaf description {
        type string {
          length "0..255";
        }
        description
          "Description of VRF";
      }
      container sr-policy {
        description
          "Segment Routing (SR) Policy";
        leaf color {
          type uint32;
          description
            "Color associated with the SR policy";
        }
        leaf fallback {
          type enumeration {
            enum "enable" {
              description
                "Specifies fallback as enable";
            }
            enum "disable" {
              description
                "Specifies fallback as disable";
            }
          }
          // NCS drop default statement
          description
            "Fallback enable is used when the SR policy is down.
             The service will still continue to be UP, but
             will fall back to labeled IGP shortest path.";
        }
      }
    }
  }

  grouping vrf-grouping {
    list vrf {
      key "vrfName";
      max-elements 129;
      description
        "Virtual Routing Forwarding (VRF) Instance";
      leaf vrfName {
        type string {
          length "1..15";
        }
        description
          "Routing Forwarding Instance Name";
      }
      leaf description {
        type string {
          length "0..255";
        }
        description
          "Description of VRF";
      }
      container sr-policy {
        description
          "Segment Routing (SR) Policy";
        leaf color {
          type uint32;
          description
            "Color associated with the SR policy";
        }
        leaf fallback {
          type enumeration {
            enum "enable" {
              description
                "Specifies fallback as enable";
            }
            enum "disable" {
              description
                "Specifies fallback as disable";
            }
          }
          default "enable";
          description
            "Fallback enable is used when the SR policy is down.
             The service will still continue to be UP, but
             will fall back to labeled IGP shortest path.";
        }
      }
    }
  }

  augment "/ncs:devices/ncs:device/ncs:config" {
    uses vrf-grouping {
      refine vrf {
        tailf:ncs-device-type "netconf";
        tailf:display-when "not(../ncs:module) or ../ncs:module[ncs:name='ciena-vrf']";
      }
    }
  }
  augment "/ncs:devices/ncs:device/ncs:live-status" {
    uses live_ncs_vrf-grouping {
      refine vrf {
        tailf:ncs-device-type "netconf";
        tailf:display-when "not(../ncs:module) or ../ncs:module[ncs:name='ciena-vrf'] or (../ncs:live-status-protocol[not(ncs:capability)]) or (../ncs:live-status-protocol/ncs:capability/ncs:module[.='ciena-vrf'])";
      }
    }
  }
  augment "/ncs:devices/ncs:template/ncs:ned-id/ncs:config" {
    uses ncs_template_vrf-grouping;
  }
}
