module ciena-openconfig-interfaces-deviation {
  // Generated by yanger -t ncs
  tailf:mount-id "ciena107s3-nc-1.0:ciena107s3-nc-1.0";
  tailf:ncs-device-type "netconf";

  namespace "http://ciena.com/ns/yang/ciena-openconfig-interfaces-deviation";
  prefix cn-oc-if-deviation;

  import openconfig-interfaces {
    prefix oc-if;
  }
  import tailf-common {
    prefix tailf;
  }
  import tailf-ncs {
    prefix ncs;
  }

  organization
    "Ciena Corporation";
  contact
    "Web URL: http://www.ciena.com/
     E-mail:  yang@ciena.com
     Postal:  7035 Ridge Road
              Hanover, Maryland 21076

              U.S.A.
     Phone:   +1 800-921-1144
     Fax:     +1 410-694-5750";
  description
    "This module contains the Ciena proprietary YANG deviations
     of the standard openconfig-interfaces YANG module.

     Copyright (c) 2016 Ciena Corporation.  All rights reserved.

     All information contained herein is, and remains
     the property of Ciena Corporation. Dissemination of this
     information or reproduction of this material is strictly
     forbidden unless prior written permission is obtained from
     Ciena Corporation.";

  revision 2018-02-28 {
    description
      "Initial version";
    reference "";
  }

  deviation "/ncs:devices/ncs:template/ncs:ned-id/ncs:config/oc-if:interfaces/oc-if:interface/oc-if:hold-time" {
    deviate not-supported;
  }
  deviation "/ncs:devices/ncs:device/ncs:live-status/oc-if:interfaces/oc-if:interface/oc-if:hold-time" {
    deviate not-supported;
  }
  deviation "/ncs:devices/ncs:device/ncs:config/oc-if:interfaces/oc-if:interface/oc-if:hold-time" {
    deviate not-supported;
  }
  deviation "/ncs:devices/ncs:template/ncs:ned-id/ncs:config/oc-if:interfaces/oc-if:interface/oc-if:subinterfaces" {
    deviate not-supported;
  }
  deviation "/ncs:devices/ncs:device/ncs:live-status/oc-if:interfaces/oc-if:interface/oc-if:subinterfaces" {
    deviate not-supported;
  }
  deviation "/ncs:devices/ncs:device/ncs:config/oc-if:interfaces/oc-if:interface/oc-if:subinterfaces" {
    deviate not-supported;
  }
  deviation "/ncs:devices/ncs:template/ncs:ned-id/ncs:config/oc-if:interfaces/oc-if:interface/oc-if:config/oc-if:type" {
    deviate not-supported;
  }
  deviation "/ncs:devices/ncs:device/ncs:live-status/oc-if:interfaces/oc-if:interface/oc-if:config/oc-if:type" {
    deviate not-supported;
  }
  deviation "/ncs:devices/ncs:device/ncs:config/oc-if:interfaces/oc-if:interface/oc-if:config/oc-if:type" {
    deviate not-supported;
  }
  deviation "/ncs:devices/ncs:template/ncs:ned-id/ncs:config/oc-if:interfaces/oc-if:interface/oc-if:config/oc-if:enabled" {
    deviate not-supported;
  }
  deviation "/ncs:devices/ncs:device/ncs:live-status/oc-if:interfaces/oc-if:interface/oc-if:config/oc-if:enabled" {
    deviate not-supported;
  }
  deviation "/ncs:devices/ncs:device/ncs:config/oc-if:interfaces/oc-if:interface/oc-if:config/oc-if:enabled" {
    deviate not-supported;
  }
  deviation "/ncs:devices/ncs:device/ncs:live-status/oc-if:interfaces/oc-if:interface/oc-if:state/oc-if:admin-status" {
    deviate not-supported;
  }
  deviation "/ncs:devices/ncs:device/ncs:live-status/oc-if:interfaces/oc-if:interface/oc-if:state/oc-if:type" {
    deviate not-supported;
  }
  deviation "/ncs:devices/ncs:device/ncs:live-status/oc-if:interfaces/oc-if:interface/oc-if:state/oc-if:enabled" {
    deviate not-supported;
  }
}
