module ciena-mef-qos-flow-deviation {
  // Generated by yanger -t ncs
  tailf:mount-id "ciena107s3-nc-1.0:ciena107s3-nc-1.0";
  tailf:ncs-device-type "netconf";

  namespace "urn:ciena:params:xml:ns:yang:ciena-pn::ciena-mef-qos-flow-deviation";
  prefix cn-qos-flow-deviation;

  import ciena-mef-qos-flow {
    prefix qf;
  }
  import tailf-common {
    prefix tailf;
  }
  import tailf-ncs {
    prefix ncs;
  }

  organization
    "Ciena Corporation";
  contact
    "Web URL: http://www.ciena.com/
     E-mail:  yang@ciena.com
     Postal:  7035 Ridge Road
                Hanover, Maryland 21076
                U.S.A.
     Phone:   +1 800-921-1144
     Fax:     +1 410-694-5750";
  description
    "This module contains the Ciena proprietary YANG deviations
     of the standard qos-flow YANG module.
     Copyright (c) 2021 Ciena Corporation.  All rights reserved.

     All information contained herein is, and remains
     the property of Ciena Corporation. Dissemination of this
     information or reproduction of this material is strictly
     forbidden unless prior written permission is obtained from
     Ciena Corporation.";

  revision 2021-01-12 {
    description
      "Initial version";
  }

  deviation "/ncs:devices/ncs:template/ncs:ned-id/ncs:config/qf:qos-flows/qf:qos-flow/qf:parent-interface/qf:logical-port/qf:parent-port" {
    deviate not-supported;
  }
  deviation "/ncs:devices/ncs:device/ncs:live-status/qf:qos-flows/qf:qos-flow/qf:parent-interface/qf:logical-port/qf:parent-port" {
    deviate not-supported;
  }
  deviation "/ncs:devices/ncs:device/ncs:config/qf:qos-flows/qf:qos-flow/qf:parent-interface/qf:logical-port/qf:parent-port" {
    deviate not-supported;
  }
}
