module ciena-management-plane {
  // Generated by yanger -t ncs
  tailf:mount-id "ciena107s3-nc-1.0:ciena107s3-nc-1.0";
  tailf:ncs-device-type "netconf";

  namespace "http://www.ciena.com/ns/yang/ciena-management-plane";
  prefix mgmt;

  import openconfig-interfaces {
    prefix oc-if;
  }
  import ciena-openconfig-interfaces {
    prefix cn-if;
  }
  import tailf-common {
    prefix tailf;
  }
  import tailf-ncs {
    prefix ncs;
  }

  organization
    "Ciena Corporation";
  contact
    "Web URL: http://www.ciena.com/
     E-mail:  yang@ciena.com
     Postal:  7035 Ridge Road
     Hanover, Maryland 21076
     U.S.A.
     Phone:   +1 800-921-1144
     Fax:     +1 410-694-5750";
  description
    "This YANG module is used to configure management plane
     behaviors, such as client source-ip overrides, application
     enable/disable, etc.

     Copyright (c) 2020  Ciena Corporation.  All rights
     reserved.

     All information contained herein is, and remains the
     property of Ciena Corporation. Dissemination of this
     information or reproduction of this material is strictly
     forbidden unless prior written permission is obtained
     from Ciena Corporation.";

  revision 2021-06-20 {
    description
      "Making enable as false by default for all the server-applications";
  }
  revision 2020-04-03 {
    description
      "Initial revision";
  }

  typedef ncs_template_server-application-type {
    description
      "Name of the server application to be configured.";
    type string;
  }

  typedef ncs_rpc_notif_server-application-type {
    description
      "Name of the server application to be configured.";
    type enumeration {
      enum "web-gui" {
        description
          "Web GUI server";
      }
    }
  }

  typedef live_ncs_server-application-type {
    description
      "Name of the server application to be configured.";
    type enumeration {
      enum "web-gui" {
        description
          "Web GUI server";
      }
    }
  }

  typedef server-application-type {
    description
      "Name of the server application to be configured.";
    type enumeration {
      enum "web-gui" {
        description
          "Web GUI server";
      }
    }
  }

  grouping ncs_template_source-ip-config {
    leaf interface {
      description
        "When clients are reaching out towards a server, the first appropriate address from this interface will be used.
         Clients using the v4 stack will use the first v4 address on this interface as their source address.
         Clients using the v6 stack will use the first v6 address on this inteface as their source address.";
      type string;
      // NCS drop must statement
    }
  }

  grouping ncs_rpc_notif_source-ip-config {
    leaf interface {
      description
        "When clients are reaching out towards a server, the first appropriate address from this interface will be used.
         Clients using the v4 stack will use the first v4 address on this interface as their source address.
         Clients using the v6 stack will use the first v6 address on this inteface as their source address.";
      type string;
      must "/oc-if:interfaces/oc-if:interface[oc-if:name=current()]/oc-if:config/cn-if:role = 'cn-if:management'" {
        tailf:xpath-root 3;
        error-message
          "The management-plane default-source-ip configuration must reference an existing management interface.
           This interface cannot be removed while it is referenced by management-plane default-source-ip.";
      }
    }
  }

  grouping live_ncs_source-ip-config {
    leaf interface {
      description
        "When clients are reaching out towards a server, the first appropriate address from this interface will be used.
         Clients using the v4 stack will use the first v4 address on this interface as their source address.
         Clients using the v6 stack will use the first v6 address on this inteface as their source address.";
      type leafref {
        path "/ncs:devices/ncs:device/ncs:live-status/oc-if:interfaces/oc-if:interface/oc-if:name" {
          tailf:xpath-root 3;
        }
      }
      // NCS drop must statement
    }
  }

  grouping source-ip-config {
    leaf interface {
      description
        "When clients are reaching out towards a server, the first appropriate address from this interface will be used.
         Clients using the v4 stack will use the first v4 address on this interface as their source address.
         Clients using the v6 stack will use the first v6 address on this inteface as their source address.";
      type leafref {
        path "/ncs:devices/ncs:device/ncs:config/oc-if:interfaces/oc-if:interface/oc-if:name" {
          tailf:xpath-root 3;
        }
      }
      must "/oc-if:interfaces/oc-if:interface[oc-if:name=current()]/oc-if:config/cn-if:role = 'cn-if:management'" {
        tailf:xpath-root 3;
        error-message
          "The management-plane default-source-ip configuration must reference an existing management interface.
           This interface cannot be removed while it is referenced by management-plane default-source-ip.";
      }
    }
  }

  augment "/ncs:devices/ncs:device/ncs:config" {
    container management-plane {
      tailf:ncs-device-type "netconf";
      tailf:display-when "not(../../ncs:module) or ../../ncs:module[ncs:name='ciena-management-plane']";
      description
        "Configuration parameters for management plane behaviors.";
      container default-source-ip {
        description
          "Used to configure the default source-ip address and/or
           interface that will be used for outgoing connections from
           the device.";
        uses source-ip-config;
      }
      container server-applications {
        description
          "Management plane configuration for server applications.
           Configuration is managed separately per application.";
        list application {
          description
            "List of applications and their management plane configuration.";
          key "application";
          leaf application {
            description
              "An application on which supports management plane configuration";
            type server-application-type;
          }
          leaf enable {
            description
              "Enable/disable application.  Not all applications support enable/disable.";
            type boolean;
            default "false";
          }
        }
      }
    }
  }
  augment "/ncs:devices/ncs:device/ncs:live-status" {
    container management-plane {
      tailf:ncs-device-type "netconf";
      tailf:display-when "not(../../ncs:module) or ../../ncs:module[ncs:name='ciena-management-plane'] or (../../ncs:live-status-protocol[not(ncs:capability)]) or (../../ncs:live-status-protocol/ncs:capability/ncs:module[.='ciena-management-plane'])";
      description
        "Configuration parameters for management plane behaviors.";
      container default-source-ip {
        description
          "Used to configure the default source-ip address and/or
           interface that will be used for outgoing connections from
           the device.";
        uses live_ncs_source-ip-config;
      }
      container server-applications {
        description
          "Management plane configuration for server applications.
           Configuration is managed separately per application.";
        list application {
          description
            "List of applications and their management plane configuration.";
          key "application";
          leaf application {
            description
              "An application on which supports management plane configuration";
            type live_ncs_server-application-type;
          }
          leaf enable {
            description
              "Enable/disable application.  Not all applications support enable/disable.";
            type boolean;
            // NCS drop default statement
          }
        }
      }
    }
  }
  augment "/ncs:devices/ncs:template/ncs:ned-id/ncs:config" {
    container management-plane {
      description
        "Configuration parameters for management plane behaviors.";
      container default-source-ip {
        description
          "Used to configure the default source-ip address and/or
           interface that will be used for outgoing connections from
           the device.";
        uses ncs_template_source-ip-config;
      }
      container server-applications {
        description
          "Management plane configuration for server applications.
           Configuration is managed separately per application.";
        list application {
          // NCS patched for predictable order
          ordered-by user;
          description
            "List of applications and their management plane configuration.";
          key "application";
          leaf application {
            description
              "An application on which supports management plane configuration";
            type ncs_template_server-application-type;
          }
          leaf enable {
            description
              "Enable/disable application.  Not all applications support enable/disable.";
            type string;
            // NCS drop default statement
          }
        }
      }
    }
  }
}
