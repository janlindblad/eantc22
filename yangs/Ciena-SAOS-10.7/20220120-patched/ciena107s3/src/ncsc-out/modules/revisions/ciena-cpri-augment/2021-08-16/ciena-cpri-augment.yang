module ciena-cpri-augment {
  // Generated by yanger -t ncs
  tailf:mount-id "ciena107s3-nc-1.0:ciena107s3-nc-1.0";
  tailf:ncs-device-type "netconf";

  namespace "http://www.ciena.com/ns/yang/ciena-cpri";
  prefix ciena-cpri;

  import ietf-interfaces {
    prefix if;
  }
  import ciena-packet-ptp {
    prefix cn-pkt-ptp;
  }
  import ciena-types {
    prefix ciena;
  }
  import ciena-packet-typedefs {
    prefix cntypes;
  }
  import ciena-ieee1914-dot3-roe-augment {
    prefix ciena-ieee1914-dot3-roe-augment;
  }
  import tailf-common {
    prefix tailf;
  }
  import tailf-ncs {
    prefix ncs;
  }

  organization
    "Ciena Corporation";
  contact
    "Web URL: http://www.ciena.com/
     E-mail:  yang@ciena.com
     Postal:  7035 Ridge Road
              Hanover, Maryland 21076
              U.S.A.
     Phone:   +1 800-921-1144
     Fax:     +1 410-694-5750";
  description
    "This YANG module defines Ciena's CPRI augments to the
     ietf-interfaces model.

     Copyright (c) 2020 Ciena Corporation.  All rights
     reserved.

     All information contained herein is, and remains
     the property of Ciena Corporation. Dissemination of this
     information or reproduction of this material is strictly
     forbidden unless prior written permission is obtained from
     Ciena Corporation.";

  revision 2021-08-16 {
    description
      "Updated to specify that container cpri-port is a presence container.";
  }
  revision 2021-07-13 {
    description
      "Added leaf roe-dcr-sync-reference (boolean).
       Updated cpri-id to become non-configurable.";
  }
  revision 2020-10-01 {
    description
      "Initial version";
    reference
      "RFC 6020: YANG - A Data Modeling Language for
       the Network Configuration Protocol (NETCONF).
       No specific reference; standard not available.";
  }

  grouping ncs_template_timestamp {
    description
      "A timestamp comprised of integer and fractional nanosecond portions.";
    reference "5.5.5.3 of IEEE Std 1914.3-2018";
    leaf integer-nanosecond {
      type string;
      units "nanoseconds";
      // NCS drop default statement
      description
        "The integer nanosecond portion of the timestamp.";
      reference "5.5.5.3 of IEEE Std 1914.3-2018";
    }
    leaf fractional-nanosecond {
      type string;
      // NCS drop default statement
      description
        "The fractional nanosecond portion of the timestamp.
         It counts in fractions of a nanosecond (0.03125 ns) where 0
         represents 0 ns and 31 represents 0.96875 ns.";
      reference "5.5.5.3 of IEEE Std 1914.3-2018";
    }
  }

  grouping ncs_rpc_notif_timestamp {
    description
      "A timestamp comprised of integer and fractional nanosecond portions.";
    reference "5.5.5.3 of IEEE Std 1914.3-2018";
    leaf integer-nanosecond {
      type uint32 {
        range "0..16777215";
      }
      units "nanoseconds";
      default "0";
      description
        "The integer nanosecond portion of the timestamp.";
      reference "5.5.5.3 of IEEE Std 1914.3-2018";
    }
    leaf fractional-nanosecond {
      type uint8 {
        range "0..31";
      }
      default "0";
      description
        "The fractional nanosecond portion of the timestamp.
         It counts in fractions of a nanosecond (0.03125 ns) where 0
         represents 0 ns and 31 represents 0.96875 ns.";
      reference "5.5.5.3 of IEEE Std 1914.3-2018";
    }
  }

  grouping live_ncs_timestamp {
    description
      "A timestamp comprised of integer and fractional nanosecond portions.";
    reference "5.5.5.3 of IEEE Std 1914.3-2018";
    leaf integer-nanosecond {
      type uint32 {
        range "0..16777215";
      }
      units "nanoseconds";
      // NCS drop default statement
      description
        "The integer nanosecond portion of the timestamp.";
      reference "5.5.5.3 of IEEE Std 1914.3-2018";
    }
    leaf fractional-nanosecond {
      type uint8 {
        range "0..31";
      }
      // NCS drop default statement
      description
        "The fractional nanosecond portion of the timestamp.
         It counts in fractions of a nanosecond (0.03125 ns) where 0
         represents 0 ns and 31 represents 0.96875 ns.";
      reference "5.5.5.3 of IEEE Std 1914.3-2018";
    }
  }

  grouping timestamp {
    description
      "A timestamp comprised of integer and fractional nanosecond portions.";
    reference "5.5.5.3 of IEEE Std 1914.3-2018";
    leaf integer-nanosecond {
      type uint32 {
        range "0..16777215";
      }
      units "nanoseconds";
      default "0";
      description
        "The integer nanosecond portion of the timestamp.";
      reference "5.5.5.3 of IEEE Std 1914.3-2018";
    }
    leaf fractional-nanosecond {
      type uint8 {
        range "0..31";
      }
      default "0";
      description
        "The fractional nanosecond portion of the timestamp.
         It counts in fractions of a nanosecond (0.03125 ns) where 0
         represents 0 ns and 31 represents 0.96875 ns.";
      reference "5.5.5.3 of IEEE Std 1914.3-2018";
    }
  }

  augment "/ncs:devices/ncs:template/ncs:ned-id/ncs:config/if:interfaces/if:interface" {
    // NCS drop when statement
    description
      "Augmenting ietf-interfaces to cpri port for ciena specific configuration.";
    container cpri-port {
      description
        "CPRI port parameters.";
      reference "Table 8 of IEEE Std 1914.3";
      presence "CPRI Port configuration";
      // NCS drop config false leaf 'cpri-id'
      leaf admin-state {
        type ciena:ncs_template_admin-state;
        // NCS drop default statement
        description
          "Cpri port admin state.";
      }
      // NCS drop config false leaf 'oper-state'
      leaf cpri-option {
        type string;
        // NCS drop default statement
        description
          "The speed option of the CPRI port.";
      }
      // NCS drop config false leaf 'cpri-speed'
      leaf forward-error-correction {
        type cntypes:ncs_template_ettp-fec-enum;
        // NCS drop default statement
        description
          "Forward error correction";
      }
      // NCS drop config false leaf 'cpri-ver'
      // NCS drop config false leaf 'cpri-hdlc'
      // NCS drop config false leaf 'cpri-l1'
      // NCS drop config false leaf 'cpri-eth'
      leaf ptp-id {
        type string;
        description
          "Unique, access identifier string of the PTP (e.g., '1/1').";
      }
      leaf associated-interface {
        type string;
        description
          "This is associated interface to the cpri interface.";
      }
      // NCS drop config false leaf 'roe-dcr-sync-status'
      // NCS drop config false container 'cpri-cable-delay'
      // NCS drop config false leaf 'roe-dcr-sync-reference'
    }
  }
  augment "/ncs:devices/ncs:device/ncs:live-status/if:interfaces/if:interface" {
    // NCS drop when statement
    description
      "Augmenting ietf-interfaces to cpri port for ciena specific configuration.";
    container cpri-port {
      tailf:ncs-device-type "netconf";
      tailf:display-when "not(../../../../ncs:module) or ../../../../ncs:module[ncs:name='ciena-cpri-augment'] or (../../../../ncs:live-status-protocol[not(ncs:capability)]) or (../../../../ncs:live-status-protocol/ncs:capability/ncs:module[.='ciena-cpri-augment'])";
      description
        "CPRI port parameters.";
      reference "Table 8 of IEEE Std 1914.3";
      presence "CPRI Port configuration";
      leaf cpri-id {
        type uint16;
        description
          "Each CPRI port in a node has a unique identifier.";
        reference "enParam 0 in Table 8 of IEEE Std 1914.3";
      }
      leaf admin-state {
        type ciena:live_ncs_admin-state;
        // NCS drop default statement
        description
          "Cpri port admin state.";
      }
      leaf oper-state {
        type ciena:live_ncs_oper-state;
        description
          "Cpri port operational state.";
      }
      leaf cpri-option {
        type enumeration {
          enum "CPRI_3" {
            description
              "For CPRI port speed of 2.457 Gbps.";
          }
          enum "CPRI_5" {
            description
              "For CPRI port speed of 4.912 Gbps.";
          }
          enum "CPRI_7" {
            description
              "For CPRI port speed of 9.83 Gbps.";
          }
          enum "CPRI_8" {
            description
              "For CPRI port speed of 10.137 Gbps.";
          }
          enum "CPRI_10" {
            description
              "For CPRI port speed of 24.33024 Gbps.";
          }
        }
        // NCS drop default statement
        description
          "The speed option of the CPRI port.";
      }
      leaf cpri-speed {
        type decimal64 {
          fraction-digits 5;
          range "0.00000..25.00000";
        }
        units "Gbps";
        description
          "CPRI port speed in Gbps";
      }
      leaf forward-error-correction {
        type cntypes:live_ncs_ettp-fec-enum;
        // NCS drop default statement
        description
          "Forward error correction";
      }
      leaf cpri-ver {
        type uint8;
        description
          "CPRI protocol version at location Z.2.0, i.e., control word 2 as
           extracted by the control process.";
        reference "enParam 2 in Table 8 and 8.3.6(.c) of IEEE Std 1914.3";
      }
      leaf cpri-hdlc {
        type uint8 {
          range "0..7";
        }
        description
          "HDLC bit rate at location Z.66.0, i.e., control word 66 as
           extracted by the control process.";
        reference "enParam 3 in Table 8 and 8.3.6(.d) of IEEE Std 1914.3";
      }
      leaf cpri-l1 {
        type uint8 {
          range "0..31";
        }
        description
          "L1 signaling at location Z.130.0, i.e., control word 130 as
           extracted by the control process.";
        reference "enParam 4 in Table 8 and 8.3.6(.e) of IEEE Std 1914.3";
      }
      leaf cpri-eth {
        type uint8 {
          range "0|20..63";
        }
        description
          "Ethernet pointer at location Z.194.0, i.e., control word 194 as
           extracted by the control process.";
        reference "enParam 5 in Table 8 and 8.3.6(.f) of IEEE Std 1914.3";
      }
      leaf ptp-id {
        type leafref {
          path "/ncs:devices/ncs:device/ncs:live-status/cn-pkt-ptp:ptps/cn-pkt-ptp:ptp/cn-pkt-ptp:ptp-id" {
            tailf:xpath-root 3;
          }
        }
        description
          "Unique, access identifier string of the PTP (e.g., '1/1').";
      }
      leaf associated-interface {
        type leafref {
          path "/ncs:devices/ncs:device/ncs:live-status/if:interfaces/if:interface/if:name" {
            tailf:xpath-root 3;
          }
        }
        description
          "This is associated interface to the cpri interface.";
      }
      leaf roe-dcr-sync-status {
        type ciena-ieee1914-dot3-roe-augment:live_ncs_sync-oper-state;
        description
          "Indicates if the cpri-port has achieved synchronization.";
      }
      container cpri-cable-delay {
        description
          "The calculated cpri cable delay.";
        uses live_ncs_timestamp;
      }
      leaf roe-dcr-sync-reference {
        type boolean;
        description
          "Indicates if the cpri-port is the sync reference for cpri-ports in the same DCR group.";
      }
    }
  }
  augment "/ncs:devices/ncs:device/ncs:config/if:interfaces/if:interface" {
    when "if:type = 'cienacpri'" {
      tailf:xpath-root 3;
    }
    description
      "Augmenting ietf-interfaces to cpri port for ciena specific configuration.";
    container cpri-port {
      tailf:ncs-device-type "netconf";
      tailf:display-when "not(../../../../ncs:module) or ../../../../ncs:module[ncs:name='ciena-cpri-augment']";
      description
        "CPRI port parameters.";
      reference "Table 8 of IEEE Std 1914.3";
      presence "CPRI Port configuration";
      // NCS drop config false leaf 'cpri-id'
      leaf admin-state {
        type ciena:admin-state;
        default "enabled";
        description
          "Cpri port admin state.";
      }
      // NCS drop config false leaf 'oper-state'
      leaf cpri-option {
        type enumeration {
          enum "CPRI_3" {
            description
              "For CPRI port speed of 2.457 Gbps.";
          }
          enum "CPRI_5" {
            description
              "For CPRI port speed of 4.912 Gbps.";
          }
          enum "CPRI_7" {
            description
              "For CPRI port speed of 9.83 Gbps.";
          }
          enum "CPRI_8" {
            description
              "For CPRI port speed of 10.137 Gbps.";
          }
          enum "CPRI_10" {
            description
              "For CPRI port speed of 24.33024 Gbps.";
          }
        }
        default "CPRI_3";
        description
          "The speed option of the CPRI port.";
      }
      // NCS drop config false leaf 'cpri-speed'
      leaf forward-error-correction {
        type cntypes:ettp-fec-enum;
        default "auto";
        description
          "Forward error correction";
      }
      // NCS drop config false leaf 'cpri-ver'
      // NCS drop config false leaf 'cpri-hdlc'
      // NCS drop config false leaf 'cpri-l1'
      // NCS drop config false leaf 'cpri-eth'
      leaf ptp-id {
        type leafref {
          path "/ncs:devices/ncs:device/ncs:config/cn-pkt-ptp:ptps/cn-pkt-ptp:ptp/cn-pkt-ptp:ptp-id" {
            tailf:xpath-root 3;
          }
        }
        description
          "Unique, access identifier string of the PTP (e.g., '1/1').";
      }
      leaf associated-interface {
        type leafref {
          path "/ncs:devices/ncs:device/ncs:config/if:interfaces/if:interface/if:name" {
            tailf:xpath-root 3;
          }
        }
        description
          "This is associated interface to the cpri interface.";
      }
      // NCS drop config false leaf 'roe-dcr-sync-status'
      // NCS drop config false container 'cpri-cable-delay'
      // NCS drop config false leaf 'roe-dcr-sync-reference'
    }
  }

  identity cienacpri {
    base if:interface-type;
    description
      "Ciena CPRI interface type.";
  }
}
