submodule ietf-snmp-proxy {
  // Generated by yanger -t ncs
  tailf:mount-id "ciena107s3-nc-1.0:ciena107s3-nc-1.0";

  belongs-to ietf-snmp {
    prefix snmp;
  }

  include ietf-snmp-common;
  include ietf-snmp-target;
  import tailf-common {
    prefix tailf;
  }
  import tailf-ncs {
    prefix ncs;
  }

  organization
    "IETF NETMOD (NETCONF Data Modeling Language) Working Group";
  contact
    "WG Web:   <http://tools.ietf.org/wg/netmod/>
     WG List:  <mailto:netmod@ietf.org>

     WG Chair: Thomas Nadeau
               <mailto:tnadeau@lucidvision.com>

     WG Chair: Juergen Schoenwaelder
               <mailto:j.schoenwaelder@jacobs-university.de>

     Editor:   Martin Bjorklund
               <mailto:mbj@tail-f.com>

     Editor:   Juergen Schoenwaelder
               <mailto:j.schoenwaelder@jacobs-university.de>";
  description
    "This submodule contains a collection of YANG definitions
     for configuring SNMP proxies.

     Copyright (c) 2014 IETF Trust and the persons identified as
     authors of the code.  All rights reserved.

     Redistribution and use in source and binary forms, with or
     without modification, is permitted pursuant to, and subject
     to the license terms contained in, the Simplified BSD License
     set forth in Section 4.c of the IETF Trust's Legal Provisions
     Relating to IETF Documents
     (http://trustee.ietf.org/license-info).

     This version of this YANG module is part of RFC 7407; see
     the RFC itself for full legal notices.";
  reference
    "RFC 3413: Simple Network Management Protocol (SNMP)
       Applications";

  revision 2014-12-10 {
    description
      "Initial revision.";
    reference "RFC 7407: A YANG Data Model for SNMP Configuration";
  }

  augment "/ncs:devices/ncs:template/ncs:ned-id/ncs:config/snmp:snmp" {
    // NCS drop if-feature statement
    list proxy {
      // NCS patched for predictable order
      ordered-by user;
      key "name";
      description
        "List of proxy parameters.";
      reference
        "RFC 3413: Simple Network Management Protocol (SNMP).
           Applications.
           SNMP-PROXY-MIB.snmpProxyTable";
      leaf name {
        type snmp:ncs_template_identifier;
        description
          "Identifies the proxy parameter entry.";
        reference
          "RFC 3413: Simple Network Management Protocol (SNMP).
             Applications.
             SNMP-PROXY-MIB.snmpProxyName";
      }
      leaf type {
        type string;
        // NCS drop mandatory statement
        reference
          "RFC 3413: Simple Network Management Protocol (SNMP).
             Applications.
             SNMP-PROXY-MIB.snmpProxyType";
      }
      leaf context-engine-id {
        type snmp:ncs_template_engine-id;
        // NCS drop mandatory statement
        reference
          "RFC 3413: Simple Network Management Protocol (SNMP).
             Applications.
             SNMP-PROXY-MIB.snmpProxyContextEngineID";
      }
      leaf context-name {
        type snmp:ncs_template_context-name;
        reference
          "RFC 3413: Simple Network Management Protocol (SNMP).
             Applications.
             SNMP-PROXY-MIB.snmpProxyContextName";
      }
      leaf target-params-in {
        type snmp:ncs_template_identifier;
        description
          "The name of a target parameters list entry.

           Implementations MAY restrict the values of this
           leaf to be one of the available values of
           /snmp/target-params/name in a valid configuration.";
        reference
          "RFC 3413: Simple Network Management Protocol (SNMP).
             Applications.
             SNMP-PROXY-MIB.snmpProxyTargetParamsIn";
      }
      leaf single-target-out {
        // NCS drop when statement
        type snmp:ncs_template_identifier;
        description
          "Implementations MAY restrict the values of this leaf
           to be one of the available values of /snmp/target/name in
           a valid configuration.";
        reference
          "RFC 3413: Simple Network Management Protocol (SNMP).
             Applications.
             SNMP-PROXY-MIB.snmpProxySingleTargetOut";
      }
      leaf multiple-target-out {
        // NCS drop when statement
        type snmp:ncs_template_tag-value;
        description
          "Implementations MAY restrict the values of this leaf
           to be one of the available values of /snmp/target/tag in
           a valid configuration.";
        reference
          "RFC 3413: Simple Network Management Protocol (SNMP).
             Applications.
             SNMP-PROXY-MIB.snmpProxyMultipleTargetOut";
      }
    }
  }
  augment "/ncs:devices/ncs:device/ncs:live-status/snmp:snmp" {
    // NCS drop if-feature statement
    list proxy {
      tailf:ncs-device-type "netconf";
      tailf:display-when "not(../../ncs:module) or ../../ncs:module[ncs:name='ietf-snmp'] or (../../ncs:live-status-protocol[not(ncs:capability)]) or (../../ncs:live-status-protocol/ncs:capability/ncs:module[.='ietf-snmp'])";
      key "name";
      description
        "List of proxy parameters.";
      reference
        "RFC 3413: Simple Network Management Protocol (SNMP).
           Applications.
           SNMP-PROXY-MIB.snmpProxyTable";
      leaf name {
        type snmp:live_ncs_identifier;
        description
          "Identifies the proxy parameter entry.";
        reference
          "RFC 3413: Simple Network Management Protocol (SNMP).
             Applications.
             SNMP-PROXY-MIB.snmpProxyName";
      }
      leaf type {
        type enumeration {
          enum "read" {
            value 1;
          }
          enum "write" {
            value 2;
          }
          enum "trap" {
            value 3;
          }
          enum "inform" {
            value 4;
          }
        }
        // NCS drop mandatory statement
        reference
          "RFC 3413: Simple Network Management Protocol (SNMP).
             Applications.
             SNMP-PROXY-MIB.snmpProxyType";
      }
      leaf context-engine-id {
        type snmp:live_ncs_engine-id;
        // NCS drop mandatory statement
        reference
          "RFC 3413: Simple Network Management Protocol (SNMP).
             Applications.
             SNMP-PROXY-MIB.snmpProxyContextEngineID";
      }
      leaf context-name {
        type snmp:live_ncs_context-name;
        reference
          "RFC 3413: Simple Network Management Protocol (SNMP).
             Applications.
             SNMP-PROXY-MIB.snmpProxyContextName";
      }
      leaf target-params-in {
        type snmp:live_ncs_identifier;
        description
          "The name of a target parameters list entry.

           Implementations MAY restrict the values of this
           leaf to be one of the available values of
           /snmp/target-params/name in a valid configuration.";
        reference
          "RFC 3413: Simple Network Management Protocol (SNMP).
             Applications.
             SNMP-PROXY-MIB.snmpProxyTargetParamsIn";
      }
      leaf single-target-out {
        // NCS drop when statement
        type snmp:live_ncs_identifier;
        description
          "Implementations MAY restrict the values of this leaf
           to be one of the available values of /snmp/target/name in
           a valid configuration.";
        reference
          "RFC 3413: Simple Network Management Protocol (SNMP).
             Applications.
             SNMP-PROXY-MIB.snmpProxySingleTargetOut";
      }
      leaf multiple-target-out {
        // NCS drop when statement
        type snmp:live_ncs_tag-value;
        description
          "Implementations MAY restrict the values of this leaf
           to be one of the available values of /snmp/target/tag in
           a valid configuration.";
        reference
          "RFC 3413: Simple Network Management Protocol (SNMP).
             Applications.
             SNMP-PROXY-MIB.snmpProxyMultipleTargetOut";
      }
    }
  }
  augment "/ncs:devices/ncs:device/ncs:config/snmp:snmp" {
    // NCS drop if-feature statement
    list proxy {
      tailf:ncs-device-type "netconf";
      tailf:display-when "not(../../ncs:module) or ../../ncs:module[ncs:name='ietf-snmp']";
      key "name";
      description
        "List of proxy parameters.";
      reference
        "RFC 3413: Simple Network Management Protocol (SNMP).
           Applications.
           SNMP-PROXY-MIB.snmpProxyTable";
      leaf name {
        type snmp:identifier;
        description
          "Identifies the proxy parameter entry.";
        reference
          "RFC 3413: Simple Network Management Protocol (SNMP).
             Applications.
             SNMP-PROXY-MIB.snmpProxyName";
      }
      leaf type {
        type enumeration {
          enum "read" {
            value 1;
          }
          enum "write" {
            value 2;
          }
          enum "trap" {
            value 3;
          }
          enum "inform" {
            value 4;
          }
        }
        mandatory true;
        reference
          "RFC 3413: Simple Network Management Protocol (SNMP).
             Applications.
             SNMP-PROXY-MIB.snmpProxyType";
      }
      leaf context-engine-id {
        type snmp:engine-id;
        mandatory true;
        reference
          "RFC 3413: Simple Network Management Protocol (SNMP).
             Applications.
             SNMP-PROXY-MIB.snmpProxyContextEngineID";
      }
      leaf context-name {
        type snmp:context-name;
        reference
          "RFC 3413: Simple Network Management Protocol (SNMP).
             Applications.
             SNMP-PROXY-MIB.snmpProxyContextName";
      }
      leaf target-params-in {
        type snmp:identifier;
        description
          "The name of a target parameters list entry.

           Implementations MAY restrict the values of this
           leaf to be one of the available values of
           /snmp/target-params/name in a valid configuration.";
        reference
          "RFC 3413: Simple Network Management Protocol (SNMP).
             Applications.
             SNMP-PROXY-MIB.snmpProxyTargetParamsIn";
      }
      leaf single-target-out {
        when "../type = 'read' or ../type = 'write'" {
          tailf:xpath-root 3;
        }
        type snmp:identifier;
        description
          "Implementations MAY restrict the values of this leaf
           to be one of the available values of /snmp/target/name in
           a valid configuration.";
        reference
          "RFC 3413: Simple Network Management Protocol (SNMP).
             Applications.
             SNMP-PROXY-MIB.snmpProxySingleTargetOut";
      }
      leaf multiple-target-out {
        when "../type = 'trap' or ../type = 'inform'" {
          tailf:xpath-root 3;
        }
        type snmp:tag-value;
        description
          "Implementations MAY restrict the values of this leaf
           to be one of the available values of /snmp/target/tag in
           a valid configuration.";
        reference
          "RFC 3413: Simple Network Management Protocol (SNMP).
             Applications.
             SNMP-PROXY-MIB.snmpProxyMultipleTargetOut";
      }
    }
  }

  feature proxy {
    description
      "A server implements this feature if it can act as an
       SNMP proxy.";
    reference
      "RFC 3413: Simple Network Management Protocol (SNMP)
         Applications";
  }
}
