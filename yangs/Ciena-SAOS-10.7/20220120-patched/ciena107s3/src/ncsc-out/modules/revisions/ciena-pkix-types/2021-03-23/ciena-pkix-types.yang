module ciena-pkix-types {
  // Generated by yanger -t ncs
  tailf:mount-id "ciena107s3-nc-1.0:ciena107s3-nc-1.0";
  tailf:ncs-device-type "netconf";

  namespace "http://www.ciena.com/ns/yang/ciena-pkix-types";
  prefix pkix-types;

  import ietf-inet-types {
    prefix inet;
  }
  import tailf-common {
    prefix tailf;
  }
  import tailf-ncs {
    prefix ncs;
  }

  organization
    "Ciena Corporation";
  contact
    "Web URL: http://www.ciena.com/
     E-mail:  yang@ciena.com
     Postal:  7035 Ridge Road
              Hanover, Maryland 21076
              U.S.A.
     Phone:   +1 800-921-1144
     Fax:     +1 410-694-5750";
  description
    "This YANG module defines the data types and groupings for Public
     Key Infrastructure (PKI) Security Certificates CA (Certificate
     Authority) and CRL (Certificate Revocation List) for the NETCONF
     protocol.

     Copyright (c) 2016-2017 Ciena Corporation.  All rights reserved.

     All information contained herein is, and remains the property of
     Ciena Corporation. Dissemination of this information or
     reproduction of this material is strictly forbidden unless prior
     written permission is obtained from Ciena Corporation.";

  revision 2021-03-23 {
    description
      "Updated to add an new algorithm type";
    reference "No specific reference; standard not available.";
  }
  revision 2018-04-27 {
    description
      "Updated to add an new algorithm type";
    reference "No specific reference; standard not available.";
  }
  revision 2017-10-27 {
    description
      "Initial version";
    reference
      "RFC 6020: YANG - A Data Modeling Language for
       the Network Configuration Protocol (NETCONF).
       No specific reference; standard not available.";
  }

  typedef ncs_template_min-tls-version {
    type string;
    description
      "This enum contains the minimum TLS versions that, once set
       within a protocol, prevents the use of any TLS version
       older than the version set.";
  }

  typedef ncs_rpc_notif_min-tls-version {
    type enumeration {
      enum "tls1_0" {
        description
          "TLSv1.0 would be minimum version supported";
      }
      enum "tls1_1" {
        description
          "TLSv1.1 would be minimum version supported";
      }
      enum "tls1_2" {
        description
          "TLSv1.2 would be minimum version supported";
      }
    }
    description
      "This enum contains the minimum TLS versions that, once set
       within a protocol, prevents the use of any TLS version
       older than the version set.";
  }

  typedef live_ncs_min-tls-version {
    type enumeration {
      enum "tls1_0" {
        description
          "TLSv1.0 would be minimum version supported";
      }
      enum "tls1_1" {
        description
          "TLSv1.1 would be minimum version supported";
      }
      enum "tls1_2" {
        description
          "TLSv1.2 would be minimum version supported";
      }
    }
    description
      "This enum contains the minimum TLS versions that, once set
       within a protocol, prevents the use of any TLS version
       older than the version set.";
  }

  typedef min-tls-version {
    type enumeration {
      enum "tls1_0" {
        description
          "TLSv1.0 would be minimum version supported";
      }
      enum "tls1_1" {
        description
          "TLSv1.1 would be minimum version supported";
      }
      enum "tls1_2" {
        description
          "TLSv1.2 would be minimum version supported";
      }
    }
    description
      "This enum contains the minimum TLS versions that, once set
       within a protocol, prevents the use of any TLS version
       older than the version set.";
  }

  grouping ncs_template_pkix-certificate-fields {
    leaf subject-common-name {
      type string;
      description
        "The Subject Common Name of this X.509 certificate.";
    }
    leaf issuer-common-name {
      type string;
      description
        "The certificate Issuer Common Name.";
    }
    leaf valid-not-after {
      type string;
      description
        "The end of the certificate's validity period.";
    }
    description
      "Common X.509 certificate fields";
  }

  grouping ncs_template_pkix-file-transfer-parameters {
    leaf remote-file-uri {
      type string;
      // NCS drop mandatory statement
      description
        "URI (Universal Resource Identifier) of the remote file.";
    }
    leaf login-id {
      type string;
      description
        "Login ID for the specified server.  Not needed for TFTP.";
    }
    leaf password {
      type string;
      description
        "The string used for the clear text password.  Not needed for
         TFTP.";
    }
    leaf sftp-passphrase {
      type string;
      description
        "Passphrase for SFTP (Secure File Transfer Protocol)
         transfers.";
    }
    leaf force {
      type string;
      description
        "Use force to overwrite the local file with the same filename.
         Applies only to install operations.";
    }
    description
      "Common file transfer parameters";
  }

  grouping ncs_rpc_notif_pkix-certificate-fields {
    leaf subject-common-name {
      type string;
      description
        "The Subject Common Name of this X.509 certificate.";
    }
    leaf issuer-common-name {
      type string;
      description
        "The certificate Issuer Common Name.";
    }
    leaf valid-not-after {
      type string;
      description
        "The end of the certificate's validity period.";
    }
    description
      "Common X.509 certificate fields";
  }

  grouping ncs_rpc_notif_pkix-file-transfer-parameters {
    leaf remote-file-uri {
      type inet:uri;
      mandatory true;
      description
        "URI (Universal Resource Identifier) of the remote file.";
    }
    leaf login-id {
      type string {
        length "0..32";
      }
      description
        "Login ID for the specified server.  Not needed for TFTP.";
    }
    leaf password {
      type string;
      description
        "The string used for the clear text password.  Not needed for
         TFTP.";
    }
    leaf sftp-passphrase {
      type string;
      description
        "Passphrase for SFTP (Secure File Transfer Protocol)
         transfers.";
    }
    leaf force {
      type boolean;
      description
        "Use force to overwrite the local file with the same filename.
         Applies only to install operations.";
    }
    description
      "Common file transfer parameters";
  }

  grouping live_ncs_pkix-certificate-fields {
    leaf subject-common-name {
      type string;
      description
        "The Subject Common Name of this X.509 certificate.";
    }
    leaf issuer-common-name {
      type string;
      description
        "The certificate Issuer Common Name.";
    }
    leaf valid-not-after {
      type string;
      description
        "The end of the certificate's validity period.";
    }
    description
      "Common X.509 certificate fields";
  }

  grouping live_ncs_pkix-file-transfer-parameters {
    leaf remote-file-uri {
      type inet:uri;
      // NCS drop mandatory statement
      description
        "URI (Universal Resource Identifier) of the remote file.";
    }
    leaf login-id {
      type string {
        length "0..32";
      }
      description
        "Login ID for the specified server.  Not needed for TFTP.";
    }
    leaf password {
      type string;
      description
        "The string used for the clear text password.  Not needed for
         TFTP.";
    }
    leaf sftp-passphrase {
      type string;
      description
        "Passphrase for SFTP (Secure File Transfer Protocol)
         transfers.";
    }
    leaf force {
      type boolean;
      description
        "Use force to overwrite the local file with the same filename.
         Applies only to install operations.";
    }
    description
      "Common file transfer parameters";
  }

  grouping pkix-certificate-fields {
    leaf subject-common-name {
      type string;
      description
        "The Subject Common Name of this X.509 certificate.";
    }
    leaf issuer-common-name {
      type string;
      description
        "The certificate Issuer Common Name.";
    }
    leaf valid-not-after {
      type string;
      description
        "The end of the certificate's validity period.";
    }
    description
      "Common X.509 certificate fields";
  }

  grouping pkix-file-transfer-parameters {
    leaf remote-file-uri {
      type inet:uri;
      mandatory true;
      description
        "URI (Universal Resource Identifier) of the remote file.";
    }
    leaf login-id {
      type string {
        length "0..32";
      }
      description
        "Login ID for the specified server.  Not needed for TFTP.";
    }
    leaf password {
      type string;
      description
        "The string used for the clear text password.  Not needed for
         TFTP.";
    }
    leaf sftp-passphrase {
      type string;
      description
        "Passphrase for SFTP (Secure File Transfer Protocol)
         transfers.";
    }
    leaf force {
      type boolean;
      description
        "Use force to overwrite the local file with the same filename.
         Applies only to install operations.";
    }
    description
      "Common file transfer parameters";
  }

  identity useExisiting {
    base key-algorithm;
    description
      "The the existing algorithm.";
    reference "";
  }

  identity dsa3072 {
    base key-algorithm;
    description
      "The dsa3072 algorithm.";
    reference "";
  }

  identity dsa2048 {
    base key-algorithm;
    description
      "The dsa2048 algorithm.";
    reference "";
  }

  identity dsa1024 {
    base key-algorithm;
    description
      "The dsa1024 algorithm.";
    reference "";
  }

  identity secp521r1 {
    base key-algorithm;
    description
      "The secp521r1 algorithm.  Also referred to in some contexts such
       as RFC 4754 as ecdsa521.";
    reference
      "RFC5480:
         Elliptic Curve Cryptography Subject Public Key Information.";
  }

  identity secp384r1 {
    base key-algorithm;
    description
      "The secp384r1 algorithm.  Also referred to in some contexts such
       as RF 4754 as ecdsa384.";
    reference
      "RFC5480:
         Elliptic Curve Cryptography Subject Public Key Information.";
  }

  identity secp256r1 {
    base key-algorithm;
    description
      "The secp256r1 algorithm.  Also referred to in some contexts such
       as RFC 4754 as ecdsa256.";
    reference
      "RFC5480:
         Elliptic Curve Cryptography Subject Public Key Information.";
  }

  identity rsa4096 {
    base key-algorithm;
    description
      "The RSA algorithm using a 4096-bit key.";
    reference
      "RFC3447: Public-Key Cryptography Standards (PKCS) #1:
                RSA Cryptography Specifications Version 2.1.";
  }

  identity rsa3072 {
    base key-algorithm;
    description
      "The RSA algorithm using a 3072-bit key.";
    reference
      "RFC3447: Public-Key Cryptography Standards (PKCS) #1:
                RSA Cryptography Specifications Version 2.1.";
  }

  identity rsa2048 {
    base key-algorithm;
    description
      "The RSA algorithm using a 2048-bit key.";
    reference
      "RFC3447: Public-Key Cryptography Standards (PKCS) #1:
                RSA Cryptography Specifications Version 2.1.";
  }

  identity rsa1024 {
    base key-algorithm;
    description
      "The RSA algorithm using a 1024-bit key.";
    reference
      "RFC3447: Public-Key Cryptography Standards (PKCS) #1:
                RSA Cryptography Specifications Version 2.1.";
  }

  identity key-algorithm {
    description
      "Base identity from which all key-algorithms are derived.";
  }
}
