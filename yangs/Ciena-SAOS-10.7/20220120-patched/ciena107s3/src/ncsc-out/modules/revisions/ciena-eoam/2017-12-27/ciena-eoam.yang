module ciena-eoam {
  // Generated by yanger -t ncs
  tailf:mount-id "ciena107s3-nc-1.0:ciena107s3-nc-1.0";
  tailf:ncs-device-type "netconf";

  namespace "urn:ciena:params:xml:ns:yang:ciena-pn:ciena-eoam";
  prefix ciena-eoam;

  import tailf-common {
    prefix tailf;
  }
  import tailf-ncs {
    prefix ncs;
  }

  organization
    "Ciena Corporation";
  contact
    "Web URL: http://www.ciena.com/
     E-mail:  yang@ciena.com
     Postal:  7035 Ridge Road
              Hanover, Maryland 21076
              U.S.A.
     Phone:   +1 800-921-1144
     Fax:     +1 410-694-5750";
  description
    "This YANG module contains the schema definition for Ciena's
     global configuration of Ethernet Operations,
     Administration and Management (EOAM).";

  revision 2017-12-27 {
    description
      " 1. Modified container names to meaningful names by adding
           protocol name (eoam) as their prefix.
        2. Added clear-eoam-statistics RPC.";
  }
  revision 2015-02-25 {
    description
      "Initial Version.";
    reference "Ciena EOAM global configuration";
  }

  augment "/ncs:devices/ncs:device/ncs:rpc" {
    container rpc-clear-eoam-statistics {
      tailf:ncs-device-type "netconf";
      tailf:display-when "not(../../ncs:module) or ../../ncs:module[ncs:name='ciena-eoam']";
      tailf:action clear-eoam-statistics {
        tailf:actionpoint ncsproxy {
          tailf:internal;
        }
        description
          "Administratively clear eoam statistics";
      }
    }
  }
  augment "/ncs:devices/ncs:device-group/ncs:ned-id/ncs:rpc" {
    container rpc-clear-eoam-statistics {
      tailf:ncs-device-type "netconf";
      tailf:display-when "/ncs:devices/ncs:device[ncs:name=current()/../../../ncs:member]/ncs:module[ncs:name='ciena-eoam']";
      tailf:action clear-eoam-statistics {
        tailf:actionpoint ncsproxy {
          tailf:internal;
        }
        description
          "Administratively clear eoam statistics";
      }
    }
  }
  augment "/ncs:devices/ncs:device/ncs:config" {
    container eoam-global-config-status {
      tailf:ncs-device-type "netconf";
      tailf:display-when "not(../../ncs:module) or ../../ncs:module[ncs:name='ciena-eoam']";
      leaf admin-state {
        type enumeration {
          enum "enabled" {
            description
              "Enable EOAM globally on this device.";
          }
          enum "disabled" {
            description
              "Disable EOAM globally on this device.";
          }
        }
        default "disabled";
        description
          "Enable or disable EOAM globally on this device";
      }
      // NCS drop config false leaf 'oper-state'
      description
        "EOAM global operational status on this device";
    }
  }
  augment "/ncs:devices/ncs:device/ncs:live-status" {
    container eoam-global-config-status {
      tailf:ncs-device-type "netconf";
      tailf:display-when "not(../../ncs:module) or ../../ncs:module[ncs:name='ciena-eoam'] or (../../ncs:live-status-protocol[not(ncs:capability)]) or (../../ncs:live-status-protocol/ncs:capability/ncs:module[.='ciena-eoam'])";
      leaf admin-state {
        type enumeration {
          enum "enabled" {
            description
              "Enable EOAM globally on this device.";
          }
          enum "disabled" {
            description
              "Disable EOAM globally on this device.";
          }
        }
        // NCS drop default statement
        description
          "Enable or disable EOAM globally on this device";
      }
      leaf oper-state {
        type enumeration {
          enum "enabled" {
            description
              "EOAM is globally enabled on this device.";
          }
          enum "disabled" {
            description
              "EOAM is globally enabled on this device.";
          }
        }
        description
          "EOAM global operational status.";
      }
      description
        "EOAM global operational status on this device";
    }
  }
  augment "/ncs:devices/ncs:template/ncs:ned-id/ncs:config" {
    container eoam-global-config-status {
      leaf admin-state {
        type string;
        // NCS drop default statement
        description
          "Enable or disable EOAM globally on this device";
      }
      // NCS drop config false leaf 'oper-state'
      description
        "EOAM global operational status on this device";
    }
  }
}
