module ciena-twamp-saos {
  // Generated by yanger -t ncs
  tailf:mount-id "ciena107s3-nc-1.0:ciena107s3-nc-1.0";
  tailf:ncs-device-type "netconf";

  namespace "urn:ciena:params:xml:ns:yang:ciena-pn:ciena-twamp-saos";
  prefix ciena-twamp-saos;

  import ietf-twamp {
    prefix ietf-twamp;
  }
  import tailf-common {
    prefix tailf;
  }
  import tailf-ncs {
    prefix ncs;
  }

  organization
    "Ciena Corporation";
  contact
    "Web URL: http://www.ciena.com/
     E-mail:  yang@ciena.com
     Postal:  7035 Ridge Road
             Hanover, Maryland 21076
             U.S.A.
     Phone:   +1 800-921-1144
     Fax:     +1 410-694-5750";
  description
    "This YANG module defines Ciena's TWAMP
     config extensions on the SAOS platform";

  revision 2020-12-10 {
    description
      "Added new leaf - connectivity mode";
    reference "ietf-twamp-yang";
  }
  revision 2018-10-05 {
    description
      "initial version";
    reference "ietf-twamp-yang";
  }

  augment "/ncs:devices/ncs:device/ncs:rpc" {
    container rpc-twamp-clear-ctrl-connection {
      tailf:ncs-device-type "netconf";
      tailf:display-when "not(../../ncs:module) or ../../ncs:module[ncs:name='ciena-twamp-saos']";
      tailf:action twamp-clear-ctrl-connection {
        tailf:actionpoint ncsproxy {
          tailf:internal;
        }
        description
          "Clear the targeted ctrl-connection.
           The ctrl-connection is uniquely identified by the 4-tuple:
           client IP, client TCP port, server IP, server TCP port.";
        input {
          leaf client-ip {
            type string;
            mandatory true;
            description
              "client IP address of the ctrl-connection to clear.";
          }
          leaf client-tcp-port {
            type string;
            mandatory true;
            description
              "client TCP port of the ctrl-connection to clear.";
          }
          leaf server-ip {
            type string;
            mandatory true;
            description
              "server IP address of the ctrl-connection to clear.";
          }
          leaf server-tcp-port {
            type string;
            mandatory true;
            description
              "server TCP port of the ctrl-connection to clear.";
          }
        }
        output {
          leaf status {
            type string;
            description
              "Status of the clear operation.";
          }
        }
      }
    }
  }
  augment "/ncs:devices/ncs:device-group/ncs:ned-id/ncs:rpc" {
    container rpc-twamp-clear-ctrl-connection {
      tailf:ncs-device-type "netconf";
      tailf:display-when "/ncs:devices/ncs:device[ncs:name=current()/../../../ncs:member]/ncs:module[ncs:name='ciena-twamp-saos']";
      tailf:action twamp-clear-ctrl-connection {
        tailf:actionpoint ncsproxy {
          tailf:internal;
        }
        description
          "Clear the targeted ctrl-connection.
           The ctrl-connection is uniquely identified by the 4-tuple:
           client IP, client TCP port, server IP, server TCP port.";
        input {
          leaf client-ip {
            type string;
            mandatory true;
            description
              "client IP address of the ctrl-connection to clear.";
          }
          leaf client-tcp-port {
            type string;
            mandatory true;
            description
              "client TCP port of the ctrl-connection to clear.";
          }
          leaf server-ip {
            type string;
            mandatory true;
            description
              "server IP address of the ctrl-connection to clear.";
          }
          leaf server-tcp-port {
            type string;
            mandatory true;
            description
              "server TCP port of the ctrl-connection to clear.";
          }
        }
        output {
          container "device" {
            leaf "name" {
              type string;
            }
            leaf "info" {
              type string;
            }
            container "result" {
              leaf status {
                type string;
                description
                  "Status of the clear operation.";
              }
            }
          }
        }
      }
    }
  }
  augment "/ncs:devices/ncs:template/ncs:ned-id/ncs:config/ietf-twamp:twamp/ietf-twamp:server" {
    description
      "Augmentation for configuration data.";
    leaf connectivity-mode {
      type string;
      // NCS drop default statement
      description
        "Some customers require a non-standard behavior where TWAMP runs
         only within a single subnet.  This leaf allows us to select restricted mode
         to accomplish this non-standard behavior.  The default is standard mode,
         where TWAMP is willing to accept sessions across different subnets.";
    }
  }
  augment "/ncs:devices/ncs:device/ncs:live-status/ietf-twamp:twamp/ietf-twamp:server" {
    description
      "Augmentation for configuration data.";
    leaf connectivity-mode {
      tailf:ncs-device-type "netconf";
      tailf:display-when "not(../../../../ncs:module) or ../../../../ncs:module[ncs:name='ciena-twamp-saos'] or (../../../../ncs:live-status-protocol[not(ncs:capability)]) or (../../../../ncs:live-status-protocol/ncs:capability/ncs:module[.='ciena-twamp-saos'])";
      type enumeration {
        enum "standard" {
          description
            "Indicates TWAMP will accept incoming sessions from any subnet";
        }
        enum "restricted" {
          description
            "Indicates TWAMP will only accept sessions where the src/dest IP are in the same subnet";
        }
      }
      // NCS drop default statement
      description
        "Some customers require a non-standard behavior where TWAMP runs
         only within a single subnet.  This leaf allows us to select restricted mode
         to accomplish this non-standard behavior.  The default is standard mode,
         where TWAMP is willing to accept sessions across different subnets.";
    }
  }
  augment "/ncs:devices/ncs:device/ncs:config/ietf-twamp:twamp/ietf-twamp:server" {
    description
      "Augmentation for configuration data.";
    leaf connectivity-mode {
      tailf:ncs-device-type "netconf";
      tailf:display-when "not(../../../../ncs:module) or ../../../../ncs:module[ncs:name='ciena-twamp-saos']";
      type enumeration {
        enum "standard" {
          description
            "Indicates TWAMP will accept incoming sessions from any subnet";
        }
        enum "restricted" {
          description
            "Indicates TWAMP will only accept sessions where the src/dest IP are in the same subnet";
        }
      }
      default "standard";
      description
        "Some customers require a non-standard behavior where TWAMP runs
         only within a single subnet.  This leaf allows us to select restricted mode
         to accomplish this non-standard behavior.  The default is standard mode,
         where TWAMP is willing to accept sessions across different subnets.";
    }
  }
}
