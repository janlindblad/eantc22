module ciena-of-vfsi {
  // Generated by yanger -t ncs
  tailf:mount-id "ciena107s3-nc-1.0:ciena107s3-nc-1.0";
  tailf:ncs-device-type "netconf";

  namespace "http://www.ciena.com/ns/yang/ciena-pn/ciena-of-vfsi";
  prefix of-vfsi;

  import ciena-of-types {
    prefix of-types;
  }
  import tailf-common {
    prefix tailf;
  }
  import tailf-ncs {
    prefix ncs;
  }

  organization
    "Ciena Corporation";
  contact
    "Web URL: http://www.ciena.com/
     E-mail:  yang@ciena.com
     Postal:  7035 Ridge Road
              Hanover, Maryland 21076
                  U.S.A.
     Phone:   +1 800-921-1144
     Fax:     +1 410-694-5750";
  description
    "This YANG module defines Ciena's management data definition for the definition of
     Virtual FlowSwitch Instances (vfsi).";

  revision 2018-09-14 {
    description
      "Initial Version.";
  }

  typedef ncs_template_vfsi-id-ref {
    type string;
    description
      "This type is used by data models that need to reference
       configured vfsis.";
  }

  typedef ncs_rpc_notif_vfsi-id-ref {
    type string;
    description
      "This type is used by data models that need to reference
       configured vfsis.";
  }

  typedef live_ncs_vfsi-id-ref {
    type leafref {
      path "/ncs:devices/ncs:device/ncs:live-status/of-vfsi:of-vfsis/of-vfsi:of-vfsi/of-vfsi:vfsi-id" {
        tailf:xpath-root 3;
      }
    }
    description
      "This type is used by data models that need to reference
       configured vfsis.";
  }

  typedef vfsi-id-ref {
    type leafref {
      path "/ncs:devices/ncs:device/ncs:config/of-vfsi:of-vfsis/of-vfsi:of-vfsi/of-vfsi:vfsi-id" {
        tailf:xpath-root 3;
      }
    }
    description
      "This type is used by data models that need to reference
       configured vfsis.";
  }

  augment "/ncs:devices/ncs:device/ncs:config" {
    container of-vfsis {
      tailf:ncs-device-type "netconf";
      tailf:display-when "not(../../ncs:module) or ../../ncs:module[ncs:name='ciena-of-vfsi']";
      description
        "The configuration model for vfsis (Virtual Flow Switch Instances) include a list of logical ports
         which are contained within the vfsi. The port list may be present at the time of vfsi creation
         or added/remapped afterwards.";
      list of-vfsi {
        description
          "This is the list of Virtual Flow Switch Instances.  These are automatically
           created and configured by the switch, and should not be created by the
           controller.
           Only the table-description should be configured by the controller.";
        key "vfsi-id";
        leaf vfsi-id {
          type of-types:vfsi-id;
          description
            "An identifier of the Virtual FlowSwitch Instance. Unique string values are chosen to
             uniquely identify the Virtual Flow Switch Instance.
             This element cannot be modified by the controller.";
        }
        leaf instance-description {
          type string;
          description
            "A more detailed description that an operator can use to describe
             the Virtual FlowSwitch Instance.";
        }
        leaf-list port-list {
          type of-types:logical-port;
          description
            "List of Logical Ports within this Virtual Flow Switch Instance.";
        }
        // NCS drop config false leaf 'default-instance'
      }
    }
    // NCS drop config false container 'of-vfsis-state'
  }
  augment "/ncs:devices/ncs:device/ncs:live-status" {
    container of-vfsis {
      tailf:ncs-device-type "netconf";
      tailf:display-when "not(../../ncs:module) or ../../ncs:module[ncs:name='ciena-of-vfsi'] or (../../ncs:live-status-protocol[not(ncs:capability)]) or (../../ncs:live-status-protocol/ncs:capability/ncs:module[.='ciena-of-vfsi'])";
      description
        "The configuration model for vfsis (Virtual Flow Switch Instances) include a list of logical ports
         which are contained within the vfsi. The port list may be present at the time of vfsi creation
         or added/remapped afterwards.";
      list of-vfsi {
        description
          "This is the list of Virtual Flow Switch Instances.  These are automatically
           created and configured by the switch, and should not be created by the
           controller.
           Only the table-description should be configured by the controller.";
        key "vfsi-id";
        leaf vfsi-id {
          type of-types:live_ncs_vfsi-id;
          description
            "An identifier of the Virtual FlowSwitch Instance. Unique string values are chosen to
             uniquely identify the Virtual Flow Switch Instance.
             This element cannot be modified by the controller.";
        }
        leaf instance-description {
          type string;
          description
            "A more detailed description that an operator can use to describe
             the Virtual FlowSwitch Instance.";
        }
        leaf-list port-list {
          type of-types:live_ncs_logical-port;
          description
            "List of Logical Ports within this Virtual Flow Switch Instance.";
        }
        leaf default-instance {
          type empty;
          description
            "Table is a default Instance. (e.g. autogenerated by a flowswitch)";
        }
      }
    }
    container of-vfsis-state {
      tailf:ncs-device-type "netconf";
      tailf:display-when "not(../../ncs:module) or ../../ncs:module[ncs:name='ciena-of-vfsi'] or (../../ncs:live-status-protocol[not(ncs:capability)]) or (../../ncs:live-status-protocol/ncs:capability/ncs:module[.='ciena-of-vfsi'])";
      list of-vfsi {
        description
          "The state and statistics associated with a vfsi.";
        key "vfsi-id";
        leaf vfsi-id {
          type of-types:live_ncs_vfsi-id;
          description
            "This object indicates the identifier and is a text string that is
             used to identify a Virtual Flow Switch Instance.";
        }
        leaf-list port-list {
          type of-types:live_ncs_logical-port;
          description
            "List of Logical Ports within this Virtual Flow Switch Instance.";
        }
      }
    }
  }
  augment "/ncs:devices/ncs:template/ncs:ned-id/ncs:config" {
    container of-vfsis {
      description
        "The configuration model for vfsis (Virtual Flow Switch Instances) include a list of logical ports
         which are contained within the vfsi. The port list may be present at the time of vfsi creation
         or added/remapped afterwards.";
      list of-vfsi {
        // NCS patched for predictable order
        ordered-by user;
        description
          "This is the list of Virtual Flow Switch Instances.  These are automatically
           created and configured by the switch, and should not be created by the
           controller.
           Only the table-description should be configured by the controller.";
        key "vfsi-id";
        leaf vfsi-id {
          type of-types:ncs_template_vfsi-id;
          description
            "An identifier of the Virtual FlowSwitch Instance. Unique string values are chosen to
             uniquely identify the Virtual Flow Switch Instance.
             This element cannot be modified by the controller.";
        }
        leaf instance-description {
          type string;
          description
            "A more detailed description that an operator can use to describe
             the Virtual FlowSwitch Instance.";
        }
        leaf-list port-list {
          // NCS patched for predictable order
          ordered-by user;
          type of-types:ncs_template_logical-port;
          description
            "List of Logical Ports within this Virtual Flow Switch Instance.";
        }
        // NCS drop config false leaf 'default-instance'
      }
    }
    // NCS drop config false container 'of-vfsis-state'
  }
}
