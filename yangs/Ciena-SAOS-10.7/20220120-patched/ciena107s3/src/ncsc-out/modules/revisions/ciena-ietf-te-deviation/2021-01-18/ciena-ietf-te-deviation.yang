module ciena-ietf-te-deviation {
  // Generated by yanger -t ncs
  tailf:mount-id "ciena107s3-nc-1.0:ciena107s3-nc-1.0";
  tailf:ncs-device-type "netconf";

  namespace "http://ciena.com/ns/yang/ciena-ietf-te-deviation";
  prefix ciena-te-deviation;

  import ciena-ietf-te {
    prefix ciena-te;
  }
  import tailf-common {
    prefix tailf;
  }
  import tailf-ncs {
    prefix ncs;
  }

  organization
    "Ciena Corporation";
  contact
    "Web URL: http://www.ciena.com/
     E-mail:  yang@ciena.com
     Postal:  7035 Ridge Road
              Hanover, Maryland 21076
              U.S.A.
     Phone:   +1 800-921-1144
     Fax:     +1 410-694-5750";
  description
    "This YANG module defines the deviations for Ciena's configuration of
     the TE attributes.";

  revision 2021-01-18 {
    description
      "Initial version";
  }

  deviation "/ncs:devices/ncs:template/ncs:ned-id/ncs:config/ciena-te:te/ciena-te:interfaces/ciena-te:interface/ciena-te:admin-status" {
    deviate replace {
      type string;
    }
  }
  deviation "/ncs:devices/ncs:device/ncs:live-status/ciena-te:te/ciena-te:interfaces/ciena-te:interface/ciena-te:admin-status" {
    deviate replace {
      type enumeration {
        enum "up" {
          description
            "Enable TE attributes signalling over this interface.";
        }
        enum "down" {
          description
            "Disable TE attributes signalling over this interface.";
        }
      }
    }
  }
  deviation "/ncs:devices/ncs:device/ncs:config/ciena-te:te/ciena-te:interfaces/ciena-te:interface/ciena-te:admin-status" {
    deviate replace {
      type enumeration {
        enum "up" {
          description
            "Enable TE attributes signalling over this interface.";
        }
        enum "down" {
          description
            "Disable TE attributes signalling over this interface.";
        }
      }
    }
  }
}
