module ciena-ieee-lag-deviation {
  // Generated by yanger -t ncs
  tailf:mount-id "ciena107s3-nc-1.0:ciena107s3-nc-1.0";
  tailf:ncs-device-type "netconf";

  namespace "urn:ietf:params:xml:ns:yang:ciena-ieee-lag-deviation";
  prefix ciena-ieee-lag-dev;

  import ciena-ieee-lag {
    prefix ciena-ieee-lag;
  }
  import ciena-ext-lag {
    prefix ciena-ext-lag;
  }
  import openconfig-interfaces {
    prefix oc-if;
  }
  import tailf-common {
    prefix tailf;
  }
  import tailf-ncs {
    prefix ncs;
  }

  organization
    "Ciena Corporation";
  contact
    "Web URL: http://www.ciena.com/
     E-mail:  yang@ciena.com
     Postal:  7035 Ridge Road
              Hanover, Maryland 21076
              U.S.A.
     Phone:   +1 800-921-1144
     Fax:     +1 410-694-5750";
  description
    "This yang module is an extension to the IEEE8023-LAG yang model.
     It defines the managed objects for the creation and
     deletion of Aggregators.";

  revision 2020-11-15 {
    description
      "Added deviation for ciena-ext-lag:hash-mode";
  }
  revision 2018-01-24 {
    description
      "Move lacp augmentations from ietf-interfaces to
       openconfig-interfaces. Remove character restriction on interface
       name to align with SAOS 6x model.";
    reference "openconfig-interfaces yang";
  }
  revision 2016-09-13 {
    description
      "Deviation added to restrict invalid characters in interface
       name";
    reference
      "IEEE Standard for Local and metropolitan area networks --
       Link Aggregation - 802.1AX";
  }
  revision 2016-02-29 {
    description
      "Initial Revision";
    reference
      "IEEE Standard for Local and metropolitan area networks --
       Link Aggregation - 802.1AX";
  }

  deviation "/ncs:devices/ncs:template/ncs:ned-id/ncs:config/oc-if:interfaces/oc-if:interface/oc-if:config/ciena-ieee-lag:agg/ciena-ieee-lag:agg-collector-max-delay" {
    // NCS drop config false deviate replace
  }
  deviation "/ncs:devices/ncs:device/ncs:live-status/oc-if:interfaces/oc-if:interface/oc-if:config/ciena-ieee-lag:agg/ciena-ieee-lag:agg-collector-max-delay" {
    deviate replace;
  }
  deviation "/ncs:devices/ncs:device/ncs:config/oc-if:interfaces/oc-if:interface/oc-if:config/ciena-ieee-lag:agg/ciena-ieee-lag:agg-collector-max-delay" {
    // NCS drop config false deviate replace
  }
  deviation "/ncs:devices/ncs:template/ncs:ned-id/ncs:config/oc-if:interfaces/oc-if:interface/oc-if:config/ciena-ieee-lag:agg/ciena-ieee-lag:member-ports/ciena-ieee-lag:agg-port-actor-system-priority" {
    // NCS drop config false deviate replace
  }
  deviation "/ncs:devices/ncs:device/ncs:live-status/oc-if:interfaces/oc-if:interface/oc-if:config/ciena-ieee-lag:agg/ciena-ieee-lag:member-ports/ciena-ieee-lag:agg-port-actor-system-priority" {
    deviate replace;
  }
  deviation "/ncs:devices/ncs:device/ncs:config/oc-if:interfaces/oc-if:interface/oc-if:config/ciena-ieee-lag:agg/ciena-ieee-lag:member-ports/ciena-ieee-lag:agg-port-actor-system-priority" {
    // NCS drop config false deviate replace
  }
  deviation "/ncs:devices/ncs:template/ncs:ned-id/ncs:config/oc-if:interfaces/oc-if:interface/oc-if:config/ciena-ieee-lag:agg/ciena-ieee-lag:member-ports/ciena-ieee-lag:agg-port-actor-admin-key" {
    // NCS drop config false deviate replace
  }
  deviation "/ncs:devices/ncs:device/ncs:live-status/oc-if:interfaces/oc-if:interface/oc-if:config/ciena-ieee-lag:agg/ciena-ieee-lag:member-ports/ciena-ieee-lag:agg-port-actor-admin-key" {
    deviate replace;
  }
  deviation "/ncs:devices/ncs:device/ncs:config/oc-if:interfaces/oc-if:interface/oc-if:config/ciena-ieee-lag:agg/ciena-ieee-lag:member-ports/ciena-ieee-lag:agg-port-actor-admin-key" {
    // NCS drop config false deviate replace
  }
  deviation "/ncs:devices/ncs:template/ncs:ned-id/ncs:config/oc-if:interfaces/oc-if:interface/oc-if:config/ciena-ieee-lag:agg/ciena-ieee-lag:member-ports/ciena-ieee-lag:agg-port-partner-admin-system-priority" {
    // NCS drop config false deviate replace
  }
  deviation "/ncs:devices/ncs:device/ncs:live-status/oc-if:interfaces/oc-if:interface/oc-if:config/ciena-ieee-lag:agg/ciena-ieee-lag:member-ports/ciena-ieee-lag:agg-port-partner-admin-system-priority" {
    deviate replace;
  }
  deviation "/ncs:devices/ncs:device/ncs:config/oc-if:interfaces/oc-if:interface/oc-if:config/ciena-ieee-lag:agg/ciena-ieee-lag:member-ports/ciena-ieee-lag:agg-port-partner-admin-system-priority" {
    // NCS drop config false deviate replace
  }
  deviation "/ncs:devices/ncs:template/ncs:ned-id/ncs:config/oc-if:interfaces/oc-if:interface/oc-if:config/ciena-ieee-lag:agg/ciena-ieee-lag:member-ports/ciena-ieee-lag:agg-port-partner-admin-system-ID" {
    // NCS drop config false deviate replace
  }
  deviation "/ncs:devices/ncs:device/ncs:live-status/oc-if:interfaces/oc-if:interface/oc-if:config/ciena-ieee-lag:agg/ciena-ieee-lag:member-ports/ciena-ieee-lag:agg-port-partner-admin-system-ID" {
    deviate replace;
  }
  deviation "/ncs:devices/ncs:device/ncs:config/oc-if:interfaces/oc-if:interface/oc-if:config/ciena-ieee-lag:agg/ciena-ieee-lag:member-ports/ciena-ieee-lag:agg-port-partner-admin-system-ID" {
    // NCS drop config false deviate replace
  }
  deviation "/ncs:devices/ncs:template/ncs:ned-id/ncs:config/oc-if:interfaces/oc-if:interface/oc-if:config/ciena-ieee-lag:agg/ciena-ieee-lag:member-ports/ciena-ieee-lag:agg-port-partner-admin-key" {
    // NCS drop config false deviate replace
  }
  deviation "/ncs:devices/ncs:device/ncs:live-status/oc-if:interfaces/oc-if:interface/oc-if:config/ciena-ieee-lag:agg/ciena-ieee-lag:member-ports/ciena-ieee-lag:agg-port-partner-admin-key" {
    deviate replace;
  }
  deviation "/ncs:devices/ncs:device/ncs:config/oc-if:interfaces/oc-if:interface/oc-if:config/ciena-ieee-lag:agg/ciena-ieee-lag:member-ports/ciena-ieee-lag:agg-port-partner-admin-key" {
    // NCS drop config false deviate replace
  }
  deviation "/ncs:devices/ncs:template/ncs:ned-id/ncs:config/oc-if:interfaces/oc-if:interface/oc-if:config/ciena-ieee-lag:agg/ciena-ieee-lag:member-ports/ciena-ieee-lag:agg-port-actor-port-priority" {
    // NCS drop config false deviate replace
  }
  deviation "/ncs:devices/ncs:device/ncs:live-status/oc-if:interfaces/oc-if:interface/oc-if:config/ciena-ieee-lag:agg/ciena-ieee-lag:member-ports/ciena-ieee-lag:agg-port-actor-port-priority" {
    deviate replace;
  }
  deviation "/ncs:devices/ncs:device/ncs:config/oc-if:interfaces/oc-if:interface/oc-if:config/ciena-ieee-lag:agg/ciena-ieee-lag:member-ports/ciena-ieee-lag:agg-port-actor-port-priority" {
    // NCS drop config false deviate replace
  }
  deviation "/ncs:devices/ncs:template/ncs:ned-id/ncs:config/oc-if:interfaces/oc-if:interface/oc-if:config/ciena-ieee-lag:agg/ciena-ieee-lag:member-ports/ciena-ieee-lag:agg-port-partner-admin-port" {
    // NCS drop config false deviate replace
  }
  deviation "/ncs:devices/ncs:device/ncs:live-status/oc-if:interfaces/oc-if:interface/oc-if:config/ciena-ieee-lag:agg/ciena-ieee-lag:member-ports/ciena-ieee-lag:agg-port-partner-admin-port" {
    deviate replace;
  }
  deviation "/ncs:devices/ncs:device/ncs:config/oc-if:interfaces/oc-if:interface/oc-if:config/ciena-ieee-lag:agg/ciena-ieee-lag:member-ports/ciena-ieee-lag:agg-port-partner-admin-port" {
    // NCS drop config false deviate replace
  }
  deviation "/ncs:devices/ncs:template/ncs:ned-id/ncs:config/oc-if:interfaces/oc-if:interface/oc-if:config/ciena-ieee-lag:agg/ciena-ieee-lag:member-ports/ciena-ieee-lag:agg-port-partner-admin-port-priority" {
    // NCS drop config false deviate replace
  }
  deviation "/ncs:devices/ncs:device/ncs:live-status/oc-if:interfaces/oc-if:interface/oc-if:config/ciena-ieee-lag:agg/ciena-ieee-lag:member-ports/ciena-ieee-lag:agg-port-partner-admin-port-priority" {
    deviate replace;
  }
  deviation "/ncs:devices/ncs:device/ncs:config/oc-if:interfaces/oc-if:interface/oc-if:config/ciena-ieee-lag:agg/ciena-ieee-lag:member-ports/ciena-ieee-lag:agg-port-partner-admin-port-priority" {
    // NCS drop config false deviate replace
  }
  deviation "/ncs:devices/ncs:template/ncs:ned-id/ncs:config/oc-if:interfaces/oc-if:interface/oc-if:config/ciena-ieee-lag:agg/ciena-ieee-lag:member-ports/ciena-ieee-lag:agg-port-actor-admin-state" {
    deviate not-supported;
  }
  deviation "/ncs:devices/ncs:device/ncs:live-status/oc-if:interfaces/oc-if:interface/oc-if:config/ciena-ieee-lag:agg/ciena-ieee-lag:member-ports/ciena-ieee-lag:agg-port-actor-admin-state" {
    deviate not-supported;
  }
  deviation "/ncs:devices/ncs:device/ncs:config/oc-if:interfaces/oc-if:interface/oc-if:config/ciena-ieee-lag:agg/ciena-ieee-lag:member-ports/ciena-ieee-lag:agg-port-actor-admin-state" {
    deviate not-supported;
  }
  deviation "/ncs:devices/ncs:template/ncs:ned-id/ncs:config/oc-if:interfaces/oc-if:interface/oc-if:config/ciena-ieee-lag:agg/ciena-ieee-lag:member-ports/ciena-ieee-lag:agg-port-partner-admin-state" {
    deviate not-supported;
  }
  deviation "/ncs:devices/ncs:device/ncs:live-status/oc-if:interfaces/oc-if:interface/oc-if:config/ciena-ieee-lag:agg/ciena-ieee-lag:member-ports/ciena-ieee-lag:agg-port-partner-admin-state" {
    deviate not-supported;
  }
  deviation "/ncs:devices/ncs:device/ncs:config/oc-if:interfaces/oc-if:interface/oc-if:config/ciena-ieee-lag:agg/ciena-ieee-lag:member-ports/ciena-ieee-lag:agg-port-partner-admin-state" {
    deviate not-supported;
  }
  deviation "/ncs:devices/ncs:template/ncs:ned-id/ncs:config/oc-if:interfaces/oc-if:interface/oc-if:config/ciena-ieee-lag:agg/ciena-ieee-lag:member-ports/ciena-ieee-lag:agg-port-protocol-DA" {
    deviate not-supported;
  }
  deviation "/ncs:devices/ncs:device/ncs:live-status/oc-if:interfaces/oc-if:interface/oc-if:config/ciena-ieee-lag:agg/ciena-ieee-lag:member-ports/ciena-ieee-lag:agg-port-protocol-DA" {
    deviate not-supported;
  }
  deviation "/ncs:devices/ncs:device/ncs:config/oc-if:interfaces/oc-if:interface/oc-if:config/ciena-ieee-lag:agg/ciena-ieee-lag:member-ports/ciena-ieee-lag:agg-port-protocol-DA" {
    deviate not-supported;
  }
  deviation "/ncs:devices/ncs:device/ncs:live-status/oc-if:interfaces/oc-if:interface/oc-if:state/ciena-ieee-lag:agg-state/ciena-ieee-lag:distribution-ports/ciena-ieee-lag:agg-port-debug-actor-churn-state" {
    deviate not-supported;
  }
  deviation "/ncs:devices/ncs:device/ncs:live-status/oc-if:interfaces/oc-if:interface/oc-if:state/ciena-ieee-lag:agg-state/ciena-ieee-lag:distribution-ports/ciena-ieee-lag:agg-port-debug-partner-churn-state" {
    deviate not-supported;
  }
  deviation "/ncs:devices/ncs:device/ncs:live-status/oc-if:interfaces/oc-if:interface/oc-if:state/ciena-ieee-lag:agg-state/ciena-ieee-lag:distribution-ports/ciena-ieee-lag:agg-port-debug-actor-churn-count" {
    deviate not-supported;
  }
  deviation "/ncs:devices/ncs:device/ncs:live-status/oc-if:interfaces/oc-if:interface/oc-if:state/ciena-ieee-lag:agg-state/ciena-ieee-lag:distribution-ports/ciena-ieee-lag:agg-port-debug-partner-churn-count" {
    deviate not-supported;
  }
  deviation "/ncs:devices/ncs:device/ncs:live-status/oc-if:interfaces/oc-if:interface/oc-if:state/ciena-ieee-lag:agg-state/ciena-ieee-lag:distribution-ports/ciena-ieee-lag:agg-port-debug-actor-sync-transition-count" {
    deviate not-supported;
  }
  deviation "/ncs:devices/ncs:device/ncs:live-status/oc-if:interfaces/oc-if:interface/oc-if:state/ciena-ieee-lag:agg-state/ciena-ieee-lag:distribution-ports/ciena-ieee-lag:agg-port-debug-partner-sync-transition-count" {
    deviate not-supported;
  }
  deviation "/ncs:devices/ncs:device/ncs:live-status/oc-if:interfaces/oc-if:interface/oc-if:state/ciena-ieee-lag:agg-state/ciena-ieee-lag:distribution-ports/ciena-ieee-lag:agg-port-debug-actor-change-count" {
    deviate not-supported;
  }
  deviation "/ncs:devices/ncs:device/ncs:live-status/oc-if:interfaces/oc-if:interface/oc-if:state/ciena-ieee-lag:agg-state/ciena-ieee-lag:distribution-ports/ciena-ieee-lag:agg-port-debug-partner-change-count" {
    deviate not-supported;
  }
  deviation "/ncs:devices/ncs:template/ncs:ned-id/ncs:config/ciena-ieee-lag:agg-global/ciena-ext-lag:flood-hash-mode" {
    deviate not-supported;
  }
  deviation "/ncs:devices/ncs:device/ncs:live-status/ciena-ieee-lag:agg-global/ciena-ext-lag:flood-hash-mode" {
    deviate not-supported;
  }
  deviation "/ncs:devices/ncs:device/ncs:config/ciena-ieee-lag:agg-global/ciena-ext-lag:flood-hash-mode" {
    deviate not-supported;
  }
  deviation "/ncs:devices/ncs:template/ncs:ned-id/ncs:config/oc-if:interfaces/oc-if:interface/oc-if:config/ciena-ieee-lag:agg/ciena-ext-lag:hash-mode" {
    deviate not-supported;
  }
  deviation "/ncs:devices/ncs:device/ncs:live-status/oc-if:interfaces/oc-if:interface/oc-if:config/ciena-ieee-lag:agg/ciena-ext-lag:hash-mode" {
    deviate not-supported;
  }
  deviation "/ncs:devices/ncs:device/ncs:config/oc-if:interfaces/oc-if:interface/oc-if:config/ciena-ieee-lag:agg/ciena-ext-lag:hash-mode" {
    deviate not-supported;
  }
}
