module ciena-bfd {
  // Generated by yanger -t ncs
  tailf:mount-id "ciena107s3-nc-1.0:ciena107s3-nc-1.0";
  tailf:ncs-device-type "netconf";

  namespace "http://ciena.com/ns/yang/ciena-bfd";
  prefix bfd;

  import openconfig-interfaces {
    prefix oc-if;
  }
  import ciena-mpls-tp-corouted {
    prefix mpls-tp;
  }
  import ciena-bfd-mpls {
    prefix bfd-mpls;
  }
  import ciena-bfd-types {
    prefix bfd-types;
  }
  import ietf-inet-types {
    prefix inet;
  }
  import ciena-vrf {
    prefix vrf;
  }
  import tailf-common {
    prefix tailf;
  }
  import tailf-ncs {
    prefix ncs;
  }

  organization
    "Ciena Corporation";
  contact
    "Web URL: http://www.ciena.com/
     E-mail:  yang@ciena.com
     Postal:  7035 Ridge Road
              Hanover, Maryland 21076
                  U.S.A.
     Phone:   +1 800-921-1144
     Fax:     +1 410-694-5750";
  description
    "This YANG module defines Ciena's specific BFD protocol.
     Copyright (c) 2019  Ciena Corporation.  All rights
     reserved.
     All information contained herein is, and remains the
     property of Ciena Corporation. Dissemination of this
     information or reproduction of this material is strictly
     forbidden unless prior written permission is obtained
     from Ciena Corporation.";

  revision 2021-07-15 {
    description
      "Added profiles and profile-state container.
       Added session-config-entry and session-config-entry-state containers.
       Added identity ipv6-unicast-address-type and a leaf destination-address-type
       for IPv6 address in session-config-entry.";
  }
  revision 2020-08-19 {
    description
      "Added Notification for BFD session state change.
       Added global-state container to get global bfd session statistics.
       Added session-summary information in bfd global-state container.
       Added a configurable global container.";
  }
  revision 2010-02-14 {
    description
      "Initial revision.";
  }

  augment "/ncs:devices/ncs:device/ncs:notifications/ncs:received-notifications/ncs:notification/ncs:data" {
    container bfd-notification {
      presence "";
      config false;
      description
        "Notification for BFD session state change.";
      leaf session-index {
        type uint32;
        description
          "An index used to uniquely identify BFD sessions.";
      }
      leaf session-type {
        type bfd-types:ncs_rpc_notif_bfd-session-type;
        description
          "BFD session type, this indicates the path type that BFD is
           running on";
      }
      leaf dest-addr {
        type inet:ip-address;
        description
          "IP address of the peer.";
      }
      leaf source-addr {
        type inet:ip-address;
        description
          "Local IP address.";
      }
      leaf interface {
        type string;
        description
          "L3 interface on which the BFD session is running.";
      }
      leaf tunnel-name {
        when "../session-type = 'tp-ingress-corout' or
../session-type = 'tp-egress-corout'" {
          tailf:xpath-root 6;
          description
            "Tunnel name applicable when session-type is tp-ingress-corout
             or tp-egress-corout.";
        }
        type string;
        description
          "Tunnel on which the BFD session is running.";
      }
      leaf local-state {
        type bfd-types:ncs_rpc_notif_state;
        description
          "Local state of the BFD session.";
      }
      leaf remote-state {
        type bfd-types:ncs_rpc_notif_state;
        description
          "Remote state of the BFD session.";
      }
    }
  }
  augment "/ncs:devices/ncs:device/ncs:netconf-notifications/ncs:received-notifications/ncs:notification/ncs:data" {
    container bfd-notification {
      presence "";
      config false;
      description
        "Notification for BFD session state change.";
      leaf session-index {
        type uint32;
        description
          "An index used to uniquely identify BFD sessions.";
      }
      leaf session-type {
        type bfd-types:ncs_rpc_notif_bfd-session-type;
        description
          "BFD session type, this indicates the path type that BFD is
           running on";
      }
      leaf dest-addr {
        type inet:ip-address;
        description
          "IP address of the peer.";
      }
      leaf source-addr {
        type inet:ip-address;
        description
          "Local IP address.";
      }
      leaf interface {
        type string;
        description
          "L3 interface on which the BFD session is running.";
      }
      leaf tunnel-name {
        when "../session-type = 'tp-ingress-corout' or
../session-type = 'tp-egress-corout'" {
          tailf:xpath-root 6;
          description
            "Tunnel name applicable when session-type is tp-ingress-corout
             or tp-egress-corout.";
        }
        type string;
        description
          "Tunnel on which the BFD session is running.";
      }
      leaf local-state {
        type bfd-types:ncs_rpc_notif_state;
        description
          "Local state of the BFD session.";
      }
      leaf remote-state {
        type bfd-types:ncs_rpc_notif_state;
        description
          "Remote state of the BFD session.";
      }
    }
  }
  augment "/ncs:devices/ncs:device/ncs:config" {
    container bfd {
      tailf:ncs-device-type "netconf";
      tailf:display-when "not(../../ncs:module) or ../../ncs:module[ncs:name='ciena-bfd']";
      description
        "BFD configuration and operational data.";
      container global {
        description
          "BFD global configuration data.";
        leaf admin-down {
          type boolean;
          default "false";
          description
            "Is BFD global administratively down.";
        }
      }
      // NCS drop config false container 'global-state'
      container profiles {
        description
          "BFD profiles";
        list ip-bfd-profile {
          description
            "List of IP BFD profiles.";
          key "name";
          uses bfd-types:profile-common-parms;
        }
        list mpls-bfd-profile {
          description
            "List of MPLS BFD profiles.";
          key "name";
          uses bfd-types:profile-common-parms;
          uses bfd-mpls:encap-cfg;
          leaf gach-type {
            type bfd-mpls:gach-value;
            description
              "GACH value for LSP BFD session";
          }
          leaf enable-cv {
            description
              "Enable Connectivity Verification (CV) feature ";
            when "../gach-type = 'mpls-tp-cc'" {
              tailf:xpath-root 3;
            }
            type empty;
          }
        }
      }
      // NCS drop config false container 'profiles-state'
      container session-config-entry {
        description
          "BFD session config entry.";
        container ip {
          description
            "Associate a BFD profile to IP-BFD session.";
          container single-hop {
            description
              "Associate a BFD profile to interface for a IP-SH BFD session.";
            list ipv4 {
              key "interface";
              description
                "List of IPv4 single-hop session configuration entries.";
              leaf interface {
                type leafref {
                  path "/ncs:devices/ncs:device/ncs:config/oc-if:interfaces/oc-if:interface/oc-if:name" {
                    tailf:xpath-root 3;
                  }
                }
                description
                  "L3 interface on which the BFD session is running.";
              }
              leaf profile {
                mandatory true;
                type leafref {
                  path "/ncs:devices/ncs:device/ncs:config/bfd:bfd/bfd:profiles/bfd:ip-bfd-profile/bfd:name" {
                    tailf:xpath-root 3;
                  }
                }
                description
                  "BFD profile to be used.";
              }
              uses bfd-types:bfd-session-config-entry-params;
            }
            list ipv6 {
              key "interface destination-address-type";
              description
                "List of IPv6 single-hop session configuration entries.";
              leaf interface {
                type leafref {
                  path "/ncs:devices/ncs:device/ncs:config/oc-if:interfaces/oc-if:interface/oc-if:name" {
                    tailf:xpath-root 3;
                  }
                }
                description
                  "L3 interface on which the BFD session is running.";
              }
              leaf destination-address-type {
                type identityref {
                  base ipv6-unicast-address-type;
                }
                description
                  "Address type for IPv6 address on which BFD session is running.";
              }
              leaf profile {
                mandatory true;
                type leafref {
                  path "/ncs:devices/ncs:device/ncs:config/bfd:bfd/bfd:profiles/bfd:ip-bfd-profile/bfd:name" {
                    tailf:xpath-root 3;
                  }
                }
                description
                  "BFD profile to be used.";
              }
              uses bfd-types:bfd-session-config-entry-params;
            }
          }
          container multi-hop {
            description
              "Associate a BFD profile to vrf-name:dest-name tuple for a IP-MH BFD session.";
            list vrf {
              key "vrfname";
              description
                "List of VRF entries";
              leaf vrfname {
                description
                  "VRF name";
                type leafref {
                  path "/ncs:devices/ncs:device/ncs:config/vrf:vrf/vrf:vrfName" {
                    tailf:xpath-root 3;
                  }
                }
              }
              list ipv4 {
                key "dest-addr";
                description
                  "List of IPv4 multi-hop session configuration entries.";
                leaf dest-addr {
                  type inet:ipv4-address;
                  description
                    "Destination IP address";
                }
                leaf profile {
                  mandatory true;
                  type leafref {
                    path "/ncs:devices/ncs:device/ncs:config/bfd:bfd/bfd:profiles/bfd:ip-bfd-profile/bfd:name" {
                      tailf:xpath-root 3;
                    }
                  }
                  description
                    "BFD profile to be used.";
                }
                uses bfd-types:bfd-session-config-entry-params;
              }
              list ipv6 {
                key "dest-addr";
                description
                  "List of IPv6 multi-hop session configuration entries.";
                leaf dest-addr {
                  type inet:ipv6-address;
                  description
                    "Destination IP address";
                }
                leaf profile {
                  mandatory true;
                  type leafref {
                    path "/ncs:devices/ncs:device/ncs:config/bfd:bfd/bfd:profiles/bfd:ip-bfd-profile/bfd:name" {
                      tailf:xpath-root 3;
                    }
                  }
                  description
                    "BFD profile to be used.";
                }
                uses bfd-types:bfd-session-config-entry-params;
              }
            }
          }
        }
      }
      // NCS drop config false container 'session-config-entry-state'
    }
  }
  augment "/ncs:devices/ncs:device/ncs:live-status" {
    container bfd {
      tailf:ncs-device-type "netconf";
      tailf:display-when "not(../../ncs:module) or ../../ncs:module[ncs:name='ciena-bfd'] or (../../ncs:live-status-protocol[not(ncs:capability)]) or (../../ncs:live-status-protocol/ncs:capability/ncs:module[.='ciena-bfd'])";
      description
        "BFD configuration and operational data.";
      container global {
        description
          "BFD global configuration data.";
        leaf admin-down {
          type boolean;
          // NCS drop default statement
          description
            "Is BFD global administratively down.";
        }
      }
      container global-state {
        description
          "Bfd global operational data.";
        container ipv4-bfd-summary {
          description
            "Ipv4 bfd session summary.";
          uses bfd-types:live_ncs_session-statistics-summary;
        }
        container ipv6-bfd-summary {
          description
            "Ipv6 bfd session summary.";
          uses bfd-types:live_ncs_session-statistics-summary;
        }
        container lsp-bfd-summary {
          description
            "Lsp bfd session summary.";
          uses bfd-types:live_ncs_session-statistics-summary;
        }
      }
      container profiles {
        description
          "BFD profiles";
        list ip-bfd-profile {
          description
            "List of IP BFD profiles.";
          key "name";
          uses bfd-types:live_ncs_profile-common-parms;
        }
        list mpls-bfd-profile {
          description
            "List of MPLS BFD profiles.";
          key "name";
          uses bfd-types:live_ncs_profile-common-parms;
          uses bfd-mpls:live_ncs_encap-cfg;
          leaf gach-type {
            type bfd-mpls:live_ncs_gach-value;
            description
              "GACH value for LSP BFD session";
          }
          leaf enable-cv {
            description
              "Enable Connectivity Verification (CV) feature ";
            // NCS drop when statement
            type empty;
          }
        }
      }
      container profiles-state {
        description
          "BFD profiles state";
        list ip-bfd-profile {
          description
            "List of IP BFD profile.";
          key "name";
          uses bfd-types:live_ncs_profile-common-parms;
          leaf num-of-ref {
            type uint16;
            description
              "Number of BFD map referring the given profile.";
          }
        }
        list mpls-bfd-profile {
          description
            "List of MPLS BFD profile.";
          key "name";
          uses bfd-types:live_ncs_profile-common-parms;
          uses bfd-mpls:live_ncs_encap-cfg;
          leaf gach-type {
            type bfd-mpls:live_ncs_gach-value;
            description
              "GACH value for LSP BFD session";
          }
          leaf enable-cv {
            description
              "Enable Connectivity Verification(CV) feature ";
            // NCS drop when statement
            type empty;
          }
          leaf num-of-ref {
            type uint16;
            description
              "Number of BFD map referring the given profile.";
          }
        }
      }
      container session-config-entry {
        description
          "BFD session config entry.";
        container ip {
          description
            "Associate a BFD profile to IP-BFD session.";
          container single-hop {
            description
              "Associate a BFD profile to interface for a IP-SH BFD session.";
            list ipv4 {
              key "interface";
              description
                "List of IPv4 single-hop session configuration entries.";
              leaf interface {
                type leafref {
                  path "/ncs:devices/ncs:device/ncs:live-status/oc-if:interfaces/oc-if:interface/oc-if:name" {
                    tailf:xpath-root 3;
                  }
                }
                description
                  "L3 interface on which the BFD session is running.";
              }
              leaf profile {
                // NCS drop mandatory statement
                type leafref {
                  path "/ncs:devices/ncs:device/ncs:live-status/bfd:bfd/bfd:profiles/bfd:ip-bfd-profile/bfd:name" {
                    tailf:xpath-root 3;
                  }
                }
                description
                  "BFD profile to be used.";
              }
              uses bfd-types:live_ncs_bfd-session-config-entry-params;
            }
            list ipv6 {
              key "interface destination-address-type";
              description
                "List of IPv6 single-hop session configuration entries.";
              leaf interface {
                type leafref {
                  path "/ncs:devices/ncs:device/ncs:live-status/oc-if:interfaces/oc-if:interface/oc-if:name" {
                    tailf:xpath-root 3;
                  }
                }
                description
                  "L3 interface on which the BFD session is running.";
              }
              leaf destination-address-type {
                type identityref {
                  base ipv6-unicast-address-type;
                }
                description
                  "Address type for IPv6 address on which BFD session is running.";
              }
              leaf profile {
                // NCS drop mandatory statement
                type leafref {
                  path "/ncs:devices/ncs:device/ncs:live-status/bfd:bfd/bfd:profiles/bfd:ip-bfd-profile/bfd:name" {
                    tailf:xpath-root 3;
                  }
                }
                description
                  "BFD profile to be used.";
              }
              uses bfd-types:live_ncs_bfd-session-config-entry-params;
            }
          }
          container multi-hop {
            description
              "Associate a BFD profile to vrf-name:dest-name tuple for a IP-MH BFD session.";
            list vrf {
              key "vrfname";
              description
                "List of VRF entries";
              leaf vrfname {
                description
                  "VRF name";
                type leafref {
                  path "/ncs:devices/ncs:device/ncs:live-status/vrf:vrf/vrf:vrfName" {
                    tailf:xpath-root 3;
                  }
                }
              }
              list ipv4 {
                key "dest-addr";
                description
                  "List of IPv4 multi-hop session configuration entries.";
                leaf dest-addr {
                  type inet:ipv4-address;
                  description
                    "Destination IP address";
                }
                leaf profile {
                  // NCS drop mandatory statement
                  type leafref {
                    path "/ncs:devices/ncs:device/ncs:live-status/bfd:bfd/bfd:profiles/bfd:ip-bfd-profile/bfd:name" {
                      tailf:xpath-root 3;
                    }
                  }
                  description
                    "BFD profile to be used.";
                }
                uses bfd-types:live_ncs_bfd-session-config-entry-params;
              }
              list ipv6 {
                key "dest-addr";
                description
                  "List of IPv6 multi-hop session configuration entries.";
                leaf dest-addr {
                  type inet:ipv6-address;
                  description
                    "Destination IP address";
                }
                leaf profile {
                  // NCS drop mandatory statement
                  type leafref {
                    path "/ncs:devices/ncs:device/ncs:live-status/bfd:bfd/bfd:profiles/bfd:ip-bfd-profile/bfd:name" {
                      tailf:xpath-root 3;
                    }
                  }
                  description
                    "BFD profile to be used.";
                }
                uses bfd-types:live_ncs_bfd-session-config-entry-params;
              }
            }
          }
        }
      }
      container session-config-entry-state {
        description
          "BFD session state for BFD provisioning";
        container ip {
          description
            "IP BFD session config entry state";
          container single-hop {
            description
              "IP-SH session config entry state";
            list ipv4 {
              key "interface";
              description
                "List of IPv4 single-hop session configuration entries.";
              leaf interface {
                type leafref {
                  path "/ncs:devices/ncs:device/ncs:live-status/oc-if:interfaces/oc-if:interface/oc-if:name" {
                    tailf:xpath-root 3;
                  }
                }
                description
                  "L3 interface on which the BFD session is running.";
              }
              leaf profile {
                type leafref {
                  path "/ncs:devices/ncs:device/ncs:live-status/bfd:bfd/bfd:profiles/bfd:ip-bfd-profile/bfd:name" {
                    tailf:xpath-root 3;
                  }
                }
                description
                  "BFD profile to be used.";
              }
              uses bfd-types:live_ncs_bfd-session-config-entry-params;
            }
            list ipv6 {
              key "interface destination-address-type";
              description
                "List of IPv6 single-hop session configuration entries.";
              leaf interface {
                type leafref {
                  path "/ncs:devices/ncs:device/ncs:live-status/oc-if:interfaces/oc-if:interface/oc-if:name" {
                    tailf:xpath-root 3;
                  }
                }
                description
                  "L3 interface on which the BFD session is running.";
              }
              leaf destination-address-type {
                type identityref {
                  base ipv6-unicast-address-type;
                }
                description
                  "Address type for IPv6 address on which BFD session is running.";
              }
              leaf profile {
                type leafref {
                  path "/ncs:devices/ncs:device/ncs:live-status/bfd:bfd/bfd:profiles/bfd:ip-bfd-profile/bfd:name" {
                    tailf:xpath-root 3;
                  }
                }
                description
                  "BFD profile to be used.";
              }
              uses bfd-types:live_ncs_bfd-session-config-entry-params;
            }
          }
          container multi-hop {
            description
              "IP-MH session config entry state";
            list vrf {
              key "vrfname";
              description
                "List of VRF entries";
              leaf vrfname {
                description
                  "VRF name";
                type leafref {
                  path "/ncs:devices/ncs:device/ncs:live-status/vrf:vrf/vrf:vrfName" {
                    tailf:xpath-root 3;
                  }
                }
              }
              list ipv4 {
                key "dest-addr";
                description
                  "List of IPv4 multi-hop session configuration entries.";
                leaf dest-addr {
                  type inet:ipv4-address;
                  description
                    "Destination IP address";
                }
                leaf profile {
                  type leafref {
                    path "/ncs:devices/ncs:device/ncs:live-status/bfd:bfd/bfd:profiles/bfd:ip-bfd-profile/bfd:name" {
                      tailf:xpath-root 3;
                    }
                  }
                  description
                    "BFD profile to be used.";
                }
                uses bfd-types:live_ncs_bfd-session-config-entry-params;
              }
              list ipv6 {
                key "dest-addr";
                description
                  "List of IPv6 multi-hop session configuration entries.";
                leaf dest-addr {
                  type inet:ipv6-address;
                  description
                    "Destination IP address";
                }
                leaf profile {
                  type leafref {
                    path "/ncs:devices/ncs:device/ncs:live-status/bfd:bfd/bfd:profiles/bfd:ip-bfd-profile/bfd:name" {
                      tailf:xpath-root 3;
                    }
                  }
                  description
                    "BFD profile to be used.";
                }
                uses bfd-types:live_ncs_bfd-session-config-entry-params;
              }
            }
          }
        }
      }
    }
  }
  augment "/ncs:devices/ncs:template/ncs:ned-id/ncs:config" {
    container bfd {
      description
        "BFD configuration and operational data.";
      container global {
        description
          "BFD global configuration data.";
        leaf admin-down {
          type string;
          // NCS drop default statement
          description
            "Is BFD global administratively down.";
        }
      }
      // NCS drop config false container 'global-state'
      container profiles {
        description
          "BFD profiles";
        list ip-bfd-profile {
          // NCS patched for predictable order
          ordered-by user;
          description
            "List of IP BFD profiles.";
          key "name";
          uses bfd-types:ncs_template_profile-common-parms;
        }
        list mpls-bfd-profile {
          // NCS patched for predictable order
          ordered-by user;
          description
            "List of MPLS BFD profiles.";
          key "name";
          uses bfd-types:ncs_template_profile-common-parms;
          uses bfd-mpls:ncs_template_encap-cfg;
          leaf gach-type {
            type bfd-mpls:ncs_template_gach-value;
            description
              "GACH value for LSP BFD session";
          }
          leaf enable-cv {
            description
              "Enable Connectivity Verification (CV) feature ";
            // NCS drop when statement
            type empty;
          }
        }
      }
      // NCS drop config false container 'profiles-state'
      container session-config-entry {
        description
          "BFD session config entry.";
        container ip {
          description
            "Associate a BFD profile to IP-BFD session.";
          container single-hop {
            description
              "Associate a BFD profile to interface for a IP-SH BFD session.";
            list ipv4 {
              // NCS patched for predictable order
              ordered-by user;
              key "interface";
              description
                "List of IPv4 single-hop session configuration entries.";
              leaf interface {
                type string;
                description
                  "L3 interface on which the BFD session is running.";
              }
              leaf profile {
                // NCS drop mandatory statement
                type string;
                description
                  "BFD profile to be used.";
              }
              uses bfd-types:ncs_template_bfd-session-config-entry-params;
            }
            list ipv6 {
              // NCS patched for predictable order
              ordered-by user;
              key "interface destination-address-type";
              description
                "List of IPv6 single-hop session configuration entries.";
              leaf interface {
                type string;
                description
                  "L3 interface on which the BFD session is running.";
              }
              leaf destination-address-type {
                type string;
                description
                  "Address type for IPv6 address on which BFD session is running.";
              }
              leaf profile {
                // NCS drop mandatory statement
                type string;
                description
                  "BFD profile to be used.";
              }
              uses bfd-types:ncs_template_bfd-session-config-entry-params;
            }
          }
          container multi-hop {
            description
              "Associate a BFD profile to vrf-name:dest-name tuple for a IP-MH BFD session.";
            list vrf {
              // NCS patched for predictable order
              ordered-by user;
              key "vrfname";
              description
                "List of VRF entries";
              leaf vrfname {
                description
                  "VRF name";
                type string;
              }
              list ipv4 {
                // NCS patched for predictable order
                ordered-by user;
                key "dest-addr";
                description
                  "List of IPv4 multi-hop session configuration entries.";
                leaf dest-addr {
                  type string;
                  description
                    "Destination IP address";
                }
                leaf profile {
                  // NCS drop mandatory statement
                  type string;
                  description
                    "BFD profile to be used.";
                }
                uses bfd-types:ncs_template_bfd-session-config-entry-params;
              }
              list ipv6 {
                // NCS patched for predictable order
                ordered-by user;
                key "dest-addr";
                description
                  "List of IPv6 multi-hop session configuration entries.";
                leaf dest-addr {
                  type string;
                  description
                    "Destination IP address";
                }
                leaf profile {
                  // NCS drop mandatory statement
                  type string;
                  description
                    "BFD profile to be used.";
                }
                uses bfd-types:ncs_template_bfd-session-config-entry-params;
              }
            }
          }
        }
      }
      // NCS drop config false container 'session-config-entry-state'
    }
  }

  identity global-unicast {
    base ipv6-unicast-address-type;
    description
      "Global Unicast as address type.";
  }

  identity link-local-unicast {
    base ipv6-unicast-address-type;
    description
      "Link Local Unicast as address type";
  }

  identity ipv6-unicast-address-type {
    description
      "IPv6 unicast address types";
  }
}
