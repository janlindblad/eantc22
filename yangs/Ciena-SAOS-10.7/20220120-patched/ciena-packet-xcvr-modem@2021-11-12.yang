module ciena-packet-xcvr-modem {
  namespace "http://www.ciena.com/ns/yang/ciena-packet-xcvr-modem";
  prefix xcvr-modem;

  import ciena-packet-typedefs {
    prefix cntypes;
  }
  import ciena-packet-xcvr {
    prefix xcvr;
  }

  organization
    "Ciena Corporation";
  contact
    "Web URL: http://www.ciena.com/
     Postal:  7035 Ridge Road
             Hanover, Maryland 21076
             U.S.A.
     Phone:   +1 800-921-1144
     Fax:     +1 410-694-5750";
  description
    "This YANG module defines Ciena's XCVR modem specific data for the NETCONF protocol. It will augment the ciena-packet-xcvr module.";

  revision 2021-11-12 {
    description
      "Changing type of frequency-resolution leaf from uint32 to decimal64";
  }

  revision 2018-05-17 {
    description
      "Based off of ciena-waveserver-xcvr-modem.yang";
  }
  augment "/xcvr:xcvrs/xcvr:xcvr/xcvr:properties/xcvr:vendor-data/xcvr:properties/xcvr:diagnostic-monitoring" {
    when "../../../xcvr:type = 'WaveLogic Ai'" {
      description
        "XCVR vendor diagnostic-monitoring properties specific to modem XCVRs.";
    }
    description
      "XCVR vendor diagnostic-monitoring properties specific to modem XCVRs.";
    leaf diagnostic-support {
      type cntypes:yes-no-enum;
      config false;
      description
        "Diagnostic Monitoring, is Diagnostic Support turned on.";
    }
    leaf dispersion-measurement {
      type cntypes:yes-no-enum;
      config false;
      description
        "Diagnostic Monitoring, is Dispersion Measurement turned on.";
    }
  }
  augment "/xcvr:xcvrs/xcvr:xcvr/xcvr:properties/xcvr:vendor-data/xcvr:properties" {
    description
      "XCVR vendor properties specific to modem XCVRs.";

    container transmitter-technology {
      config false;
      description
        "Modem Transmitter Technology properties/capabilities.";
      leaf tunable {
        type cntypes:yes-no-enum;
        config false;
        description
          "Modem Transmitter Technology, Tunable.";
      }
      leaf wavelength-min {
        type cntypes:decimal-2-dig;
        units "nm";
        config false;
        description
          "Modem Transmitter Technology, Wavelength Min value, in nanometers.";
      }
      leaf wavelength-max {
        type cntypes:decimal-2-dig;
        units "nm";
        config false;
        description
          "Modem Transmitter Technology, Wavelength Max value, in nanometers.";
      }
      leaf frequency-min {
        type cntypes:modem-frequency;
        units "GHz";
        config false;
        description
          "Modem Transmitter Technology, minimum supported frequency, in GHz.";
      }
      leaf frequency-max {
        type cntypes:modem-frequency;
        units "GHz";
        config false;
        description
          "Modem Transmitter Technology, maximum supported frequency, in GHz.";
      }
      leaf frequency-resolution {
        type decimal64 {
          fraction-digits 2;
        }
        units "MHz";
        config false;
        description
          "Modem Transmitter Technology, frequency resolution, in MHz.";
      }
      leaf tx-dispersion-min {
        type int32;
        units "ps/nm";
        config false;
        description
          "Modem Transmitter Technology, Tx Dispersion Min (ps/nm).";
      }
      leaf tx-dispersion-max {
        type int32;
        units "ps/nm";
        config false;
        description
          "Modem Transmitter Technology, Tx Dispersion Max (ps/nm).";
      }
      leaf edfa {
        type cntypes:yes-no-enum;
        config false;
        description
          "Whether this modem is an EDFA modem.";
      }
      leaf c-band {
        type cntypes:yes-no-enum;
        config false;
        description
          "Whether this modem supports C-Band frequencies.";
      }
      leaf l-band {
        type cntypes:yes-no-enum;
        config false;
        description
          "Whether this modem supports L-Band frequencies.";
      }
    }
  }
  augment "/xcvr:xcvrs/xcvr:xcvr/xcvr:properties/xcvr:vendor-data/xcvr:properties/xcvr:supported-modes" {
    when "../../../xcvr:type = 'WaveLogic Ai'" {
      description
        "XCVR supported-mode properties specific to modem XCVRs.";
    }
    description
      "XCVR supported-mode properties specific to modem XCVRs.";

    leaf default-link-optimization-mode {
      type cntypes:link-optimization-mode;
      description
        "The default link optimization mode for this XCVR mode.";
    }
    leaf supported-link-optimization-modes {
      type cntypes:supported-link-optimization-modes;
      description
        "The set of supported link optimization modes for this XCVR mode.";
    }
  }
  augment "/xcvr:xcvrs/xcvr:xcvr/xcvr:properties/xcvr:diagnostics/xcvr:device" {
    description
      "XCVR device diagnostic properties specific to modem XCVRs.";
    container equipment-status {
      config false;
      description
        "XCVR modem equipment status properties.";
      leaf transmitter-state {
        type cntypes:enabled-disabled-enum;
        config false;
        description
          "Transmitter State of the Modem.";
      }
      leaf equipment-out-of-spec {
        type cntypes:yes-no-enum;
        config false;
        description
          "Is the alarm associated with Equipment Out of Spec raised.";
      }
      leaf temperature-critical {
        type cntypes:yes-no-enum;
        config false;
        description
          "Is there a critical temperature alarm currently raised.";
      }
      leaf temperature-warning {
        type cntypes:yes-no-enum;
        config false;
        description
          "Is there a temperature warning currently raised.";
      }
      leaf equipment-failure {
        type cntypes:yes-no-enum;
        config false;
        description
          "Is the alarm associated with Equipment Failure raised.";
      }
      leaf data-link-suspect {
        type cntypes:yes-no-enum;
        config false;
        description
          "Is the alarm associated with Data Link Suspect raised.";
      }
      leaf comms-link-suspect {
        type cntypes:yes-no-enum;
        config false;
        description
          "Is the alarm associated with Comms Link Suspect raised.";
      }
      leaf clock-suspect {
        type cntypes:yes-no-enum;
        config false;
        description
          "Is the alarm associated with Clock Suspect raised.";
      }
      leaf loss-of-synchronization-tick {
        type cntypes:yes-no-enum;
        config false;
        description
          "Is the alarm associated with Loss of Synchronization Tick raised.";
      }
    }
  }
}
