/*
Copyright (C) 2020 Huawei Technologies Co., Ltd. All rights reserved.
*/
module huawei-openconfig-if-aggregate-deviations-NE8000 {
  yang-version 1;
  namespace "urn:huawei:yang:huawei-openconfig-if-aggregate-deviations-NE8000";
  prefix of-if-aggregate-devs-NE8000;

  import openconfig-interfaces {
    prefix oc-if;
  }
  import openconfig-if-aggregate {
    prefix oc-lag;
  }
  import openconfig-if-ethernet {
    prefix oc-eth;
  }
  import iana-if-type {
    prefix ianaift;
  }

  organization
    "Huawei Technologies Co., Ltd.";
  contact
    "Huawei Industrial Base
     Bantian, Longgang
     Shenzhen 518129
     People's Republic of China
     Website: http://www.huawei.com
     Email: support@huawei.com";
  description
    "Common interface management, which includes the public configuration of interfaces.";

  revision 2020-06-17 {
    description
      "Initial revision.";
    reference "Huawei private.";
  }

  deviation "/oc-if:interfaces/oc-if:interface/oc-lag:aggregation/oc-lag:config/oc-lag:lag-type" {
    deviate add {
      default "STATIC";
    }
  }
  deviation "/oc-if:interfaces/oc-if:interface/oc-lag:aggregation/oc-lag:config/oc-lag:min-links" {
    deviate add {
      default "1";
    }
    deviate replace {
      type uint16 {
        range "1..64";
      }
    }
  }
  deviation "/oc-if:interfaces/oc-if:interface/oc-lag:aggregation/oc-lag:state/oc-lag:lag-speed" {
    deviate not-supported;
  }
  deviation "/oc-if:interfaces/oc-if:interface/oc-lag:aggregation/oc-lag:state/oc-lag:member" {
    deviate not-supported;
  }
  deviation "/oc-if:interfaces/oc-if:interface/oc-eth:ethernet/oc-eth:config/oc-lag:aggregate-id" {
    deviate add {
      must "../../../oc-if:config/oc-if:type = 'ianaift:ethernetCsmacd' and /oc-if:interfaces/oc-if:interface[oc-if:name = current()]/oc-if:config/oc-if:type = 'ianaift:ieee8023adLag' ";
    }
  }
}
