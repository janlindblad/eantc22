/*
Copyright (C) 2019 Huawei Technologies Co., Ltd. All rights reserved.
*/
submodule huawei-diagnostic-tools-tcp {
  yang-version 1;
  belongs-to huawei-diagnostic-tools {
    prefix diagnostic-tools;
  }
  import huawei-pub-type {
    prefix pub-type;
  }
  import ietf-inet-types {
    prefix inet;
  }
  import huawei-network-instance {
    prefix ni;
  }
  import huawei-extension {
    prefix ext;
  }

  include huawei-diagnostic-tools-common;
  include huawei-diagnostic-tools-type;
  organization
    "Huawei Technologies Co., Ltd.";
  contact
    "Huawei Industrial Base
     Bantian, Longgang
     Shenzhen 518129
     People's Republic of China
     Website: http://www.huawei.com
     Email: support@huawei.com";

description
     "TCP diagnosis tool.";
  revision 2019-04-13 {
    description
      "Initial revision.";
    reference
      "Huawei private.";
  }

  grouping tcp-test-result-type {
    description
      "TCP test results.";
    container ping-results {
      config false;
      description
        "List of TCP ping results.";
      list ping-result {
        key "test-name";
        config false;
        description
          "Statistics of TCP ping result.";
        leaf test-name {
          type string {
            length "1..32";
          }
          config false;
          description
            "Test name.";
        }
        leaf packet-send {
          type uint32;
          units "packet"; 
          config false;
          description
            "Total number of sent packets.";
        }
        leaf packet-receive {
          type uint32;
          units "packet"; 
          config false;
          description
            "Total number of received packets.";
        }
        leaf loss-ratio {
          type pub-type:percent {
            range "0..100";
          }
          units "%";
          config false;
          description
            "Packet loss ratio of a test.";
        }
        leaf rtt-min {
          type uint32;
          units "ms";
          config false;
          description
            "Minimum RTT of all test packets.";
        }
        leaf rtt-max {
          type uint32;
          units "ms";
          config false;
          description
            "Maximum RTT of all test packets.";
        }
        leaf rtt-average {
          type uint32;
          units "ms";
          config false;
          description
            "Average RTT of all test packets.";
        }
        leaf status {
          type dgntl-test-status-type;
          config false;
          description
            "Test status.";
        }
        container probes {
          config false;
          description
            "List of ping results of all packets in a test.";				
          list probe {
            key "sequence";
            config false;
            description
              "Statistics of ping result of a single packet in a test.";
            leaf sequence {
              type uint32;
              config false;
              description
                "Serial number of a test packet received.";
            }
            leaf replier {
              type inet:ipv4-address-no-zone;
              config false;
              description
                "Destination address of the related hop in a test.";
            }
            leaf rtt {
              type uint32;
              units "ms";
              config false;
              description
                "RTT of test packets.";
            }
            leaf result-type  {
              type probe-result-type;
              config false;
              description
                "Result of packet sending.";
            }
            leaf is-delete {
              type boolean;
              config false;
              description
                "Enable/disable the function of deleting test results.";
            }
          }
        }
      }
    }
  }
  rpc tcp-start-ping {
    description
      "Start TCP ping.";
    input  {
      leaf test-name {
        type string {
          length "1..32";
        }
        mandatory true;
        description
          "Test name.";
      }
      leaf destination {
        type pub-type:host-name;
        mandatory true;
        description
          "Destination address of the string type.";
      }
      leaf timeout {
        type uint32 {
          range "0..65535";
        }
        units "ms";
        default "2000";
        description
          "Time to wait for a response packet after a test packet is sent.";
      }
      leaf count {
        type uint32 {
          range "1..4294967295";
        }
        units "packet";
        default "5";
        description
          "Number of sent test packets.";
      }
      leaf interval {
        type uint32 {
          range "1..10000";
        }
        units "ms";
        default "500";
        description
          "Interval for sending test packets.";
      }
      leaf ttl {
        type uint32 {
          range "1..255";
        }
        default "30";
        description
          "Time to live.";
      }
      leaf pass-route {
        type boolean;
        default "false";
        description
          "Send packet pass route.";
      }
      leaf ni-name {
        type leafref {
          path "/ni:network-instance/ni:instances/ni:instance/ni:name";
        }
        description
          "Name of a VPN instance.";
      }
      leaf dest-port {
        type uint32 {
          range "1..65535";
        }
        default "7";
        description
          "Destination TCP port.";
      }
      leaf source-address {
        type inet:ipv4-address-no-zone;
        description
          "Source address.";
      }	  
    }
  }
  rpc tcp-stop-ping {
    description
      "Stop TCP ping.";
    ext:node-ref "/diagnostic-tools:diagnostic-tools/diagnostic-tools:tcp/diagnostic-tools:ping-results/diagnostic-tools:ping-result";
    input  {
      leaf test-name {
        type leafref {
          path "/diagnostic-tools:diagnostic-tools/diagnostic-tools:tcp/diagnostic-tools:ping-results/diagnostic-tools:ping-result/diagnostic-tools:test-name";
        }
        mandatory true;
        description
          "Test name.";
      }
    }
  }
  rpc tcp-delete-ping {
    description
      "Delete TCP ping.";
    ext:node-ref "/diagnostic-tools:diagnostic-tools/diagnostic-tools:tcp/diagnostic-tools:ping-results/diagnostic-tools:ping-result";
    input  {
      leaf test-name {
        type leafref {
          path "/diagnostic-tools:diagnostic-tools/diagnostic-tools:tcp/diagnostic-tools:ping-results/diagnostic-tools:ping-result/diagnostic-tools:test-name";
        }
        mandatory true;
        description
          "Test name.";
      }
    }
  }

  augment /diagnostic-tools:diagnostic-tools {
    description
      "List of TCP tests.";
    container tcp {
      config false;
      description
        "Statistics of TCP tests.";
      uses tcp-test-result-type;
    }
  }    
}
