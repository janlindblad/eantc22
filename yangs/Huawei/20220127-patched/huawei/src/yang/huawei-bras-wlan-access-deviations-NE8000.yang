/*
Copyright (C) 2019 Huawei Technologies Co., Ltd. All rights reserved.
*/
module huawei-bras-wlan-access-deviations-NE8000 {
  namespace "urn:huawei:yang:huawei-bras-wlan-access-deviations-NE8000";
  prefix bras-wlan-access-devs-NE8000;

  import huawei-bras-wlan-access {
    prefix bras-wlan-access;
  }

  import huawei-ifm {
    prefix ifm;
  }

  import huawei-bras-basic-access {
    prefix bras-basic-access;
  }

  organization
    "Huawei Technologies Co., Ltd.";

  contact
    "Huawei Industrial Base
     Bantian, Longgang
     Shenzhen 518129
     People's Republic of China
     Website: http://www.huawei.com
     Email: support@huawei.com";

  description
    "This module defines deviation statements for huawei-bras-wlan-access module.";

  revision 2019-11-06 {
    description
      "Initial revision.";
    reference
      "Huawei private.";
  }

  deviation "/ifm:ifm/ifm:interfaces/ifm:interface/bras-basic-access:bas/bras-basic-access:access-type/bras-basic-access:layer2-subscriber/bras-basic-access:layer2-subscriber/bras-wlan-access:wlan-option82-decode-ssid/bras-wlan-access:mode/bras-wlan-access:huawei/bras-wlan-access:huawei" {
    deviate not-supported;
  }

}
