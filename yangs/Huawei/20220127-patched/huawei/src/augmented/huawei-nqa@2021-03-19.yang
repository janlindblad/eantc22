module huawei-nqa {
  // Generated by yanger -t ncs
  tailf:mount-id "huawei-nc-1.0:huawei-nc-1.0";
  tailf:ncs-device-type "netconf";

  yang-version 1;
  namespace "urn:huawei:yang:huawei-nqa";
  prefix nqa;

  import huawei-pub-type {
    prefix pub-type;
  }
  import huawei-extension {
    prefix ext;
  }
  import huawei-ifm {
    prefix ifm;
  }
  include huawei-nqa-global;
  include huawei-nqa-server;
  include huawei-nqa-instance;
  include huawei-nqa-reflector;
  include huawei-nqa-record;
  import tailf-common {
    prefix tailf;
  }
  import tailf-ncs {
    prefix ncs;
  }
  import ietf-inet-types {
    prefix inet;
  }
  import ietf-yang-types {
    prefix yang;
  }

  organization
    "Huawei Technologies Co., Ltd.";
  contact
    "Huawei Industrial Base
     Bantian, Longgang
     Shenzhen 518129
     People's Republic of China
     Website: http://www.huawei.com
     Email: support@huawei.com";
  description
    "Network quality analysis.";

  revision 2021-03-19 {
    description
      "Modify default-value of probe-count, jitter-packet-num, and data-size in a jitter test instance.";
    reference "Huawei private.";
  }
  revision 2020-09-24 {
    description
      "Add MAC ping test instance and modify jitter-results.";
    reference "Huawei private.";
  }
  revision 2020-07-04 {
    description
      "Add BIERv6 OAM.";
    reference "Huawei private.";
  }
  revision 2020-06-30 {
    description
      "Add rpc for nqa execution policy.";
    reference "Huawei private.";
  }
  revision 2019-10-25 {
    description
      "Initial revision.";
    reference "Huawei private.";
  }
  ext:task-name "sla";

  augment "/ncs:devices/ncs:device/ncs:rpc" {
    container rpc-test-instance-execution {
      tailf:ncs-device-type "netconf";
      tailf:display-when "not(../../ncs:module) or ../../ncs:module[ncs:name='huawei-nqa']";
      tailf:action test-instance-execution {
        tailf:actionpoint ncsproxy {
          tailf:internal;
        }
        description
          "The test instance execution.";
        ext:node-ref "/nqa:nqa/nqa:instances/nqa:instance";
        input {
          leaf admin-name {
            type string;
            mandatory true;
            description
              "Administrator name.";
          }
          leaf test-name {
            type string;
            mandatory true;
            description
              "Test name.";
          }
          choice execution-policy {
            description
              "The test instance start policy.";
            case start {
              description
                "Start the test.";
              choice start-type {
                description
                  "The test instance start type.";
                case start-now {
                  description
                    "Start the test now.";
                  leaf start-now {
                    type empty;
                    mandatory true;
                    description
                      "Receive the command then start the test.";
                  }
                  choice start-now-end-type {
                    description
                      "Test instance end type.";
                    case at {
                      description
                        "Stop the test at the specified time.";
                      leaf start-now-end-time {
                        type pub-type:ncs_rpc_notif_time;
                        mandatory true;
                        description
                          "The test instance end time.";
                      }
                      leaf start-now-end-date {
                        type pub-type:ncs_rpc_notif_date;
                        description
                          "The test instance end date.";
                      }
                    }
                    case delay {
                      description
                        "Stop the test after the specified delay time.";
                      choice start-now-end-delay-type {
                        mandatory true;
                        description
                          "The test instance end delay type.";
                        case end-delay-time {
                          description
                            "The test instance end delay time.";
                          leaf start-now-end-delay-time {
                            type pub-type:ncs_rpc_notif_time;
                            description
                              "The test instance end delay time.";
                          }
                        }
                        case end-delay-seconds {
                          description
                            "The test instance end delay seconds.";
                          leaf start-now-end-delay-seconds {
                            type uint32 {
                              range "6..86399";
                            }
                            units "s";
                            description
                              "The test instance end delay seconds.";
                          }
                        }
                      }
                    }
                    case lifetime {
                      description
                        "Stop the test after the specified life time.";
                      choice start-now-end-lifetime-type {
                        mandatory true;
                        description
                          "The test instance end lifetime type.";
                        case lifetime-time {
                          description
                            "The test instance end lifetime time.";
                          leaf start-now-end-lifetime-time {
                            type pub-type:ncs_rpc_notif_time;
                            description
                              "The test instance end lifetime time.";
                          }
                        }
                        case lifetime-seconds {
                          description
                            "The test instance end lifetime seconds.";
                          leaf start-now-end-lifetime-seconds {
                            type uint32 {
                              range "6..86399";
                            }
                            units "s";
                            description
                              "The test instance end lifetime seconds.";
                          }
                        }
                      }
                    }
                  }
                }
                case start-at {
                  description
                    "Execute at the specified time.";
                  leaf start-time {
                    type pub-type:ncs_rpc_notif_time;
                    mandatory true;
                    description
                      "The test instance start time.";
                  }
                  leaf start-date {
                    type pub-type:ncs_rpc_notif_date;
                    description
                      "The test instance start date.";
                  }
                  choice start-at-end-type {
                    description
                      "Test instance end type.";
                    case at {
                      description
                        "Stop the test at the specified time.";
                      leaf start-at-end-time {
                        type pub-type:ncs_rpc_notif_time;
                        mandatory true;
                        description
                          "The test instance end time.";
                      }
                      leaf start-at-end-date {
                        type pub-type:ncs_rpc_notif_date;
                        description
                          "The test instance end date.";
                      }
                    }
                    case delay {
                      description
                        "Stop the test after the specified delay time.";
                      choice start-at-end-delay-type {
                        mandatory true;
                        description
                          "The test instance end delay type.";
                        case end-delay-time {
                          description
                            "The test instance end delay time.";
                          leaf start-at-end-delay-time {
                            type pub-type:ncs_rpc_notif_time;
                            description
                              "The test instance end delay time.";
                          }
                        }
                        case end-delay-seconds {
                          description
                            "The test instance end delay seconds.";
                          leaf start-at-end-delay-seconds {
                            type uint32 {
                              range "6..86399";
                            }
                            units "s";
                            description
                              "The test instance end delay seconds.";
                          }
                        }
                      }
                    }
                    case lifetime {
                      description
                        "Stop the test after the specified life time.";
                      choice start-at-end-lifetime-type {
                        mandatory true;
                        description
                          "The test instance end lifetime type.";
                        case lifetime-time {
                          description
                            "The test instance end lifetime time.";
                          leaf start-at-end-lifetime-time {
                            type pub-type:ncs_rpc_notif_time;
                            description
                              "The test instance end lifetime time.";
                          }
                        }
                        case lifetime-seconds {
                          description
                            "The test instance end lifetime seconds.";
                          leaf start-at-end-lifetime-seconds {
                            type uint32 {
                              range "6..86399";
                            }
                            units "s";
                            description
                              "The test instance end lifetime seconds.";
                          }
                        }
                      }
                    }
                  }
                }
                case start-delay {
                  description
                    "Delay some time then execute testcase.";
                  choice start-delay-type {
                    mandatory true;
                    description
                      "The test instance start delay time.";
                    case start-delay-time {
                      description
                        "Execute at the specified time.";
                      leaf start-delay-time {
                        type pub-type:ncs_rpc_notif_time;
                        description
                          "The test instance start delay time.";
                      }
                    }
                    case start-delay-seconds {
                      description
                        "The test instance start delay seconds.";
                      leaf start-delay-seconds {
                        type uint32 {
                          range "1..86399";
                        }
                        units "s";
                        description
                          "The test instance start delay seconds.";
                      }
                    }
                  }
                  choice start-delay-end-type {
                    description
                      "Test instance end type.";
                    case at {
                      description
                        "Stop the test at the specified time.";
                      leaf start-delay-end-time {
                        type pub-type:ncs_rpc_notif_time;
                        mandatory true;
                        description
                          "The test instance end time.";
                      }
                      leaf start-delay-end-date {
                        type pub-type:ncs_rpc_notif_date;
                        description
                          "The test instance end date.";
                      }
                    }
                    case delay {
                      description
                        "Stop the test after the specified delay time.";
                      choice start-delay-end-delay-type {
                        mandatory true;
                        description
                          "The test instance end delay type.";
                        case end-delay-time {
                          description
                            "The test instance end delay time.";
                          leaf start-delay-end-delay-time {
                            type pub-type:ncs_rpc_notif_time;
                            description
                              "The test instance end delay time.";
                          }
                        }
                        case end-delay-seconds {
                          description
                            "The test instance end delay seconds.";
                          leaf start-delay-end-delay-seconds {
                            type uint32 {
                              range "6..86399";
                            }
                            units "s";
                            description
                              "The test instance end delay seconds.";
                          }
                        }
                      }
                    }
                    case lifetime {
                      description
                        "Stop the test after the specified life time.";
                      choice start-delay-end-lifetime-type {
                        mandatory true;
                        description
                          "The test instance end lifetime type.";
                        case lifetime-time {
                          description
                            "The test instance end lifetime time.";
                          leaf start-delay-end-lifetime-time {
                            type pub-type:ncs_rpc_notif_time;
                            description
                              "The test instance end lifetime time.";
                          }
                        }
                        case lifetime-seconds {
                          description
                            "The test instance end lifetime seconds.";
                          leaf start-delay-end-lifetime-seconds {
                            type uint32 {
                              range "6..86399";
                            }
                            units "s";
                            description
                              "The test instance end lifetime seconds.";
                          }
                        }
                      }
                    }
                  }
                }
                case start-daily {
                  description
                    "Execute the test instance daily.";
                  leaf daily-start-time {
                    type pub-type:ncs_rpc_notif_time;
                    mandatory true;
                    description
                      "Start time of daily execution.";
                  }
                  leaf daily-start-date {
                    type pub-type:ncs_rpc_notif_date;
                    description
                      "Start date of daily execution.";
                  }
                  leaf daily-end-time {
                    type pub-type:ncs_rpc_notif_time;
                    mandatory true;
                    description
                      "End time of daily execution.";
                  }
                  leaf daily-end-date {
                    type pub-type:ncs_rpc_notif_date;
                    description
                      "End date of daily execution.";
                  }
                }
              }
            }
            case stop {
              description
                "Stop the test.";
              leaf stop {
                type empty;
                description
                  "Stop the test.";
              }
            }
            case restart {
              description
                "Restart the test.";
              leaf restart {
                type empty;
                description
                  "Restart the test.";
              }
            }
          }
        }
      }
    }
  }
  augment "/ncs:devices/ncs:device-group/ncs:ned-id/ncs:rpc" {
    container rpc-test-instance-execution {
      tailf:ncs-device-type "netconf";
      tailf:display-when "/ncs:devices/ncs:device[ncs:name=current()/../../../ncs:member]/ncs:module[ncs:name='huawei-nqa']";
      tailf:action test-instance-execution {
        tailf:actionpoint ncsproxy {
          tailf:internal;
        }
        description
          "The test instance execution.";
        ext:node-ref "/nqa:nqa/nqa:instances/nqa:instance";
        input {
          leaf admin-name {
            type string;
            mandatory true;
            description
              "Administrator name.";
          }
          leaf test-name {
            type string;
            mandatory true;
            description
              "Test name.";
          }
          choice execution-policy {
            description
              "The test instance start policy.";
            case start {
              description
                "Start the test.";
              choice start-type {
                description
                  "The test instance start type.";
                case start-now {
                  description
                    "Start the test now.";
                  leaf start-now {
                    type empty;
                    mandatory true;
                    description
                      "Receive the command then start the test.";
                  }
                  choice start-now-end-type {
                    description
                      "Test instance end type.";
                    case at {
                      description
                        "Stop the test at the specified time.";
                      leaf start-now-end-time {
                        type pub-type:ncs_rpc_notif_time;
                        mandatory true;
                        description
                          "The test instance end time.";
                      }
                      leaf start-now-end-date {
                        type pub-type:ncs_rpc_notif_date;
                        description
                          "The test instance end date.";
                      }
                    }
                    case delay {
                      description
                        "Stop the test after the specified delay time.";
                      choice start-now-end-delay-type {
                        mandatory true;
                        description
                          "The test instance end delay type.";
                        case end-delay-time {
                          description
                            "The test instance end delay time.";
                          leaf start-now-end-delay-time {
                            type pub-type:ncs_rpc_notif_time;
                            description
                              "The test instance end delay time.";
                          }
                        }
                        case end-delay-seconds {
                          description
                            "The test instance end delay seconds.";
                          leaf start-now-end-delay-seconds {
                            type uint32 {
                              range "6..86399";
                            }
                            units "s";
                            description
                              "The test instance end delay seconds.";
                          }
                        }
                      }
                    }
                    case lifetime {
                      description
                        "Stop the test after the specified life time.";
                      choice start-now-end-lifetime-type {
                        mandatory true;
                        description
                          "The test instance end lifetime type.";
                        case lifetime-time {
                          description
                            "The test instance end lifetime time.";
                          leaf start-now-end-lifetime-time {
                            type pub-type:ncs_rpc_notif_time;
                            description
                              "The test instance end lifetime time.";
                          }
                        }
                        case lifetime-seconds {
                          description
                            "The test instance end lifetime seconds.";
                          leaf start-now-end-lifetime-seconds {
                            type uint32 {
                              range "6..86399";
                            }
                            units "s";
                            description
                              "The test instance end lifetime seconds.";
                          }
                        }
                      }
                    }
                  }
                }
                case start-at {
                  description
                    "Execute at the specified time.";
                  leaf start-time {
                    type pub-type:ncs_rpc_notif_time;
                    mandatory true;
                    description
                      "The test instance start time.";
                  }
                  leaf start-date {
                    type pub-type:ncs_rpc_notif_date;
                    description
                      "The test instance start date.";
                  }
                  choice start-at-end-type {
                    description
                      "Test instance end type.";
                    case at {
                      description
                        "Stop the test at the specified time.";
                      leaf start-at-end-time {
                        type pub-type:ncs_rpc_notif_time;
                        mandatory true;
                        description
                          "The test instance end time.";
                      }
                      leaf start-at-end-date {
                        type pub-type:ncs_rpc_notif_date;
                        description
                          "The test instance end date.";
                      }
                    }
                    case delay {
                      description
                        "Stop the test after the specified delay time.";
                      choice start-at-end-delay-type {
                        mandatory true;
                        description
                          "The test instance end delay type.";
                        case end-delay-time {
                          description
                            "The test instance end delay time.";
                          leaf start-at-end-delay-time {
                            type pub-type:ncs_rpc_notif_time;
                            description
                              "The test instance end delay time.";
                          }
                        }
                        case end-delay-seconds {
                          description
                            "The test instance end delay seconds.";
                          leaf start-at-end-delay-seconds {
                            type uint32 {
                              range "6..86399";
                            }
                            units "s";
                            description
                              "The test instance end delay seconds.";
                          }
                        }
                      }
                    }
                    case lifetime {
                      description
                        "Stop the test after the specified life time.";
                      choice start-at-end-lifetime-type {
                        mandatory true;
                        description
                          "The test instance end lifetime type.";
                        case lifetime-time {
                          description
                            "The test instance end lifetime time.";
                          leaf start-at-end-lifetime-time {
                            type pub-type:ncs_rpc_notif_time;
                            description
                              "The test instance end lifetime time.";
                          }
                        }
                        case lifetime-seconds {
                          description
                            "The test instance end lifetime seconds.";
                          leaf start-at-end-lifetime-seconds {
                            type uint32 {
                              range "6..86399";
                            }
                            units "s";
                            description
                              "The test instance end lifetime seconds.";
                          }
                        }
                      }
                    }
                  }
                }
                case start-delay {
                  description
                    "Delay some time then execute testcase.";
                  choice start-delay-type {
                    mandatory true;
                    description
                      "The test instance start delay time.";
                    case start-delay-time {
                      description
                        "Execute at the specified time.";
                      leaf start-delay-time {
                        type pub-type:ncs_rpc_notif_time;
                        description
                          "The test instance start delay time.";
                      }
                    }
                    case start-delay-seconds {
                      description
                        "The test instance start delay seconds.";
                      leaf start-delay-seconds {
                        type uint32 {
                          range "1..86399";
                        }
                        units "s";
                        description
                          "The test instance start delay seconds.";
                      }
                    }
                  }
                  choice start-delay-end-type {
                    description
                      "Test instance end type.";
                    case at {
                      description
                        "Stop the test at the specified time.";
                      leaf start-delay-end-time {
                        type pub-type:ncs_rpc_notif_time;
                        mandatory true;
                        description
                          "The test instance end time.";
                      }
                      leaf start-delay-end-date {
                        type pub-type:ncs_rpc_notif_date;
                        description
                          "The test instance end date.";
                      }
                    }
                    case delay {
                      description
                        "Stop the test after the specified delay time.";
                      choice start-delay-end-delay-type {
                        mandatory true;
                        description
                          "The test instance end delay type.";
                        case end-delay-time {
                          description
                            "The test instance end delay time.";
                          leaf start-delay-end-delay-time {
                            type pub-type:ncs_rpc_notif_time;
                            description
                              "The test instance end delay time.";
                          }
                        }
                        case end-delay-seconds {
                          description
                            "The test instance end delay seconds.";
                          leaf start-delay-end-delay-seconds {
                            type uint32 {
                              range "6..86399";
                            }
                            units "s";
                            description
                              "The test instance end delay seconds.";
                          }
                        }
                      }
                    }
                    case lifetime {
                      description
                        "Stop the test after the specified life time.";
                      choice start-delay-end-lifetime-type {
                        mandatory true;
                        description
                          "The test instance end lifetime type.";
                        case lifetime-time {
                          description
                            "The test instance end lifetime time.";
                          leaf start-delay-end-lifetime-time {
                            type pub-type:ncs_rpc_notif_time;
                            description
                              "The test instance end lifetime time.";
                          }
                        }
                        case lifetime-seconds {
                          description
                            "The test instance end lifetime seconds.";
                          leaf start-delay-end-lifetime-seconds {
                            type uint32 {
                              range "6..86399";
                            }
                            units "s";
                            description
                              "The test instance end lifetime seconds.";
                          }
                        }
                      }
                    }
                  }
                }
                case start-daily {
                  description
                    "Execute the test instance daily.";
                  leaf daily-start-time {
                    type pub-type:ncs_rpc_notif_time;
                    mandatory true;
                    description
                      "Start time of daily execution.";
                  }
                  leaf daily-start-date {
                    type pub-type:ncs_rpc_notif_date;
                    description
                      "Start date of daily execution.";
                  }
                  leaf daily-end-time {
                    type pub-type:ncs_rpc_notif_time;
                    mandatory true;
                    description
                      "End time of daily execution.";
                  }
                  leaf daily-end-date {
                    type pub-type:ncs_rpc_notif_date;
                    description
                      "End date of daily execution.";
                  }
                }
              }
            }
            case stop {
              description
                "Stop the test.";
              leaf stop {
                type empty;
                description
                  "Stop the test.";
              }
            }
            case restart {
              description
                "Restart the test.";
              leaf restart {
                type empty;
                description
                  "Restart the test.";
              }
            }
          }
        }
      }
    }
  }
  augment "/ncs:devices/ncs:device/ncs:config" {
    container nqa {
      tailf:ncs-device-type "netconf";
      tailf:display-when "not(../../ncs:module) or ../../ncs:module[ncs:name='huawei-nqa']";
      description
        "Network quality analysis (NQA) service.";
      container global {
        description
          "Configure NQA global configuration.";
        // NCS expand uses statement
        leaf fec-validation-ldp-enable {
          type boolean;
          default "true";
          description
            "Enable/disable LDP FEC validation.";
        }
        leaf fec-validation-sr-prefix-enable {
          type boolean;
          default "true";
          description
            "Enable/disable sr-prefix FEC validation.";
        }
        leaf lspv-cpu-limit {
          type uint16 {
            range "10..65535";
          }
          default "1000";
          description
            "Lspv cpu limit.";
        }
        leaf jitter-tag-version {
          type uint32 {
            range "1..2";
          }
          default "1";
          description
            "Version number of jitter.";
        }
        leaf lbm-receive-enable {
          type boolean;
          default "true";
          description
            "Enable/disable a device from receiving LBM packets.";
        }
        leaf ltm-receive-enable {
          type boolean;
          default "true";
          description
            "Enable/disable a device from receiving LTM packets.";
        }
        leaf gmac-ltm-receive-enable {
          type boolean;
          default "true";
          description
            "Enable/disable a device from receiving GMAC-LTM packets.";
        }
        leaf lspv-enable {
          type boolean;
          default "true";
          description
            "Enable/disable a device to respond to MPLS echo request packets.";
        }
        leaf lspv-ipv6-enable {
          type boolean;
          default "true";
          description
            "Enable/disable a device to respond to MPLS echo request IPv6 packets.";
        }
        leaf lspv-fec-compitable-enable {
          type boolean;
          default "false";
          description
            "Enable/disable the LSPV's compatibility function, and reply response packets don't carry FEC information.";
        }
        leaf gmac-ping-enable {
          type boolean;
          default "false";
          description
            "Enable/disable general GMAC ping function.";
        }
        leaf gmac-trace-enable {
          type boolean;
          default "false";
          description
            "Enable/disable general GMAC trace function.";
        }
        container vxlan-echo-v4 {
          presence "If enabled vxlan echo IPv4";
          description
            "Enable/disable NQA VXLANECHO.";
          leaf port {
            type uint16 {
              range "1..65535";
            }
            mandatory true;
            description
              "Port of NQA VXLANECHO server.";
          }
          leaf source-ip-if-name {
            type leafref {
              path "/ncs:devices/ncs:device/ncs:config/ifm:ifm/ifm:interfaces/ifm:interface/ifm:name" {
                tailf:xpath-root 3;
              }
            }
            description
              "Source ip interface of VXLANECHO.";
            must "/ifm:ifm/ifm:interfaces/ifm:interface[ifm:name=current()]/ifm:type = 'LoopBack'" {
              tailf:xpath-root 3;
            }
          }
        }
        container bier6-oam {
          description
            "Configure BIERv6 OAM.";
          leaf dest-port {
            type uint16 {
              range "1..65535";
            }
            default "49100";
            description
              "Destination UDP port of BIERv6 echo packet.";
          }
          leaf echo-reply-disable {
            type boolean;
            default "false";
            description
              "Enable/disable BIERv6 reply function.";
          }
          leaf rate-limit {
            type uint16 {
              range "10..65535";
            }
            units "pps";
            default "1000";
            description
              "BIERv6 receive rate limit.";
          }
        }
      }
      container server {
        description
          "Configure NQA server list.";
        uses nqa:server-type;
      }
      container reflectors {
        description
          "Configure reflector list.";
        // NCS expand uses statement
        list reflector {
          key "reflector-id";
          description
            "Configure reflector table.";
          leaf reflector-id {
            type uint32 {
              range "1..65535";
            }
            description
              "Reflector ID.";
          }
          leaf if-name {
            type leafref {
              path "/ncs:devices/ncs:device/ncs:config/ifm:ifm/ifm:interfaces/ifm:interface/ifm:name" {
                tailf:xpath-root 3;
              }
            }
            mandatory true;
            description
              "Reflector interface name.";
            must "/ifm:ifm/ifm:interfaces/ifm:interface[ifm:name=current()]/ifm:type = 'Ethernet' or /ifm:ifm/ifm:interfaces/ifm:interface[ifm:name=current()]/ifm:type = 'Eth-Trunk' or /ifm:ifm/ifm:interfaces/ifm:interface[ifm:name=current()]/ifm:type = 'Ip-Trunk' or /ifm:ifm/ifm:interfaces/ifm:interface[ifm:name=current()]/ifm:type = 'Virtual-Ethernet' or /ifm:ifm/ifm:interfaces/ifm:interface[ifm:name=current()]/ifm:type = 'Pos' or /ifm:ifm/ifm:interfaces/ifm:interface[ifm:name=current()]/ifm:type = '100GE' or /ifm:ifm/ifm:interfaces/ifm:interface[ifm:name=current()]/ifm:type = '200GE' or /ifm:ifm/ifm:interfaces/ifm:interface[ifm:name=current()]/ifm:type = '40GE' or /ifm:ifm/ifm:interfaces/ifm:interface[ifm:name=current()]/ifm:type = '10GE' or /ifm:ifm/ifm:interfaces/ifm:interface[ifm:name=current()]/ifm:type = 'GEBrief' or /ifm:ifm/ifm:interfaces/ifm:interface[ifm:name=current()]/ifm:type = 'GigabitEthernet' or /ifm:ifm/ifm:interfaces/ifm:interface[ifm:name=current()]/ifm:type = '25GE' or /ifm:ifm/ifm:interfaces/ifm:interface[ifm:name=current()]/ifm:type = '4x10GE' or /ifm:ifm/ifm:interfaces/ifm:interface[ifm:name=current()]/ifm:type = 'XGigabitEthernet' or /ifm:ifm/ifm:interfaces/ifm:interface[ifm:name=current()]/ifm:type = '50GE' or /ifm:ifm/ifm:interfaces/ifm:interface[ifm:name=current()]/ifm:type = '50|100GE' or /ifm:ifm/ifm:interfaces/ifm:interface[ifm:name=current()]/ifm:type = 'FlexE' or /ifm:ifm/ifm:interfaces/ifm:interface[ifm:name=current()]/ifm:type = '400GE' or /ifm:ifm/ifm:interfaces/ifm:interface[ifm:name=current()]/ifm:type = 'Global-VE'" {
              tailf:xpath-root 3;
            }
          }
          leaf reflector-type {
            type reflect-type;
            mandatory true;
            description
              "Reflector type.";
          }
          leaf exchange-port {
            type boolean;
            default "false";
            description
              "Enable/disable reflector UDP port exchange.";
          }
          leaf pe-vlan {
            type uint16 {
              range "1..4094";
            }
            must "../reflector-type='flow-general' and ../pe-vlan and ../ce-vlan" {
              tailf:xpath-root 3;
            }
            description
              "Reflector PE VLAN ID.";
          }
          leaf ce-vlan {
            type uint16 {
              range "1..4094";
            }
            must "../reflector-type='flow-general'" {
              tailf:xpath-root 3;
            }
            description
              "Reflector CE VLAN ID.";
          }
          leaf source-port {
            type uint16 {
              range "0..65535";
            }
            must "../reflector-type='flow-general'" {
              tailf:xpath-root 3;
            }
            default "49184";
            description
              "Reflector source port.";
          }
          leaf dest-port {
            type uint16 {
              range "0..65535";
            }
            must "../reflector-type='flow-general'" {
              tailf:xpath-root 3;
            }
            default "7";
            description
              "Reflector destination port.";
          }
          leaf end-time {
            type yang:date-and-time;
            mandatory true;
            description
              "Absolute time of reflector aging, the value must not be earlier than the current system time plus 10s or later than the current system time plus 173400s.";
          }
          leaf share-mode {
            type boolean;
            must "../share-mode = 'false' or ../reflector-type='flow-general'" {
              tailf:xpath-root 3;
            }
            default "false";
            description
              "Enable/disable the share mode on the reflector.";
          }
          choice address {
            description
              "Reflector address.";
            case ipv4-address {
              description
                "Reflector IPv4 address.";
              leaf ipv4-address {
                type inet:ipv4-address-no-zone;
                must "../reflector-type='flow-general'" {
                  tailf:xpath-root 3;
                }
                description
                  "Reflector IPv4 address.";
              }
            }
            case simulate-ipv4-address {
              description
                "Reflector simulate IPv4 address.";
              leaf simulate-ipv4-address {
                type inet:ipv4-address-no-zone;
                must "../reflector-type='flow-general'" {
                  tailf:xpath-root 3;
                }
                description
                  "Reflector simulate IPv4 address.";
              }
            }
            case mac-address {
              description
                "Reflector MAC address.";
              leaf mac-address {
                type pub-type:mac-address;
                must "../reflector-type='flow-general'" {
                  tailf:xpath-root 3;
                }
                description
                  "Reflector MAC address.";
              }
            }
          }
          // NCS drop config false leaf 'survival-time'
          // NCS drop config false leaf 'recommended-test-mac'
        }
      }
      container instances {
        description
          "Configure NQA test instance list.";
        // NCS expand uses statement
        list instance {
          key "admin-name test-name";
          description
            "Configure test instance.";
          leaf admin-name {
            type string {
              length "1..32";
            }
            description
              "Administrator name.";
          }
          leaf test-name {
            type string {
              length "1..32";
            }
            description
              "Test name.";
          }
          choice type {
            description
              "The test type of instance.";
            case icmp {
              description
                "ICMP NQA test.";
              container icmp-input {
                must "not(ipv4-next-hop and (ni-name != '_public_' or fwd-if-name or path-type = 'bypass'))" {
                  tailf:xpath-root 3;
                }
                must "not(ipv6-next-hop and (ni-name != '_public_' or fwd-if-name or path-type = 'bypass'))" {
                  tailf:xpath-root 3;
                }
                must "not(path-type = 'bypass' and (pass-route = 'true' or fwd-if-name or ipv6-dest-address or ipv6-source-address or ipv6-next-hop))" {
                  tailf:xpath-root 3;
                }
                must "not(pass-route = 'true' and fwd-if-name)" {
                  tailf:xpath-root 3;
                }
                must 'not(out-if-name and fwd-if-name)' {
                  tailf:xpath-root 3;
                }
                presence "ICMP PING test instance.";
                description
                  "Enable/disable ICMP test instance input.";
                // NCS expand uses statement
                choice address {
                  description
                    "Address information.";
                  case ipv4-address {
                    description
                      "IPv4 address.";
                    leaf ipv4-dest-address {
                      type inet:ipv4-address-no-zone;
                      description
                        "Destination IPv4 address.";
                    }
                    leaf ipv4-source-address {
                      type inet:ipv4-address-no-zone;
                      description
                        "Source IPv4 address.";
                    }
                    leaf ipv4-next-hop {
                      type inet:ipv4-address-no-zone;
                      description
                        "IPv4 next hop address.";
                    }
                  }
                  case ipv6-address {
                    description
                      "IPv6 address.";
                    leaf ipv6-dest-address {
                      type inet:ipv6-address-no-zone;
                      description
                        "Destination IPv6 address.";
                    }
                    leaf ipv6-source-address {
                      type inet:ipv6-address-no-zone;
                      description
                        "Source IPv6 address.";
                    }
                    leaf ipv6-next-hop {
                      type inet:ipv6-address-no-zone;
                      description
                        "IPv6 next hop address.";
                    }
                  }
                }
                leaf ni-name {
                  type string;
                  default "_public_";
                  description
                    "Name of a VPN instance.";
                }
                leaf out-if-name {
                  type leafref {
                    path "/ncs:devices/ncs:device/ncs:config/ifm:ifm/ifm:interfaces/ifm:interface/ifm:name" {
                      tailf:xpath-root 3;
                    }
                  }
                  description
                    "Out interface name.";
                  must "/ifm:ifm/ifm:interfaces/ifm:interface[ifm:name=current()]/ifm:type != 'NULL' and /ifm:ifm/ifm:interfaces/ifm:interface[ifm:name=current()]/ifm:type != 'Cpos' and /ifm:ifm/ifm:interfaces/ifm:interface[ifm:name=current()]/ifm:type != 'E1' and /ifm:ifm/ifm:interfaces/ifm:interface[ifm:name=current()]/ifm:type != 'Fabric-Port' and /ifm:ifm/ifm:interfaces/ifm:interface[ifm:name=current()]/ifm:type != 'Stack-Port' and /ifm:ifm/ifm:interfaces/ifm:interface[ifm:name=current()]/ifm:type != 'Atm-Bundle' and /ifm:ifm/ifm:interfaces/ifm:interface[ifm:name=current()]/ifm:type != 'Ima-group' and /ifm:ifm/ifm:interfaces/ifm:interface[ifm:name=current()]/ifm:type != 'Cpos-Trunk' and /ifm:ifm/ifm:interfaces/ifm:interface[ifm:name=current()]/ifm:type != 'Global-Ima-Group' and /ifm:ifm/ifm:interfaces/ifm:interface[ifm:name=current()]/ifm:type != 'FCoE-Port' and /ifm:ifm/ifm:interfaces/ifm:interface[ifm:name=current()]/ifm:type != 'FC' and /ifm:ifm/ifm:interfaces/ifm:interface[ifm:name=current()]/ifm:type != 'Remote-Ap' and /ifm:ifm/ifm:interfaces/ifm:interface[ifm:name=current()]/ifm:type != 'ServiceIf' and /ifm:ifm/ifm:interfaces/ifm:interface[ifm:name=current()]/ifm:type != 'ATM' and /ifm:ifm/ifm:interfaces/ifm:interface[ifm:name=current()]/ifm:type != 'FlexE-200GE' and /ifm:ifm/ifm:interfaces/ifm:interface[ifm:name=current()]/ifm:type != 'FlexE-50G' and /ifm:ifm/ifm:interfaces/ifm:interface[ifm:name=current()]/ifm:type != 'FlexE-100G' and /ifm:ifm/ifm:interfaces/ifm:interface[ifm:name=current()]/ifm:type != 'FlexE-50|100G' and /ifm:ifm/ifm:interfaces/ifm:interface[ifm:name=current()]/ifm:type != 'Virtual-if' and /ifm:ifm/ifm:interfaces/ifm:interface[ifm:name=current()]/ifm:type != 'FlexE-400G'" {
                    tailf:xpath-root 3;
                  }
                }
                leaf fwd-if-name {
                  type leafref {
                    path "/ncs:devices/ncs:device/ncs:config/ifm:ifm/ifm:interfaces/ifm:interface/ifm:name" {
                      tailf:xpath-root 3;
                    }
                  }
                  description
                    "Simulated inbound-interface name.";
                  must "/ifm:ifm/ifm:interfaces/ifm:interface[ifm:name=current()]/ifm:type != 'Atm-Bundle' and /ifm:ifm/ifm:interfaces/ifm:interface[ifm:name=current()]/ifm:type != 'Virtual-Ethernet' and /ifm:ifm/ifm:interfaces/ifm:interface[ifm:name=current()]/ifm:type != 'MTunnel' and /ifm:ifm/ifm:interfaces/ifm:interface[ifm:name=current()]/ifm:type != 'Tunnel' and /ifm:ifm/ifm:interfaces/ifm:interface[ifm:name=current()]/ifm:type != 'LoopBack' and /ifm:ifm/ifm:interfaces/ifm:interface[ifm:name=current()]/ifm:type != 'Vbdif' and /ifm:ifm/ifm:interfaces/ifm:interface[ifm:name=current()]/ifm:type != 'Serial' and /ifm:ifm/ifm:interfaces/ifm:interface[ifm:name=current()]/ifm:type != 'Mp-group' and /ifm:ifm/ifm:interfaces/ifm:interface[ifm:name=current()]/ifm:type != 'Global-Mp-Group' and /ifm:ifm/ifm:interfaces/ifm:interface[ifm:name=current()]/ifm:type != 'Trunk-Serial' and /ifm:ifm/ifm:interfaces/ifm:interface[ifm:name=current()]/ifm:type != 'Fabric-Port' and /ifm:ifm/ifm:interfaces/ifm:interface[ifm:name=current()]/ifm:type != 'Stack-Port' and /ifm:ifm/ifm:interfaces/ifm:interface[ifm:name=current()]/ifm:type != 'Cpos-Trunk' and /ifm:ifm/ifm:interfaces/ifm:interface[ifm:name=current()]/ifm:type != 'NULL' and /ifm:ifm/ifm:interfaces/ifm:interface[ifm:name=current()]/ifm:type != 'Ima-group' and /ifm:ifm/ifm:interfaces/ifm:interface[ifm:name=current()]/ifm:type != 'Global-Ima-Group' and /ifm:ifm/ifm:interfaces/ifm:interface[ifm:name=current()]/ifm:type != 'FCoE-Port' and /ifm:ifm/ifm:interfaces/ifm:interface[ifm:name=current()]/ifm:type != 'FC' and /ifm:ifm/ifm:interfaces/ifm:interface[ifm:name=current()]/ifm:type != 'Remote-Ap' and /ifm:ifm/ifm:interfaces/ifm:interface[ifm:name=current()]/ifm:type != 'ServiceIf' and /ifm:ifm/ifm:interfaces/ifm:interface[ifm:name=current()]/ifm:type != 'ATM' and /ifm:ifm/ifm:interfaces/ifm:interface[ifm:name=current()]/ifm:type != 'FlexE-200GE' and /ifm:ifm/ifm:interfaces/ifm:interface[ifm:name=current()]/ifm:type != 'FlexE-50G' and /ifm:ifm/ifm:interfaces/ifm:interface[ifm:name=current()]/ifm:type != 'FlexE-100G' and /ifm:ifm/ifm:interfaces/ifm:interface[ifm:name=current()]/ifm:type != 'FlexE-50|100G' and /ifm:ifm/ifm:interfaces/ifm:interface[ifm:name=current()]/ifm:type != 'Global-VE' and /ifm:ifm/ifm:interfaces/ifm:interface[ifm:name=current()]/ifm:type != 'Virtual-if' and /ifm:ifm/ifm:interfaces/ifm:interface[ifm:name=current()]/ifm:type != 'FlexE-400G'" {
                    tailf:xpath-root 3;
                  }
                }
                leaf interval {
                  type uint32 {
                    range "1..60";
                  }
                  units "s";
                  default "4";
                  description
                    "Interval for sending packets.";
                }
                leaf probe-count {
                  type uint32 {
                    range "1..15";
                  }
                  default "3";
                  description
                    "Number of sent packets.";
                }
                leaf timeout {
                  type uint32 {
                    range "1..60";
                  }
                  units "s";
                  default "3";
                  description
                    "Time to wait for a response packet after a test packet is sent.";
                }
                leaf frequency {
                  type uint32 {
                    range "1..604800";
                  }
                  units "s";
                  description
                    "Cyclic scheduling period of test cases. The frequency must be greater than the value of the following formula; otherwise, the test results may be inaccurate:
                     (number of sent packets - 1) * (packet sending interval) + (timeout period).";
                }
                leaf fail-percent {
                  type uint32 {
                    range "1..100";
                  }
                  units "%";
                  default "100";
                  description
                    "Indicates the packet loss ratio threshold of an NQA test instance. If the packet loss ratio exceeds the threshold, the test fails.";
                }
                leaf data-size {
                  type uint32 {
                    range "0..8100";
                  }
                  units "Byte";
                  default "0";
                  description
                    "Packet size.";
                }
                leaf data-fill {
                  type string {
                    length "1..230";
                  }
                  description
                    "Specify an NQA test packet payload string.";
                }
                leaf ttl {
                  type uint8 {
                    range "1..255";
                  }
                  default "30";
                  description
                    "Time to live.";
                }
                leaf pass-route {
                  type boolean;
                  default "false";
                  description
                    "Enable/disable the function of sending packets without searching for routes.";
                }
                leaf probe-fails {
                  type uint32 {
                    range "1..15";
                  }
                  default "1";
                  description
                    "The maximum number of probe failures of an NQA test to send trap or events.";
                }
                leaf test-fails {
                  type uint32 {
                    range "1..15";
                  }
                  default "1";
                  description
                    "The maximum number of the NQA test consecutive test failures to send trap or events.";
                }
                leaf send-trap-bits {
                  type bits {
                    bit probefailure {
                      position 31;
                      description
                        "Indicates that a trap is sent when the OWD from the source to the destination exceeds the threshold.";
                    }
                    bit rtd {
                      position 28;
                      description
                        "Indicates that a trap is sent when the RTD exceeds the threshold.";
                    }
                    bit testcomplete {
                      position 29;
                      description
                        "Indicates that a trap is sent when a test succeeds.";
                    }
                    bit testfailure {
                      position 30;
                      description
                        "Indicates that a trap is sent when the number of test failures reaches the threshold.";
                    }
                  }
                  description
                    "Configure conditions for sending traps.";
                }
                leaf compatibility {
                  type boolean;
                  default "false";
                  description
                    "Enable/disable compatibility mode. When the ptn79 interworks with the ptn39, the no result is converted to failed and success.";
                }
                leaf result-num {
                  type uint32 {
                    range "1..10";
                  }
                  default "5";
                  description
                    "The maximum number of test result records.";
                }
                leaf history-num {
                  type uint32 {
                    range "0..1000";
                  }
                  default "60";
                  description
                    "The maximum number of historical test records.";
                }
                leaf description {
                  type string {
                    length "1..230";
                  }
                  description
                    "Description of test instance.";
                }
                leaf age-time {
                  type pub-type:time;
                  default "00:00:00";
                  description
                    "Aging time of test instance.";
                }
                leaf path-type {
                  type path-type;
                  description
                    "Path type.";
                }
                leaf threshold-rtd {
                  type uint32 {
                    range "1..60000";
                  }
                  description
                    "Threshold value of round trip delay.";
                }
                choice priority {
                  default "tos-value";
                  description
                    "Priority type.";
                  case tos-value {
                    description
                      "ToS value.";
                    leaf tos {
                      type uint16 {
                        range "0..255";
                      }
                      default "0";
                      description
                        "ToS.";
                    }
                  }
                  case dscp-value {
                    description
                      "DSCP value.";
                    leaf dscp {
                      type uint32 {
                        range "0..63";
                      }
                      description
                        "DSCP value.";
                    }
                  }
                }
              }
            }
            case trace {
              description
                "TRACE NQA test.";
              container trace-input {
                must 'first-ttl<=max-ttl' {
                  tailf:xpath-root 3;
                }
                must "not(non-fragment = 'true' and (ipv6-dest-address or ipv6-source-address))" {
                  tailf:xpath-root 3;
                }
                presence "Present enable trace test instance input.";
                description
                  "Enable/disable trace test instance input.";
                // NCS expand uses statement
                choice address {
                  description
                    "Address information.";
                  case ipv4-address {
                    description
                      "IPv4 address.";
                    leaf ipv4-dest-address {
                      type inet:ipv4-address-no-zone;
                      description
                        "Destination IPv4 address.";
                    }
                    leaf ipv4-source-address {
                      type inet:ipv4-address-no-zone;
                      description
                        "Source IPv4 address.";
                    }
                    leaf ipv4-next-hop {
                      type inet:ipv4-address-no-zone;
                      description
                        "IPv4 next hop address.";
                    }
                  }
                  case ipv6-address {
                    description
                      "IPv6 address.";
                    leaf ipv6-dest-address {
                      type inet:ipv6-address-no-zone;
                      description
                        "Destination IPv6 address.";
                    }
                    leaf ipv6-source-address {
                      type inet:ipv6-address-no-zone;
                      description
                        "Source IPv6 address.";
                    }
                    leaf ipv6-next-hop {
                      type inet:ipv6-address-no-zone;
                      description
                        "IPv6 next hop address.";
                    }
                  }
                }
                leaf timeout {
                  type uint32 {
                    range "1..60";
                  }
                  units "s";
                  default "3";
                  description
                    "Time to wait for a response packet after a test packet is sent.";
                }
                leaf first-ttl {
                  type uint8 {
                    range "1..255";
                  }
                  default "1";
                  description
                    "Start TTL of probe packet.";
                }
                leaf max-ttl {
                  type uint8 {
                    range "1..255";
                  }
                  default "30";
                  description
                    "Maximum TTL of probe packet.";
                }
                leaf probe-count {
                  type uint32 {
                    range "1..15";
                  }
                  default "3";
                  description
                    "Number of sent packets.";
                }
                leaf data-size {
                  type uint32 {
                    range "0..8100";
                  }
                  units "Byte";
                  default "0";
                  description
                    "Packet size.";
                }
                leaf ni-name {
                  type string;
                  default "_public_";
                  description
                    "Name of a VPN instance.";
                }
                leaf result-num {
                  type uint32 {
                    range "1..10";
                  }
                  default "5";
                  description
                    "The maximum number of test result records.";
                }
                leaf history-num {
                  type uint32 {
                    range "0..1000";
                  }
                  default "60";
                  description
                    "The maximum number of historical test records.";
                }
                leaf description {
                  type string {
                    length "1..230";
                  }
                  description
                    "Description of test instance.";
                }
                leaf age-time {
                  type pub-type:time;
                  default "00:00:00";
                  description
                    "Aging time of test instance.";
                }
                leaf frequency {
                  type uint32 {
                    range "60..604800";
                  }
                  description
                    "Cyclic scheduling period of test cases.";
                }
                choice priority {
                  default "tos-value";
                  description
                    "Priority type.";
                  case tos-value {
                    description
                      "ToS value.";
                    leaf tos {
                      type uint16 {
                        range "0..255";
                      }
                      default "0";
                      description
                        "ToS.";
                    }
                  }
                  case dscp-value {
                    description
                      "DSCP value.";
                    leaf dscp {
                      type uint32 {
                        range "0..63";
                      }
                      description
                        "DSCP value.";
                    }
                  }
                }
                leaf data-fill {
                  type string {
                    length "1..230";
                  }
                  description
                    "Specify an NQA test packet payload string.";
                }
                leaf dest-port {
                  type uint16 {
                    range "1..65535";
                  }
                  default "33434";
                  description
                    "TRACE destination port number.";
                }
                leaf hop-fail-times {
                  type uint32 {
                    range "1..255";
                  }
                  default "5";
                  description
                    "The times of hop failure.";
                }
                leaf pass-route {
                  type boolean;
                  default "false";
                  description
                    "Enable/disable the function of sending packets without searching for routes.";
                }
                leaf out-if-name {
                  type leafref {
                    path "/ncs:devices/ncs:device/ncs:config/ifm:ifm/ifm:interfaces/ifm:interface/ifm:name" {
                      tailf:xpath-root 3;
                    }
                  }
                  description
                    "Out interface name.";
                  must "/ifm:ifm/ifm:interfaces/ifm:interface[ifm:name=current()]/ifm:type != 'NULL' and /ifm:ifm/ifm:interfaces/ifm:interface[ifm:name=current()]/ifm:type != 'Cpos' and /ifm:ifm/ifm:interfaces/ifm:interface[ifm:name=current()]/ifm:type != 'E1' and /ifm:ifm/ifm:interfaces/ifm:interface[ifm:name=current()]/ifm:type != 'Fabric-Port' and /ifm:ifm/ifm:interfaces/ifm:interface[ifm:name=current()]/ifm:type != 'Stack-Port' and /ifm:ifm/ifm:interfaces/ifm:interface[ifm:name=current()]/ifm:type != 'Atm-Bundle' and /ifm:ifm/ifm:interfaces/ifm:interface[ifm:name=current()]/ifm:type != 'Ima-group' and /ifm:ifm/ifm:interfaces/ifm:interface[ifm:name=current()]/ifm:type != 'Cpos-Trunk' and /ifm:ifm/ifm:interfaces/ifm:interface[ifm:name=current()]/ifm:type != 'Global-Ima-Group' and /ifm:ifm/ifm:interfaces/ifm:interface[ifm:name=current()]/ifm:type != 'FCoE-Port' and /ifm:ifm/ifm:interfaces/ifm:interface[ifm:name=current()]/ifm:type != 'FC' and /ifm:ifm/ifm:interfaces/ifm:interface[ifm:name=current()]/ifm:type != 'Remote-Ap' and /ifm:ifm/ifm:interfaces/ifm:interface[ifm:name=current()]/ifm:type != 'ServiceIf' and /ifm:ifm/ifm:interfaces/ifm:interface[ifm:name=current()]/ifm:type != 'ATM' and /ifm:ifm/ifm:interfaces/ifm:interface[ifm:name=current()]/ifm:type != 'FlexE-200GE' and /ifm:ifm/ifm:interfaces/ifm:interface[ifm:name=current()]/ifm:type != 'FlexE-50G' and /ifm:ifm/ifm:interfaces/ifm:interface[ifm:name=current()]/ifm:type != 'FlexE-100G' and /ifm:ifm/ifm:interfaces/ifm:interface[ifm:name=current()]/ifm:type != 'FlexE-50|100G' and /ifm:ifm/ifm:interfaces/ifm:interface[ifm:name=current()]/ifm:type != 'Virtual-if' and /ifm:ifm/ifm:interfaces/ifm:interface[ifm:name=current()]/ifm:type != 'FlexE-400G'" {
                    tailf:xpath-root 3;
                  }
                }
                leaf test-fail-times {
                  type uint32 {
                    range "1..15";
                  }
                  default "1";
                  description
                    "The maximum number of the NQA test consecutive test failures to send trap or events.";
                }
                leaf threshold-rtd {
                  type uint32 {
                    range "1..60000";
                  }
                  description
                    "Threshold value of round trip delay.";
                }
                leaf non-fragment {
                  type boolean;
                  default "false";
                  description
                    "Enable/disable the mark of message no fragment.";
                }
                leaf send-trap-bits {
                  type bits {
                    bit rtd {
                      position 28;
                      description
                        "Indicates that a trap is sent when the RTD exceeds the threshold.";
                    }
                    bit testcomplete {
                      position 29;
                      description
                        "Indicates that a trap is sent when a test succeeds.";
                    }
                    bit testfailure {
                      position 30;
                      description
                        "Indicates that a trap is sent when the number of test failures reaches the threshold.";
                    }
                  }
                  description
                    "Configure conditions for sending traps.";
                }
              }
            }
            case udp {
              description
                "UDP NQA test.";
              container udp-input {
                must "not((pass-route = 'true' and ipv6-dest-address) or (pass-route = 'true' and ipv6-source-address))" {
                  tailf:xpath-root 3;
                }
                presence "Present enable UDP test instance input.";
                description
                  "Enable/disable UDP test instance input.";
                // NCS expand uses statement
                choice address {
                  description
                    "Address information.";
                  case ipv4-address {
                    description
                      "IPv4 address.";
                    leaf ipv4-dest-address {
                      type inet:ipv4-address-no-zone;
                      description
                        "Destination IPv4 address.";
                    }
                    leaf ipv4-source-address {
                      type inet:ipv4-address-no-zone;
                      description
                        "Source IPv4 address.";
                    }
                  }
                  case ipv6-address {
                    description
                      "IPv6 address.";
                    leaf ipv6-dest-address {
                      type inet:ipv6-address-no-zone;
                      description
                        "Destination IPv6 address.";
                    }
                    leaf ipv6-source-address {
                      type inet:ipv6-address-no-zone;
                      description
                        "Source IPv6 address.";
                    }
                  }
                }
                leaf dest-port {
                  type uint16 {
                    range "1..65535";
                  }
                  default "7";
                  description
                    "UDP destination port.";
                }
                leaf source-port {
                  type uint16 {
                    range "1..65535";
                  }
                  description
                    "UDP source port.";
                }
                leaf ttl {
                  type uint8 {
                    range "1..255";
                  }
                  default "30";
                  description
                    "Time to live.";
                }
                leaf data-size {
                  type uint16 {
                    range "0..8100";
                  }
                  units "Byte";
                  default "0";
                  description
                    "Packet size.";
                }
                leaf pass-route {
                  type boolean;
                  default "false";
                  description
                    "Enable/disable the function of sending packets without searching for routes.";
                }
                leaf probe-count {
                  type uint32 {
                    range "1..15";
                  }
                  default "3";
                  description
                    "Number of sent packets.";
                }
                leaf send-trap-bits {
                  type bits {
                    bit probefailure {
                      position 31;
                      description
                        "Indicates that a trap is sent when the OWD from the source to the destination exceeds the threshold.";
                    }
                    bit rtd {
                      position 28;
                      description
                        "Indicates that a trap is sent when the RTD exceeds the threshold.";
                    }
                    bit testcomplete {
                      position 29;
                      description
                        "Indicates that a trap is sent when a test succeeds.";
                    }
                    bit testfailure {
                      position 30;
                      description
                        "Indicates that a trap is sent when the number of test failures reaches the threshold.";
                    }
                  }
                  description
                    "Configure conditions for sending traps.";
                }
                leaf threshold-rtd {
                  type uint32 {
                    range "1..60000";
                  }
                  description
                    "Threshold value of round trip delay.";
                }
                leaf probe-failtimes {
                  type uint32 {
                    range "1..15";
                  }
                  default "1";
                  description
                    "The maximum number of probe failures of an NQA test to send trap or events.";
                }
                leaf test-failtimes {
                  type uint32 {
                    range "1..15";
                  }
                  default "1";
                  description
                    "The maximum number of the NQA test consecutive test failures to send trap or events.";
                }
                leaf tos {
                  type uint16 {
                    range "0..255";
                  }
                  default "0";
                  description
                    "ToS.";
                }
                leaf fail-percent {
                  type uint32 {
                    range "1..100";
                  }
                  units "%";
                  default "100";
                  description
                    "Loss ratio, determining whether the test is successful.";
                }
                leaf interval {
                  type uint32 {
                    range "1..60";
                  }
                  units "s";
                  default "4";
                  description
                    "Interval for sending packets.";
                }
                leaf ni-name {
                  type string;
                  default "_public_";
                  description
                    "Name of a VPN instance.";
                }
                leaf timeout {
                  type uint32 {
                    range "1..60";
                  }
                  units "s";
                  default "3";
                  description
                    "Time to wait for a response packet after a test packet is sent.";
                }
                leaf data-fill {
                  type string {
                    length "1..230";
                  }
                  description
                    "Specify an NQA test packet payload string.";
                }
                leaf description {
                  type string {
                    length "1..230";
                  }
                  description
                    "Description of test instance.";
                }
                leaf result-num {
                  type uint32 {
                    range "1..10";
                  }
                  default "5";
                  description
                    "The maximum number of test result records.";
                }
                leaf history-num {
                  type uint32 {
                    range "0..1000";
                  }
                  default "60";
                  description
                    "The maximum number of historical test records.";
                }
                leaf age-time {
                  type pub-type:time;
                  default "00:00:00";
                  description
                    "Aging time of test instance.";
                }
                leaf frequency {
                  type uint32 {
                    range "1..604800";
                  }
                  units "s";
                  description
                    "Cyclic scheduling period of test cases. The frequency must be greater than the value of the following formula; otherwise, the test results may be inaccurate:
                     (Number of Sent Packets - 1) * (Packet Sending Interval) + (Timeout Period).";
                }
              }
            }
            case tcp {
              description
                "TCP NQA test.";
              container tcp-input {
                presence "Present enable TCP test instance input.";
                description
                  "Enable/disable TCP test instance input.";
                // NCS expand uses statement
                leaf dest-address {
                  type inet:ipv4-address-no-zone;
                  description
                    "Destination IP address.";
                }
                leaf source-address {
                  type inet:ipv4-address-no-zone;
                  description
                    "Source IP address.";
                }
                leaf interval {
                  type uint32 {
                    range "1..60";
                  }
                  units "s";
                  default "4";
                  description
                    "Interval for sending packets.";
                }
                leaf timeout {
                  type uint32 {
                    range "1..60";
                  }
                  units "s";
                  default "3";
                  description
                    "Time to wait for a response packet after a test packet is sent.";
                }
                leaf ttl {
                  type uint8 {
                    range "1..255";
                  }
                  default "30";
                  description
                    "TTL value of NQA test packets.";
                }
                leaf probe-count {
                  type uint32 {
                    range "1..15";
                  }
                  default "3";
                  description
                    "Number of sent packets.";
                }
                leaf tos {
                  type uint16 {
                    range "0..255";
                  }
                  default "0";
                  description
                    "ToS.";
                }
                leaf dest-port {
                  type uint16 {
                    range "1..65535";
                  }
                  default "7";
                  description
                    "TCP destination port number.";
                }
                leaf source-port {
                  type uint16 {
                    range "1..65535";
                  }
                  description
                    "TCP source port number.";
                }
                leaf pass-route {
                  type boolean;
                  default "false";
                  description
                    "Enable/disable the function of sending packets without searching for routes.";
                }
                leaf ni-name {
                  type string;
                  default "_public_";
                  description
                    "Name of a VPN instance.";
                }
                leaf threshold-rtd {
                  type uint32 {
                    range "1..60000";
                  }
                  description
                    "Threshold value of round trip delay.";
                }
                leaf probe-fails {
                  type uint32 {
                    range "1..15";
                  }
                  default "1";
                  description
                    "The maximum number of probe failures of an NQA test to send trap or events.";
                }
                leaf fail-percent {
                  type uint32 {
                    range "1..100";
                  }
                  units "%";
                  default "100";
                  description
                    "The rate of loss that the test case performed successfully.";
                }
                leaf test-fail-times {
                  type uint32 {
                    range "1..15";
                  }
                  default "1";
                  description
                    "The maximum number of the NQA test consecutive test failures to send trap or events.";
                }
                leaf result-num {
                  type uint32 {
                    range "1..10";
                  }
                  default "5";
                  description
                    "The maximum number of test result records.";
                }
                leaf history-num {
                  type uint32 {
                    range "0..1000";
                  }
                  default "60";
                  description
                    "The maximum number of historical test records.";
                }
                leaf description {
                  type string {
                    length "1..230";
                  }
                  description
                    "Description of test instance.";
                }
                leaf age-time {
                  type pub-type:time;
                  default "00:00:00";
                  description
                    "Aging time of test instance.";
                }
                leaf frequency {
                  type uint32 {
                    range "1..604800";
                  }
                  units "s";
                  description
                    "Cyclic scheduling period of test cases. The frequency must be greater than the value of the following formula; otherwise, the test results may be inaccurate:
                     (number of sent packets - 1) * (packet sending interval) + (timeout period).";
                }
              }
            }
            case jitter {
              description
                "Jitter NQA test that tests UDP-packet jitter.";
              container jitter-input {
                must "not(hardware-enable = 'true' and data-fill)" {
                  tailf:xpath-root 3;
                }
                must "not(hardware-enable = 'false' and timestamp = 'microsecond')" {
                  tailf:xpath-root 3;
                }
                must "(hardware-enable = 'false' and interval >= 20) or (hardware-enable = 'true' and interval >= 10)" {
                  tailf:xpath-root 3;
                }
                presence "Present enable jitter test instance input";
                description
                  "Enable/disable jitter test instance input.";
                // NCS expand uses statement
                choice address {
                  description
                    "IP address configurations.";
                  case ipv4-address {
                    description
                      "IPv4 address.";
                    leaf ipv4-dest-address {
                      type inet:ipv4-address-no-zone;
                      description
                        "Destination IPv4 address.";
                    }
                    leaf ipv4-source-address {
                      type inet:ipv4-address-no-zone;
                      description
                        "Source IPv4 address.";
                    }
                  }
                  case ipv6-address {
                    description
                      "IPv6 address.";
                    leaf ipv6-dest-address {
                      type inet:ipv6-address-no-zone;
                      description
                        "Destination IPv6 address.";
                    }
                    leaf ipv6-source-address {
                      type inet:ipv6-address-no-zone;
                      description
                        "Source IPv6 address.";
                    }
                  }
                }
                leaf dest-port {
                  type uint16 {
                    range "1..65535";
                  }
                  description
                    "UDP destination port.";
                }
                leaf source-port {
                  type uint16 {
                    range "1..65535";
                  }
                  description
                    "UDP source port.";
                }
                leaf ttl {
                  type uint8 {
                    range "1..255";
                  }
                  default "30";
                  description
                    "Time to live.";
                }
                leaf hardware-enable {
                  type boolean;
                  default "false";
                  description
                    "Enable/disable packets are sent by hardware.";
                }
                leaf interval {
                  type uint32 {
                    range "10..60000";
                  }
                  units "ms";
                  default "20";
                  description
                    "Interval for sending packets.";
                }
                leaf probe-count {
                  type uint32 {
                    range "1..15";
                  }
                  ext:dynamic-default {
                    ext:default-value "3" {
                      when "../code-type='none'" {
                        tailf:xpath-root 3;
                      }
                      description
                        "The default value is 3 when code-type is none.";
                    }
                    ext:default-value "1" {
                      when "../code-type='g711a' or ../code-type='g711u' or ../code-type='g729a'" {
                        tailf:xpath-root 3;
                      }
                      description
                        "The default value is 1 when code-type is g711a, g711u or g729a.";
                    }
                  }
                  description
                    "Number of probes.";
                }
                leaf jitter-packet-num {
                  type uint32 {
                    range "1..3000";
                  }
                  ext:dynamic-default {
                    ext:default-value "20" {
                      when "../code-type='none'" {
                        tailf:xpath-root 3;
                      }
                      description
                        "The default value is 20 when code-type is none.";
                    }
                    ext:default-value "1000" {
                      when "../code-type='g711a' or ../code-type='g711u' or ../code-type='g729a'" {
                        tailf:xpath-root 3;
                      }
                      description
                        "The default value is 1000 when code-type is g711a, g711u or g729a.";
                    }
                  }
                  description
                    "Number of sent packets.";
                }
                leaf data-size {
                  type uint16 {
                    range "0..8100";
                  }
                  units "Byte";
                  must "(../hardware-enable = 'true' and ../data-size <= 1472) or (../hardware-enable = 'false') or not(../hardware-enable)" {
                    tailf:xpath-root 3;
                  }
                  ext:dynamic-default {
                    ext:default-value "0" {
                      when "../code-type='none'" {
                        tailf:xpath-root 3;
                      }
                      description
                        "The default value is 0 when code-type is none.";
                    }
                    ext:default-value "172" {
                      when "../code-type='g711a' or ../code-type='g711u'" {
                        tailf:xpath-root 3;
                      }
                      description
                        "The default value is 172 when code-type is g711a or g711u.";
                    }
                    ext:default-value "32" {
                      when "../code-type='g729a'" {
                        tailf:xpath-root 3;
                      }
                      description
                        "The default value is 32 when code-type is g729a.";
                    }
                  }
                  description
                    "Packet size.";
                }
                leaf data-fill {
                  type string {
                    length "1..230";
                  }
                  description
                    "Specify an NQA test packet payload string.";
                }
                leaf pass-route {
                  type boolean;
                  default "false";
                  description
                    "Enable/disable the function of sending packets without searching for routes.";
                }
                leaf tos {
                  type uint16 {
                    range "0..255";
                  }
                  default "0";
                  description
                    "ToS.";
                }
                leaf ni-name {
                  type string;
                  default "_public_";
                  description
                    "Name of a VPN instance.";
                }
                leaf code-type {
                  type jitter-code-type;
                  default "none";
                  description
                    "Code type.";
                }
                leaf adv-factor {
                  when "../code-type='g711a' or ../code-type='g711u' or ../code-type='g729a'" {
                    tailf:xpath-root 3;
                  }
                  type uint8 {
                    range "0..20";
                  }
                  default "0";
                  description
                    "Advantage factor.";
                }
                leaf threshold-owd-ds {
                  type uint32 {
                    range "1..60000";
                  }
                  description
                    "One way delay threshold value from destination to source.";
                }
                leaf threshold-owd-sd {
                  type uint32 {
                    range "1..60000";
                  }
                  description
                    "One way delay threshold value from source to destination.";
                }
                leaf threshold-rtd {
                  type uint32 {
                    range "1..60000";
                  }
                  description
                    "Threshold value of round trip delay.";
                }
                leaf fail-percent {
                  type uint32 {
                    range "1..100";
                  }
                  units "%";
                  default "100";
                  description
                    "Indicates the packet loss ratio threshold of an NQA test instance. If the packet loss ratio exceeds the threshold, the test fails.";
                }
                leaf test-failtimes {
                  type uint32 {
                    range "1..15";
                  }
                  default "1";
                  description
                    "The maximum number of the NQA test consecutive test failures to send trap or events.";
                }
                leaf timestamp {
                  type time-unit-type;
                  default "millisecond";
                  description
                    "The unit of timestamp.";
                }
                leaf out-if-name {
                  type leafref {
                    path "/ncs:devices/ncs:device/ncs:config/ifm:ifm/ifm:interfaces/ifm:interface/ifm:name" {
                      tailf:xpath-root 3;
                    }
                  }
                  description
                    "Out interface name.";
                  must "/ifm:ifm/ifm:interfaces/ifm:interface[ifm:name=current()]/ifm:type != 'NULL' and /ifm:ifm/ifm:interfaces/ifm:interface[ifm:name=current()]/ifm:type != 'Cpos' and /ifm:ifm/ifm:interfaces/ifm:interface[ifm:name=current()]/ifm:type != 'E1' and /ifm:ifm/ifm:interfaces/ifm:interface[ifm:name=current()]/ifm:type != 'Fabric-Port' and /ifm:ifm/ifm:interfaces/ifm:interface[ifm:name=current()]/ifm:type != 'Stack-Port' and /ifm:ifm/ifm:interfaces/ifm:interface[ifm:name=current()]/ifm:type != 'Atm-Bundle' and /ifm:ifm/ifm:interfaces/ifm:interface[ifm:name=current()]/ifm:type != 'Ima-group' and /ifm:ifm/ifm:interfaces/ifm:interface[ifm:name=current()]/ifm:type != 'Cpos-Trunk' and /ifm:ifm/ifm:interfaces/ifm:interface[ifm:name=current()]/ifm:type != 'Global-Ima-Group' and /ifm:ifm/ifm:interfaces/ifm:interface[ifm:name=current()]/ifm:type != 'FCoE-Port' and /ifm:ifm/ifm:interfaces/ifm:interface[ifm:name=current()]/ifm:type != 'FC' and /ifm:ifm/ifm:interfaces/ifm:interface[ifm:name=current()]/ifm:type != 'Remote-Ap' and /ifm:ifm/ifm:interfaces/ifm:interface[ifm:name=current()]/ifm:type != 'ServiceIf' and /ifm:ifm/ifm:interfaces/ifm:interface[ifm:name=current()]/ifm:type != 'ATM' and /ifm:ifm/ifm:interfaces/ifm:interface[ifm:name=current()]/ifm:type != 'FlexE-200GE' and /ifm:ifm/ifm:interfaces/ifm:interface[ifm:name=current()]/ifm:type != 'FlexE-50G' and /ifm:ifm/ifm:interfaces/ifm:interface[ifm:name=current()]/ifm:type != 'FlexE-100G' and /ifm:ifm/ifm:interfaces/ifm:interface[ifm:name=current()]/ifm:type != 'FlexE-50|100G' and /ifm:ifm/ifm:interfaces/ifm:interface[ifm:name=current()]/ifm:type != 'Virtual-if' and /ifm:ifm/ifm:interfaces/ifm:interface[ifm:name=current()]/ifm:type != 'FlexE-400G'" {
                    tailf:xpath-root 3;
                  }
                }
                leaf timeout {
                  type uint32 {
                    range "1..60";
                  }
                  units "s";
                  default "3";
                  description
                    "Time to wait for a response packet after a test packet is sent.";
                }
                leaf result-num {
                  type uint32 {
                    range "1..10";
                  }
                  default "5";
                  description
                    "The maximum number of test result records.";
                }
                leaf history-num {
                  type uint32 {
                    range "0..1000";
                  }
                  default "60";
                  description
                    "The maximum number of historical test records.";
                }
                leaf description {
                  type string {
                    length "1..230";
                  }
                  description
                    "Description of test instance.";
                }
                leaf age-time {
                  type pub-type:time;
                  default "00:00:00";
                  description
                    "Aging time of test instance.";
                }
                leaf frequency {
                  type uint32 {
                    range "1..604800";
                  }
                  units "s";
                  description
                    "Cyclic scheduling period of test cases. The frequency must be greater than the value of the following formula; otherwise, the test results may be inaccurate:
                     (number of sent packets - 1) * (packet sending interval) + (timeout period).";
                }
              }
            }
            case icmp-jitter {
              description
                "ICMP jitter NQA test.";
              container icmp-jitter-input {
                presence "Present enable ICMP jitter test instance input.";
                description
                  "Enable/disable ICMP jitter test instance input.";
                // NCS expand uses statement
                choice address {
                  description
                    "IP address configurations.";
                  case ipv4-address {
                    description
                      "IPv4 address.";
                    leaf ipv4-dest-address {
                      type inet:ipv4-address-no-zone;
                      description
                        "Destination IPv4 address.";
                    }
                    leaf ipv4-source-address {
                      type inet:ipv4-address-no-zone;
                      description
                        "Source IPv4 address.";
                    }
                  }
                  case ipv6-address {
                    description
                      "IPv6 address.";
                    leaf ipv6-dest-address {
                      type inet:ipv6-address-no-zone;
                      description
                        "Destination IPv6 address.";
                    }
                    leaf ipv6-source-address {
                      type inet:ipv6-address-no-zone;
                      description
                        "Source IPv6 address.";
                    }
                  }
                }
                leaf ttl {
                  type uint8 {
                    range "1..255";
                  }
                  default "30";
                  description
                    "Time to live.";
                }
                leaf probe-count {
                  type uint32 {
                    range "1..15";
                  }
                  default "3";
                  description
                    "Number of probes.";
                }
                leaf hardware-enable {
                  type boolean;
                  must "../jitter-mode='icmp-timestamp' or (not(../jitter-mode='icmp-timestamp') and (../hardware-enable='false'))" {
                    tailf:xpath-root 3;
                  }
                  default "false";
                  description
                    "Enable/disable packets are sent by hardware.";
                }
                leaf jitter-packet-num {
                  type uint32 {
                    range "1..3000";
                  }
                  default "20";
                  description
                    "Number of packets.";
                }
                leaf data-size {
                  when "../jitter-mode='icmp-echo'" {
                    tailf:xpath-root 3;
                  }
                  type uint16 {
                    range "0..8100";
                  }
                  units "Byte";
                  default "0";
                  description
                    "Packet size.";
                }
                leaf data-fill {
                  when "../jitter-mode='icmp-echo'" {
                    tailf:xpath-root 3;
                  }
                  type string {
                    length "1..230";
                  }
                  description
                    "Specify an NQA test packet payload string.";
                }
                leaf tos {
                  type uint16 {
                    range "0..255";
                  }
                  default "0";
                  description
                    "ToS.";
                }
                leaf ni-name {
                  type string;
                  default "_public_";
                  description
                    "Name of a VPN instance.";
                }
                leaf jitter-mode {
                  when 'not(../ipv6-dest-address) and not(../ipv6-source-address)' {
                    tailf:xpath-root 3;
                  }
                  type jitter-mode-type;
                  default "icmp-timestamp";
                  description
                    "Packet format.";
                }
                leaf interval {
                  type uint32 {
                    range "10..60000";
                  }
                  units "ms";
                  must "../hardware-enable = 'false' and ../interval >= 20 or ../hardware-enable = 'true'" {
                    tailf:xpath-root 3;
                  }
                  default "20";
                  description
                    "Interval for sending packets.";
                }
                leaf timestamp {
                  when 'not(../ipv6-dest-address) and not(../ipv6-source-address)' {
                    tailf:xpath-root 3;
                  }
                  type time-unit-type;
                  must "(../hardware-enable='true') or (../hardware-enable='false' and ../timestamp='millisecond')" {
                    tailf:xpath-root 3;
                  }
                  default "millisecond";
                  description
                    "The unit of timestamp.";
                }
                leaf out-if-name {
                  type leafref {
                    path "/ncs:devices/ncs:device/ncs:config/ifm:ifm/ifm:interfaces/ifm:interface/ifm:name" {
                      tailf:xpath-root 3;
                    }
                  }
                  description
                    "Out interface name.";
                  must "/ifm:ifm/ifm:interfaces/ifm:interface[ifm:name=current()]/ifm:type != 'NULL' and /ifm:ifm/ifm:interfaces/ifm:interface[ifm:name=current()]/ifm:type != 'Cpos' and /ifm:ifm/ifm:interfaces/ifm:interface[ifm:name=current()]/ifm:type != 'E1' and /ifm:ifm/ifm:interfaces/ifm:interface[ifm:name=current()]/ifm:type != 'Fabric-Port' and /ifm:ifm/ifm:interfaces/ifm:interface[ifm:name=current()]/ifm:type != 'Stack-Port' and /ifm:ifm/ifm:interfaces/ifm:interface[ifm:name=current()]/ifm:type != 'Atm-Bundle' and /ifm:ifm/ifm:interfaces/ifm:interface[ifm:name=current()]/ifm:type != 'Ima-group' and /ifm:ifm/ifm:interfaces/ifm:interface[ifm:name=current()]/ifm:type != 'Cpos-Trunk' and /ifm:ifm/ifm:interfaces/ifm:interface[ifm:name=current()]/ifm:type != 'Global-Ima-Group' and /ifm:ifm/ifm:interfaces/ifm:interface[ifm:name=current()]/ifm:type != 'FCoE-Port' and /ifm:ifm/ifm:interfaces/ifm:interface[ifm:name=current()]/ifm:type != 'FC' and /ifm:ifm/ifm:interfaces/ifm:interface[ifm:name=current()]/ifm:type != 'Remote-Ap' and /ifm:ifm/ifm:interfaces/ifm:interface[ifm:name=current()]/ifm:type != 'ServiceIf' and /ifm:ifm/ifm:interfaces/ifm:interface[ifm:name=current()]/ifm:type != 'ATM' and /ifm:ifm/ifm:interfaces/ifm:interface[ifm:name=current()]/ifm:type != 'FlexE-200GE' and /ifm:ifm/ifm:interfaces/ifm:interface[ifm:name=current()]/ifm:type != 'FlexE-50G' and /ifm:ifm/ifm:interfaces/ifm:interface[ifm:name=current()]/ifm:type != 'FlexE-100G' and /ifm:ifm/ifm:interfaces/ifm:interface[ifm:name=current()]/ifm:type != 'FlexE-50|100G' and /ifm:ifm/ifm:interfaces/ifm:interface[ifm:name=current()]/ifm:type != 'Virtual-if' and /ifm:ifm/ifm:interfaces/ifm:interface[ifm:name=current()]/ifm:type != 'FlexE-400G'" {
                    tailf:xpath-root 3;
                  }
                }
                leaf timeout {
                  type uint32 {
                    range "1..60";
                  }
                  units "s";
                  default "3";
                  description
                    "Time to wait for a response packet after a test packet is sent.";
                }
                leaf receive-timeunit {
                  type recv-time-unit-type;
                  must "(../hardware-enable='true') or (../hardware-enable='false' and ../receive-timeunit='unknown')" {
                    tailf:xpath-root 3;
                  }
                  default "unknown";
                  description
                    "The unit of receive timestamp.";
                }
                leaf fail-percent {
                  type uint32 {
                    range "1..100";
                  }
                  units "%";
                  default "100";
                  description
                    "Indicates the packet loss ratio threshold of an NQA test instance. If the packet loss ratio exceeds the threshold, the test fails.";
                }
                leaf result-num {
                  type uint32 {
                    range "1..10";
                  }
                  default "5";
                  description
                    "The maximum number of test result records.";
                }
                leaf history-num {
                  type uint32 {
                    range "0..1000";
                  }
                  default "60";
                  description
                    "The maximum number of historical test records.";
                }
                leaf description {
                  type string {
                    length "1..230";
                  }
                  description
                    "Description of test instance.";
                }
                leaf age-time {
                  type pub-type:time;
                  default "00:00:00";
                  description
                    "Aging time of test instance.";
                }
                leaf frequency {
                  type uint32 {
                    range "1..604800";
                  }
                  units "s";
                  description
                    "Cyclic scheduling period of test cases. The frequency must be greater than the value of the following formula; otherwise, the test results may be inaccurate:
                     (number of sent packets - 1) * (packet sending interval) + (timeout period).";
                }
              }
            }
            case lsp-ping {
              description
                "LSP ping NQA test.";
              container lsp-ping-input {
                presence "Present enable LSP ping test instance input.";
                description
                  "Enable/disable LSP ping test instance input.";
                // NCS expand uses statement
                choice lsp-protocol {
                  default "ipv4";
                  description
                    "The LSP type. The default LSP type is IPv4.";
                  case ipv4 {
                    description
                      "The LSP type is LDP.";
                    container ldp-lsp-ping {
                      must '(dest-address and mask-len) or (not(dest-address) and not(mask-len))' {
                        tailf:xpath-root 3;
                      }
                      description
                        "Configure container of LDP LSP ping.";
                      leaf dest-address {
                        type inet:ipv4-address-no-zone;
                        description
                          "Destination IPv4 address.";
                      }
                      leaf mask-len {
                        type uint8 {
                          range "0..32";
                        }
                        description
                          "LSP IPv4 prefix mask length.";
                      }
                      leaf loopback-address {
                        when '../dest-address' {
                          tailf:xpath-root 3;
                        }
                        type inet:ipv4-address-no-zone;
                        description
                          "Set a 127/8 address of MPLS ping packets' destination address in the IP header.";
                      }
                      leaf next-hop {
                        type inet:ipv4-address-no-zone;
                        description
                          "Next hop address.";
                      }
                      leaf reply-mode {
                        type ip-lsp-reply-mode-type;
                        default "udp";
                        description
                          "Specify an LSP test reply mode.";
                      }
                    }
                  }
                  case bgp {
                    description
                      "The LSP type is BGP.";
                    container bgp-lsp-ping {
                      must '(dest-address and mask-len) or (not(dest-address) and not(mask-len))' {
                        tailf:xpath-root 3;
                      }
                      presence "Present enable BGP LSP ping.";
                      description
                        "Configure container of BGP LSP ping.";
                      leaf dest-address {
                        type inet:ipv4-address-no-zone;
                        description
                          "Destination IPv4 address.";
                      }
                      leaf mask-len {
                        type uint8 {
                          range "0..32";
                        }
                        description
                          "LSP IPv4 prefix mask length.";
                      }
                      leaf loopback-address {
                        when '../dest-address' {
                          tailf:xpath-root 3;
                        }
                        type inet:ipv4-address-no-zone;
                        description
                          "Set a 127/8 address of MPLS ping packets' destination address in the IP header.";
                      }
                      leaf next-hop {
                        type inet:ipv4-address-no-zone;
                        description
                          "Next hop address.";
                      }
                      leaf reply-mode {
                        type bgp-lsp-reply-mode-type;
                        default "udp";
                        description
                          "Specify an LSP test reply mode.";
                      }
                    }
                  }
                  case te {
                    description
                      "The LSP type is TE.";
                    container te-lsp-ping {
                      presence "Present enable TE LSP ping.";
                      description
                        "Configure container of TE LSP ping.";
                      leaf tunnel-name {
                        type leafref {
                          path "/ncs:devices/ncs:device/ncs:config/ifm:ifm/ifm:interfaces/ifm:interface/ifm:name" {
                            tailf:xpath-root 3;
                          }
                        }
                        description
                          "TE tunnel name.";
                      }
                      leaf lsp-path {
                        when '../tunnel-name' {
                          tailf:xpath-root 3;
                        }
                        type lsp-ping-trace-lsp-path;
                        description
                          "Lsp path (hot-standby or primary).";
                      }
                      leaf reply-mode {
                        type te-lsp-reply-mode-type;
                        default "udp";
                        description
                          "Specify an LSP test reply mode.";
                      }
                    }
                  }
                  case srte {
                    description
                      "The LSP type is SR-TE.";
                    container srte-lsp-ping {
                      presence "Present enable SR-TE LSP ping.";
                      description
                        "Configure container of SR-TE LSP ping.";
                      leaf tunnel-name {
                        type leafref {
                          path "/ncs:devices/ncs:device/ncs:config/ifm:ifm/ifm:interfaces/ifm:interface/ifm:name" {
                            tailf:xpath-root 3;
                          }
                        }
                        description
                          "TE tunnel name.";
                      }
                      leaf lsp-path {
                        when '../tunnel-name' {
                          tailf:xpath-root 3;
                        }
                        type lsp-ping-trace-lsp-path;
                        description
                          "Lsp path (hot-standby or primary).";
                      }
                    }
                  }
                  case srbe {
                    description
                      "The LSP type is SR-BE.";
                    container srbe-lsp-ping {
                      must '(dest-address and mask-len) or (not (dest-address) and not (mask-len))' {
                        tailf:xpath-root 3;
                      }
                      presence "Present enable SR-BE LSP ping.";
                      description
                        "Configure container of SR-BE LSP ping.";
                      leaf dest-address {
                        type inet:ipv4-address-no-zone;
                        description
                          "Destination IP address.";
                      }
                      leaf mask-len {
                        type uint8 {
                          range "0..32";
                        }
                        description
                          "LSP IPv4 prefix mask length.";
                      }
                      leaf flex-algo-id {
                        type uint8 {
                          range "128..255";
                        }
                        description
                          "Flexible algorithm ID.";
                      }
                      leaf path-type {
                        type path-type;
                        description
                          "Path type.";
                      }
                      choice remote-fec {
                        description
                          "Remote FEC type.";
                        case ldp {
                          description
                            "Configure the remote FEC type as LDP.";
                          container remote-fec-ldp {
                            must '(remote-fec-ip-address and remote-mask-len) or (not (remote-fec-ip-address) and not (remote-mask-len))' {
                              tailf:xpath-root 3;
                            }
                            presence "Present enable remote FEC type as LDP.";
                            description
                              "Configure container of remote FEC LDP.";
                            leaf remote-fec-ip-address {
                              type inet:ipv4-address-no-zone;
                              description
                                "Configure remote FEC IPv4 address.";
                            }
                            leaf remote-mask-len {
                              type uint8 {
                                range "0..32";
                              }
                              description
                                "Configure remote FEC mask length.";
                            }
                          }
                        }
                      }
                    }
                  }
                  case srte-policy {
                    description
                      "The LSP type is SR-TE policy.";
                    container srte-policy-lsp-ping {
                      must '(end-point-ip and color) or (not(end-point-ip) and not(color))' {
                        tailf:xpath-root 3;
                      }
                      presence "Present enable SR-TE policy LSP ping.";
                      description
                        "Configure container of SR-TE policy LSP ping.";
                      choice probe-type {
                        description
                          "Probe type of SR-TE policy.";
                        case policy-name {
                          description
                            "Policy name.";
                          leaf policy-name {
                            type string {
                              length "1..31";
                            }
                            description
                              "SR-TE policy name.";
                          }
                        }
                        case end-point {
                          description
                            "End point.";
                          leaf end-point-ip {
                            type inet:ipv4-address-no-zone;
                            description
                              "Endpoint IPv4 address.";
                          }
                          leaf color {
                            type uint32 {
                              range "1..4294967295";
                            }
                            description
                              "Endpoint color ID.";
                          }
                        }
                        case binding-sid {
                          description
                            "Policy name.";
                          leaf binding-sid {
                            type uint32 {
                              range "16..1048575";
                            }
                            description
                              "Binding segmentlist ID.";
                          }
                        }
                      }
                    }
                  }
                }
                leaf timeout {
                  type uint32 {
                    range "1..60";
                  }
                  units "s";
                  default "3";
                  description
                    "Time to wait for a response packet after test packets are sent.";
                }
                leaf frag-flag {
                  type boolean;
                  default "false";
                  description
                    "Enable/disable packet fragmentation function.";
                }
                leaf source-address {
                  type inet:ipv4-address-no-zone;
                  description
                    "Source IPv4 address.";
                }
                leaf exp {
                  type uint8 {
                    range "0..7";
                  }
                  default "0";
                  description
                    "Configures the LSP EXP value.";
                }
                leaf ttl {
                  type uint8 {
                    range "1..255";
                  }
                  default "30";
                  description
                    "TTL value of NQA test packets.";
                }
                leaf interval {
                  type uint32 {
                    range "1..60";
                  }
                  units "s";
                  default "4";
                  description
                    "Interval for sending packets.";
                }
                leaf probe-count {
                  type uint32 {
                    range "1..15";
                  }
                  default "3";
                  description
                    "Number of sent packets.";
                }
                leaf data-size {
                  type uint32 {
                    range "0..9600";
                  }
                  units "Byte";
                  default "0";
                  description
                    "Packet size.";
                }
                leaf data-fill {
                  type string {
                    length "1..230";
                  }
                  description
                    "Specify an NQA test packet payload string.";
                }
                leaf fail-percent {
                  type uint32 {
                    range "1..100";
                  }
                  units "%";
                  default "100";
                  description
                    "Indicates the packet loss ratio threshold of an NQA test instance. If the packet loss ratio exceeds the threshold, the test fails.";
                }
                leaf result-num {
                  type uint32 {
                    range "1..10";
                  }
                  default "5";
                  description
                    "The maximum number of test result records.";
                }
                leaf history-num {
                  type uint32 {
                    range "0..1000";
                  }
                  default "60";
                  description
                    "The maximum number of historical test records.";
                }
                leaf description {
                  type string {
                    length "1..230";
                  }
                  description
                    "Description of test instance.";
                }
                leaf age-time {
                  type pub-type:time;
                  default "00:00:00";
                  description
                    "Aging time of test instance.";
                }
                leaf frequency {
                  type uint32 {
                    range "1..604800";
                  }
                  units "s";
                  description
                    "Cyclic scheduling period of test cases. The frequency must be greater than the value of the following formula; otherwise, the test results may be inaccurate:
                     (number of sent packets - 1) * (packet sending interval) + (timeout period).";
                }
              }
            }
            case lsp-trace {
              description
                "LSP trace NQA test.";
              container lsp-trace-input {
                presence "Present enable LSP trace test instance input.";
                description
                  "Enable/disable LSP trace test instance input.";
                // NCS expand uses statement
                choice lsp-protocol {
                  default "ipv4";
                  description
                    "The LSP type. The default LSP type is IPv4.";
                  case ipv4 {
                    description
                      "The LSP type is LDP.";
                    container ldp-lsp-trace {
                      must '(dest-address and mask-len) or (not(dest-address) and not(mask-len))' {
                        tailf:xpath-root 3;
                      }
                      description
                        "Configure container of LDP LSP trace.";
                      leaf dest-address {
                        type inet:ipv4-address-no-zone;
                        description
                          "Destination IPv4 address.";
                      }
                      leaf mask-len {
                        type uint8 {
                          range "0..32";
                        }
                        description
                          "LSP IPv4 prefix mask length.";
                      }
                      leaf loopback-address {
                        when '../dest-address' {
                          tailf:xpath-root 3;
                        }
                        type inet:ipv4-address-no-zone;
                        description
                          "Set a 127/8 address of MPLS ping packets' destination address in the IP header.";
                      }
                      leaf next-hop {
                        type inet:ipv4-address-no-zone;
                        description
                          "Next hop address.";
                      }
                      leaf reply-mode {
                        type ip-lsp-reply-mode-type;
                        default "udp";
                        description
                          "Specify an LSP test reply mode.";
                      }
                    }
                  }
                  case bgp {
                    description
                      "The LSP type is BGP.";
                    container bgp-lsp-trace {
                      must '(dest-address and mask-len) or (not(dest-address) and not(mask-len))' {
                        tailf:xpath-root 3;
                      }
                      presence "Present enable BGP LSP trace.";
                      description
                        "Configure container of BGP LSP trace.";
                      leaf dest-address {
                        type inet:ipv4-address-no-zone;
                        description
                          "Destination IPv4 address.";
                      }
                      leaf mask-len {
                        type uint8 {
                          range "0..32";
                        }
                        description
                          "LSP IPv4 prefix mask length.";
                      }
                      leaf loopback-address {
                        when '../dest-address' {
                          tailf:xpath-root 3;
                        }
                        type inet:ipv4-address-no-zone;
                        description
                          "Set a 127/8 address of MPLS ping packets' destination address in the IP header.";
                      }
                      leaf next-hop {
                        type inet:ipv4-address-no-zone;
                        description
                          "Next hop address.";
                      }
                      leaf reply-mode {
                        type bgp-lsp-reply-mode-type;
                        default "udp";
                        description
                          "Specify an LSP test reply mode.";
                      }
                    }
                  }
                  case te {
                    description
                      "The LSP type is TE.";
                    container te-lsp-trace {
                      presence "Present enable TE LSP trace.";
                      description
                        "Configure container of TE LSP trace.";
                      leaf tunnel-name {
                        type leafref {
                          path "/ncs:devices/ncs:device/ncs:config/ifm:ifm/ifm:interfaces/ifm:interface/ifm:name" {
                            tailf:xpath-root 3;
                          }
                        }
                        description
                          "TE tunnel name.";
                      }
                      leaf next-hop {
                        type inet:ipv4-address-no-zone;
                        description
                          "Next hop address.";
                      }
                      leaf lsp-path {
                        when '../tunnel-name' {
                          tailf:xpath-root 3;
                        }
                        type lsp-ping-trace-lsp-path;
                        description
                          "Lsp path (hot-standby or primary).";
                      }
                      leaf reply-mode {
                        type te-lsp-reply-mode-type;
                        default "udp";
                        description
                          "Specify an LSP test reply mode.";
                      }
                    }
                  }
                  case srte {
                    description
                      "The LSP type is SR-TE.";
                    container srte-lsp-trace {
                      presence "Present enable SR-TE LSP trace.";
                      description
                        "Configure container of SR-TE LSP trace.";
                      leaf tunnel-name {
                        type leafref {
                          path "/ncs:devices/ncs:device/ncs:config/ifm:ifm/ifm:interfaces/ifm:interface/ifm:name" {
                            tailf:xpath-root 3;
                          }
                        }
                        description
                          "TE tunnel name.";
                      }
                      leaf lsp-path {
                        when '../tunnel-name' {
                          tailf:xpath-root 3;
                        }
                        type lsp-ping-trace-lsp-path;
                        description
                          "Lsp path (hot-standby or primary).";
                      }
                    }
                  }
                  case srbe {
                    description
                      "The LSP type is SR-BE.";
                    container srbe-lsp-trace {
                      must '(dest-address and mask-len) or (not (dest-address) and not (mask-len))' {
                        tailf:xpath-root 3;
                      }
                      presence "Present enable SR-BE LSP trace.";
                      description
                        "Configure container of SR-BE LSP trace.";
                      leaf dest-address {
                        type inet:ipv4-address-no-zone;
                        description
                          "Destination IPv4 address.";
                      }
                      leaf mask-len {
                        type uint8 {
                          range "0..32";
                        }
                        description
                          "LSP IPv4 prefix mask length.";
                      }
                      leaf flex-algo-id {
                        type uint8 {
                          range "128..255";
                        }
                        description
                          "Flexible algorithm ID.";
                      }
                      leaf path-type {
                        type path-type;
                        description
                          "Path type.";
                      }
                      choice remote-fec {
                        description
                          "Remote FEC type.";
                        case ldp {
                          description
                            "Configure the remote FEC type as LDP.";
                          container remote-fec-ldp {
                            must '(remote-fec-ip-address and remote-mask-len) or (not (remote-fec-ip-address) and not (remote-mask-len))' {
                              tailf:xpath-root 3;
                            }
                            presence "Present enable remote FEC type as LDP.";
                            description
                              "Configure container of remote FEC LDP.";
                            leaf remote-fec-ip-address {
                              type inet:ipv4-address-no-zone;
                              description
                                "Configure remote FEC IPv4 address.";
                            }
                            leaf remote-mask-len {
                              type uint8 {
                                range "0..32";
                              }
                              description
                                "Configure remote FEC mask length.";
                            }
                          }
                        }
                      }
                    }
                  }
                  case srte-policy {
                    description
                      "The LSP type is SR-TE policy.";
                    container srte-policy-lsp-trace {
                      must '(end-point-ip and color) or (not(end-point-ip) and not(color))' {
                        tailf:xpath-root 3;
                      }
                      presence "Present enable SR-TE policy LSP trace.";
                      description
                        "Configure container of SR-TE policy LSP trace.";
                      choice probe-type {
                        description
                          "Probe type of SR-TE policy.";
                        case policy-name {
                          description
                            "Policy name.";
                          leaf policy-name {
                            type string {
                              length "1..31";
                            }
                            description
                              "SR-TE policy name.";
                          }
                        }
                        case end-point {
                          description
                            "End point.";
                          leaf end-point-ip {
                            type inet:ipv4-address-no-zone;
                            description
                              "Endpoint IPv4 address.";
                          }
                          leaf color {
                            type uint32 {
                              range "1..4294967295";
                            }
                            description
                              "Endpoint color ID.";
                          }
                        }
                        case binding-sid {
                          description
                            "Policy name.";
                          leaf binding-sid {
                            type uint32 {
                              range "16..1048575";
                            }
                            description
                              "Binding segmentlist ID.";
                          }
                        }
                      }
                    }
                  }
                }
                leaf frag-flag {
                  type boolean;
                  default "false";
                  description
                    "Enable/disable packet fragmentation function.";
                }
                leaf exp {
                  type uint8 {
                    range "0..7";
                  }
                  default "0";
                  description
                    "Configures the LSP EXP value.";
                }
                leaf probe-count {
                  type uint32 {
                    range "1..15";
                  }
                  default "3";
                  description
                    "Number of sent packets.";
                }
                leaf source-address {
                  type inet:ipv4-address-no-zone;
                  description
                    "Source IPv4 address.";
                }
                leaf first-ttl {
                  type uint8 {
                    range "1..255";
                  }
                  must '../first-ttl<=../max-ttl' {
                    tailf:xpath-root 3;
                  }
                  default "1";
                  description
                    "Start TTL of probe packet.";
                }
                leaf max-ttl {
                  type uint8 {
                    range "1..255";
                  }
                  must '../first-ttl<=../max-ttl' {
                    tailf:xpath-root 3;
                  }
                  default "30";
                  description
                    "Maximum TTL of probe packet.";
                }
                leaf timeout {
                  type uint32 {
                    range "1..60";
                  }
                  units "s";
                  default "3";
                  description
                    "Time to wait for a response packet after a test packet is sent.";
                }
                leaf hop-fail-times {
                  type uint8 {
                    range "1..255";
                  }
                  default "5";
                  description
                    "Specify the upper limit of the number of failed hops before the NQA tracert test stops.";
                }
                leaf result-num {
                  type uint32 {
                    range "1..10";
                  }
                  default "5";
                  description
                    "The maximum number of test result records.";
                }
                leaf history-num {
                  type uint32 {
                    range "0..1000";
                  }
                  default "60";
                  description
                    "The maximum number of historical test records.";
                }
                leaf description {
                  type string {
                    length "1..230";
                  }
                  description
                    "Description of test instance.";
                }
                leaf age-time {
                  type pub-type:time;
                  default "00:00:00";
                  description
                    "Aging time of test instance.";
                }
                leaf frequency {
                  type uint32 {
                    range "1..604800";
                  }
                  units "s";
                  must '(../frequency>=60)' {
                    tailf:xpath-root 3;
                  }
                  description
                    "Cyclic scheduling period of test cases. The frequency must be greater than the value of the following formula; otherwise, the test results may be inaccurate:
                     (number of sent packets - 1) * (packet sending interval) + (timeout period).";
                }
              }
            }
            case lsp-jitter {
              description
                "LSP jitter NQA test.";
              container lsp-jitter-input {
                presence "Present enable LSP jitter test instance input";
                description
                  "Enable/disable LSP jitter test instance input.";
                // NCS expand uses statement
                choice lsp-protocol {
                  description
                    "The test-type of LSP.";
                  case te {
                    description
                      "The test-type of LSP is TE.";
                    container te-lsp-jitter {
                      presence "Present enable te jitter test instance input.";
                      description
                        "Enable/disable te jitter instance container.";
                      leaf tunnel-name {
                        type leafref {
                          path "/ncs:devices/ncs:device/ncs:config/ifm:ifm/ifm:interfaces/ifm:interface/ifm:name" {
                            tailf:xpath-root 3;
                          }
                        }
                        description
                          "TE tunnel name.";
                        must "/ifm:ifm/ifm:interfaces/ifm:interface[ifm:name=current()]/ifm:type = 'Tunnel'" {
                          tailf:xpath-root 3;
                        }
                      }
                      leaf lsp-path {
                        when '../tunnel-name' {
                          tailf:xpath-root 3;
                        }
                        type lsp-path;
                        default "working";
                        description
                          "LSP path (working or hot-standby or primary).";
                      }
                      leaf reply-mode {
                        type lsp-reply-mode-type;
                        default "udp";
                        description
                          "Specify an LSP test reply mode.";
                      }
                    }
                  }
                }
                leaf timeout {
                  type uint32 {
                    range "1..60";
                  }
                  units "s";
                  default "3";
                  description
                    "Time to wait for a response packet after a test packet is sent.";
                }
                leaf frag-flag {
                  type boolean;
                  default "false";
                  description
                    "Enable/disable packet fragmentation function.";
                }
                leaf source-address {
                  type inet:ipv4-address-no-zone;
                  description
                    "Source IP address.";
                }
                leaf exp {
                  type uint8 {
                    range "0..7";
                  }
                  default "0";
                  description
                    "Configures the LSP EXP value.";
                }
                leaf ttl {
                  type uint8 {
                    range "1..255";
                  }
                  default "30";
                  description
                    "TTL value of NQA test packets.";
                }
                leaf interval {
                  type uint32 {
                    range "1..60";
                  }
                  units "s";
                  default "1";
                  description
                    "Interval for sending packets.";
                }
                leaf probe-count {
                  type uint32 {
                    range "1..15";
                  }
                  default "3";
                  description
                    "Number of probes.";
                }
                leaf jitter-packet-num {
                  type uint32 {
                    range "1..3000";
                  }
                  default "20";
                  description
                    "Number of sent packets.";
                }
                leaf data-size {
                  type uint32 {
                    range "0..9600";
                  }
                  units "Byte";
                  default "0";
                  description
                    "Packet size.";
                }
                leaf data-fill {
                  type string {
                    length "1..230";
                  }
                  description
                    "Specify an NQA test packet payload string.";
                }
                leaf fail-percent {
                  type uint32 {
                    range "1..100";
                  }
                  units "%";
                  default "100";
                  description
                    "Indicates the packet loss ratio threshold of an NQA test instance. If the packet loss ratio exceeds the threshold, the test fails.";
                }
                leaf result-num {
                  type uint32 {
                    range "1..10";
                  }
                  default "5";
                  description
                    "The maximum number of test result records.";
                }
                leaf history-num {
                  type uint32 {
                    range "0..1000";
                  }
                  default "60";
                  description
                    "The maximum number of historical test records.";
                }
                leaf description {
                  type string {
                    length "1..230";
                  }
                  description
                    "Description of test instance.";
                }
                leaf age-time {
                  type pub-type:time;
                  default "00:00:00";
                  description
                    "Aging time of test instance.";
                }
                leaf frequency {
                  type uint32 {
                    range "1..604800";
                  }
                  units "s";
                  description
                    "Cyclic scheduling period of test cases. The frequency must be greater than the value of the following formula; otherwise, the test results may be inaccurate:
                     (number of sent packets - 1) * (packet sending interval) + (timeout period).";
                }
              }
            }
            case pwe3-trace {
              description
                "PWE3 trace NQA test.";
              container pwe3-trace-input {
                presence "Present enable PWE3 trace test instance input";
                description
                  "Enable/disable PWE3 trace test instance input.";
                // NCS expand uses statement
                leaf vc-type {
                  type vc-type;
                  default "ldp";
                  description
                    "VC type.";
                }
                leaf local-pw-type {
                  type pw-type;
                  default "ethernet";
                  description
                    "Local PW type.";
                }
                leaf local-pw-id {
                  type uint32 {
                    range "1..4294967295";
                  }
                  description
                    "Local PW ID.";
                }
                leaf label-type {
                  type pwe3-label-type;
                  default "control-word";
                  description
                    "Label type.";
                }
                leaf dest-address {
                  type inet:ipv4-address-no-zone;
                  description
                    "Destination IP address. (Must specify the destination address to start the test)";
                }
                leaf timeout {
                  type uint32 {
                    range "1..60";
                  }
                  units "s";
                  default "3";
                  description
                    "Time to wait for a response packet after a test packet is sent.";
                }
                leaf first-ttl {
                  type uint8 {
                    range "1..255";
                  }
                  must '(../first-ttl <= ../max-ttl)' {
                    tailf:xpath-root 3;
                  }
                  default "1";
                  description
                    "Start TTL of probe packet.";
                }
                leaf max-ttl {
                  type uint8 {
                    range "1..255";
                  }
                  must '(../max-ttl >= ../first-ttl)' {
                    tailf:xpath-root 3;
                  }
                  default "30";
                  description
                    "Maximum TTL of probe packet.";
                }
                leaf exp {
                  type uint8 {
                    range "0..7";
                  }
                  default "0";
                  description
                    "Configures the Pwe3Trace EXP value.";
                }
                leaf reply-mode {
                  type lsp-reply-mode-type;
                  default "udp";
                  description
                    "Specify an LSP test reply mode.";
                }
                leaf packet-count {
                  type uint32 {
                    range "1..15";
                  }
                  units "packet";
                  default "3";
                  description
                    "Number of sent packets.";
                }
                leaf probe-failtimes {
                  type uint32 {
                    range "1..15";
                  }
                  default "1";
                  description
                    "The maximum number of probe failures of an NQA test to send trap or events.";
                }
                leaf test-failtimes {
                  type uint32 {
                    range "1..15";
                  }
                  default "1";
                  description
                    "The maximum number of the NQA test consecutive test failures to send trap or events.";
                }
                leaf lsp-version {
                  type lsp-version;
                  default "rfc4379";
                  description
                    "Lsp version.";
                }
                leaf threshold-rtd {
                  type uint32 {
                    range "1..60000";
                  }
                  description
                    "Threshold value of round trip delay.";
                }
                leaf ttl-mode {
                  type ttl-mode;
                  default "uniform";
                  description
                    "TTL mode.";
                }
                leaf hop-fail-times {
                  type uint8 {
                    range "1..255";
                  }
                  default "5";
                  description
                    "Specify the upper limit of the number of failed hops before the NQA tracert test stops.";
                }
                leaf frag-flag {
                  type boolean;
                  default "false";
                  description
                    "Enable/disable packet fragmentation function.";
                }
                leaf peer-address {
                  type inet:ipv4-address-no-zone;
                  description
                    "Peer IP Address.";
                }
                leaf no-cw-flag {
                  when "../label-type!='control-word'" {
                    tailf:xpath-root 3;
                  }
                  type boolean;
                  default "false";
                  description
                    "Enable/disable the option of not carrying control word.";
                }
                leaf result-num {
                  type uint32 {
                    range "1..10";
                  }
                  default "5";
                  description
                    "The maximum number of test result records.";
                }
                leaf history-num {
                  type uint32 {
                    range "0..1000";
                  }
                  default "60";
                  description
                    "The maximum number of historical test records.";
                }
                leaf description {
                  type string {
                    length "1..230";
                  }
                  description
                    "Description of test instance.";
                }
                leaf age-time {
                  type pub-type:time;
                  default "00:00:00";
                  description
                    "Aging time of test instance.";
                }
                leaf frequency {
                  type uint32 {
                    range "60..604800";
                  }
                  units "s";
                  description
                    "Cyclic scheduling period of test cases. The frequency must be greater than the value of the following formula; otherwise, the test results may be inaccurate:
                     (number of sent packets - 1) * (packet sending interval) + (timeout period).";
                }
              }
            }
            case mac-ping {
              description
                "MAC ping NQA test.";
              container mac-ping-input {
                must '(md-name and ma-name) or (not(md-name) and not(ma-name))' {
                  tailf:xpath-root 3;
                }
                must "not(dest-mac-address) or (dest-mac-address != '0000-0000-0000')" {
                  tailf:xpath-root 3;
                }
                presence "Present enable MAC ping test instance input.";
                description
                  "Enable/disable MAC ping test instance input.";
                // NCS expand uses statement
                choice destination {
                  description
                    "Destination information.";
                  case mac-address {
                    description
                      "MAC address.";
                    leaf dest-mac-address {
                      type unicast-mac-address;
                      description
                        "Destination MAC, must be unicast MAC and not 0-0-0 MAC.";
                    }
                  }
                  case remote-mep-id {
                    description
                      "Remote MEP ID.";
                    leaf remote-mep-id {
                      type uint32 {
                        range "1..8191";
                      }
                      description
                        "Remote MEP ID.";
                    }
                  }
                }
                leaf mep-id {
                  type uint32 {
                    range "1..8191";
                  }
                  description
                    "MEP ID.";
                }
                leaf md-name {
                  type string {
                    length "1..43";
                  }
                  description
                    "Maintenance domain name.";
                }
                leaf ma-name {
                  type string {
                    length "1..43";
                  }
                  description
                    "Maintenance association name.";
                }
                leaf interval {
                  type uint32 {
                    range "1..60";
                  }
                  units "s";
                  default "4";
                  description
                    "Interval for sending packets.";
                }
                leaf probe-count {
                  type uint32 {
                    range "1..15";
                  }
                  default "3";
                  description
                    "Number of sent packets.";
                }
                leaf timeout {
                  type uint32 {
                    range "1..60";
                  }
                  units "s";
                  default "3";
                  description
                    "Time to wait for a response packet after a test packet is sent.";
                }
                leaf data-size {
                  type uint32 {
                    range "64..2000";
                  }
                  units "Byte";
                  default "95";
                  description
                    "Packet size.";
                }
                leaf source-if-name {
                  type leafref {
                    path "/ncs:devices/ncs:device/ncs:config/ifm:ifm/ifm:interfaces/ifm:interface/ifm:name" {
                      tailf:xpath-root 3;
                    }
                  }
                  description
                    "Out interface name.";
                  must "/ifm:ifm/ifm:interfaces/ifm:interface[ifm:name=current()]/ifm:type = 'Ethernet' or /ifm:ifm/ifm:interfaces/ifm:interface[ifm:name=current()]/ifm:type = 'GigabitEthernet' or /ifm:ifm/ifm:interfaces/ifm:interface[ifm:name=current()]/ifm:type = '100GE' or /ifm:ifm/ifm:interfaces/ifm:interface[ifm:name=current()]/ifm:type = '200GE' or /ifm:ifm/ifm:interfaces/ifm:interface[ifm:name=current()]/ifm:type = '40GE' or /ifm:ifm/ifm:interfaces/ifm:interface[ifm:name=current()]/ifm:type = '10GE' or /ifm:ifm/ifm:interfaces/ifm:interface[ifm:name=current()]/ifm:type = 'Eth-Trunk' or /ifm:ifm/ifm:interfaces/ifm:interface[ifm:name=current()]/ifm:type = 'GEBrief' or /ifm:ifm/ifm:interfaces/ifm:interface[ifm:name=current()]/ifm:type = '25GE' or /ifm:ifm/ifm:interfaces/ifm:interface[ifm:name=current()]/ifm:type = '4x10GE' or /ifm:ifm/ifm:interfaces/ifm:interface[ifm:name=current()]/ifm:type = '50GE' or /ifm:ifm/ifm:interfaces/ifm:interface[ifm:name=current()]/ifm:type = '50|100GE' or /ifm:ifm/ifm:interfaces/ifm:interface[ifm:name=current()]/ifm:type = '400GE' or /ifm:ifm/ifm:interfaces/ifm:interface[ifm:name=current()]/ifm:type = 'FlexE' or /ifm:ifm/ifm:interfaces/ifm:interface[ifm:name=current()]/ifm:type = 'XGigabitEthernet'" {
                    tailf:xpath-root 3;
                  }
                }
                leaf fail-percent {
                  type uint32 {
                    range "1..100";
                  }
                  units "%";
                  default "100";
                  description
                    "Loss ratio, determining whether the test is successful.";
                }
                leaf probe-fails {
                  type uint32 {
                    range "1..15";
                  }
                  default "1";
                  description
                    "The maximum number of probe failures of an NQA test to send trap or events.";
                }
                leaf test-fails {
                  type uint32 {
                    range "1..15";
                  }
                  default "1";
                  description
                    "The maximum number of the NQA test consecutive test failures to send trap or events.";
                }
                leaf send-trap-bits {
                  type bits {
                    bit probefailure {
                      position 31;
                      description
                        "Indicates that a trap is sent when the OWD from the source to the
                         destination exceeds the threshold.";
                    }
                    bit rtd {
                      position 28;
                      description
                        "Indicates that a trap is sent when the RTD exceeds the threshold.";
                    }
                    bit testcomplete {
                      position 29;
                      description
                        "Indicates that a trap is sent when a test succeeds.";
                    }
                    bit testfailure {
                      position 30;
                      description
                        "Indicates that a trap is sent when the number of test failures reaches the threshold.";
                    }
                  }
                  description
                    "Configure conditions for sending traps.";
                }
                leaf threshold-rtd {
                  type uint32 {
                    range "1..60000";
                  }
                  description
                    "Threshold value of round trip delay.";
                }
                leaf jitter-packet-num {
                  type uint32 {
                    range "1..3000";
                  }
                  default "1";
                  description
                    "Number of sent packets.";
                }
                leaf frequency {
                  type uint32 {
                    range "1..604800";
                  }
                  units "s";
                  description
                    "Cyclic scheduling period of test cases. The Frequency must be greater than the value of the following formula; otherwise, the test results may be inaccurate:
                     (Number of Sent Packets - 1) * (Packet Sending Interval) + (Timeout Period)";
                }
                leaf result-num {
                  type uint32 {
                    range "1..10";
                  }
                  default "5";
                  description
                    "The maximum number of test result records.";
                }
                leaf history-num {
                  type uint32 {
                    range "0..1000";
                  }
                  default "60";
                  description
                    "The maximum number of historical test records.";
                }
                leaf description {
                  type string {
                    length "1..230";
                  }
                  description
                    "Description of test instance.";
                }
                leaf age-time {
                  type pub-type:time;
                  default "00:00:00";
                  description
                    "Aging time of test instance.";
                }
              }
            }
            case arp-ping-ip {
              description
                "Arp ping IP NQA test.";
              container arp-ping-ip-input {
                presence "Present enable arp ping IP test intance input.";
                description
                  "Enable/disable arp ping IP test intance input.";
                // NCS expand uses statement
                leaf ipv4-dest-address {
                  type inet:ipv4-address-no-zone;
                  description
                    "Destination IPv4 address.";
                }
                leaf probe-count {
                  type uint32 {
                    range "1..15";
                  }
                  default "3";
                  description
                    "Number of sent packets.";
                }
                leaf out-if-name {
                  type leafref {
                    path "/ncs:devices/ncs:device/ncs:config/ifm:ifm/ifm:interfaces/ifm:interface/ifm:name" {
                      tailf:xpath-root 3;
                    }
                  }
                  description
                    "Out interface name.";
                  must "/ifm:ifm/ifm:interfaces/ifm:interface[ifm:name=current()]/ifm:type = 'Ethernet' or /ifm:ifm/ifm:interfaces/ifm:interface[ifm:name=current()]/ifm:type = 'GigabitEthernet' or /ifm:ifm/ifm:interfaces/ifm:interface[ifm:name=current()]/ifm:type = 'Eth-Trunk' or /ifm:ifm/ifm:interfaces/ifm:interface[ifm:name=current()]/ifm:type = 'Vlanif' or /ifm:ifm/ifm:interfaces/ifm:interface[ifm:name=current()]/ifm:type = 'Virtual-Ethernet' or /ifm:ifm/ifm:interfaces/ifm:interface[ifm:name=current()]/ifm:type = '100GE' or /ifm:ifm/ifm:interfaces/ifm:interface[ifm:name=current()]/ifm:type = '200GE' or /ifm:ifm/ifm:interfaces/ifm:interface[ifm:name=current()]/ifm:type = '40GE' or /ifm:ifm/ifm:interfaces/ifm:interface[ifm:name=current()]/ifm:type = '10GE' or /ifm:ifm/ifm:interfaces/ifm:interface[ifm:name=current()]/ifm:type = 'GEBrief' or /ifm:ifm/ifm:interfaces/ifm:interface[ifm:name=current()]/ifm:type = 'MEth' or /ifm:ifm/ifm:interfaces/ifm:interface[ifm:name=current()]/ifm:type = 'Vbdif' or /ifm:ifm/ifm:interfaces/ifm:interface[ifm:name=current()]/ifm:type = 'Global-VE' or /ifm:ifm/ifm:interfaces/ifm:interface[ifm:name=current()]/ifm:type = '25GE' or /ifm:ifm/ifm:interfaces/ifm:interface[ifm:name=current()]/ifm:type = '50GE' or /ifm:ifm/ifm:interfaces/ifm:interface[ifm:name=current()]/ifm:type = '50|100GE' or /ifm:ifm/ifm:interfaces/ifm:interface[ifm:name=current()]/ifm:type = 'FlexE' or /ifm:ifm/ifm:interfaces/ifm:interface[ifm:name=current()]/ifm:type = '400GE' or /ifm:ifm/ifm:interfaces/ifm:interface[ifm:name=current()]/ifm:type = '4x10GE' or /ifm:ifm/ifm:interfaces/ifm:interface[ifm:name=current()]/ifm:type = 'XGigabitEthernet'" {
                    tailf:xpath-root 3;
                  }
                }
                leaf timeout {
                  type uint32 {
                    range "1..10";
                  }
                  units "s";
                  default "3";
                  description
                    "Time to wait for a response packet after a test packet is sent, expressed in seconds.";
                }
                leaf result-num {
                  type uint32 {
                    range "1..10";
                  }
                  default "5";
                  description
                    "The maximum number of test result records.";
                }
                leaf history-num {
                  type uint32 {
                    range "0..1000";
                  }
                  default "60";
                  description
                    "The maximum number of historical test records.";
                }
                leaf description {
                  type string {
                    length "1..230";
                  }
                  description
                    "Description of test instance.";
                }
                leaf age-time {
                  type pub-type:time;
                  default "00:00:00";
                  description
                    "Aging time of test instance.";
                }
                leaf frequency {
                  type uint32 {
                    range "1..604800";
                  }
                  units "s";
                  description
                    "Cyclic scheduling period of test cases. The frequency must be greater than the value of the following formula; otherwise, the test results may be inaccurate:
                     (Number of sent Packets - 1) * (Packet sending interval) + (Timeout period).";
                }
              }
            }
          }
          // NCS drop config false container 'execution-policy'
        }
      }
      // NCS drop config false container record
    }
  }
  augment "/ncs:devices/ncs:device/ncs:live-status" {
    container nqa {
      tailf:ncs-device-type "netconf";
      tailf:display-when "not(../../ncs:module) or ../../ncs:module[ncs:name='huawei-nqa'] or (../../ncs:live-status-protocol[not(ncs:capability)]) or (../../ncs:live-status-protocol/ncs:capability/ncs:module[.='huawei-nqa'])";
      description
        "Network quality analysis (NQA) service.";
      container global {
        description
          "Configure NQA global configuration.";
        // NCS expand uses statement
        leaf fec-validation-ldp-enable {
          type boolean;
          // NCS drop default statement
          description
            "Enable/disable LDP FEC validation.";
        }
        leaf fec-validation-sr-prefix-enable {
          type boolean;
          // NCS drop default statement
          description
            "Enable/disable sr-prefix FEC validation.";
        }
        leaf lspv-cpu-limit {
          type uint16 {
            range "10..65535";
          }
          // NCS drop default statement
          description
            "Lspv cpu limit.";
        }
        leaf jitter-tag-version {
          type uint32 {
            range "1..2";
          }
          // NCS drop default statement
          description
            "Version number of jitter.";
        }
        leaf lbm-receive-enable {
          type boolean;
          // NCS drop default statement
          description
            "Enable/disable a device from receiving LBM packets.";
        }
        leaf ltm-receive-enable {
          type boolean;
          // NCS drop default statement
          description
            "Enable/disable a device from receiving LTM packets.";
        }
        leaf gmac-ltm-receive-enable {
          type boolean;
          // NCS drop default statement
          description
            "Enable/disable a device from receiving GMAC-LTM packets.";
        }
        leaf lspv-enable {
          type boolean;
          // NCS drop default statement
          description
            "Enable/disable a device to respond to MPLS echo request packets.";
        }
        leaf lspv-ipv6-enable {
          type boolean;
          // NCS drop default statement
          description
            "Enable/disable a device to respond to MPLS echo request IPv6 packets.";
        }
        leaf lspv-fec-compitable-enable {
          type boolean;
          // NCS drop default statement
          description
            "Enable/disable the LSPV's compatibility function, and reply response packets don't carry FEC information.";
        }
        leaf gmac-ping-enable {
          type boolean;
          // NCS drop default statement
          description
            "Enable/disable general GMAC ping function.";
        }
        leaf gmac-trace-enable {
          type boolean;
          // NCS drop default statement
          description
            "Enable/disable general GMAC trace function.";
        }
        container vxlan-echo-v4 {
          presence "If enabled vxlan echo IPv4";
          description
            "Enable/disable NQA VXLANECHO.";
          leaf port {
            type uint16 {
              range "1..65535";
            }
            // NCS drop mandatory statement
            description
              "Port of NQA VXLANECHO server.";
          }
          leaf source-ip-if-name {
            type leafref {
              path "/ncs:devices/ncs:device/ncs:live-status/ifm:ifm/ifm:interfaces/ifm:interface/ifm:name" {
                tailf:xpath-root 3;
              }
            }
            description
              "Source ip interface of VXLANECHO.";
            // NCS drop must statement
          }
        }
        container bier6-oam {
          description
            "Configure BIERv6 OAM.";
          leaf dest-port {
            type uint16 {
              range "1..65535";
            }
            // NCS drop default statement
            description
              "Destination UDP port of BIERv6 echo packet.";
          }
          leaf echo-reply-disable {
            type boolean;
            // NCS drop default statement
            description
              "Enable/disable BIERv6 reply function.";
          }
          leaf rate-limit {
            type uint16 {
              range "10..65535";
            }
            units "pps";
            // NCS drop default statement
            description
              "BIERv6 receive rate limit.";
          }
        }
      }
      container server {
        description
          "Configure NQA server list.";
        uses nqa:live_ncs_server-type;
      }
      container reflectors {
        description
          "Configure reflector list.";
        // NCS expand uses statement
        list reflector {
          key "reflector-id";
          description
            "Configure reflector table.";
          leaf reflector-id {
            type uint32 {
              range "1..65535";
            }
            description
              "Reflector ID.";
          }
          leaf if-name {
            type leafref {
              path "/ncs:devices/ncs:device/ncs:live-status/ifm:ifm/ifm:interfaces/ifm:interface/ifm:name" {
                tailf:xpath-root 3;
              }
            }
            // NCS drop mandatory statement
            description
              "Reflector interface name.";
            // NCS drop must statement
          }
          leaf reflector-type {
            type live_ncs_reflect-type;
            // NCS drop mandatory statement
            description
              "Reflector type.";
          }
          leaf exchange-port {
            type boolean;
            // NCS drop default statement
            description
              "Enable/disable reflector UDP port exchange.";
          }
          leaf pe-vlan {
            type uint16 {
              range "1..4094";
            }
            // NCS drop must statement
            description
              "Reflector PE VLAN ID.";
          }
          leaf ce-vlan {
            type uint16 {
              range "1..4094";
            }
            // NCS drop must statement
            description
              "Reflector CE VLAN ID.";
          }
          leaf source-port {
            type uint16 {
              range "0..65535";
            }
            // NCS drop must statement
            // NCS drop default statement
            description
              "Reflector source port.";
          }
          leaf dest-port {
            type uint16 {
              range "0..65535";
            }
            // NCS drop must statement
            // NCS drop default statement
            description
              "Reflector destination port.";
          }
          leaf end-time {
            type yang:date-and-time;
            // NCS drop mandatory statement
            description
              "Absolute time of reflector aging, the value must not be earlier than the current system time plus 10s or later than the current system time plus 173400s.";
          }
          leaf share-mode {
            type boolean;
            // NCS drop must statement
            // NCS drop default statement
            description
              "Enable/disable the share mode on the reflector.";
          }
          choice address {
            description
              "Reflector address.";
            case ipv4-address {
              description
                "Reflector IPv4 address.";
              leaf ipv4-address {
                type inet:ipv4-address-no-zone;
                // NCS drop must statement
                description
                  "Reflector IPv4 address.";
              }
            }
            case simulate-ipv4-address {
              description
                "Reflector simulate IPv4 address.";
              leaf simulate-ipv4-address {
                type inet:ipv4-address-no-zone;
                // NCS drop must statement
                description
                  "Reflector simulate IPv4 address.";
              }
            }
            case mac-address {
              description
                "Reflector MAC address.";
              leaf mac-address {
                type pub-type:live_ncs_mac-address;
                // NCS drop must statement
                description
                  "Reflector MAC address.";
              }
            }
          }
          leaf survival-time {
            type uint32;
            units "s";
            description
              "Reflector survival time.";
          }
          leaf recommended-test-mac {
            type pub-type:live_ncs_mac-address;
            description
              "Reflector recommended MAC address.";
          }
        }
      }
      container instances {
        description
          "Configure NQA test instance list.";
        // NCS expand uses statement
        list instance {
          key "admin-name test-name";
          description
            "Configure test instance.";
          leaf admin-name {
            type string {
              length "1..32";
            }
            description
              "Administrator name.";
          }
          leaf test-name {
            type string {
              length "1..32";
            }
            description
              "Test name.";
          }
          choice type {
            description
              "The test type of instance.";
            case icmp {
              description
                "ICMP NQA test.";
              container icmp-input {
                // NCS drop must statement
                // NCS drop must statement
                // NCS drop must statement
                // NCS drop must statement
                // NCS drop must statement
                presence "ICMP PING test instance.";
                description
                  "Enable/disable ICMP test instance input.";
                // NCS expand uses statement
                choice address {
                  description
                    "Address information.";
                  case ipv4-address {
                    description
                      "IPv4 address.";
                    leaf ipv4-dest-address {
                      type inet:ipv4-address-no-zone;
                      description
                        "Destination IPv4 address.";
                    }
                    leaf ipv4-source-address {
                      type inet:ipv4-address-no-zone;
                      description
                        "Source IPv4 address.";
                    }
                    leaf ipv4-next-hop {
                      type inet:ipv4-address-no-zone;
                      description
                        "IPv4 next hop address.";
                    }
                  }
                  case ipv6-address {
                    description
                      "IPv6 address.";
                    leaf ipv6-dest-address {
                      type inet:ipv6-address-no-zone;
                      description
                        "Destination IPv6 address.";
                    }
                    leaf ipv6-source-address {
                      type inet:ipv6-address-no-zone;
                      description
                        "Source IPv6 address.";
                    }
                    leaf ipv6-next-hop {
                      type inet:ipv6-address-no-zone;
                      description
                        "IPv6 next hop address.";
                    }
                  }
                }
                leaf ni-name {
                  type leafref {
                    path "/ncs:devices/ncs:device/ncs:live-status/ni:network-instance/ni:instances/ni:instance/ni:name" {
                      tailf:xpath-root 3;
                    }
                  }
                  // NCS drop default statement
                  description
                    "Name of a VPN instance.";
                }
                leaf out-if-name {
                  type leafref {
                    path "/ncs:devices/ncs:device/ncs:live-status/ifm:ifm/ifm:interfaces/ifm:interface/ifm:name" {
                      tailf:xpath-root 3;
                    }
                  }
                  description
                    "Out interface name.";
                  // NCS drop must statement
                }
                leaf fwd-if-name {
                  type leafref {
                    path "/ncs:devices/ncs:device/ncs:live-status/ifm:ifm/ifm:interfaces/ifm:interface/ifm:name" {
                      tailf:xpath-root 3;
                    }
                  }
                  description
                    "Simulated inbound-interface name.";
                  // NCS drop must statement
                }
                leaf interval {
                  type uint32 {
                    range "1..60";
                  }
                  units "s";
                  // NCS drop default statement
                  description
                    "Interval for sending packets.";
                }
                leaf probe-count {
                  type uint32 {
                    range "1..15";
                  }
                  // NCS drop default statement
                  description
                    "Number of sent packets.";
                }
                leaf timeout {
                  type uint32 {
                    range "1..60";
                  }
                  units "s";
                  // NCS drop default statement
                  description
                    "Time to wait for a response packet after a test packet is sent.";
                }
                leaf frequency {
                  type uint32 {
                    range "1..604800";
                  }
                  units "s";
                  description
                    "Cyclic scheduling period of test cases. The frequency must be greater than the value of the following formula; otherwise, the test results may be inaccurate:
                     (number of sent packets - 1) * (packet sending interval) + (timeout period).";
                }
                leaf fail-percent {
                  type uint32 {
                    range "1..100";
                  }
                  units "%";
                  // NCS drop default statement
                  description
                    "Indicates the packet loss ratio threshold of an NQA test instance. If the packet loss ratio exceeds the threshold, the test fails.";
                }
                leaf data-size {
                  type uint32 {
                    range "0..8100";
                  }
                  units "Byte";
                  // NCS drop default statement
                  description
                    "Packet size.";
                }
                leaf data-fill {
                  type string {
                    length "1..230";
                  }
                  description
                    "Specify an NQA test packet payload string.";
                }
                leaf ttl {
                  type uint8 {
                    range "1..255";
                  }
                  // NCS drop default statement
                  description
                    "Time to live.";
                }
                leaf pass-route {
                  type boolean;
                  // NCS drop default statement
                  description
                    "Enable/disable the function of sending packets without searching for routes.";
                }
                leaf probe-fails {
                  type uint32 {
                    range "1..15";
                  }
                  // NCS drop default statement
                  description
                    "The maximum number of probe failures of an NQA test to send trap or events.";
                }
                leaf test-fails {
                  type uint32 {
                    range "1..15";
                  }
                  // NCS drop default statement
                  description
                    "The maximum number of the NQA test consecutive test failures to send trap or events.";
                }
                leaf send-trap-bits {
                  type bits {
                    bit probefailure {
                      position 31;
                      description
                        "Indicates that a trap is sent when the OWD from the source to the destination exceeds the threshold.";
                    }
                    bit rtd {
                      position 28;
                      description
                        "Indicates that a trap is sent when the RTD exceeds the threshold.";
                    }
                    bit testcomplete {
                      position 29;
                      description
                        "Indicates that a trap is sent when a test succeeds.";
                    }
                    bit testfailure {
                      position 30;
                      description
                        "Indicates that a trap is sent when the number of test failures reaches the threshold.";
                    }
                  }
                  description
                    "Configure conditions for sending traps.";
                }
                leaf compatibility {
                  type boolean;
                  // NCS drop default statement
                  description
                    "Enable/disable compatibility mode. When the ptn79 interworks with the ptn39, the no result is converted to failed and success.";
                }
                leaf result-num {
                  type uint32 {
                    range "1..10";
                  }
                  // NCS drop default statement
                  description
                    "The maximum number of test result records.";
                }
                leaf history-num {
                  type uint32 {
                    range "0..1000";
                  }
                  // NCS drop default statement
                  description
                    "The maximum number of historical test records.";
                }
                leaf description {
                  type string {
                    length "1..230";
                  }
                  description
                    "Description of test instance.";
                }
                leaf age-time {
                  type pub-type:live_ncs_time;
                  // NCS drop default statement
                  description
                    "Aging time of test instance.";
                }
                leaf path-type {
                  type live_ncs_path-type;
                  description
                    "Path type.";
                }
                leaf threshold-rtd {
                  type uint32 {
                    range "1..60000";
                  }
                  description
                    "Threshold value of round trip delay.";
                }
                choice priority {
                  // NCS drop default statement
                  description
                    "Priority type.";
                  case tos-value {
                    description
                      "ToS value.";
                    leaf tos {
                      type uint16 {
                        range "0..255";
                      }
                      // NCS drop default statement
                      description
                        "ToS.";
                    }
                  }
                  case dscp-value {
                    description
                      "DSCP value.";
                    leaf dscp {
                      type uint32 {
                        range "0..63";
                      }
                      description
                        "DSCP value.";
                    }
                  }
                }
              }
            }
            case trace {
              description
                "TRACE NQA test.";
              container trace-input {
                // NCS drop must statement
                // NCS drop must statement
                presence "Present enable trace test instance input.";
                description
                  "Enable/disable trace test instance input.";
                // NCS expand uses statement
                choice address {
                  description
                    "Address information.";
                  case ipv4-address {
                    description
                      "IPv4 address.";
                    leaf ipv4-dest-address {
                      type inet:ipv4-address-no-zone;
                      description
                        "Destination IPv4 address.";
                    }
                    leaf ipv4-source-address {
                      type inet:ipv4-address-no-zone;
                      description
                        "Source IPv4 address.";
                    }
                    leaf ipv4-next-hop {
                      type inet:ipv4-address-no-zone;
                      description
                        "IPv4 next hop address.";
                    }
                  }
                  case ipv6-address {
                    description
                      "IPv6 address.";
                    leaf ipv6-dest-address {
                      type inet:ipv6-address-no-zone;
                      description
                        "Destination IPv6 address.";
                    }
                    leaf ipv6-source-address {
                      type inet:ipv6-address-no-zone;
                      description
                        "Source IPv6 address.";
                    }
                    leaf ipv6-next-hop {
                      type inet:ipv6-address-no-zone;
                      description
                        "IPv6 next hop address.";
                    }
                  }
                }
                leaf timeout {
                  type uint32 {
                    range "1..60";
                  }
                  units "s";
                  // NCS drop default statement
                  description
                    "Time to wait for a response packet after a test packet is sent.";
                }
                leaf first-ttl {
                  type uint8 {
                    range "1..255";
                  }
                  // NCS drop default statement
                  description
                    "Start TTL of probe packet.";
                }
                leaf max-ttl {
                  type uint8 {
                    range "1..255";
                  }
                  // NCS drop default statement
                  description
                    "Maximum TTL of probe packet.";
                }
                leaf probe-count {
                  type uint32 {
                    range "1..15";
                  }
                  // NCS drop default statement
                  description
                    "Number of sent packets.";
                }
                leaf data-size {
                  type uint32 {
                    range "0..8100";
                  }
                  units "Byte";
                  // NCS drop default statement
                  description
                    "Packet size.";
                }
                leaf ni-name {
                  type leafref {
                    path "/ncs:devices/ncs:device/ncs:live-status/ni:network-instance/ni:instances/ni:instance/ni:name" {
                      tailf:xpath-root 3;
                    }
                  }
                  // NCS drop default statement
                  description
                    "Name of a VPN instance.";
                }
                leaf result-num {
                  type uint32 {
                    range "1..10";
                  }
                  // NCS drop default statement
                  description
                    "The maximum number of test result records.";
                }
                leaf history-num {
                  type uint32 {
                    range "0..1000";
                  }
                  // NCS drop default statement
                  description
                    "The maximum number of historical test records.";
                }
                leaf description {
                  type string {
                    length "1..230";
                  }
                  description
                    "Description of test instance.";
                }
                leaf age-time {
                  type pub-type:live_ncs_time;
                  // NCS drop default statement
                  description
                    "Aging time of test instance.";
                }
                leaf frequency {
                  type uint32 {
                    range "60..604800";
                  }
                  description
                    "Cyclic scheduling period of test cases.";
                }
                choice priority {
                  // NCS drop default statement
                  description
                    "Priority type.";
                  case tos-value {
                    description
                      "ToS value.";
                    leaf tos {
                      type uint16 {
                        range "0..255";
                      }
                      // NCS drop default statement
                      description
                        "ToS.";
                    }
                  }
                  case dscp-value {
                    description
                      "DSCP value.";
                    leaf dscp {
                      type uint32 {
                        range "0..63";
                      }
                      description
                        "DSCP value.";
                    }
                  }
                }
                leaf data-fill {
                  type string {
                    length "1..230";
                  }
                  description
                    "Specify an NQA test packet payload string.";
                }
                leaf dest-port {
                  type uint16 {
                    range "1..65535";
                  }
                  // NCS drop default statement
                  description
                    "TRACE destination port number.";
                }
                leaf hop-fail-times {
                  type uint32 {
                    range "1..255";
                  }
                  // NCS drop default statement
                  description
                    "The times of hop failure.";
                }
                leaf pass-route {
                  type boolean;
                  // NCS drop default statement
                  description
                    "Enable/disable the function of sending packets without searching for routes.";
                }
                leaf out-if-name {
                  type leafref {
                    path "/ncs:devices/ncs:device/ncs:live-status/ifm:ifm/ifm:interfaces/ifm:interface/ifm:name" {
                      tailf:xpath-root 3;
                    }
                  }
                  description
                    "Out interface name.";
                  // NCS drop must statement
                }
                leaf test-fail-times {
                  type uint32 {
                    range "1..15";
                  }
                  // NCS drop default statement
                  description
                    "The maximum number of the NQA test consecutive test failures to send trap or events.";
                }
                leaf threshold-rtd {
                  type uint32 {
                    range "1..60000";
                  }
                  description
                    "Threshold value of round trip delay.";
                }
                leaf non-fragment {
                  type boolean;
                  // NCS drop default statement
                  description
                    "Enable/disable the mark of message no fragment.";
                }
                leaf send-trap-bits {
                  type bits {
                    bit rtd {
                      position 28;
                      description
                        "Indicates that a trap is sent when the RTD exceeds the threshold.";
                    }
                    bit testcomplete {
                      position 29;
                      description
                        "Indicates that a trap is sent when a test succeeds.";
                    }
                    bit testfailure {
                      position 30;
                      description
                        "Indicates that a trap is sent when the number of test failures reaches the threshold.";
                    }
                  }
                  description
                    "Configure conditions for sending traps.";
                }
              }
            }
            case udp {
              description
                "UDP NQA test.";
              container udp-input {
                // NCS drop must statement
                presence "Present enable UDP test instance input.";
                description
                  "Enable/disable UDP test instance input.";
                // NCS expand uses statement
                choice address {
                  description
                    "Address information.";
                  case ipv4-address {
                    description
                      "IPv4 address.";
                    leaf ipv4-dest-address {
                      type inet:ipv4-address-no-zone;
                      description
                        "Destination IPv4 address.";
                    }
                    leaf ipv4-source-address {
                      type inet:ipv4-address-no-zone;
                      description
                        "Source IPv4 address.";
                    }
                  }
                  case ipv6-address {
                    description
                      "IPv6 address.";
                    leaf ipv6-dest-address {
                      type inet:ipv6-address-no-zone;
                      description
                        "Destination IPv6 address.";
                    }
                    leaf ipv6-source-address {
                      type inet:ipv6-address-no-zone;
                      description
                        "Source IPv6 address.";
                    }
                  }
                }
                leaf dest-port {
                  type uint16 {
                    range "1..65535";
                  }
                  // NCS drop default statement
                  description
                    "UDP destination port.";
                }
                leaf source-port {
                  type uint16 {
                    range "1..65535";
                  }
                  description
                    "UDP source port.";
                }
                leaf ttl {
                  type uint8 {
                    range "1..255";
                  }
                  // NCS drop default statement
                  description
                    "Time to live.";
                }
                leaf data-size {
                  type uint16 {
                    range "0..8100";
                  }
                  units "Byte";
                  // NCS drop default statement
                  description
                    "Packet size.";
                }
                leaf pass-route {
                  type boolean;
                  // NCS drop default statement
                  description
                    "Enable/disable the function of sending packets without searching for routes.";
                }
                leaf probe-count {
                  type uint32 {
                    range "1..15";
                  }
                  // NCS drop default statement
                  description
                    "Number of sent packets.";
                }
                leaf send-trap-bits {
                  type bits {
                    bit probefailure {
                      position 31;
                      description
                        "Indicates that a trap is sent when the OWD from the source to the destination exceeds the threshold.";
                    }
                    bit rtd {
                      position 28;
                      description
                        "Indicates that a trap is sent when the RTD exceeds the threshold.";
                    }
                    bit testcomplete {
                      position 29;
                      description
                        "Indicates that a trap is sent when a test succeeds.";
                    }
                    bit testfailure {
                      position 30;
                      description
                        "Indicates that a trap is sent when the number of test failures reaches the threshold.";
                    }
                  }
                  description
                    "Configure conditions for sending traps.";
                }
                leaf threshold-rtd {
                  type uint32 {
                    range "1..60000";
                  }
                  description
                    "Threshold value of round trip delay.";
                }
                leaf probe-failtimes {
                  type uint32 {
                    range "1..15";
                  }
                  // NCS drop default statement
                  description
                    "The maximum number of probe failures of an NQA test to send trap or events.";
                }
                leaf test-failtimes {
                  type uint32 {
                    range "1..15";
                  }
                  // NCS drop default statement
                  description
                    "The maximum number of the NQA test consecutive test failures to send trap or events.";
                }
                leaf tos {
                  type uint16 {
                    range "0..255";
                  }
                  // NCS drop default statement
                  description
                    "ToS.";
                }
                leaf fail-percent {
                  type uint32 {
                    range "1..100";
                  }
                  units "%";
                  // NCS drop default statement
                  description
                    "Loss ratio, determining whether the test is successful.";
                }
                leaf interval {
                  type uint32 {
                    range "1..60";
                  }
                  units "s";
                  // NCS drop default statement
                  description
                    "Interval for sending packets.";
                }
                leaf ni-name {
                  type leafref {
                    path "/ncs:devices/ncs:device/ncs:live-status/ni:network-instance/ni:instances/ni:instance/ni:name" {
                      tailf:xpath-root 3;
                    }
                  }
                  // NCS drop default statement
                  description
                    "Name of a VPN instance.";
                }
                leaf timeout {
                  type uint32 {
                    range "1..60";
                  }
                  units "s";
                  // NCS drop default statement
                  description
                    "Time to wait for a response packet after a test packet is sent.";
                }
                leaf data-fill {
                  type string {
                    length "1..230";
                  }
                  description
                    "Specify an NQA test packet payload string.";
                }
                leaf description {
                  type string {
                    length "1..230";
                  }
                  description
                    "Description of test instance.";
                }
                leaf result-num {
                  type uint32 {
                    range "1..10";
                  }
                  // NCS drop default statement
                  description
                    "The maximum number of test result records.";
                }
                leaf history-num {
                  type uint32 {
                    range "0..1000";
                  }
                  // NCS drop default statement
                  description
                    "The maximum number of historical test records.";
                }
                leaf age-time {
                  type pub-type:live_ncs_time;
                  // NCS drop default statement
                  description
                    "Aging time of test instance.";
                }
                leaf frequency {
                  type uint32 {
                    range "1..604800";
                  }
                  units "s";
                  description
                    "Cyclic scheduling period of test cases. The frequency must be greater than the value of the following formula; otherwise, the test results may be inaccurate:
                     (Number of Sent Packets - 1) * (Packet Sending Interval) + (Timeout Period).";
                }
              }
            }
            case tcp {
              description
                "TCP NQA test.";
              container tcp-input {
                presence "Present enable TCP test instance input.";
                description
                  "Enable/disable TCP test instance input.";
                // NCS expand uses statement
                leaf dest-address {
                  type inet:ipv4-address-no-zone;
                  description
                    "Destination IP address.";
                }
                leaf source-address {
                  type inet:ipv4-address-no-zone;
                  description
                    "Source IP address.";
                }
                leaf interval {
                  type uint32 {
                    range "1..60";
                  }
                  units "s";
                  // NCS drop default statement
                  description
                    "Interval for sending packets.";
                }
                leaf timeout {
                  type uint32 {
                    range "1..60";
                  }
                  units "s";
                  // NCS drop default statement
                  description
                    "Time to wait for a response packet after a test packet is sent.";
                }
                leaf ttl {
                  type uint8 {
                    range "1..255";
                  }
                  // NCS drop default statement
                  description
                    "TTL value of NQA test packets.";
                }
                leaf probe-count {
                  type uint32 {
                    range "1..15";
                  }
                  // NCS drop default statement
                  description
                    "Number of sent packets.";
                }
                leaf tos {
                  type uint16 {
                    range "0..255";
                  }
                  // NCS drop default statement
                  description
                    "ToS.";
                }
                leaf dest-port {
                  type uint16 {
                    range "1..65535";
                  }
                  // NCS drop default statement
                  description
                    "TCP destination port number.";
                }
                leaf source-port {
                  type uint16 {
                    range "1..65535";
                  }
                  description
                    "TCP source port number.";
                }
                leaf pass-route {
                  type boolean;
                  // NCS drop default statement
                  description
                    "Enable/disable the function of sending packets without searching for routes.";
                }
                leaf ni-name {
                  type leafref {
                    path "/ncs:devices/ncs:device/ncs:live-status/ni:network-instance/ni:instances/ni:instance/ni:name" {
                      tailf:xpath-root 3;
                    }
                  }
                  // NCS drop default statement
                  description
                    "Name of a VPN instance.";
                }
                leaf threshold-rtd {
                  type uint32 {
                    range "1..60000";
                  }
                  description
                    "Threshold value of round trip delay.";
                }
                leaf probe-fails {
                  type uint32 {
                    range "1..15";
                  }
                  // NCS drop default statement
                  description
                    "The maximum number of probe failures of an NQA test to send trap or events.";
                }
                leaf fail-percent {
                  type uint32 {
                    range "1..100";
                  }
                  units "%";
                  // NCS drop default statement
                  description
                    "The rate of loss that the test case performed successfully.";
                }
                leaf test-fail-times {
                  type uint32 {
                    range "1..15";
                  }
                  // NCS drop default statement
                  description
                    "The maximum number of the NQA test consecutive test failures to send trap or events.";
                }
                leaf result-num {
                  type uint32 {
                    range "1..10";
                  }
                  // NCS drop default statement
                  description
                    "The maximum number of test result records.";
                }
                leaf history-num {
                  type uint32 {
                    range "0..1000";
                  }
                  // NCS drop default statement
                  description
                    "The maximum number of historical test records.";
                }
                leaf description {
                  type string {
                    length "1..230";
                  }
                  description
                    "Description of test instance.";
                }
                leaf age-time {
                  type pub-type:live_ncs_time;
                  // NCS drop default statement
                  description
                    "Aging time of test instance.";
                }
                leaf frequency {
                  type uint32 {
                    range "1..604800";
                  }
                  units "s";
                  description
                    "Cyclic scheduling period of test cases. The frequency must be greater than the value of the following formula; otherwise, the test results may be inaccurate:
                     (number of sent packets - 1) * (packet sending interval) + (timeout period).";
                }
              }
            }
            case jitter {
              description
                "Jitter NQA test that tests UDP-packet jitter.";
              container jitter-input {
                // NCS drop must statement
                // NCS drop must statement
                // NCS drop must statement
                presence "Present enable jitter test instance input";
                description
                  "Enable/disable jitter test instance input.";
                // NCS expand uses statement
                choice address {
                  description
                    "IP address configurations.";
                  case ipv4-address {
                    description
                      "IPv4 address.";
                    leaf ipv4-dest-address {
                      type inet:ipv4-address-no-zone;
                      description
                        "Destination IPv4 address.";
                    }
                    leaf ipv4-source-address {
                      type inet:ipv4-address-no-zone;
                      description
                        "Source IPv4 address.";
                    }
                  }
                  case ipv6-address {
                    description
                      "IPv6 address.";
                    leaf ipv6-dest-address {
                      type inet:ipv6-address-no-zone;
                      description
                        "Destination IPv6 address.";
                    }
                    leaf ipv6-source-address {
                      type inet:ipv6-address-no-zone;
                      description
                        "Source IPv6 address.";
                    }
                  }
                }
                leaf dest-port {
                  type uint16 {
                    range "1..65535";
                  }
                  description
                    "UDP destination port.";
                }
                leaf source-port {
                  type uint16 {
                    range "1..65535";
                  }
                  description
                    "UDP source port.";
                }
                leaf ttl {
                  type uint8 {
                    range "1..255";
                  }
                  // NCS drop default statement
                  description
                    "Time to live.";
                }
                leaf hardware-enable {
                  type boolean;
                  // NCS drop default statement
                  description
                    "Enable/disable packets are sent by hardware.";
                }
                leaf interval {
                  type uint32 {
                    range "10..60000";
                  }
                  units "ms";
                  // NCS drop default statement
                  description
                    "Interval for sending packets.";
                }
                leaf probe-count {
                  type uint32 {
                    range "1..15";
                  }
                  ext:dynamic-default {
                    ext:default-value "3" {
                      // NCS drop when statement
                      description
                        "The default value is 3 when code-type is none.";
                    }
                    ext:default-value "1" {
                      // NCS drop when statement
                      description
                        "The default value is 1 when code-type is g711a, g711u or g729a.";
                    }
                  }
                  description
                    "Number of probes.";
                }
                leaf jitter-packet-num {
                  type uint32 {
                    range "1..3000";
                  }
                  ext:dynamic-default {
                    ext:default-value "20" {
                      // NCS drop when statement
                      description
                        "The default value is 20 when code-type is none.";
                    }
                    ext:default-value "1000" {
                      // NCS drop when statement
                      description
                        "The default value is 1000 when code-type is g711a, g711u or g729a.";
                    }
                  }
                  description
                    "Number of sent packets.";
                }
                leaf data-size {
                  type uint16 {
                    range "0..8100";
                  }
                  units "Byte";
                  // NCS drop must statement
                  ext:dynamic-default {
                    ext:default-value "0" {
                      // NCS drop when statement
                      description
                        "The default value is 0 when code-type is none.";
                    }
                    ext:default-value "172" {
                      // NCS drop when statement
                      description
                        "The default value is 172 when code-type is g711a or g711u.";
                    }
                    ext:default-value "32" {
                      // NCS drop when statement
                      description
                        "The default value is 32 when code-type is g729a.";
                    }
                  }
                  description
                    "Packet size.";
                }
                leaf data-fill {
                  type string {
                    length "1..230";
                  }
                  description
                    "Specify an NQA test packet payload string.";
                }
                leaf pass-route {
                  type boolean;
                  // NCS drop default statement
                  description
                    "Enable/disable the function of sending packets without searching for routes.";
                }
                leaf tos {
                  type uint16 {
                    range "0..255";
                  }
                  // NCS drop default statement
                  description
                    "ToS.";
                }
                leaf ni-name {
                  type leafref {
                    path "/ncs:devices/ncs:device/ncs:live-status/ni:network-instance/ni:instances/ni:instance/ni:name" {
                      tailf:xpath-root 3;
                    }
                  }
                  // NCS drop default statement
                  description
                    "Name of a VPN instance.";
                }
                leaf code-type {
                  type live_ncs_jitter-code-type;
                  // NCS drop default statement
                  description
                    "Code type.";
                }
                leaf adv-factor {
                  // NCS drop when statement
                  type uint8 {
                    range "0..20";
                  }
                  // NCS drop default statement
                  description
                    "Advantage factor.";
                }
                leaf threshold-owd-ds {
                  type uint32 {
                    range "1..60000";
                  }
                  description
                    "One way delay threshold value from destination to source.";
                }
                leaf threshold-owd-sd {
                  type uint32 {
                    range "1..60000";
                  }
                  description
                    "One way delay threshold value from source to destination.";
                }
                leaf threshold-rtd {
                  type uint32 {
                    range "1..60000";
                  }
                  description
                    "Threshold value of round trip delay.";
                }
                leaf fail-percent {
                  type uint32 {
                    range "1..100";
                  }
                  units "%";
                  // NCS drop default statement
                  description
                    "Indicates the packet loss ratio threshold of an NQA test instance. If the packet loss ratio exceeds the threshold, the test fails.";
                }
                leaf test-failtimes {
                  type uint32 {
                    range "1..15";
                  }
                  // NCS drop default statement
                  description
                    "The maximum number of the NQA test consecutive test failures to send trap or events.";
                }
                leaf timestamp {
                  type live_ncs_time-unit-type;
                  // NCS drop default statement
                  description
                    "The unit of timestamp.";
                }
                leaf out-if-name {
                  type leafref {
                    path "/ncs:devices/ncs:device/ncs:live-status/ifm:ifm/ifm:interfaces/ifm:interface/ifm:name" {
                      tailf:xpath-root 3;
                    }
                  }
                  description
                    "Out interface name.";
                  // NCS drop must statement
                }
                leaf timeout {
                  type uint32 {
                    range "1..60";
                  }
                  units "s";
                  // NCS drop default statement
                  description
                    "Time to wait for a response packet after a test packet is sent.";
                }
                leaf result-num {
                  type uint32 {
                    range "1..10";
                  }
                  // NCS drop default statement
                  description
                    "The maximum number of test result records.";
                }
                leaf history-num {
                  type uint32 {
                    range "0..1000";
                  }
                  // NCS drop default statement
                  description
                    "The maximum number of historical test records.";
                }
                leaf description {
                  type string {
                    length "1..230";
                  }
                  description
                    "Description of test instance.";
                }
                leaf age-time {
                  type pub-type:live_ncs_time;
                  // NCS drop default statement
                  description
                    "Aging time of test instance.";
                }
                leaf frequency {
                  type uint32 {
                    range "1..604800";
                  }
                  units "s";
                  description
                    "Cyclic scheduling period of test cases. The frequency must be greater than the value of the following formula; otherwise, the test results may be inaccurate:
                     (number of sent packets - 1) * (packet sending interval) + (timeout period).";
                }
              }
            }
            case icmp-jitter {
              description
                "ICMP jitter NQA test.";
              container icmp-jitter-input {
                presence "Present enable ICMP jitter test instance input.";
                description
                  "Enable/disable ICMP jitter test instance input.";
                // NCS expand uses statement
                choice address {
                  description
                    "IP address configurations.";
                  case ipv4-address {
                    description
                      "IPv4 address.";
                    leaf ipv4-dest-address {
                      type inet:ipv4-address-no-zone;
                      description
                        "Destination IPv4 address.";
                    }
                    leaf ipv4-source-address {
                      type inet:ipv4-address-no-zone;
                      description
                        "Source IPv4 address.";
                    }
                  }
                  case ipv6-address {
                    description
                      "IPv6 address.";
                    leaf ipv6-dest-address {
                      type inet:ipv6-address-no-zone;
                      description
                        "Destination IPv6 address.";
                    }
                    leaf ipv6-source-address {
                      type inet:ipv6-address-no-zone;
                      description
                        "Source IPv6 address.";
                    }
                  }
                }
                leaf ttl {
                  type uint8 {
                    range "1..255";
                  }
                  // NCS drop default statement
                  description
                    "Time to live.";
                }
                leaf probe-count {
                  type uint32 {
                    range "1..15";
                  }
                  // NCS drop default statement
                  description
                    "Number of probes.";
                }
                leaf hardware-enable {
                  type boolean;
                  // NCS drop must statement
                  // NCS drop default statement
                  description
                    "Enable/disable packets are sent by hardware.";
                }
                leaf jitter-packet-num {
                  type uint32 {
                    range "1..3000";
                  }
                  // NCS drop default statement
                  description
                    "Number of packets.";
                }
                leaf data-size {
                  // NCS drop when statement
                  type uint16 {
                    range "0..8100";
                  }
                  units "Byte";
                  // NCS drop default statement
                  description
                    "Packet size.";
                }
                leaf data-fill {
                  // NCS drop when statement
                  type string {
                    length "1..230";
                  }
                  description
                    "Specify an NQA test packet payload string.";
                }
                leaf tos {
                  type uint16 {
                    range "0..255";
                  }
                  // NCS drop default statement
                  description
                    "ToS.";
                }
                leaf ni-name {
                  type leafref {
                    path "/ncs:devices/ncs:device/ncs:live-status/ni:network-instance/ni:instances/ni:instance/ni:name" {
                      tailf:xpath-root 3;
                    }
                  }
                  // NCS drop default statement
                  description
                    "Name of a VPN instance.";
                }
                leaf jitter-mode {
                  // NCS drop when statement
                  type live_ncs_jitter-mode-type;
                  // NCS drop default statement
                  description
                    "Packet format.";
                }
                leaf interval {
                  type uint32 {
                    range "10..60000";
                  }
                  units "ms";
                  // NCS drop must statement
                  // NCS drop default statement
                  description
                    "Interval for sending packets.";
                }
                leaf timestamp {
                  // NCS drop when statement
                  type live_ncs_time-unit-type;
                  // NCS drop must statement
                  // NCS drop default statement
                  description
                    "The unit of timestamp.";
                }
                leaf out-if-name {
                  type leafref {
                    path "/ncs:devices/ncs:device/ncs:live-status/ifm:ifm/ifm:interfaces/ifm:interface/ifm:name" {
                      tailf:xpath-root 3;
                    }
                  }
                  description
                    "Out interface name.";
                  // NCS drop must statement
                }
                leaf timeout {
                  type uint32 {
                    range "1..60";
                  }
                  units "s";
                  // NCS drop default statement
                  description
                    "Time to wait for a response packet after a test packet is sent.";
                }
                leaf receive-timeunit {
                  type live_ncs_recv-time-unit-type;
                  // NCS drop must statement
                  // NCS drop default statement
                  description
                    "The unit of receive timestamp.";
                }
                leaf fail-percent {
                  type uint32 {
                    range "1..100";
                  }
                  units "%";
                  // NCS drop default statement
                  description
                    "Indicates the packet loss ratio threshold of an NQA test instance. If the packet loss ratio exceeds the threshold, the test fails.";
                }
                leaf result-num {
                  type uint32 {
                    range "1..10";
                  }
                  // NCS drop default statement
                  description
                    "The maximum number of test result records.";
                }
                leaf history-num {
                  type uint32 {
                    range "0..1000";
                  }
                  // NCS drop default statement
                  description
                    "The maximum number of historical test records.";
                }
                leaf description {
                  type string {
                    length "1..230";
                  }
                  description
                    "Description of test instance.";
                }
                leaf age-time {
                  type pub-type:live_ncs_time;
                  // NCS drop default statement
                  description
                    "Aging time of test instance.";
                }
                leaf frequency {
                  type uint32 {
                    range "1..604800";
                  }
                  units "s";
                  description
                    "Cyclic scheduling period of test cases. The frequency must be greater than the value of the following formula; otherwise, the test results may be inaccurate:
                     (number of sent packets - 1) * (packet sending interval) + (timeout period).";
                }
              }
            }
            case lsp-ping {
              description
                "LSP ping NQA test.";
              container lsp-ping-input {
                presence "Present enable LSP ping test instance input.";
                description
                  "Enable/disable LSP ping test instance input.";
                // NCS expand uses statement
                choice lsp-protocol {
                  // NCS drop default statement
                  description
                    "The LSP type. The default LSP type is IPv4.";
                  case ipv4 {
                    description
                      "The LSP type is LDP.";
                    container ldp-lsp-ping {
                      // NCS drop must statement
                      description
                        "Configure container of LDP LSP ping.";
                      leaf dest-address {
                        type inet:ipv4-address-no-zone;
                        description
                          "Destination IPv4 address.";
                      }
                      leaf mask-len {
                        type uint8 {
                          range "0..32";
                        }
                        description
                          "LSP IPv4 prefix mask length.";
                      }
                      leaf loopback-address {
                        // NCS drop when statement
                        type inet:ipv4-address-no-zone;
                        description
                          "Set a 127/8 address of MPLS ping packets' destination address in the IP header.";
                      }
                      leaf next-hop {
                        type inet:ipv4-address-no-zone;
                        description
                          "Next hop address.";
                      }
                      leaf reply-mode {
                        type live_ncs_ip-lsp-reply-mode-type;
                        // NCS drop default statement
                        description
                          "Specify an LSP test reply mode.";
                      }
                    }
                  }
                  case bgp {
                    description
                      "The LSP type is BGP.";
                    container bgp-lsp-ping {
                      // NCS drop must statement
                      presence "Present enable BGP LSP ping.";
                      description
                        "Configure container of BGP LSP ping.";
                      leaf dest-address {
                        type inet:ipv4-address-no-zone;
                        description
                          "Destination IPv4 address.";
                      }
                      leaf mask-len {
                        type uint8 {
                          range "0..32";
                        }
                        description
                          "LSP IPv4 prefix mask length.";
                      }
                      leaf loopback-address {
                        // NCS drop when statement
                        type inet:ipv4-address-no-zone;
                        description
                          "Set a 127/8 address of MPLS ping packets' destination address in the IP header.";
                      }
                      leaf next-hop {
                        type inet:ipv4-address-no-zone;
                        description
                          "Next hop address.";
                      }
                      leaf reply-mode {
                        type live_ncs_bgp-lsp-reply-mode-type;
                        // NCS drop default statement
                        description
                          "Specify an LSP test reply mode.";
                      }
                    }
                  }
                  case te {
                    description
                      "The LSP type is TE.";
                    container te-lsp-ping {
                      presence "Present enable TE LSP ping.";
                      description
                        "Configure container of TE LSP ping.";
                      leaf tunnel-name {
                        type leafref {
                          path "/ncs:devices/ncs:device/ncs:live-status/ifm:ifm/ifm:interfaces/ifm:interface/ifm:name" {
                            tailf:xpath-root 3;
                          }
                        }
                        description
                          "TE tunnel name.";
                      }
                      leaf lsp-path {
                        // NCS drop when statement
                        type live_ncs_lsp-ping-trace-lsp-path;
                        description
                          "Lsp path (hot-standby or primary).";
                      }
                      leaf reply-mode {
                        type live_ncs_te-lsp-reply-mode-type;
                        // NCS drop default statement
                        description
                          "Specify an LSP test reply mode.";
                      }
                    }
                  }
                  case srte {
                    description
                      "The LSP type is SR-TE.";
                    container srte-lsp-ping {
                      presence "Present enable SR-TE LSP ping.";
                      description
                        "Configure container of SR-TE LSP ping.";
                      leaf tunnel-name {
                        type leafref {
                          path "/ncs:devices/ncs:device/ncs:live-status/ifm:ifm/ifm:interfaces/ifm:interface/ifm:name" {
                            tailf:xpath-root 3;
                          }
                        }
                        description
                          "TE tunnel name.";
                      }
                      leaf lsp-path {
                        // NCS drop when statement
                        type live_ncs_lsp-ping-trace-lsp-path;
                        description
                          "Lsp path (hot-standby or primary).";
                      }
                    }
                  }
                  case srbe {
                    description
                      "The LSP type is SR-BE.";
                    container srbe-lsp-ping {
                      // NCS drop must statement
                      presence "Present enable SR-BE LSP ping.";
                      description
                        "Configure container of SR-BE LSP ping.";
                      leaf dest-address {
                        type inet:ipv4-address-no-zone;
                        description
                          "Destination IP address.";
                      }
                      leaf mask-len {
                        type uint8 {
                          range "0..32";
                        }
                        description
                          "LSP IPv4 prefix mask length.";
                      }
                      leaf flex-algo-id {
                        type uint8 {
                          range "128..255";
                        }
                        description
                          "Flexible algorithm ID.";
                      }
                      leaf path-type {
                        type live_ncs_path-type;
                        description
                          "Path type.";
                      }
                      choice remote-fec {
                        description
                          "Remote FEC type.";
                        case ldp {
                          description
                            "Configure the remote FEC type as LDP.";
                          container remote-fec-ldp {
                            // NCS drop must statement
                            presence "Present enable remote FEC type as LDP.";
                            description
                              "Configure container of remote FEC LDP.";
                            leaf remote-fec-ip-address {
                              type inet:ipv4-address-no-zone;
                              description
                                "Configure remote FEC IPv4 address.";
                            }
                            leaf remote-mask-len {
                              type uint8 {
                                range "0..32";
                              }
                              description
                                "Configure remote FEC mask length.";
                            }
                          }
                        }
                      }
                    }
                  }
                  case srte-policy {
                    description
                      "The LSP type is SR-TE policy.";
                    container srte-policy-lsp-ping {
                      // NCS drop must statement
                      presence "Present enable SR-TE policy LSP ping.";
                      description
                        "Configure container of SR-TE policy LSP ping.";
                      choice probe-type {
                        description
                          "Probe type of SR-TE policy.";
                        case policy-name {
                          description
                            "Policy name.";
                          leaf policy-name {
                            type string {
                              length "1..31";
                            }
                            description
                              "SR-TE policy name.";
                          }
                        }
                        case end-point {
                          description
                            "End point.";
                          leaf end-point-ip {
                            type inet:ipv4-address-no-zone;
                            description
                              "Endpoint IPv4 address.";
                          }
                          leaf color {
                            type uint32 {
                              range "1..4294967295";
                            }
                            description
                              "Endpoint color ID.";
                          }
                        }
                        case binding-sid {
                          description
                            "Policy name.";
                          leaf binding-sid {
                            type uint32 {
                              range "16..1048575";
                            }
                            description
                              "Binding segmentlist ID.";
                          }
                        }
                      }
                    }
                  }
                }
                leaf timeout {
                  type uint32 {
                    range "1..60";
                  }
                  units "s";
                  // NCS drop default statement
                  description
                    "Time to wait for a response packet after test packets are sent.";
                }
                leaf frag-flag {
                  type boolean;
                  // NCS drop default statement
                  description
                    "Enable/disable packet fragmentation function.";
                }
                leaf source-address {
                  type inet:ipv4-address-no-zone;
                  description
                    "Source IPv4 address.";
                }
                leaf exp {
                  type uint8 {
                    range "0..7";
                  }
                  // NCS drop default statement
                  description
                    "Configures the LSP EXP value.";
                }
                leaf ttl {
                  type uint8 {
                    range "1..255";
                  }
                  // NCS drop default statement
                  description
                    "TTL value of NQA test packets.";
                }
                leaf interval {
                  type uint32 {
                    range "1..60";
                  }
                  units "s";
                  // NCS drop default statement
                  description
                    "Interval for sending packets.";
                }
                leaf probe-count {
                  type uint32 {
                    range "1..15";
                  }
                  // NCS drop default statement
                  description
                    "Number of sent packets.";
                }
                leaf data-size {
                  type uint32 {
                    range "0..9600";
                  }
                  units "Byte";
                  // NCS drop default statement
                  description
                    "Packet size.";
                }
                leaf data-fill {
                  type string {
                    length "1..230";
                  }
                  description
                    "Specify an NQA test packet payload string.";
                }
                leaf fail-percent {
                  type uint32 {
                    range "1..100";
                  }
                  units "%";
                  // NCS drop default statement
                  description
                    "Indicates the packet loss ratio threshold of an NQA test instance. If the packet loss ratio exceeds the threshold, the test fails.";
                }
                leaf result-num {
                  type uint32 {
                    range "1..10";
                  }
                  // NCS drop default statement
                  description
                    "The maximum number of test result records.";
                }
                leaf history-num {
                  type uint32 {
                    range "0..1000";
                  }
                  // NCS drop default statement
                  description
                    "The maximum number of historical test records.";
                }
                leaf description {
                  type string {
                    length "1..230";
                  }
                  description
                    "Description of test instance.";
                }
                leaf age-time {
                  type pub-type:live_ncs_time;
                  // NCS drop default statement
                  description
                    "Aging time of test instance.";
                }
                leaf frequency {
                  type uint32 {
                    range "1..604800";
                  }
                  units "s";
                  description
                    "Cyclic scheduling period of test cases. The frequency must be greater than the value of the following formula; otherwise, the test results may be inaccurate:
                     (number of sent packets - 1) * (packet sending interval) + (timeout period).";
                }
              }
            }
            case lsp-trace {
              description
                "LSP trace NQA test.";
              container lsp-trace-input {
                presence "Present enable LSP trace test instance input.";
                description
                  "Enable/disable LSP trace test instance input.";
                // NCS expand uses statement
                choice lsp-protocol {
                  // NCS drop default statement
                  description
                    "The LSP type. The default LSP type is IPv4.";
                  case ipv4 {
                    description
                      "The LSP type is LDP.";
                    container ldp-lsp-trace {
                      // NCS drop must statement
                      description
                        "Configure container of LDP LSP trace.";
                      leaf dest-address {
                        type inet:ipv4-address-no-zone;
                        description
                          "Destination IPv4 address.";
                      }
                      leaf mask-len {
                        type uint8 {
                          range "0..32";
                        }
                        description
                          "LSP IPv4 prefix mask length.";
                      }
                      leaf loopback-address {
                        // NCS drop when statement
                        type inet:ipv4-address-no-zone;
                        description
                          "Set a 127/8 address of MPLS ping packets' destination address in the IP header.";
                      }
                      leaf next-hop {
                        type inet:ipv4-address-no-zone;
                        description
                          "Next hop address.";
                      }
                      leaf reply-mode {
                        type live_ncs_ip-lsp-reply-mode-type;
                        // NCS drop default statement
                        description
                          "Specify an LSP test reply mode.";
                      }
                    }
                  }
                  case bgp {
                    description
                      "The LSP type is BGP.";
                    container bgp-lsp-trace {
                      // NCS drop must statement
                      presence "Present enable BGP LSP trace.";
                      description
                        "Configure container of BGP LSP trace.";
                      leaf dest-address {
                        type inet:ipv4-address-no-zone;
                        description
                          "Destination IPv4 address.";
                      }
                      leaf mask-len {
                        type uint8 {
                          range "0..32";
                        }
                        description
                          "LSP IPv4 prefix mask length.";
                      }
                      leaf loopback-address {
                        // NCS drop when statement
                        type inet:ipv4-address-no-zone;
                        description
                          "Set a 127/8 address of MPLS ping packets' destination address in the IP header.";
                      }
                      leaf next-hop {
                        type inet:ipv4-address-no-zone;
                        description
                          "Next hop address.";
                      }
                      leaf reply-mode {
                        type live_ncs_bgp-lsp-reply-mode-type;
                        // NCS drop default statement
                        description
                          "Specify an LSP test reply mode.";
                      }
                    }
                  }
                  case te {
                    description
                      "The LSP type is TE.";
                    container te-lsp-trace {
                      presence "Present enable TE LSP trace.";
                      description
                        "Configure container of TE LSP trace.";
                      leaf tunnel-name {
                        type leafref {
                          path "/ncs:devices/ncs:device/ncs:live-status/ifm:ifm/ifm:interfaces/ifm:interface/ifm:name" {
                            tailf:xpath-root 3;
                          }
                        }
                        description
                          "TE tunnel name.";
                      }
                      leaf next-hop {
                        type inet:ipv4-address-no-zone;
                        description
                          "Next hop address.";
                      }
                      leaf lsp-path {
                        // NCS drop when statement
                        type live_ncs_lsp-ping-trace-lsp-path;
                        description
                          "Lsp path (hot-standby or primary).";
                      }
                      leaf reply-mode {
                        type live_ncs_te-lsp-reply-mode-type;
                        // NCS drop default statement
                        description
                          "Specify an LSP test reply mode.";
                      }
                    }
                  }
                  case srte {
                    description
                      "The LSP type is SR-TE.";
                    container srte-lsp-trace {
                      presence "Present enable SR-TE LSP trace.";
                      description
                        "Configure container of SR-TE LSP trace.";
                      leaf tunnel-name {
                        type leafref {
                          path "/ncs:devices/ncs:device/ncs:live-status/ifm:ifm/ifm:interfaces/ifm:interface/ifm:name" {
                            tailf:xpath-root 3;
                          }
                        }
                        description
                          "TE tunnel name.";
                      }
                      leaf lsp-path {
                        // NCS drop when statement
                        type live_ncs_lsp-ping-trace-lsp-path;
                        description
                          "Lsp path (hot-standby or primary).";
                      }
                    }
                  }
                  case srbe {
                    description
                      "The LSP type is SR-BE.";
                    container srbe-lsp-trace {
                      // NCS drop must statement
                      presence "Present enable SR-BE LSP trace.";
                      description
                        "Configure container of SR-BE LSP trace.";
                      leaf dest-address {
                        type inet:ipv4-address-no-zone;
                        description
                          "Destination IPv4 address.";
                      }
                      leaf mask-len {
                        type uint8 {
                          range "0..32";
                        }
                        description
                          "LSP IPv4 prefix mask length.";
                      }
                      leaf flex-algo-id {
                        type uint8 {
                          range "128..255";
                        }
                        description
                          "Flexible algorithm ID.";
                      }
                      leaf path-type {
                        type live_ncs_path-type;
                        description
                          "Path type.";
                      }
                      choice remote-fec {
                        description
                          "Remote FEC type.";
                        case ldp {
                          description
                            "Configure the remote FEC type as LDP.";
                          container remote-fec-ldp {
                            // NCS drop must statement
                            presence "Present enable remote FEC type as LDP.";
                            description
                              "Configure container of remote FEC LDP.";
                            leaf remote-fec-ip-address {
                              type inet:ipv4-address-no-zone;
                              description
                                "Configure remote FEC IPv4 address.";
                            }
                            leaf remote-mask-len {
                              type uint8 {
                                range "0..32";
                              }
                              description
                                "Configure remote FEC mask length.";
                            }
                          }
                        }
                      }
                    }
                  }
                  case srte-policy {
                    description
                      "The LSP type is SR-TE policy.";
                    container srte-policy-lsp-trace {
                      // NCS drop must statement
                      presence "Present enable SR-TE policy LSP trace.";
                      description
                        "Configure container of SR-TE policy LSP trace.";
                      choice probe-type {
                        description
                          "Probe type of SR-TE policy.";
                        case policy-name {
                          description
                            "Policy name.";
                          leaf policy-name {
                            type string {
                              length "1..31";
                            }
                            description
                              "SR-TE policy name.";
                          }
                        }
                        case end-point {
                          description
                            "End point.";
                          leaf end-point-ip {
                            type inet:ipv4-address-no-zone;
                            description
                              "Endpoint IPv4 address.";
                          }
                          leaf color {
                            type uint32 {
                              range "1..4294967295";
                            }
                            description
                              "Endpoint color ID.";
                          }
                        }
                        case binding-sid {
                          description
                            "Policy name.";
                          leaf binding-sid {
                            type uint32 {
                              range "16..1048575";
                            }
                            description
                              "Binding segmentlist ID.";
                          }
                        }
                      }
                    }
                  }
                }
                leaf frag-flag {
                  type boolean;
                  // NCS drop default statement
                  description
                    "Enable/disable packet fragmentation function.";
                }
                leaf exp {
                  type uint8 {
                    range "0..7";
                  }
                  // NCS drop default statement
                  description
                    "Configures the LSP EXP value.";
                }
                leaf probe-count {
                  type uint32 {
                    range "1..15";
                  }
                  // NCS drop default statement
                  description
                    "Number of sent packets.";
                }
                leaf source-address {
                  type inet:ipv4-address-no-zone;
                  description
                    "Source IPv4 address.";
                }
                leaf first-ttl {
                  type uint8 {
                    range "1..255";
                  }
                  // NCS drop must statement
                  // NCS drop default statement
                  description
                    "Start TTL of probe packet.";
                }
                leaf max-ttl {
                  type uint8 {
                    range "1..255";
                  }
                  // NCS drop must statement
                  // NCS drop default statement
                  description
                    "Maximum TTL of probe packet.";
                }
                leaf timeout {
                  type uint32 {
                    range "1..60";
                  }
                  units "s";
                  // NCS drop default statement
                  description
                    "Time to wait for a response packet after a test packet is sent.";
                }
                leaf hop-fail-times {
                  type uint8 {
                    range "1..255";
                  }
                  // NCS drop default statement
                  description
                    "Specify the upper limit of the number of failed hops before the NQA tracert test stops.";
                }
                leaf result-num {
                  type uint32 {
                    range "1..10";
                  }
                  // NCS drop default statement
                  description
                    "The maximum number of test result records.";
                }
                leaf history-num {
                  type uint32 {
                    range "0..1000";
                  }
                  // NCS drop default statement
                  description
                    "The maximum number of historical test records.";
                }
                leaf description {
                  type string {
                    length "1..230";
                  }
                  description
                    "Description of test instance.";
                }
                leaf age-time {
                  type pub-type:live_ncs_time;
                  // NCS drop default statement
                  description
                    "Aging time of test instance.";
                }
                leaf frequency {
                  type uint32 {
                    range "1..604800";
                  }
                  units "s";
                  // NCS drop must statement
                  description
                    "Cyclic scheduling period of test cases. The frequency must be greater than the value of the following formula; otherwise, the test results may be inaccurate:
                     (number of sent packets - 1) * (packet sending interval) + (timeout period).";
                }
              }
            }
            case lsp-jitter {
              description
                "LSP jitter NQA test.";
              container lsp-jitter-input {
                presence "Present enable LSP jitter test instance input";
                description
                  "Enable/disable LSP jitter test instance input.";
                // NCS expand uses statement
                choice lsp-protocol {
                  description
                    "The test-type of LSP.";
                  case te {
                    description
                      "The test-type of LSP is TE.";
                    container te-lsp-jitter {
                      presence "Present enable te jitter test instance input.";
                      description
                        "Enable/disable te jitter instance container.";
                      leaf tunnel-name {
                        type leafref {
                          path "/ncs:devices/ncs:device/ncs:live-status/ifm:ifm/ifm:interfaces/ifm:interface/ifm:name" {
                            tailf:xpath-root 3;
                          }
                        }
                        description
                          "TE tunnel name.";
                        // NCS drop must statement
                      }
                      leaf lsp-path {
                        // NCS drop when statement
                        type live_ncs_lsp-path;
                        // NCS drop default statement
                        description
                          "LSP path (working or hot-standby or primary).";
                      }
                      leaf reply-mode {
                        type live_ncs_lsp-reply-mode-type;
                        // NCS drop default statement
                        description
                          "Specify an LSP test reply mode.";
                      }
                    }
                  }
                }
                leaf timeout {
                  type uint32 {
                    range "1..60";
                  }
                  units "s";
                  // NCS drop default statement
                  description
                    "Time to wait for a response packet after a test packet is sent.";
                }
                leaf frag-flag {
                  type boolean;
                  // NCS drop default statement
                  description
                    "Enable/disable packet fragmentation function.";
                }
                leaf source-address {
                  type inet:ipv4-address-no-zone;
                  description
                    "Source IP address.";
                }
                leaf exp {
                  type uint8 {
                    range "0..7";
                  }
                  // NCS drop default statement
                  description
                    "Configures the LSP EXP value.";
                }
                leaf ttl {
                  type uint8 {
                    range "1..255";
                  }
                  // NCS drop default statement
                  description
                    "TTL value of NQA test packets.";
                }
                leaf interval {
                  type uint32 {
                    range "1..60";
                  }
                  units "s";
                  // NCS drop default statement
                  description
                    "Interval for sending packets.";
                }
                leaf probe-count {
                  type uint32 {
                    range "1..15";
                  }
                  // NCS drop default statement
                  description
                    "Number of probes.";
                }
                leaf jitter-packet-num {
                  type uint32 {
                    range "1..3000";
                  }
                  // NCS drop default statement
                  description
                    "Number of sent packets.";
                }
                leaf data-size {
                  type uint32 {
                    range "0..9600";
                  }
                  units "Byte";
                  // NCS drop default statement
                  description
                    "Packet size.";
                }
                leaf data-fill {
                  type string {
                    length "1..230";
                  }
                  description
                    "Specify an NQA test packet payload string.";
                }
                leaf fail-percent {
                  type uint32 {
                    range "1..100";
                  }
                  units "%";
                  // NCS drop default statement
                  description
                    "Indicates the packet loss ratio threshold of an NQA test instance. If the packet loss ratio exceeds the threshold, the test fails.";
                }
                leaf result-num {
                  type uint32 {
                    range "1..10";
                  }
                  // NCS drop default statement
                  description
                    "The maximum number of test result records.";
                }
                leaf history-num {
                  type uint32 {
                    range "0..1000";
                  }
                  // NCS drop default statement
                  description
                    "The maximum number of historical test records.";
                }
                leaf description {
                  type string {
                    length "1..230";
                  }
                  description
                    "Description of test instance.";
                }
                leaf age-time {
                  type pub-type:live_ncs_time;
                  // NCS drop default statement
                  description
                    "Aging time of test instance.";
                }
                leaf frequency {
                  type uint32 {
                    range "1..604800";
                  }
                  units "s";
                  description
                    "Cyclic scheduling period of test cases. The frequency must be greater than the value of the following formula; otherwise, the test results may be inaccurate:
                     (number of sent packets - 1) * (packet sending interval) + (timeout period).";
                }
              }
            }
            case pwe3-trace {
              description
                "PWE3 trace NQA test.";
              container pwe3-trace-input {
                presence "Present enable PWE3 trace test instance input";
                description
                  "Enable/disable PWE3 trace test instance input.";
                // NCS expand uses statement
                leaf vc-type {
                  type live_ncs_vc-type;
                  // NCS drop default statement
                  description
                    "VC type.";
                }
                leaf local-pw-type {
                  type live_ncs_pw-type;
                  // NCS drop default statement
                  description
                    "Local PW type.";
                }
                leaf local-pw-id {
                  type uint32 {
                    range "1..4294967295";
                  }
                  description
                    "Local PW ID.";
                }
                leaf label-type {
                  type live_ncs_pwe3-label-type;
                  // NCS drop default statement
                  description
                    "Label type.";
                }
                leaf dest-address {
                  type inet:ipv4-address-no-zone;
                  description
                    "Destination IP address. (Must specify the destination address to start the test)";
                }
                leaf timeout {
                  type uint32 {
                    range "1..60";
                  }
                  units "s";
                  // NCS drop default statement
                  description
                    "Time to wait for a response packet after a test packet is sent.";
                }
                leaf first-ttl {
                  type uint8 {
                    range "1..255";
                  }
                  // NCS drop must statement
                  // NCS drop default statement
                  description
                    "Start TTL of probe packet.";
                }
                leaf max-ttl {
                  type uint8 {
                    range "1..255";
                  }
                  // NCS drop must statement
                  // NCS drop default statement
                  description
                    "Maximum TTL of probe packet.";
                }
                leaf exp {
                  type uint8 {
                    range "0..7";
                  }
                  // NCS drop default statement
                  description
                    "Configures the Pwe3Trace EXP value.";
                }
                leaf reply-mode {
                  type live_ncs_lsp-reply-mode-type;
                  // NCS drop default statement
                  description
                    "Specify an LSP test reply mode.";
                }
                leaf packet-count {
                  type uint32 {
                    range "1..15";
                  }
                  units "packet";
                  // NCS drop default statement
                  description
                    "Number of sent packets.";
                }
                leaf probe-failtimes {
                  type uint32 {
                    range "1..15";
                  }
                  // NCS drop default statement
                  description
                    "The maximum number of probe failures of an NQA test to send trap or events.";
                }
                leaf test-failtimes {
                  type uint32 {
                    range "1..15";
                  }
                  // NCS drop default statement
                  description
                    "The maximum number of the NQA test consecutive test failures to send trap or events.";
                }
                leaf lsp-version {
                  type live_ncs_lsp-version;
                  // NCS drop default statement
                  description
                    "Lsp version.";
                }
                leaf threshold-rtd {
                  type uint32 {
                    range "1..60000";
                  }
                  description
                    "Threshold value of round trip delay.";
                }
                leaf ttl-mode {
                  type live_ncs_ttl-mode;
                  // NCS drop default statement
                  description
                    "TTL mode.";
                }
                leaf hop-fail-times {
                  type uint8 {
                    range "1..255";
                  }
                  // NCS drop default statement
                  description
                    "Specify the upper limit of the number of failed hops before the NQA tracert test stops.";
                }
                leaf frag-flag {
                  type boolean;
                  // NCS drop default statement
                  description
                    "Enable/disable packet fragmentation function.";
                }
                leaf peer-address {
                  type inet:ipv4-address-no-zone;
                  description
                    "Peer IP Address.";
                }
                leaf no-cw-flag {
                  // NCS drop when statement
                  type boolean;
                  // NCS drop default statement
                  description
                    "Enable/disable the option of not carrying control word.";
                }
                leaf result-num {
                  type uint32 {
                    range "1..10";
                  }
                  // NCS drop default statement
                  description
                    "The maximum number of test result records.";
                }
                leaf history-num {
                  type uint32 {
                    range "0..1000";
                  }
                  // NCS drop default statement
                  description
                    "The maximum number of historical test records.";
                }
                leaf description {
                  type string {
                    length "1..230";
                  }
                  description
                    "Description of test instance.";
                }
                leaf age-time {
                  type pub-type:live_ncs_time;
                  // NCS drop default statement
                  description
                    "Aging time of test instance.";
                }
                leaf frequency {
                  type uint32 {
                    range "60..604800";
                  }
                  units "s";
                  description
                    "Cyclic scheduling period of test cases. The frequency must be greater than the value of the following formula; otherwise, the test results may be inaccurate:
                     (number of sent packets - 1) * (packet sending interval) + (timeout period).";
                }
              }
            }
            case mac-ping {
              description
                "MAC ping NQA test.";
              container mac-ping-input {
                // NCS drop must statement
                // NCS drop must statement
                presence "Present enable MAC ping test instance input.";
                description
                  "Enable/disable MAC ping test instance input.";
                // NCS expand uses statement
                choice destination {
                  description
                    "Destination information.";
                  case mac-address {
                    description
                      "MAC address.";
                    leaf dest-mac-address {
                      type live_ncs_unicast-mac-address;
                      description
                        "Destination MAC, must be unicast MAC and not 0-0-0 MAC.";
                    }
                  }
                  case remote-mep-id {
                    description
                      "Remote MEP ID.";
                    leaf remote-mep-id {
                      type uint32 {
                        range "1..8191";
                      }
                      description
                        "Remote MEP ID.";
                    }
                  }
                }
                leaf mep-id {
                  type uint32 {
                    range "1..8191";
                  }
                  description
                    "MEP ID.";
                }
                leaf md-name {
                  type string {
                    length "1..43";
                  }
                  description
                    "Maintenance domain name.";
                }
                leaf ma-name {
                  type string {
                    length "1..43";
                  }
                  description
                    "Maintenance association name.";
                }
                leaf interval {
                  type uint32 {
                    range "1..60";
                  }
                  units "s";
                  // NCS drop default statement
                  description
                    "Interval for sending packets.";
                }
                leaf probe-count {
                  type uint32 {
                    range "1..15";
                  }
                  // NCS drop default statement
                  description
                    "Number of sent packets.";
                }
                leaf timeout {
                  type uint32 {
                    range "1..60";
                  }
                  units "s";
                  // NCS drop default statement
                  description
                    "Time to wait for a response packet after a test packet is sent.";
                }
                leaf data-size {
                  type uint32 {
                    range "64..2000";
                  }
                  units "Byte";
                  // NCS drop default statement
                  description
                    "Packet size.";
                }
                leaf source-if-name {
                  type leafref {
                    path "/ncs:devices/ncs:device/ncs:live-status/ifm:ifm/ifm:interfaces/ifm:interface/ifm:name" {
                      tailf:xpath-root 3;
                    }
                  }
                  description
                    "Out interface name.";
                  // NCS drop must statement
                }
                leaf fail-percent {
                  type uint32 {
                    range "1..100";
                  }
                  units "%";
                  // NCS drop default statement
                  description
                    "Loss ratio, determining whether the test is successful.";
                }
                leaf probe-fails {
                  type uint32 {
                    range "1..15";
                  }
                  // NCS drop default statement
                  description
                    "The maximum number of probe failures of an NQA test to send trap or events.";
                }
                leaf test-fails {
                  type uint32 {
                    range "1..15";
                  }
                  // NCS drop default statement
                  description
                    "The maximum number of the NQA test consecutive test failures to send trap or events.";
                }
                leaf send-trap-bits {
                  type bits {
                    bit probefailure {
                      position 31;
                      description
                        "Indicates that a trap is sent when the OWD from the source to the
                         destination exceeds the threshold.";
                    }
                    bit rtd {
                      position 28;
                      description
                        "Indicates that a trap is sent when the RTD exceeds the threshold.";
                    }
                    bit testcomplete {
                      position 29;
                      description
                        "Indicates that a trap is sent when a test succeeds.";
                    }
                    bit testfailure {
                      position 30;
                      description
                        "Indicates that a trap is sent when the number of test failures reaches the threshold.";
                    }
                  }
                  description
                    "Configure conditions for sending traps.";
                }
                leaf threshold-rtd {
                  type uint32 {
                    range "1..60000";
                  }
                  description
                    "Threshold value of round trip delay.";
                }
                leaf jitter-packet-num {
                  type uint32 {
                    range "1..3000";
                  }
                  // NCS drop default statement
                  description
                    "Number of sent packets.";
                }
                leaf frequency {
                  type uint32 {
                    range "1..604800";
                  }
                  units "s";
                  description
                    "Cyclic scheduling period of test cases. The Frequency must be greater than the value of the following formula; otherwise, the test results may be inaccurate:
                     (Number of Sent Packets - 1) * (Packet Sending Interval) + (Timeout Period)";
                }
                leaf result-num {
                  type uint32 {
                    range "1..10";
                  }
                  // NCS drop default statement
                  description
                    "The maximum number of test result records.";
                }
                leaf history-num {
                  type uint32 {
                    range "0..1000";
                  }
                  // NCS drop default statement
                  description
                    "The maximum number of historical test records.";
                }
                leaf description {
                  type string {
                    length "1..230";
                  }
                  description
                    "Description of test instance.";
                }
                leaf age-time {
                  type pub-type:live_ncs_time;
                  // NCS drop default statement
                  description
                    "Aging time of test instance.";
                }
              }
            }
            case arp-ping-ip {
              description
                "Arp ping IP NQA test.";
              container arp-ping-ip-input {
                presence "Present enable arp ping IP test intance input.";
                description
                  "Enable/disable arp ping IP test intance input.";
                // NCS expand uses statement
                leaf ipv4-dest-address {
                  type inet:ipv4-address-no-zone;
                  description
                    "Destination IPv4 address.";
                }
                leaf probe-count {
                  type uint32 {
                    range "1..15";
                  }
                  // NCS drop default statement
                  description
                    "Number of sent packets.";
                }
                leaf out-if-name {
                  type leafref {
                    path "/ncs:devices/ncs:device/ncs:live-status/ifm:ifm/ifm:interfaces/ifm:interface/ifm:name" {
                      tailf:xpath-root 3;
                    }
                  }
                  description
                    "Out interface name.";
                  // NCS drop must statement
                }
                leaf timeout {
                  type uint32 {
                    range "1..10";
                  }
                  units "s";
                  // NCS drop default statement
                  description
                    "Time to wait for a response packet after a test packet is sent, expressed in seconds.";
                }
                leaf result-num {
                  type uint32 {
                    range "1..10";
                  }
                  // NCS drop default statement
                  description
                    "The maximum number of test result records.";
                }
                leaf history-num {
                  type uint32 {
                    range "0..1000";
                  }
                  // NCS drop default statement
                  description
                    "The maximum number of historical test records.";
                }
                leaf description {
                  type string {
                    length "1..230";
                  }
                  description
                    "Description of test instance.";
                }
                leaf age-time {
                  type pub-type:live_ncs_time;
                  // NCS drop default statement
                  description
                    "Aging time of test instance.";
                }
                leaf frequency {
                  type uint32 {
                    range "1..604800";
                  }
                  units "s";
                  description
                    "Cyclic scheduling period of test cases. The frequency must be greater than the value of the following formula; otherwise, the test results may be inaccurate:
                     (Number of sent Packets - 1) * (Packet sending interval) + (Timeout period).";
                }
              }
            }
          }
          container execution-policy {
            description
              "Statistics of the test instance execution policy.";
            choice execution-policy {
              description
                "The test instance start policy.";
              case start {
                description
                  "Start the test.";
                choice start-type {
                  description
                    "The test instance start type.";
                  case start-now {
                    description
                      "Start now.";
                    leaf start-now {
                      type live_ncs_start-now-type;
                      description
                        "Start the test instance instantly.";
                    }
                    choice start-now-end-type {
                      description
                        "Test instance end type.";
                      case at {
                        description
                          "Stop the test at the specified time.";
                        leaf start-now-end-date-time {
                          type yang:date-and-time;
                          description
                            "The test instance end time.";
                        }
                      }
                      case delay {
                        description
                          "Stop the test after the specified delay time.";
                        leaf start-now-end-delay-seconds {
                          type uint32 {
                            range "6..86399";
                          }
                          units "s";
                          description
                            "The test instance end delay seconds.";
                        }
                      }
                      case lifetime {
                        description
                          "Stop the test after the specified life time.";
                        leaf start-now-end-lifetime-seconds {
                          type uint32 {
                            range "6..86399";
                          }
                          units "s";
                          description
                            "The test instance end lifetime seconds.";
                        }
                      }
                    }
                  }
                  case start-at {
                    description
                      "Execute at the specified time.";
                    leaf start-date-time {
                      type yang:date-and-time;
                      description
                        "The test instance start time.";
                    }
                    choice start-at-end-type {
                      description
                        "Test instance end type.";
                      case at {
                        description
                          "Stop the test at the specified time.";
                        leaf start-at-end-date-time {
                          type yang:date-and-time;
                          description
                            "The test instance end time.";
                        }
                      }
                      case delay {
                        description
                          "Stop the test after the specified delay time.";
                        leaf start-at-end-delay-seconds {
                          type uint32 {
                            range "6..86399";
                          }
                          units "s";
                          description
                            "The test instance end delay seconds.";
                        }
                      }
                      case lifetime {
                        description
                          "Stop the test after the specified life time.";
                        leaf start-at-end-lifetime-seconds {
                          type uint32 {
                            range "6..86399";
                          }
                          units "s";
                          description
                            "The test instance end lifetime seconds.";
                        }
                      }
                    }
                  }
                  case start-delay {
                    description
                      "Delay some time then execute testcase.";
                    leaf start-delay-seconds {
                      type uint32 {
                        range "1..86399";
                      }
                      units "s";
                      description
                        "The test instance start delay seconds.";
                    }
                    choice start-delay-end-type {
                      description
                        "Test instance end type.";
                      case at {
                        description
                          "Stop the test at the specified time.";
                        leaf start-delay-end-date-time {
                          type yang:date-and-time;
                          description
                            "The test instance end time.";
                        }
                      }
                      case delay {
                        description
                          "Stop the test after the specified delay time.";
                        leaf start-delay-end-delay-seconds {
                          type uint32 {
                            range "6..86399";
                          }
                          units "s";
                          description
                            "The test instance end delay seconds.";
                        }
                      }
                      case lifetime {
                        description
                          "Stop the test after the specified life time.";
                        leaf start-delay-end-lifetime-seconds {
                          type uint32 {
                            range "6..86399";
                          }
                          units "s";
                          description
                            "The test instance end lifetime seconds.";
                        }
                      }
                    }
                  }
                  case start-daily {
                    description
                      "Execute the test instance daily.";
                    leaf daily-start-time {
                      type pub-type:live_ncs_time;
                      description
                        "Start time of daily execution.";
                    }
                    leaf daily-start-date {
                      type pub-type:live_ncs_date;
                      description
                        "Start date of daily execution.";
                    }
                    leaf daily-end-time {
                      type pub-type:live_ncs_time;
                      description
                        "End time of daily execution.";
                    }
                    leaf daily-end-date {
                      type pub-type:live_ncs_date;
                      description
                        "End date of daily execution.";
                    }
                  }
                }
              }
              case stop {
                description
                  "Stop the test.";
                leaf stop {
                  type live_ncs_stop-type;
                  description
                    "Stop the test.";
                }
              }
            }
          }
        }
      }
      container record {
        description
          "Statistics of NQA test instance test record table.";
        uses nqa:live_ncs_record-type;
      }
    }
  }
  augment "/ncs:devices/ncs:template/ncs:ned-id/ncs:config" {
    container nqa {
      description
        "Network quality analysis (NQA) service.";
      container global {
        description
          "Configure NQA global configuration.";
        // NCS expand uses statement
        leaf fec-validation-ldp-enable {
          type string;
          // NCS drop default statement
          description
            "Enable/disable LDP FEC validation.";
        }
        leaf fec-validation-sr-prefix-enable {
          type string;
          // NCS drop default statement
          description
            "Enable/disable sr-prefix FEC validation.";
        }
        leaf lspv-cpu-limit {
          type string;
          // NCS drop default statement
          description
            "Lspv cpu limit.";
        }
        leaf jitter-tag-version {
          type string;
          // NCS drop default statement
          description
            "Version number of jitter.";
        }
        leaf lbm-receive-enable {
          type string;
          // NCS drop default statement
          description
            "Enable/disable a device from receiving LBM packets.";
        }
        leaf ltm-receive-enable {
          type string;
          // NCS drop default statement
          description
            "Enable/disable a device from receiving LTM packets.";
        }
        leaf gmac-ltm-receive-enable {
          type string;
          // NCS drop default statement
          description
            "Enable/disable a device from receiving GMAC-LTM packets.";
        }
        leaf lspv-enable {
          type string;
          // NCS drop default statement
          description
            "Enable/disable a device to respond to MPLS echo request packets.";
        }
        leaf lspv-ipv6-enable {
          type string;
          // NCS drop default statement
          description
            "Enable/disable a device to respond to MPLS echo request IPv6 packets.";
        }
        leaf lspv-fec-compitable-enable {
          type string;
          // NCS drop default statement
          description
            "Enable/disable the LSPV's compatibility function, and reply response packets don't carry FEC information.";
        }
        leaf gmac-ping-enable {
          type string;
          // NCS drop default statement
          description
            "Enable/disable general GMAC ping function.";
        }
        leaf gmac-trace-enable {
          type string;
          // NCS drop default statement
          description
            "Enable/disable general GMAC trace function.";
        }
        container vxlan-echo-v4 {
          presence "If enabled vxlan echo IPv4";
          description
            "Enable/disable NQA VXLANECHO.";
          leaf port {
            type string;
            // NCS drop mandatory statement
            description
              "Port of NQA VXLANECHO server.";
          }
          leaf source-ip-if-name {
            type string;
            description
              "Source ip interface of VXLANECHO.";
            // NCS drop must statement
          }
        }
        container bier6-oam {
          description
            "Configure BIERv6 OAM.";
          leaf dest-port {
            type string;
            // NCS drop default statement
            description
              "Destination UDP port of BIERv6 echo packet.";
          }
          leaf echo-reply-disable {
            type string;
            // NCS drop default statement
            description
              "Enable/disable BIERv6 reply function.";
          }
          leaf rate-limit {
            type string;
            units "pps";
            // NCS drop default statement
            description
              "BIERv6 receive rate limit.";
          }
        }
      }
      container server {
        description
          "Configure NQA server list.";
        uses nqa:ncs_template_server-type;
      }
      container reflectors {
        description
          "Configure reflector list.";
        // NCS expand uses statement
        list reflector {
          // NCS patched for predictable order
          ordered-by user;
          key "reflector-id";
          description
            "Configure reflector table.";
          leaf reflector-id {
            type string;
            description
              "Reflector ID.";
          }
          leaf if-name {
            type string;
            // NCS drop mandatory statement
            description
              "Reflector interface name.";
            // NCS drop must statement
          }
          leaf reflector-type {
            type ncs_template_reflect-type;
            // NCS drop mandatory statement
            description
              "Reflector type.";
          }
          leaf exchange-port {
            type string;
            // NCS drop default statement
            description
              "Enable/disable reflector UDP port exchange.";
          }
          leaf pe-vlan {
            type string;
            // NCS drop must statement
            description
              "Reflector PE VLAN ID.";
          }
          leaf ce-vlan {
            type string;
            // NCS drop must statement
            description
              "Reflector CE VLAN ID.";
          }
          leaf source-port {
            type string;
            // NCS drop must statement
            // NCS drop default statement
            description
              "Reflector source port.";
          }
          leaf dest-port {
            type string;
            // NCS drop must statement
            // NCS drop default statement
            description
              "Reflector destination port.";
          }
          leaf end-time {
            type string;
            // NCS drop mandatory statement
            description
              "Absolute time of reflector aging, the value must not be earlier than the current system time plus 10s or later than the current system time plus 173400s.";
          }
          leaf share-mode {
            type string;
            // NCS drop must statement
            // NCS drop default statement
            description
              "Enable/disable the share mode on the reflector.";
          }
          choice address {
            description
              "Reflector address.";
            case ipv4-address {
              description
                "Reflector IPv4 address.";
              leaf ipv4-address {
                type string;
                // NCS drop must statement
                description
                  "Reflector IPv4 address.";
              }
            }
            case simulate-ipv4-address {
              description
                "Reflector simulate IPv4 address.";
              leaf simulate-ipv4-address {
                type string;
                // NCS drop must statement
                description
                  "Reflector simulate IPv4 address.";
              }
            }
            case mac-address {
              description
                "Reflector MAC address.";
              leaf mac-address {
                type pub-type:ncs_template_mac-address;
                // NCS drop must statement
                description
                  "Reflector MAC address.";
              }
            }
          }
          // NCS drop config false leaf 'survival-time'
          // NCS drop config false leaf 'recommended-test-mac'
        }
      }
      container instances {
        description
          "Configure NQA test instance list.";
        // NCS expand uses statement
        list instance {
          // NCS patched for predictable order
          ordered-by user;
          key "admin-name test-name";
          description
            "Configure test instance.";
          leaf admin-name {
            type string;
            description
              "Administrator name.";
          }
          leaf test-name {
            type string;
            description
              "Test name.";
          }
          choice type {
            description
              "The test type of instance.";
            case icmp {
              description
                "ICMP NQA test.";
              container icmp-input {
                // NCS drop must statement
                // NCS drop must statement
                // NCS drop must statement
                // NCS drop must statement
                // NCS drop must statement
                presence "ICMP PING test instance.";
                description
                  "Enable/disable ICMP test instance input.";
                // NCS expand uses statement
                choice address {
                  description
                    "Address information.";
                  case ipv4-address {
                    description
                      "IPv4 address.";
                    leaf ipv4-dest-address {
                      type string;
                      description
                        "Destination IPv4 address.";
                    }
                    leaf ipv4-source-address {
                      type string;
                      description
                        "Source IPv4 address.";
                    }
                    leaf ipv4-next-hop {
                      type string;
                      description
                        "IPv4 next hop address.";
                    }
                  }
                  case ipv6-address {
                    description
                      "IPv6 address.";
                    leaf ipv6-dest-address {
                      type string;
                      description
                        "Destination IPv6 address.";
                    }
                    leaf ipv6-source-address {
                      type string;
                      description
                        "Source IPv6 address.";
                    }
                    leaf ipv6-next-hop {
                      type string;
                      description
                        "IPv6 next hop address.";
                    }
                  }
                }
                leaf ni-name {
                  type string;
                  // NCS drop default statement
                  description
                    "Name of a VPN instance.";
                }
                leaf out-if-name {
                  type string;
                  description
                    "Out interface name.";
                  // NCS drop must statement
                }
                leaf fwd-if-name {
                  type string;
                  description
                    "Simulated inbound-interface name.";
                  // NCS drop must statement
                }
                leaf interval {
                  type string;
                  units "s";
                  // NCS drop default statement
                  description
                    "Interval for sending packets.";
                }
                leaf probe-count {
                  type string;
                  // NCS drop default statement
                  description
                    "Number of sent packets.";
                }
                leaf timeout {
                  type string;
                  units "s";
                  // NCS drop default statement
                  description
                    "Time to wait for a response packet after a test packet is sent.";
                }
                leaf frequency {
                  type string;
                  units "s";
                  description
                    "Cyclic scheduling period of test cases. The frequency must be greater than the value of the following formula; otherwise, the test results may be inaccurate:
                     (number of sent packets - 1) * (packet sending interval) + (timeout period).";
                }
                leaf fail-percent {
                  type string;
                  units "%";
                  // NCS drop default statement
                  description
                    "Indicates the packet loss ratio threshold of an NQA test instance. If the packet loss ratio exceeds the threshold, the test fails.";
                }
                leaf data-size {
                  type string;
                  units "Byte";
                  // NCS drop default statement
                  description
                    "Packet size.";
                }
                leaf data-fill {
                  type string;
                  description
                    "Specify an NQA test packet payload string.";
                }
                leaf ttl {
                  type string;
                  // NCS drop default statement
                  description
                    "Time to live.";
                }
                leaf pass-route {
                  type string;
                  // NCS drop default statement
                  description
                    "Enable/disable the function of sending packets without searching for routes.";
                }
                leaf probe-fails {
                  type string;
                  // NCS drop default statement
                  description
                    "The maximum number of probe failures of an NQA test to send trap or events.";
                }
                leaf test-fails {
                  type string;
                  // NCS drop default statement
                  description
                    "The maximum number of the NQA test consecutive test failures to send trap or events.";
                }
                leaf send-trap-bits {
                  type string;
                  description
                    "Configure conditions for sending traps.";
                }
                leaf compatibility {
                  type string;
                  // NCS drop default statement
                  description
                    "Enable/disable compatibility mode. When the ptn79 interworks with the ptn39, the no result is converted to failed and success.";
                }
                leaf result-num {
                  type string;
                  // NCS drop default statement
                  description
                    "The maximum number of test result records.";
                }
                leaf history-num {
                  type string;
                  // NCS drop default statement
                  description
                    "The maximum number of historical test records.";
                }
                leaf description {
                  type string;
                  description
                    "Description of test instance.";
                }
                leaf age-time {
                  type pub-type:ncs_template_time;
                  // NCS drop default statement
                  description
                    "Aging time of test instance.";
                }
                leaf path-type {
                  type ncs_template_path-type;
                  description
                    "Path type.";
                }
                leaf threshold-rtd {
                  type string;
                  description
                    "Threshold value of round trip delay.";
                }
                choice priority {
                  // NCS drop default statement
                  description
                    "Priority type.";
                  case tos-value {
                    description
                      "ToS value.";
                    leaf tos {
                      type string;
                      // NCS drop default statement
                      description
                        "ToS.";
                    }
                  }
                  case dscp-value {
                    description
                      "DSCP value.";
                    leaf dscp {
                      type string;
                      description
                        "DSCP value.";
                    }
                  }
                }
              }
            }
            case trace {
              description
                "TRACE NQA test.";
              container trace-input {
                // NCS drop must statement
                // NCS drop must statement
                presence "Present enable trace test instance input.";
                description
                  "Enable/disable trace test instance input.";
                // NCS expand uses statement
                choice address {
                  description
                    "Address information.";
                  case ipv4-address {
                    description
                      "IPv4 address.";
                    leaf ipv4-dest-address {
                      type string;
                      description
                        "Destination IPv4 address.";
                    }
                    leaf ipv4-source-address {
                      type string;
                      description
                        "Source IPv4 address.";
                    }
                    leaf ipv4-next-hop {
                      type string;
                      description
                        "IPv4 next hop address.";
                    }
                  }
                  case ipv6-address {
                    description
                      "IPv6 address.";
                    leaf ipv6-dest-address {
                      type string;
                      description
                        "Destination IPv6 address.";
                    }
                    leaf ipv6-source-address {
                      type string;
                      description
                        "Source IPv6 address.";
                    }
                    leaf ipv6-next-hop {
                      type string;
                      description
                        "IPv6 next hop address.";
                    }
                  }
                }
                leaf timeout {
                  type string;
                  units "s";
                  // NCS drop default statement
                  description
                    "Time to wait for a response packet after a test packet is sent.";
                }
                leaf first-ttl {
                  type string;
                  // NCS drop default statement
                  description
                    "Start TTL of probe packet.";
                }
                leaf max-ttl {
                  type string;
                  // NCS drop default statement
                  description
                    "Maximum TTL of probe packet.";
                }
                leaf probe-count {
                  type string;
                  // NCS drop default statement
                  description
                    "Number of sent packets.";
                }
                leaf data-size {
                  type string;
                  units "Byte";
                  // NCS drop default statement
                  description
                    "Packet size.";
                }
                leaf ni-name {
                  type string;
                  // NCS drop default statement
                  description
                    "Name of a VPN instance.";
                }
                leaf result-num {
                  type string;
                  // NCS drop default statement
                  description
                    "The maximum number of test result records.";
                }
                leaf history-num {
                  type string;
                  // NCS drop default statement
                  description
                    "The maximum number of historical test records.";
                }
                leaf description {
                  type string;
                  description
                    "Description of test instance.";
                }
                leaf age-time {
                  type pub-type:ncs_template_time;
                  // NCS drop default statement
                  description
                    "Aging time of test instance.";
                }
                leaf frequency {
                  type string;
                  description
                    "Cyclic scheduling period of test cases.";
                }
                choice priority {
                  // NCS drop default statement
                  description
                    "Priority type.";
                  case tos-value {
                    description
                      "ToS value.";
                    leaf tos {
                      type string;
                      // NCS drop default statement
                      description
                        "ToS.";
                    }
                  }
                  case dscp-value {
                    description
                      "DSCP value.";
                    leaf dscp {
                      type string;
                      description
                        "DSCP value.";
                    }
                  }
                }
                leaf data-fill {
                  type string;
                  description
                    "Specify an NQA test packet payload string.";
                }
                leaf dest-port {
                  type string;
                  // NCS drop default statement
                  description
                    "TRACE destination port number.";
                }
                leaf hop-fail-times {
                  type string;
                  // NCS drop default statement
                  description
                    "The times of hop failure.";
                }
                leaf pass-route {
                  type string;
                  // NCS drop default statement
                  description
                    "Enable/disable the function of sending packets without searching for routes.";
                }
                leaf out-if-name {
                  type string;
                  description
                    "Out interface name.";
                  // NCS drop must statement
                }
                leaf test-fail-times {
                  type string;
                  // NCS drop default statement
                  description
                    "The maximum number of the NQA test consecutive test failures to send trap or events.";
                }
                leaf threshold-rtd {
                  type string;
                  description
                    "Threshold value of round trip delay.";
                }
                leaf non-fragment {
                  type string;
                  // NCS drop default statement
                  description
                    "Enable/disable the mark of message no fragment.";
                }
                leaf send-trap-bits {
                  type string;
                  description
                    "Configure conditions for sending traps.";
                }
              }
            }
            case udp {
              description
                "UDP NQA test.";
              container udp-input {
                // NCS drop must statement
                presence "Present enable UDP test instance input.";
                description
                  "Enable/disable UDP test instance input.";
                // NCS expand uses statement
                choice address {
                  description
                    "Address information.";
                  case ipv4-address {
                    description
                      "IPv4 address.";
                    leaf ipv4-dest-address {
                      type string;
                      description
                        "Destination IPv4 address.";
                    }
                    leaf ipv4-source-address {
                      type string;
                      description
                        "Source IPv4 address.";
                    }
                  }
                  case ipv6-address {
                    description
                      "IPv6 address.";
                    leaf ipv6-dest-address {
                      type string;
                      description
                        "Destination IPv6 address.";
                    }
                    leaf ipv6-source-address {
                      type string;
                      description
                        "Source IPv6 address.";
                    }
                  }
                }
                leaf dest-port {
                  type string;
                  // NCS drop default statement
                  description
                    "UDP destination port.";
                }
                leaf source-port {
                  type string;
                  description
                    "UDP source port.";
                }
                leaf ttl {
                  type string;
                  // NCS drop default statement
                  description
                    "Time to live.";
                }
                leaf data-size {
                  type string;
                  units "Byte";
                  // NCS drop default statement
                  description
                    "Packet size.";
                }
                leaf pass-route {
                  type string;
                  // NCS drop default statement
                  description
                    "Enable/disable the function of sending packets without searching for routes.";
                }
                leaf probe-count {
                  type string;
                  // NCS drop default statement
                  description
                    "Number of sent packets.";
                }
                leaf send-trap-bits {
                  type string;
                  description
                    "Configure conditions for sending traps.";
                }
                leaf threshold-rtd {
                  type string;
                  description
                    "Threshold value of round trip delay.";
                }
                leaf probe-failtimes {
                  type string;
                  // NCS drop default statement
                  description
                    "The maximum number of probe failures of an NQA test to send trap or events.";
                }
                leaf test-failtimes {
                  type string;
                  // NCS drop default statement
                  description
                    "The maximum number of the NQA test consecutive test failures to send trap or events.";
                }
                leaf tos {
                  type string;
                  // NCS drop default statement
                  description
                    "ToS.";
                }
                leaf fail-percent {
                  type string;
                  units "%";
                  // NCS drop default statement
                  description
                    "Loss ratio, determining whether the test is successful.";
                }
                leaf interval {
                  type string;
                  units "s";
                  // NCS drop default statement
                  description
                    "Interval for sending packets.";
                }
                leaf ni-name {
                  type string;
                  // NCS drop default statement
                  description
                    "Name of a VPN instance.";
                }
                leaf timeout {
                  type string;
                  units "s";
                  // NCS drop default statement
                  description
                    "Time to wait for a response packet after a test packet is sent.";
                }
                leaf data-fill {
                  type string;
                  description
                    "Specify an NQA test packet payload string.";
                }
                leaf description {
                  type string;
                  description
                    "Description of test instance.";
                }
                leaf result-num {
                  type string;
                  // NCS drop default statement
                  description
                    "The maximum number of test result records.";
                }
                leaf history-num {
                  type string;
                  // NCS drop default statement
                  description
                    "The maximum number of historical test records.";
                }
                leaf age-time {
                  type pub-type:ncs_template_time;
                  // NCS drop default statement
                  description
                    "Aging time of test instance.";
                }
                leaf frequency {
                  type string;
                  units "s";
                  description
                    "Cyclic scheduling period of test cases. The frequency must be greater than the value of the following formula; otherwise, the test results may be inaccurate:
                     (Number of Sent Packets - 1) * (Packet Sending Interval) + (Timeout Period).";
                }
              }
            }
            case tcp {
              description
                "TCP NQA test.";
              container tcp-input {
                presence "Present enable TCP test instance input.";
                description
                  "Enable/disable TCP test instance input.";
                // NCS expand uses statement
                leaf dest-address {
                  type string;
                  description
                    "Destination IP address.";
                }
                leaf source-address {
                  type string;
                  description
                    "Source IP address.";
                }
                leaf interval {
                  type string;
                  units "s";
                  // NCS drop default statement
                  description
                    "Interval for sending packets.";
                }
                leaf timeout {
                  type string;
                  units "s";
                  // NCS drop default statement
                  description
                    "Time to wait for a response packet after a test packet is sent.";
                }
                leaf ttl {
                  type string;
                  // NCS drop default statement
                  description
                    "TTL value of NQA test packets.";
                }
                leaf probe-count {
                  type string;
                  // NCS drop default statement
                  description
                    "Number of sent packets.";
                }
                leaf tos {
                  type string;
                  // NCS drop default statement
                  description
                    "ToS.";
                }
                leaf dest-port {
                  type string;
                  // NCS drop default statement
                  description
                    "TCP destination port number.";
                }
                leaf source-port {
                  type string;
                  description
                    "TCP source port number.";
                }
                leaf pass-route {
                  type string;
                  // NCS drop default statement
                  description
                    "Enable/disable the function of sending packets without searching for routes.";
                }
                leaf ni-name {
                  type string;
                  // NCS drop default statement
                  description
                    "Name of a VPN instance.";
                }
                leaf threshold-rtd {
                  type string;
                  description
                    "Threshold value of round trip delay.";
                }
                leaf probe-fails {
                  type string;
                  // NCS drop default statement
                  description
                    "The maximum number of probe failures of an NQA test to send trap or events.";
                }
                leaf fail-percent {
                  type string;
                  units "%";
                  // NCS drop default statement
                  description
                    "The rate of loss that the test case performed successfully.";
                }
                leaf test-fail-times {
                  type string;
                  // NCS drop default statement
                  description
                    "The maximum number of the NQA test consecutive test failures to send trap or events.";
                }
                leaf result-num {
                  type string;
                  // NCS drop default statement
                  description
                    "The maximum number of test result records.";
                }
                leaf history-num {
                  type string;
                  // NCS drop default statement
                  description
                    "The maximum number of historical test records.";
                }
                leaf description {
                  type string;
                  description
                    "Description of test instance.";
                }
                leaf age-time {
                  type pub-type:ncs_template_time;
                  // NCS drop default statement
                  description
                    "Aging time of test instance.";
                }
                leaf frequency {
                  type string;
                  units "s";
                  description
                    "Cyclic scheduling period of test cases. The frequency must be greater than the value of the following formula; otherwise, the test results may be inaccurate:
                     (number of sent packets - 1) * (packet sending interval) + (timeout period).";
                }
              }
            }
            case jitter {
              description
                "Jitter NQA test that tests UDP-packet jitter.";
              container jitter-input {
                // NCS drop must statement
                // NCS drop must statement
                // NCS drop must statement
                presence "Present enable jitter test instance input";
                description
                  "Enable/disable jitter test instance input.";
                // NCS expand uses statement
                choice address {
                  description
                    "IP address configurations.";
                  case ipv4-address {
                    description
                      "IPv4 address.";
                    leaf ipv4-dest-address {
                      type string;
                      description
                        "Destination IPv4 address.";
                    }
                    leaf ipv4-source-address {
                      type string;
                      description
                        "Source IPv4 address.";
                    }
                  }
                  case ipv6-address {
                    description
                      "IPv6 address.";
                    leaf ipv6-dest-address {
                      type string;
                      description
                        "Destination IPv6 address.";
                    }
                    leaf ipv6-source-address {
                      type string;
                      description
                        "Source IPv6 address.";
                    }
                  }
                }
                leaf dest-port {
                  type string;
                  description
                    "UDP destination port.";
                }
                leaf source-port {
                  type string;
                  description
                    "UDP source port.";
                }
                leaf ttl {
                  type string;
                  // NCS drop default statement
                  description
                    "Time to live.";
                }
                leaf hardware-enable {
                  type string;
                  // NCS drop default statement
                  description
                    "Enable/disable packets are sent by hardware.";
                }
                leaf interval {
                  type string;
                  units "ms";
                  // NCS drop default statement
                  description
                    "Interval for sending packets.";
                }
                leaf probe-count {
                  type string;
                  ext:dynamic-default {
                    ext:default-value "3" {
                      // NCS drop when statement
                      description
                        "The default value is 3 when code-type is none.";
                    }
                    ext:default-value "1" {
                      // NCS drop when statement
                      description
                        "The default value is 1 when code-type is g711a, g711u or g729a.";
                    }
                  }
                  description
                    "Number of probes.";
                }
                leaf jitter-packet-num {
                  type string;
                  ext:dynamic-default {
                    ext:default-value "20" {
                      // NCS drop when statement
                      description
                        "The default value is 20 when code-type is none.";
                    }
                    ext:default-value "1000" {
                      // NCS drop when statement
                      description
                        "The default value is 1000 when code-type is g711a, g711u or g729a.";
                    }
                  }
                  description
                    "Number of sent packets.";
                }
                leaf data-size {
                  type string;
                  units "Byte";
                  // NCS drop must statement
                  ext:dynamic-default {
                    ext:default-value "0" {
                      // NCS drop when statement
                      description
                        "The default value is 0 when code-type is none.";
                    }
                    ext:default-value "172" {
                      // NCS drop when statement
                      description
                        "The default value is 172 when code-type is g711a or g711u.";
                    }
                    ext:default-value "32" {
                      // NCS drop when statement
                      description
                        "The default value is 32 when code-type is g729a.";
                    }
                  }
                  description
                    "Packet size.";
                }
                leaf data-fill {
                  type string;
                  description
                    "Specify an NQA test packet payload string.";
                }
                leaf pass-route {
                  type string;
                  // NCS drop default statement
                  description
                    "Enable/disable the function of sending packets without searching for routes.";
                }
                leaf tos {
                  type string;
                  // NCS drop default statement
                  description
                    "ToS.";
                }
                leaf ni-name {
                  type string;
                  // NCS drop default statement
                  description
                    "Name of a VPN instance.";
                }
                leaf code-type {
                  type ncs_template_jitter-code-type;
                  // NCS drop default statement
                  description
                    "Code type.";
                }
                leaf adv-factor {
                  // NCS drop when statement
                  type string;
                  // NCS drop default statement
                  description
                    "Advantage factor.";
                }
                leaf threshold-owd-ds {
                  type string;
                  description
                    "One way delay threshold value from destination to source.";
                }
                leaf threshold-owd-sd {
                  type string;
                  description
                    "One way delay threshold value from source to destination.";
                }
                leaf threshold-rtd {
                  type string;
                  description
                    "Threshold value of round trip delay.";
                }
                leaf fail-percent {
                  type string;
                  units "%";
                  // NCS drop default statement
                  description
                    "Indicates the packet loss ratio threshold of an NQA test instance. If the packet loss ratio exceeds the threshold, the test fails.";
                }
                leaf test-failtimes {
                  type string;
                  // NCS drop default statement
                  description
                    "The maximum number of the NQA test consecutive test failures to send trap or events.";
                }
                leaf timestamp {
                  type ncs_template_time-unit-type;
                  // NCS drop default statement
                  description
                    "The unit of timestamp.";
                }
                leaf out-if-name {
                  type string;
                  description
                    "Out interface name.";
                  // NCS drop must statement
                }
                leaf timeout {
                  type string;
                  units "s";
                  // NCS drop default statement
                  description
                    "Time to wait for a response packet after a test packet is sent.";
                }
                leaf result-num {
                  type string;
                  // NCS drop default statement
                  description
                    "The maximum number of test result records.";
                }
                leaf history-num {
                  type string;
                  // NCS drop default statement
                  description
                    "The maximum number of historical test records.";
                }
                leaf description {
                  type string;
                  description
                    "Description of test instance.";
                }
                leaf age-time {
                  type pub-type:ncs_template_time;
                  // NCS drop default statement
                  description
                    "Aging time of test instance.";
                }
                leaf frequency {
                  type string;
                  units "s";
                  description
                    "Cyclic scheduling period of test cases. The frequency must be greater than the value of the following formula; otherwise, the test results may be inaccurate:
                     (number of sent packets - 1) * (packet sending interval) + (timeout period).";
                }
              }
            }
            case icmp-jitter {
              description
                "ICMP jitter NQA test.";
              container icmp-jitter-input {
                presence "Present enable ICMP jitter test instance input.";
                description
                  "Enable/disable ICMP jitter test instance input.";
                // NCS expand uses statement
                choice address {
                  description
                    "IP address configurations.";
                  case ipv4-address {
                    description
                      "IPv4 address.";
                    leaf ipv4-dest-address {
                      type string;
                      description
                        "Destination IPv4 address.";
                    }
                    leaf ipv4-source-address {
                      type string;
                      description
                        "Source IPv4 address.";
                    }
                  }
                  case ipv6-address {
                    description
                      "IPv6 address.";
                    leaf ipv6-dest-address {
                      type string;
                      description
                        "Destination IPv6 address.";
                    }
                    leaf ipv6-source-address {
                      type string;
                      description
                        "Source IPv6 address.";
                    }
                  }
                }
                leaf ttl {
                  type string;
                  // NCS drop default statement
                  description
                    "Time to live.";
                }
                leaf probe-count {
                  type string;
                  // NCS drop default statement
                  description
                    "Number of probes.";
                }
                leaf hardware-enable {
                  type string;
                  // NCS drop must statement
                  // NCS drop default statement
                  description
                    "Enable/disable packets are sent by hardware.";
                }
                leaf jitter-packet-num {
                  type string;
                  // NCS drop default statement
                  description
                    "Number of packets.";
                }
                leaf data-size {
                  // NCS drop when statement
                  type string;
                  units "Byte";
                  // NCS drop default statement
                  description
                    "Packet size.";
                }
                leaf data-fill {
                  // NCS drop when statement
                  type string;
                  description
                    "Specify an NQA test packet payload string.";
                }
                leaf tos {
                  type string;
                  // NCS drop default statement
                  description
                    "ToS.";
                }
                leaf ni-name {
                  type string;
                  // NCS drop default statement
                  description
                    "Name of a VPN instance.";
                }
                leaf jitter-mode {
                  // NCS drop when statement
                  type ncs_template_jitter-mode-type;
                  // NCS drop default statement
                  description
                    "Packet format.";
                }
                leaf interval {
                  type string;
                  units "ms";
                  // NCS drop must statement
                  // NCS drop default statement
                  description
                    "Interval for sending packets.";
                }
                leaf timestamp {
                  // NCS drop when statement
                  type ncs_template_time-unit-type;
                  // NCS drop must statement
                  // NCS drop default statement
                  description
                    "The unit of timestamp.";
                }
                leaf out-if-name {
                  type string;
                  description
                    "Out interface name.";
                  // NCS drop must statement
                }
                leaf timeout {
                  type string;
                  units "s";
                  // NCS drop default statement
                  description
                    "Time to wait for a response packet after a test packet is sent.";
                }
                leaf receive-timeunit {
                  type ncs_template_recv-time-unit-type;
                  // NCS drop must statement
                  // NCS drop default statement
                  description
                    "The unit of receive timestamp.";
                }
                leaf fail-percent {
                  type string;
                  units "%";
                  // NCS drop default statement
                  description
                    "Indicates the packet loss ratio threshold of an NQA test instance. If the packet loss ratio exceeds the threshold, the test fails.";
                }
                leaf result-num {
                  type string;
                  // NCS drop default statement
                  description
                    "The maximum number of test result records.";
                }
                leaf history-num {
                  type string;
                  // NCS drop default statement
                  description
                    "The maximum number of historical test records.";
                }
                leaf description {
                  type string;
                  description
                    "Description of test instance.";
                }
                leaf age-time {
                  type pub-type:ncs_template_time;
                  // NCS drop default statement
                  description
                    "Aging time of test instance.";
                }
                leaf frequency {
                  type string;
                  units "s";
                  description
                    "Cyclic scheduling period of test cases. The frequency must be greater than the value of the following formula; otherwise, the test results may be inaccurate:
                     (number of sent packets - 1) * (packet sending interval) + (timeout period).";
                }
              }
            }
            case lsp-ping {
              description
                "LSP ping NQA test.";
              container lsp-ping-input {
                presence "Present enable LSP ping test instance input.";
                description
                  "Enable/disable LSP ping test instance input.";
                // NCS expand uses statement
                choice lsp-protocol {
                  // NCS drop default statement
                  description
                    "The LSP type. The default LSP type is IPv4.";
                  case ipv4 {
                    description
                      "The LSP type is LDP.";
                    container ldp-lsp-ping {
                      // NCS drop must statement
                      description
                        "Configure container of LDP LSP ping.";
                      leaf dest-address {
                        type string;
                        description
                          "Destination IPv4 address.";
                      }
                      leaf mask-len {
                        type string;
                        description
                          "LSP IPv4 prefix mask length.";
                      }
                      leaf loopback-address {
                        // NCS drop when statement
                        type string;
                        description
                          "Set a 127/8 address of MPLS ping packets' destination address in the IP header.";
                      }
                      leaf next-hop {
                        type string;
                        description
                          "Next hop address.";
                      }
                      leaf reply-mode {
                        type ncs_template_ip-lsp-reply-mode-type;
                        // NCS drop default statement
                        description
                          "Specify an LSP test reply mode.";
                      }
                    }
                  }
                  case bgp {
                    description
                      "The LSP type is BGP.";
                    container bgp-lsp-ping {
                      // NCS drop must statement
                      presence "Present enable BGP LSP ping.";
                      description
                        "Configure container of BGP LSP ping.";
                      leaf dest-address {
                        type string;
                        description
                          "Destination IPv4 address.";
                      }
                      leaf mask-len {
                        type string;
                        description
                          "LSP IPv4 prefix mask length.";
                      }
                      leaf loopback-address {
                        // NCS drop when statement
                        type string;
                        description
                          "Set a 127/8 address of MPLS ping packets' destination address in the IP header.";
                      }
                      leaf next-hop {
                        type string;
                        description
                          "Next hop address.";
                      }
                      leaf reply-mode {
                        type ncs_template_bgp-lsp-reply-mode-type;
                        // NCS drop default statement
                        description
                          "Specify an LSP test reply mode.";
                      }
                    }
                  }
                  case te {
                    description
                      "The LSP type is TE.";
                    container te-lsp-ping {
                      presence "Present enable TE LSP ping.";
                      description
                        "Configure container of TE LSP ping.";
                      leaf tunnel-name {
                        type string;
                        description
                          "TE tunnel name.";
                      }
                      leaf lsp-path {
                        // NCS drop when statement
                        type ncs_template_lsp-ping-trace-lsp-path;
                        description
                          "Lsp path (hot-standby or primary).";
                      }
                      leaf reply-mode {
                        type ncs_template_te-lsp-reply-mode-type;
                        // NCS drop default statement
                        description
                          "Specify an LSP test reply mode.";
                      }
                    }
                  }
                  case srte {
                    description
                      "The LSP type is SR-TE.";
                    container srte-lsp-ping {
                      presence "Present enable SR-TE LSP ping.";
                      description
                        "Configure container of SR-TE LSP ping.";
                      leaf tunnel-name {
                        type string;
                        description
                          "TE tunnel name.";
                      }
                      leaf lsp-path {
                        // NCS drop when statement
                        type ncs_template_lsp-ping-trace-lsp-path;
                        description
                          "Lsp path (hot-standby or primary).";
                      }
                    }
                  }
                  case srbe {
                    description
                      "The LSP type is SR-BE.";
                    container srbe-lsp-ping {
                      // NCS drop must statement
                      presence "Present enable SR-BE LSP ping.";
                      description
                        "Configure container of SR-BE LSP ping.";
                      leaf dest-address {
                        type string;
                        description
                          "Destination IP address.";
                      }
                      leaf mask-len {
                        type string;
                        description
                          "LSP IPv4 prefix mask length.";
                      }
                      leaf flex-algo-id {
                        type string;
                        description
                          "Flexible algorithm ID.";
                      }
                      leaf path-type {
                        type ncs_template_path-type;
                        description
                          "Path type.";
                      }
                      choice remote-fec {
                        description
                          "Remote FEC type.";
                        case ldp {
                          description
                            "Configure the remote FEC type as LDP.";
                          container remote-fec-ldp {
                            // NCS drop must statement
                            presence "Present enable remote FEC type as LDP.";
                            description
                              "Configure container of remote FEC LDP.";
                            leaf remote-fec-ip-address {
                              type string;
                              description
                                "Configure remote FEC IPv4 address.";
                            }
                            leaf remote-mask-len {
                              type string;
                              description
                                "Configure remote FEC mask length.";
                            }
                          }
                        }
                      }
                    }
                  }
                  case srte-policy {
                    description
                      "The LSP type is SR-TE policy.";
                    container srte-policy-lsp-ping {
                      // NCS drop must statement
                      presence "Present enable SR-TE policy LSP ping.";
                      description
                        "Configure container of SR-TE policy LSP ping.";
                      choice probe-type {
                        description
                          "Probe type of SR-TE policy.";
                        case policy-name {
                          description
                            "Policy name.";
                          leaf policy-name {
                            type string;
                            description
                              "SR-TE policy name.";
                          }
                        }
                        case end-point {
                          description
                            "End point.";
                          leaf end-point-ip {
                            type string;
                            description
                              "Endpoint IPv4 address.";
                          }
                          leaf color {
                            type string;
                            description
                              "Endpoint color ID.";
                          }
                        }
                        case binding-sid {
                          description
                            "Policy name.";
                          leaf binding-sid {
                            type string;
                            description
                              "Binding segmentlist ID.";
                          }
                        }
                      }
                    }
                  }
                }
                leaf timeout {
                  type string;
                  units "s";
                  // NCS drop default statement
                  description
                    "Time to wait for a response packet after test packets are sent.";
                }
                leaf frag-flag {
                  type string;
                  // NCS drop default statement
                  description
                    "Enable/disable packet fragmentation function.";
                }
                leaf source-address {
                  type string;
                  description
                    "Source IPv4 address.";
                }
                leaf exp {
                  type string;
                  // NCS drop default statement
                  description
                    "Configures the LSP EXP value.";
                }
                leaf ttl {
                  type string;
                  // NCS drop default statement
                  description
                    "TTL value of NQA test packets.";
                }
                leaf interval {
                  type string;
                  units "s";
                  // NCS drop default statement
                  description
                    "Interval for sending packets.";
                }
                leaf probe-count {
                  type string;
                  // NCS drop default statement
                  description
                    "Number of sent packets.";
                }
                leaf data-size {
                  type string;
                  units "Byte";
                  // NCS drop default statement
                  description
                    "Packet size.";
                }
                leaf data-fill {
                  type string;
                  description
                    "Specify an NQA test packet payload string.";
                }
                leaf fail-percent {
                  type string;
                  units "%";
                  // NCS drop default statement
                  description
                    "Indicates the packet loss ratio threshold of an NQA test instance. If the packet loss ratio exceeds the threshold, the test fails.";
                }
                leaf result-num {
                  type string;
                  // NCS drop default statement
                  description
                    "The maximum number of test result records.";
                }
                leaf history-num {
                  type string;
                  // NCS drop default statement
                  description
                    "The maximum number of historical test records.";
                }
                leaf description {
                  type string;
                  description
                    "Description of test instance.";
                }
                leaf age-time {
                  type pub-type:ncs_template_time;
                  // NCS drop default statement
                  description
                    "Aging time of test instance.";
                }
                leaf frequency {
                  type string;
                  units "s";
                  description
                    "Cyclic scheduling period of test cases. The frequency must be greater than the value of the following formula; otherwise, the test results may be inaccurate:
                     (number of sent packets - 1) * (packet sending interval) + (timeout period).";
                }
              }
            }
            case lsp-trace {
              description
                "LSP trace NQA test.";
              container lsp-trace-input {
                presence "Present enable LSP trace test instance input.";
                description
                  "Enable/disable LSP trace test instance input.";
                // NCS expand uses statement
                choice lsp-protocol {
                  // NCS drop default statement
                  description
                    "The LSP type. The default LSP type is IPv4.";
                  case ipv4 {
                    description
                      "The LSP type is LDP.";
                    container ldp-lsp-trace {
                      // NCS drop must statement
                      description
                        "Configure container of LDP LSP trace.";
                      leaf dest-address {
                        type string;
                        description
                          "Destination IPv4 address.";
                      }
                      leaf mask-len {
                        type string;
                        description
                          "LSP IPv4 prefix mask length.";
                      }
                      leaf loopback-address {
                        // NCS drop when statement
                        type string;
                        description
                          "Set a 127/8 address of MPLS ping packets' destination address in the IP header.";
                      }
                      leaf next-hop {
                        type string;
                        description
                          "Next hop address.";
                      }
                      leaf reply-mode {
                        type ncs_template_ip-lsp-reply-mode-type;
                        // NCS drop default statement
                        description
                          "Specify an LSP test reply mode.";
                      }
                    }
                  }
                  case bgp {
                    description
                      "The LSP type is BGP.";
                    container bgp-lsp-trace {
                      // NCS drop must statement
                      presence "Present enable BGP LSP trace.";
                      description
                        "Configure container of BGP LSP trace.";
                      leaf dest-address {
                        type string;
                        description
                          "Destination IPv4 address.";
                      }
                      leaf mask-len {
                        type string;
                        description
                          "LSP IPv4 prefix mask length.";
                      }
                      leaf loopback-address {
                        // NCS drop when statement
                        type string;
                        description
                          "Set a 127/8 address of MPLS ping packets' destination address in the IP header.";
                      }
                      leaf next-hop {
                        type string;
                        description
                          "Next hop address.";
                      }
                      leaf reply-mode {
                        type ncs_template_bgp-lsp-reply-mode-type;
                        // NCS drop default statement
                        description
                          "Specify an LSP test reply mode.";
                      }
                    }
                  }
                  case te {
                    description
                      "The LSP type is TE.";
                    container te-lsp-trace {
                      presence "Present enable TE LSP trace.";
                      description
                        "Configure container of TE LSP trace.";
                      leaf tunnel-name {
                        type string;
                        description
                          "TE tunnel name.";
                      }
                      leaf next-hop {
                        type string;
                        description
                          "Next hop address.";
                      }
                      leaf lsp-path {
                        // NCS drop when statement
                        type ncs_template_lsp-ping-trace-lsp-path;
                        description
                          "Lsp path (hot-standby or primary).";
                      }
                      leaf reply-mode {
                        type ncs_template_te-lsp-reply-mode-type;
                        // NCS drop default statement
                        description
                          "Specify an LSP test reply mode.";
                      }
                    }
                  }
                  case srte {
                    description
                      "The LSP type is SR-TE.";
                    container srte-lsp-trace {
                      presence "Present enable SR-TE LSP trace.";
                      description
                        "Configure container of SR-TE LSP trace.";
                      leaf tunnel-name {
                        type string;
                        description
                          "TE tunnel name.";
                      }
                      leaf lsp-path {
                        // NCS drop when statement
                        type ncs_template_lsp-ping-trace-lsp-path;
                        description
                          "Lsp path (hot-standby or primary).";
                      }
                    }
                  }
                  case srbe {
                    description
                      "The LSP type is SR-BE.";
                    container srbe-lsp-trace {
                      // NCS drop must statement
                      presence "Present enable SR-BE LSP trace.";
                      description
                        "Configure container of SR-BE LSP trace.";
                      leaf dest-address {
                        type string;
                        description
                          "Destination IPv4 address.";
                      }
                      leaf mask-len {
                        type string;
                        description
                          "LSP IPv4 prefix mask length.";
                      }
                      leaf flex-algo-id {
                        type string;
                        description
                          "Flexible algorithm ID.";
                      }
                      leaf path-type {
                        type ncs_template_path-type;
                        description
                          "Path type.";
                      }
                      choice remote-fec {
                        description
                          "Remote FEC type.";
                        case ldp {
                          description
                            "Configure the remote FEC type as LDP.";
                          container remote-fec-ldp {
                            // NCS drop must statement
                            presence "Present enable remote FEC type as LDP.";
                            description
                              "Configure container of remote FEC LDP.";
                            leaf remote-fec-ip-address {
                              type string;
                              description
                                "Configure remote FEC IPv4 address.";
                            }
                            leaf remote-mask-len {
                              type string;
                              description
                                "Configure remote FEC mask length.";
                            }
                          }
                        }
                      }
                    }
                  }
                  case srte-policy {
                    description
                      "The LSP type is SR-TE policy.";
                    container srte-policy-lsp-trace {
                      // NCS drop must statement
                      presence "Present enable SR-TE policy LSP trace.";
                      description
                        "Configure container of SR-TE policy LSP trace.";
                      choice probe-type {
                        description
                          "Probe type of SR-TE policy.";
                        case policy-name {
                          description
                            "Policy name.";
                          leaf policy-name {
                            type string;
                            description
                              "SR-TE policy name.";
                          }
                        }
                        case end-point {
                          description
                            "End point.";
                          leaf end-point-ip {
                            type string;
                            description
                              "Endpoint IPv4 address.";
                          }
                          leaf color {
                            type string;
                            description
                              "Endpoint color ID.";
                          }
                        }
                        case binding-sid {
                          description
                            "Policy name.";
                          leaf binding-sid {
                            type string;
                            description
                              "Binding segmentlist ID.";
                          }
                        }
                      }
                    }
                  }
                }
                leaf frag-flag {
                  type string;
                  // NCS drop default statement
                  description
                    "Enable/disable packet fragmentation function.";
                }
                leaf exp {
                  type string;
                  // NCS drop default statement
                  description
                    "Configures the LSP EXP value.";
                }
                leaf probe-count {
                  type string;
                  // NCS drop default statement
                  description
                    "Number of sent packets.";
                }
                leaf source-address {
                  type string;
                  description
                    "Source IPv4 address.";
                }
                leaf first-ttl {
                  type string;
                  // NCS drop must statement
                  // NCS drop default statement
                  description
                    "Start TTL of probe packet.";
                }
                leaf max-ttl {
                  type string;
                  // NCS drop must statement
                  // NCS drop default statement
                  description
                    "Maximum TTL of probe packet.";
                }
                leaf timeout {
                  type string;
                  units "s";
                  // NCS drop default statement
                  description
                    "Time to wait for a response packet after a test packet is sent.";
                }
                leaf hop-fail-times {
                  type string;
                  // NCS drop default statement
                  description
                    "Specify the upper limit of the number of failed hops before the NQA tracert test stops.";
                }
                leaf result-num {
                  type string;
                  // NCS drop default statement
                  description
                    "The maximum number of test result records.";
                }
                leaf history-num {
                  type string;
                  // NCS drop default statement
                  description
                    "The maximum number of historical test records.";
                }
                leaf description {
                  type string;
                  description
                    "Description of test instance.";
                }
                leaf age-time {
                  type pub-type:ncs_template_time;
                  // NCS drop default statement
                  description
                    "Aging time of test instance.";
                }
                leaf frequency {
                  type string;
                  units "s";
                  // NCS drop must statement
                  description
                    "Cyclic scheduling period of test cases. The frequency must be greater than the value of the following formula; otherwise, the test results may be inaccurate:
                     (number of sent packets - 1) * (packet sending interval) + (timeout period).";
                }
              }
            }
            case lsp-jitter {
              description
                "LSP jitter NQA test.";
              container lsp-jitter-input {
                presence "Present enable LSP jitter test instance input";
                description
                  "Enable/disable LSP jitter test instance input.";
                // NCS expand uses statement
                choice lsp-protocol {
                  description
                    "The test-type of LSP.";
                  case te {
                    description
                      "The test-type of LSP is TE.";
                    container te-lsp-jitter {
                      presence "Present enable te jitter test instance input.";
                      description
                        "Enable/disable te jitter instance container.";
                      leaf tunnel-name {
                        type string;
                        description
                          "TE tunnel name.";
                        // NCS drop must statement
                      }
                      leaf lsp-path {
                        // NCS drop when statement
                        type ncs_template_lsp-path;
                        // NCS drop default statement
                        description
                          "LSP path (working or hot-standby or primary).";
                      }
                      leaf reply-mode {
                        type ncs_template_lsp-reply-mode-type;
                        // NCS drop default statement
                        description
                          "Specify an LSP test reply mode.";
                      }
                    }
                  }
                }
                leaf timeout {
                  type string;
                  units "s";
                  // NCS drop default statement
                  description
                    "Time to wait for a response packet after a test packet is sent.";
                }
                leaf frag-flag {
                  type string;
                  // NCS drop default statement
                  description
                    "Enable/disable packet fragmentation function.";
                }
                leaf source-address {
                  type string;
                  description
                    "Source IP address.";
                }
                leaf exp {
                  type string;
                  // NCS drop default statement
                  description
                    "Configures the LSP EXP value.";
                }
                leaf ttl {
                  type string;
                  // NCS drop default statement
                  description
                    "TTL value of NQA test packets.";
                }
                leaf interval {
                  type string;
                  units "s";
                  // NCS drop default statement
                  description
                    "Interval for sending packets.";
                }
                leaf probe-count {
                  type string;
                  // NCS drop default statement
                  description
                    "Number of probes.";
                }
                leaf jitter-packet-num {
                  type string;
                  // NCS drop default statement
                  description
                    "Number of sent packets.";
                }
                leaf data-size {
                  type string;
                  units "Byte";
                  // NCS drop default statement
                  description
                    "Packet size.";
                }
                leaf data-fill {
                  type string;
                  description
                    "Specify an NQA test packet payload string.";
                }
                leaf fail-percent {
                  type string;
                  units "%";
                  // NCS drop default statement
                  description
                    "Indicates the packet loss ratio threshold of an NQA test instance. If the packet loss ratio exceeds the threshold, the test fails.";
                }
                leaf result-num {
                  type string;
                  // NCS drop default statement
                  description
                    "The maximum number of test result records.";
                }
                leaf history-num {
                  type string;
                  // NCS drop default statement
                  description
                    "The maximum number of historical test records.";
                }
                leaf description {
                  type string;
                  description
                    "Description of test instance.";
                }
                leaf age-time {
                  type pub-type:ncs_template_time;
                  // NCS drop default statement
                  description
                    "Aging time of test instance.";
                }
                leaf frequency {
                  type string;
                  units "s";
                  description
                    "Cyclic scheduling period of test cases. The frequency must be greater than the value of the following formula; otherwise, the test results may be inaccurate:
                     (number of sent packets - 1) * (packet sending interval) + (timeout period).";
                }
              }
            }
            case pwe3-trace {
              description
                "PWE3 trace NQA test.";
              container pwe3-trace-input {
                presence "Present enable PWE3 trace test instance input";
                description
                  "Enable/disable PWE3 trace test instance input.";
                // NCS expand uses statement
                leaf vc-type {
                  type ncs_template_vc-type;
                  // NCS drop default statement
                  description
                    "VC type.";
                }
                leaf local-pw-type {
                  type ncs_template_pw-type;
                  // NCS drop default statement
                  description
                    "Local PW type.";
                }
                leaf local-pw-id {
                  type string;
                  description
                    "Local PW ID.";
                }
                leaf label-type {
                  type ncs_template_pwe3-label-type;
                  // NCS drop default statement
                  description
                    "Label type.";
                }
                leaf dest-address {
                  type string;
                  description
                    "Destination IP address. (Must specify the destination address to start the test)";
                }
                leaf timeout {
                  type string;
                  units "s";
                  // NCS drop default statement
                  description
                    "Time to wait for a response packet after a test packet is sent.";
                }
                leaf first-ttl {
                  type string;
                  // NCS drop must statement
                  // NCS drop default statement
                  description
                    "Start TTL of probe packet.";
                }
                leaf max-ttl {
                  type string;
                  // NCS drop must statement
                  // NCS drop default statement
                  description
                    "Maximum TTL of probe packet.";
                }
                leaf exp {
                  type string;
                  // NCS drop default statement
                  description
                    "Configures the Pwe3Trace EXP value.";
                }
                leaf reply-mode {
                  type ncs_template_lsp-reply-mode-type;
                  // NCS drop default statement
                  description
                    "Specify an LSP test reply mode.";
                }
                leaf packet-count {
                  type string;
                  units "packet";
                  // NCS drop default statement
                  description
                    "Number of sent packets.";
                }
                leaf probe-failtimes {
                  type string;
                  // NCS drop default statement
                  description
                    "The maximum number of probe failures of an NQA test to send trap or events.";
                }
                leaf test-failtimes {
                  type string;
                  // NCS drop default statement
                  description
                    "The maximum number of the NQA test consecutive test failures to send trap or events.";
                }
                leaf lsp-version {
                  type ncs_template_lsp-version;
                  // NCS drop default statement
                  description
                    "Lsp version.";
                }
                leaf threshold-rtd {
                  type string;
                  description
                    "Threshold value of round trip delay.";
                }
                leaf ttl-mode {
                  type ncs_template_ttl-mode;
                  // NCS drop default statement
                  description
                    "TTL mode.";
                }
                leaf hop-fail-times {
                  type string;
                  // NCS drop default statement
                  description
                    "Specify the upper limit of the number of failed hops before the NQA tracert test stops.";
                }
                leaf frag-flag {
                  type string;
                  // NCS drop default statement
                  description
                    "Enable/disable packet fragmentation function.";
                }
                leaf peer-address {
                  type string;
                  description
                    "Peer IP Address.";
                }
                leaf no-cw-flag {
                  // NCS drop when statement
                  type string;
                  // NCS drop default statement
                  description
                    "Enable/disable the option of not carrying control word.";
                }
                leaf result-num {
                  type string;
                  // NCS drop default statement
                  description
                    "The maximum number of test result records.";
                }
                leaf history-num {
                  type string;
                  // NCS drop default statement
                  description
                    "The maximum number of historical test records.";
                }
                leaf description {
                  type string;
                  description
                    "Description of test instance.";
                }
                leaf age-time {
                  type pub-type:ncs_template_time;
                  // NCS drop default statement
                  description
                    "Aging time of test instance.";
                }
                leaf frequency {
                  type string;
                  units "s";
                  description
                    "Cyclic scheduling period of test cases. The frequency must be greater than the value of the following formula; otherwise, the test results may be inaccurate:
                     (number of sent packets - 1) * (packet sending interval) + (timeout period).";
                }
              }
            }
            case mac-ping {
              description
                "MAC ping NQA test.";
              container mac-ping-input {
                // NCS drop must statement
                // NCS drop must statement
                presence "Present enable MAC ping test instance input.";
                description
                  "Enable/disable MAC ping test instance input.";
                // NCS expand uses statement
                choice destination {
                  description
                    "Destination information.";
                  case mac-address {
                    description
                      "MAC address.";
                    leaf dest-mac-address {
                      type ncs_template_unicast-mac-address;
                      description
                        "Destination MAC, must be unicast MAC and not 0-0-0 MAC.";
                    }
                  }
                  case remote-mep-id {
                    description
                      "Remote MEP ID.";
                    leaf remote-mep-id {
                      type string;
                      description
                        "Remote MEP ID.";
                    }
                  }
                }
                leaf mep-id {
                  type string;
                  description
                    "MEP ID.";
                }
                leaf md-name {
                  type string;
                  description
                    "Maintenance domain name.";
                }
                leaf ma-name {
                  type string;
                  description
                    "Maintenance association name.";
                }
                leaf interval {
                  type string;
                  units "s";
                  // NCS drop default statement
                  description
                    "Interval for sending packets.";
                }
                leaf probe-count {
                  type string;
                  // NCS drop default statement
                  description
                    "Number of sent packets.";
                }
                leaf timeout {
                  type string;
                  units "s";
                  // NCS drop default statement
                  description
                    "Time to wait for a response packet after a test packet is sent.";
                }
                leaf data-size {
                  type string;
                  units "Byte";
                  // NCS drop default statement
                  description
                    "Packet size.";
                }
                leaf source-if-name {
                  type string;
                  description
                    "Out interface name.";
                  // NCS drop must statement
                }
                leaf fail-percent {
                  type string;
                  units "%";
                  // NCS drop default statement
                  description
                    "Loss ratio, determining whether the test is successful.";
                }
                leaf probe-fails {
                  type string;
                  // NCS drop default statement
                  description
                    "The maximum number of probe failures of an NQA test to send trap or events.";
                }
                leaf test-fails {
                  type string;
                  // NCS drop default statement
                  description
                    "The maximum number of the NQA test consecutive test failures to send trap or events.";
                }
                leaf send-trap-bits {
                  type string;
                  description
                    "Configure conditions for sending traps.";
                }
                leaf threshold-rtd {
                  type string;
                  description
                    "Threshold value of round trip delay.";
                }
                leaf jitter-packet-num {
                  type string;
                  // NCS drop default statement
                  description
                    "Number of sent packets.";
                }
                leaf frequency {
                  type string;
                  units "s";
                  description
                    "Cyclic scheduling period of test cases. The Frequency must be greater than the value of the following formula; otherwise, the test results may be inaccurate:
                     (Number of Sent Packets - 1) * (Packet Sending Interval) + (Timeout Period)";
                }
                leaf result-num {
                  type string;
                  // NCS drop default statement
                  description
                    "The maximum number of test result records.";
                }
                leaf history-num {
                  type string;
                  // NCS drop default statement
                  description
                    "The maximum number of historical test records.";
                }
                leaf description {
                  type string;
                  description
                    "Description of test instance.";
                }
                leaf age-time {
                  type pub-type:ncs_template_time;
                  // NCS drop default statement
                  description
                    "Aging time of test instance.";
                }
              }
            }
            case arp-ping-ip {
              description
                "Arp ping IP NQA test.";
              container arp-ping-ip-input {
                presence "Present enable arp ping IP test intance input.";
                description
                  "Enable/disable arp ping IP test intance input.";
                // NCS expand uses statement
                leaf ipv4-dest-address {
                  type string;
                  description
                    "Destination IPv4 address.";
                }
                leaf probe-count {
                  type string;
                  // NCS drop default statement
                  description
                    "Number of sent packets.";
                }
                leaf out-if-name {
                  type string;
                  description
                    "Out interface name.";
                  // NCS drop must statement
                }
                leaf timeout {
                  type string;
                  units "s";
                  // NCS drop default statement
                  description
                    "Time to wait for a response packet after a test packet is sent, expressed in seconds.";
                }
                leaf result-num {
                  type string;
                  // NCS drop default statement
                  description
                    "The maximum number of test result records.";
                }
                leaf history-num {
                  type string;
                  // NCS drop default statement
                  description
                    "The maximum number of historical test records.";
                }
                leaf description {
                  type string;
                  description
                    "Description of test instance.";
                }
                leaf age-time {
                  type pub-type:ncs_template_time;
                  // NCS drop default statement
                  description
                    "Aging time of test instance.";
                }
                leaf frequency {
                  type string;
                  units "s";
                  description
                    "Cyclic scheduling period of test cases. The frequency must be greater than the value of the following formula; otherwise, the test results may be inaccurate:
                     (Number of sent Packets - 1) * (Packet sending interval) + (Timeout period).";
                }
              }
            }
          }
          // NCS drop config false container 'execution-policy'
        }
      }
      // NCS drop config false container record
    }
  }
}
