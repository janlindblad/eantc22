module huawei-vaccess {
  // Generated by yanger -t ncs
  tailf:mount-id "huawei-nc-1.0:huawei-nc-1.0";
  tailf:ncs-device-type "netconf";

  namespace "urn:huawei:yang:huawei-vaccess";
  prefix vaccess;

  import huawei-extension {
    prefix ext;
  }
  import ietf-inet-types {
    prefix inet;
  }
  include huawei-vaccess-type;
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Virtual Access.";

  revision 2020-03-24 {
    description
      "Fixed some problems.";
    reference "Huawei private.";
  }
  revision 2020-03-10 {
    description
      "Add a node primary-master-ip.";
    reference "Huawei private.";
  }
  revision 2019-11-13 {
    description
      "Add some condition for vaccess container.";
    reference "Huawei private.";
  }
  revision 2019-10-14 {
    description
      "The modifications in the schema file are synchronized to the YANG file.";
    reference "Huawei private.";
  }
  revision 2019-06-05 {
    description
      "Initial revision.";
    reference "Huawei private.";
  }
  ext:task-name "virtual-access";

  augment "/ncs:devices/ncs:device/ncs:config" {
    container vaccess {
      tailf:ncs-device-type "netconf";
      tailf:display-when "not(../../ncs:module) or ../../ncs:module[ncs:name='huawei-vaccess']";
      description
        "Virtual Access.";
      container global {
        must "not(port-extend-enable='true' and enable='true')" {
          tailf:xpath-root 3;
        }
        description
          "Configure bisic function of virtural access.";
        leaf enable {
          type boolean;
          default "false";
          description
            "Enable/disable state of virtural access. Default is no configuration.";
        }
        leaf port-extend-enable {
          type boolean;
          default "false";
          description
            "Enable/disable state of virtural access port-extend. Default is no configuration.";
        }
        leaf role {
          when "../enable='true' or ../port-extend-enable='true'" {
            tailf:xpath-root 3;
          }
          type vaccess-va-role;
          must "(../role='default') or (../enable='true' and ../role='ap') or (../port-extend-enable='true' and ../role='master')" {
            tailf:xpath-root 3;
          }
          default "default";
          description
            "Role of virtual access. Default is no configuration.";
        }
      }
      container ap {
        when "../global/role='ap'" {
          tailf:xpath-root 3;
        }
        description
          "Configure ap of virtual access configuration.";
        container master {
          description
            "Configure basic function of master.";
          leaf primary-master-ip {
            type inet:ip-address;
            description
              "Primary master IP address.";
          }
        }
      }
    }
  }
  augment "/ncs:devices/ncs:device/ncs:live-status" {
    container vaccess {
      tailf:ncs-device-type "netconf";
      tailf:display-when "not(../../ncs:module) or ../../ncs:module[ncs:name='huawei-vaccess'] or (../../ncs:live-status-protocol[not(ncs:capability)]) or (../../ncs:live-status-protocol/ncs:capability/ncs:module[.='huawei-vaccess'])";
      description
        "Virtual Access.";
      container global {
        // NCS drop must statement
        description
          "Configure bisic function of virtural access.";
        leaf enable {
          type boolean;
          // NCS drop default statement
          description
            "Enable/disable state of virtural access. Default is no configuration.";
        }
        leaf port-extend-enable {
          type boolean;
          // NCS drop default statement
          description
            "Enable/disable state of virtural access port-extend. Default is no configuration.";
        }
        leaf role {
          // NCS drop when statement
          type live_ncs_vaccess-va-role;
          // NCS drop must statement
          // NCS drop default statement
          description
            "Role of virtual access. Default is no configuration.";
        }
      }
      container ap {
        // NCS drop when statement
        description
          "Configure ap of virtual access configuration.";
        container master {
          description
            "Configure basic function of master.";
          leaf primary-master-ip {
            type inet:ip-address;
            description
              "Primary master IP address.";
          }
        }
      }
    }
  }
  augment "/ncs:devices/ncs:template/ncs:ned-id/ncs:config" {
    container vaccess {
      description
        "Virtual Access.";
      container global {
        // NCS drop must statement
        description
          "Configure bisic function of virtural access.";
        leaf enable {
          type string;
          // NCS drop default statement
          description
            "Enable/disable state of virtural access. Default is no configuration.";
        }
        leaf port-extend-enable {
          type string;
          // NCS drop default statement
          description
            "Enable/disable state of virtural access port-extend. Default is no configuration.";
        }
        leaf role {
          // NCS drop when statement
          type ncs_template_vaccess-va-role;
          // NCS drop must statement
          // NCS drop default statement
          description
            "Role of virtual access. Default is no configuration.";
        }
      }
      container ap {
        // NCS drop when statement
        description
          "Configure ap of virtual access configuration.";
        container master {
          description
            "Configure basic function of master.";
          leaf primary-master-ip {
            type string;
            description
              "Primary master IP address.";
          }
        }
      }
    }
  }
}
