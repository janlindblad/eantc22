module huawei-gre-fwd {
  // Generated by yanger -t ncs
  tailf:mount-id "huawei-nc-1.0:huawei-nc-1.0";
  tailf:ncs-device-type "netconf";

  yang-version 1;
  namespace "urn:huawei:yang:huawei-gre-fwd";
  prefix gre-fwd;

  import huawei-gre {
    prefix gre;
  }
  import huawei-tunnel-management {
    prefix tnlm;
  }
  import huawei-extension {
    prefix ext;
  }
  import huawei-ifm {
    prefix ifm;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Unicast forward GRE configuration.";

  revision 2020-08-13 {
    description
      "Initial revision.";
    reference "Huawei private.";
  }
  ext:task-name "forwarding";

  augment "/ncs:devices/ncs:template/ncs:ned-id/ncs:config/ifm:ifm/ifm:interfaces/ifm:interface/tnlm:tunnel-protocol/tnlm:type/gre:gre/gre:gre-tunnel" {
    description
      "Unicast forward configuration to the GRE module.";
    container unicast-forward {
      description
        "Configure GRE unicast forward.";
      leaf tcp-mss {
        type string;
        units "Byte";
        description
          "Maximum Segment Size of an interface.";
      }
    }
  }
  augment "/ncs:devices/ncs:device/ncs:live-status/ifm:ifm/ifm:interfaces/ifm:interface/tnlm:tunnel-protocol/tnlm:type/gre:gre/gre:gre-tunnel" {
    description
      "Unicast forward configuration to the GRE module.";
    container unicast-forward {
      tailf:ncs-device-type "netconf";
      tailf:display-when "not(../../../../../../../../../ncs:module) or ../../../../../../../../../ncs:module[ncs:name='huawei-gre-fwd'] or (../../../../../../../../../ncs:live-status-protocol[not(ncs:capability)]) or (../../../../../../../../../ncs:live-status-protocol/ncs:capability/ncs:module[.='huawei-gre-fwd'])";
      description
        "Configure GRE unicast forward.";
      leaf tcp-mss {
        type uint16 {
          range "32..9500";
        }
        units "Byte";
        description
          "Maximum Segment Size of an interface.";
      }
    }
  }
  augment "/ncs:devices/ncs:device/ncs:config/ifm:ifm/ifm:interfaces/ifm:interface/tnlm:tunnel-protocol/tnlm:type/gre:gre/gre:gre-tunnel" {
    description
      "Unicast forward configuration to the GRE module.";
    container unicast-forward {
      tailf:ncs-device-type "netconf";
      tailf:display-when "not(../../../../../../../../../ncs:module) or ../../../../../../../../../ncs:module[ncs:name='huawei-gre-fwd']";
      description
        "Configure GRE unicast forward.";
      leaf tcp-mss {
        type uint16 {
          range "32..9500";
        }
        units "Byte";
        description
          "Maximum Segment Size of an interface.";
      }
    }
  }
}
