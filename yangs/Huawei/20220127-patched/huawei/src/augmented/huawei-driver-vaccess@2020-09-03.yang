module huawei-driver-vaccess {
  // Generated by yanger -t ncs
  tailf:mount-id "huawei-nc-1.0:huawei-nc-1.0";
  tailf:ncs-device-type "netconf";

  yang-version 1;
  namespace "urn:huawei:yang:huawei-driver-vaccess";
  prefix driver-vaccess;

  import huawei-extension {
    prefix ext;
  }
  import huawei-vaccess {
    prefix vaccess;
  }
  import huawei-vaccess-master {
    prefix vaccess-master;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Virtual Access Entity Management.";

  revision 2020-09-03 {
    description
      "Init revision.";
    reference "Huawei private.";
  }
  ext:task-name "device-mgr";

  augment "/ncs:devices/ncs:device/ncs:config" {
    container driver-vaccess {
      tailf:ncs-device-type "netconf";
      tailf:display-when "not(../../ncs:module) or ../../ncs:module[ncs:name='huawei-driver-vaccess']";
      description
        "Configuration of the driver vaccess.";
      // NCS drop config false container 'board-infos'
    }
  }
  augment "/ncs:devices/ncs:device/ncs:live-status" {
    container driver-vaccess {
      tailf:ncs-device-type "netconf";
      tailf:display-when "not(../../ncs:module) or ../../ncs:module[ncs:name='huawei-driver-vaccess'] or (../../ncs:live-status-protocol[not(ncs:capability)]) or (../../ncs:live-status-protocol/ncs:capability/ncs:module[.='huawei-driver-vaccess'])";
      description
        "Configuration of the driver vaccess.";
      container board-infos {
        description
          "List of AP board information.";
        list board-info {
          key "ap-id index";
          description
            "Operational state of AP board information.";
          leaf ap-id {
            type leafref {
              path "/ncs:devices/ncs:device/ncs:live-status/vaccess:vaccess/vaccess-master:master/vaccess-master:aps/vaccess-master:ap/vaccess-master:ap-id" {
                tailf:xpath-root 3;
              }
            }
            description
              "AP ID.";
          }
          leaf index {
            type uint32;
            description
              "Board index.";
          }
          leaf host-name {
            type string {
              length "1..246";
            }
            description
              "The host name of the system.";
          }
          leaf chassis-id {
            type uint32;
            description
              "Chassis ID.";
          }
          leaf slot-id {
            type uint32;
            description
              "Slot ID.";
          }
          leaf board-type {
            type string {
              length "1..19";
            }
            description
              "Board type.";
          }
        }
      }
    }
  }
  augment "/ncs:devices/ncs:template/ncs:ned-id/ncs:config" {
    container driver-vaccess {
      description
        "Configuration of the driver vaccess.";
      // NCS drop config false container 'board-infos'
    }
  }
}
