module huawei-fim-lcs {
  // Generated by yanger -t ncs
  tailf:mount-id "huawei-nc-1.0:huawei-nc-1.0";
  tailf:ncs-device-type "netconf";

  yang-version 1;
  namespace "urn:huawei:yang:huawei-fim-lcs";
  prefix fim-lcs;

  import huawei-extension {
    prefix ext;
  }
  import huawei-license {
    prefix lcs;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Global Configuration.";

  revision 2020-03-11 {
    description
      "Initial revision.";
    reference "Huawei private.";
  }
  ext:task-name "forwarding";

  typedef ncs_template_lcs-active-type {
    type string;
    description
      "Lcsense active type.";
  }

  typedef ncs_template_lcs-active-status-type {
    type string;
    description
      "Liscense active status type.";
  }

  typedef ncs_rpc_notif_lcs-active-type {
    type enumeration {
      enum "deactive" {
        value 0;
        description
          "Deactivate.";
      }
      enum "active" {
        value 1;
        description
          "Activate.";
      }
    }
    description
      "Lcsense active type.";
  }

  typedef ncs_rpc_notif_lcs-active-status-type {
    type enumeration {
      enum "unallocated" {
        value 0;
        description
          "Unallocated.";
      }
      enum "allocated" {
        value 1;
        description
          "Allocated.";
      }
      enum "activated" {
        value 2;
        description
          "Activated.";
      }
    }
    description
      "Liscense active status type.";
  }

  typedef live_ncs_lcs-active-type {
    type enumeration {
      enum "deactive" {
        value 0;
        description
          "Deactivate.";
      }
      enum "active" {
        value 1;
        description
          "Activate.";
      }
    }
    description
      "Lcsense active type.";
  }

  typedef live_ncs_lcs-active-status-type {
    type enumeration {
      enum "unallocated" {
        value 0;
        description
          "Unallocated.";
      }
      enum "allocated" {
        value 1;
        description
          "Allocated.";
      }
      enum "activated" {
        value 2;
        description
          "Activated.";
      }
    }
    description
      "Liscense active status type.";
  }

  typedef lcs-active-type {
    type enumeration {
      enum "deactive" {
        value 0;
        description
          "Deactivate.";
      }
      enum "active" {
        value 1;
        description
          "Activate.";
      }
    }
    description
      "Lcsense active type.";
  }

  typedef lcs-active-status-type {
    type enumeration {
      enum "unallocated" {
        value 0;
        description
          "Unallocated.";
      }
      enum "allocated" {
        value 1;
        description
          "Allocated.";
      }
      enum "activated" {
        value 2;
        description
          "Activated.";
      }
    }
    description
      "Liscense active status type.";
  }

  augment "/ncs:devices/ncs:template/ncs:ned-id/ncs:config/lcs:license/lcs:license-items/lcs:license-item" {
    description
      "Channelized sub-interface license information list.";
    container port-mode-channels {
      // NCS drop when statement
      description
        "List of channelized sub-interface license information.";
      list port-mode-channel {
        // NCS patched for predictable order
        ordered-by user;
        key "position";
        description
          "Configure channelized sub-interface license information.";
        leaf position {
          type string;
          description
            "Port position.";
        }
      }
    }
    container port-slicings {
      // NCS drop when statement
      description
        "List of port slicing license information.";
      list port-slicing {
        // NCS patched for predictable order
        ordered-by user;
        key "position";
        description
          "Configure port slicing license information.";
        leaf position {
          type string;
          description
            "Port position.";
        }
      }
    }
  }
  augment "/ncs:devices/ncs:device/ncs:live-status/lcs:license/lcs:license-items/lcs:license-item" {
    description
      "Channelized sub-interface license information list.";
    container port-mode-channels {
      tailf:ncs-device-type "netconf";
      tailf:display-when "not(../../../../../ncs:module) or ../../../../../ncs:module[ncs:name='huawei-fim-lcs'] or (../../../../../ncs:live-status-protocol[not(ncs:capability)]) or (../../../../../ncs:live-status-protocol/ncs:capability/ncs:module[.='huawei-fim-lcs'])";
      // NCS drop when statement
      description
        "List of channelized sub-interface license information.";
      list port-mode-channel {
        key "position";
        description
          "Configure channelized sub-interface license information.";
        leaf position {
          type string {
            length "1..32";
          }
          description
            "Port position.";
        }
      }
    }
    container port-slicings {
      tailf:ncs-device-type "netconf";
      tailf:display-when "not(../../../../../ncs:module) or ../../../../../ncs:module[ncs:name='huawei-fim-lcs'] or (../../../../../ncs:live-status-protocol[not(ncs:capability)]) or (../../../../../ncs:live-status-protocol/ncs:capability/ncs:module[.='huawei-fim-lcs'])";
      // NCS drop when statement
      description
        "List of port slicing license information.";
      list port-slicing {
        key "position";
        description
          "Configure port slicing license information.";
        leaf position {
          type string {
            length "1..32";
          }
          description
            "Port position.";
        }
      }
    }
  }
  augment "/ncs:devices/ncs:device/ncs:config/lcs:license/lcs:license-items/lcs:license-item" {
    description
      "Channelized sub-interface license information list.";
    container port-mode-channels {
      tailf:ncs-device-type "netconf";
      tailf:display-when "not(../../../../../ncs:module) or ../../../../../ncs:module[ncs:name='huawei-fim-lcs']";
      when "(../lcs:name ='LCR5S0FCHAN91' or ../lcs:name ='LCR5S0FCHAN92' or ../lcs:name ='LCR5S0FCHAN93' or ../lcs:name ='LCR5S0FCHAN94' or ../lcs:name ='LCR5S03SUBC93' or ../lcs:name ='LCR5S03SUBC94' or ../lcs:name ='LCR5S03SUBC95' or ../lcs:name ='LCR5S03SUBC92' or ../lcs:name ='LCR5S42CHAN70' or ../lcs:name ='LCR5S42CHAN71' or ../lcs:name ='LCR5S42CHAN72' or ../lcs:name ='LCR5S42CHAN73' or ../lcs:name ='LCR5S42CHAN90' or ../lcs:name ='LCR5S42CHAN91' or ../lcs:name ='LCR5S42CHAN92' or ../lcs:name ='LCR5S42CHAN93' or ../lcs:name ='LCR5S40CHIN00' or ../lcs:name ='LCR5S40CHIN01' or ../lcs:name ='LCR5S40CHIN02' or ../lcs:name ='LCX6S40CHIN00' or ../lcs:name ='LCX6S40CHIN01' or ../lcs:name ='LCX6S40CHIN02' or ../lcs:name ='LTNRS69CHIN00' or ../lcs:name ='LTNRS69CHIN01' or ../lcs:name ='LTNRS69CHIN02' or ../lcs:name ='LCR9S9KXCSF80' or ../lcs:name ='LCR9S9KNCSF81' or ../lcs:name ='LCR9S9KNCSF80' or ../lcs:name ='LCR9S9KKCSF80')" {
        tailf:xpath-root 3;
      }
      description
        "List of channelized sub-interface license information.";
      list port-mode-channel {
        key "position";
        description
          "Configure channelized sub-interface license information.";
        leaf position {
          type string {
            length "1..32";
          }
          description
            "Port position.";
        }
      }
    }
    container port-slicings {
      tailf:ncs-device-type "netconf";
      tailf:display-when "not(../../../../../ncs:module) or ../../../../../ncs:module[ncs:name='huawei-fim-lcs']";
      when "(../lcs:name ='LCR8S00VSLIC0' or ../lcs:name ='LCR8S00XSLIC0' or ../lcs:name ='LCR8S00VSLIC3' or ../lcs:name ='LCR8S00XSLIC3' or ../lcs:name ='LCR8S00SLC0C2' or ../lcs:name ='LCR8S00SLC0C4' or ../lcs:name ='LCR8S00SLC0C2' or ../lcs:name ='LCR8S00SLC0C4' or ../lcs:name ='LCR8SF0SLC0C4' or ../lcs:name ='LCR8SF0SLC0C5' or ../lcs:name ='LTNRS00SLC0C2' or ../lcs:name ='LTNRS00SLC0C4' or ../lcs:name ='LTNRS00SLC0C2' or ../lcs:name ='LTNRS00SLC0C4' or ../lcs:name ='LCR5S00SLC0C2' or ../lcs:name ='LCR5S00SLC0C4')" {
        tailf:xpath-root 3;
      }
      description
        "List of port slicing license information.";
      list port-slicing {
        key "position";
        description
          "Configure port slicing license information.";
        leaf position {
          type string {
            length "1..32";
          }
          description
            "Port position.";
        }
      }
    }
  }
}
