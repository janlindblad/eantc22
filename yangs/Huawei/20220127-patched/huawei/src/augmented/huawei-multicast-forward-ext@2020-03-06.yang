module huawei-multicast-forward-ext {
  // Generated by yanger -t ncs
  tailf:mount-id "huawei-nc-1.0:huawei-nc-1.0";
  tailf:ncs-device-type "netconf";

  namespace "urn:huawei:yang:huawei-multicast-forward-ext";
  prefix multicast-forward-ext;

  import huawei-multicast-forward {
    prefix multicast-forward;
  }
  import huawei-extension {
    prefix ext;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "L2 control protocol management ext.";

  revision 2020-03-06 {
    description
      "Change description.";
    reference "Huawei private.";
  }
  revision 2019-04-23 {
    description
      "Initial revision.";
    reference "Huawei private.";
  }
  ext:task-name "forwarding";

  typedef ncs_template_mac-suppression-status {
    type string;
    description
      "Description of mac-suppression-status.";
  }

  typedef ncs_rpc_notif_mac-suppression-status {
    type enumeration {
      enum "disable" {
        value 0;
        description
          "Specify mac-suppression-status disable.";
      }
      enum "enable" {
        value 1;
        description
          "Specify mac-suppression-status enable.";
      }
    }
    description
      "Description of mac-suppression-status.";
  }

  typedef live_ncs_mac-suppression-status {
    type enumeration {
      enum "disable" {
        value 0;
        description
          "Specify mac-suppression-status disable.";
      }
      enum "enable" {
        value 1;
        description
          "Specify mac-suppression-status enable.";
      }
    }
    description
      "Description of mac-suppression-status.";
  }

  typedef mac-suppression-status {
    type enumeration {
      enum "disable" {
        value 0;
        description
          "Specify mac-suppression-status disable.";
      }
      enum "enable" {
        value 1;
        description
          "Specify mac-suppression-status enable.";
      }
    }
    description
      "Description of mac-suppression-status.";
  }

  augment "/ncs:devices/ncs:template/ncs:ned-id/ncs:config/multicast-forward:multicast-forward" {
    description
      "L2 control protocol management.";
    container stand-group-mac-suppressions {
      description
        "Configure standard-group MAC address suppression configuration.";
      leaf stand-group-mac-suppression {
        type ncs_template_mac-suppression-status;
        // NCS drop default statement
        description
          "Specify standard-group MAC address suppression configuration information.";
      }
    }
  }
  augment "/ncs:devices/ncs:device/ncs:live-status/multicast-forward:multicast-forward" {
    description
      "L2 control protocol management.";
    container stand-group-mac-suppressions {
      tailf:ncs-device-type "netconf";
      tailf:display-when "not(../../../ncs:module) or ../../../ncs:module[ncs:name='huawei-multicast-forward-ext'] or (../../../ncs:live-status-protocol[not(ncs:capability)]) or (../../../ncs:live-status-protocol/ncs:capability/ncs:module[.='huawei-multicast-forward-ext'])";
      description
        "Configure standard-group MAC address suppression configuration.";
      leaf stand-group-mac-suppression {
        type live_ncs_mac-suppression-status;
        // NCS drop default statement
        description
          "Specify standard-group MAC address suppression configuration information.";
      }
    }
  }
  augment "/ncs:devices/ncs:device/ncs:config/multicast-forward:multicast-forward" {
    description
      "L2 control protocol management.";
    container stand-group-mac-suppressions {
      tailf:ncs-device-type "netconf";
      tailf:display-when "not(../../../ncs:module) or ../../../ncs:module[ncs:name='huawei-multicast-forward-ext']";
      description
        "Configure standard-group MAC address suppression configuration.";
      leaf stand-group-mac-suppression {
        type mac-suppression-status;
        default "disable";
        description
          "Specify standard-group MAC address suppression configuration information.";
      }
    }
  }
}
