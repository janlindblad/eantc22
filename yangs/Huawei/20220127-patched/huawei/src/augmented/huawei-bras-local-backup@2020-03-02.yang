module huawei-bras-local-backup {
  // Generated by yanger -t ncs
  tailf:mount-id "huawei-nc-1.0:huawei-nc-1.0";
  tailf:ncs-device-type "netconf";

  namespace "urn:huawei:yang:huawei-bras-local-backup";
  prefix bras-local-backup;

  import huawei-aaa {
    prefix aaa;
  }
  import huawei-extension {
    prefix ext;
  }
  import huawei-bras-basic-access {
    prefix bras-basic-access;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Bras local backup.";

  revision 2020-03-02 {
    description
      "Modify description.";
    reference "Huawei private.";
  }
  revision 2019-04-02 {
    description
      "Initial revision.";
    reference "Huawei private.";
  }
  ext:task-name "bras-control";

  augment "/ncs:devices/ncs:device/ncs:config" {
    container bras-local-backup {
      tailf:ncs-device-type "netconf";
      tailf:display-when "not(../../ncs:module) or ../../ncs:module[ncs:name='huawei-bras-local-backup']";
      description
        "Bras local backup.";
      container backup-user {
        description
          "Configure the backup of local user information.";
        leaf enable {
          type boolean;
          default "true";
          description
            "Enable/disable the backup of local user information.";
        }
        leaf quota-out-backup-enable {
          type boolean;
          default "false";
          description
            "Enable/disable information backup for users who are logged out due to duration or traffic volume quota exhaustion.";
        }
      }
      container backup-user-limit {
        description
          "Configure the maximum number of users whose information can be backed up.";
        leaf value {
          type uint32 {
            range "1..256";
          }
          default "128";
          description
            "Specifies the maximum number of users whose information can be backed up.";
        }
      }
    }
  }
  augment "/ncs:devices/ncs:device/ncs:live-status" {
    container bras-local-backup {
      tailf:ncs-device-type "netconf";
      tailf:display-when "not(../../ncs:module) or ../../ncs:module[ncs:name='huawei-bras-local-backup'] or (../../ncs:live-status-protocol[not(ncs:capability)]) or (../../ncs:live-status-protocol/ncs:capability/ncs:module[.='huawei-bras-local-backup'])";
      description
        "Bras local backup.";
      container backup-user {
        description
          "Configure the backup of local user information.";
        leaf enable {
          type boolean;
          // NCS drop default statement
          description
            "Enable/disable the backup of local user information.";
        }
        leaf quota-out-backup-enable {
          type boolean;
          // NCS drop default statement
          description
            "Enable/disable information backup for users who are logged out due to duration or traffic volume quota exhaustion.";
        }
      }
      container backup-user-limit {
        description
          "Configure the maximum number of users whose information can be backed up.";
        leaf value {
          type uint32 {
            range "1..256";
          }
          // NCS drop default statement
          description
            "Specifies the maximum number of users whose information can be backed up.";
        }
      }
    }
  }
  augment "/ncs:devices/ncs:template/ncs:ned-id/ncs:config" {
    container bras-local-backup {
      description
        "Bras local backup.";
      container backup-user {
        description
          "Configure the backup of local user information.";
        leaf enable {
          type string;
          // NCS drop default statement
          description
            "Enable/disable the backup of local user information.";
        }
        leaf quota-out-backup-enable {
          type string;
          // NCS drop default statement
          description
            "Enable/disable information backup for users who are logged out due to duration or traffic volume quota exhaustion.";
        }
      }
      container backup-user-limit {
        description
          "Configure the maximum number of users whose information can be backed up.";
        leaf value {
          type string;
          // NCS drop default statement
          description
            "Specifies the maximum number of users whose information can be backed up.";
        }
      }
    }
  }
  augment "/ncs:devices/ncs:template/ncs:ned-id/ncs:config/aaa:aaa/aaa:domains/aaa:domain/bras-basic-access:bas" {
    description
      "Bras local backup domain configuration.";
    container local-backup {
      description
        "Configure local backup domain.";
      container local-user-backup {
        description
          "Configure local user information backup in a domain.";
        leaf enable {
          type string;
          // NCS drop default statement
          description
            "Enable/disable local user information backup in a domain.";
        }
      }
    }
  }
  augment "/ncs:devices/ncs:device/ncs:live-status/aaa:aaa/aaa:domains/aaa:domain/bras-basic-access:bas" {
    description
      "Bras local backup domain configuration.";
    container local-backup {
      tailf:ncs-device-type "netconf";
      tailf:display-when "not(../../../../../../ncs:module) or ../../../../../../ncs:module[ncs:name='huawei-bras-local-backup'] or (../../../../../../ncs:live-status-protocol[not(ncs:capability)]) or (../../../../../../ncs:live-status-protocol/ncs:capability/ncs:module[.='huawei-bras-local-backup'])";
      description
        "Configure local backup domain.";
      container local-user-backup {
        description
          "Configure local user information backup in a domain.";
        leaf enable {
          type boolean;
          // NCS drop default statement
          description
            "Enable/disable local user information backup in a domain.";
        }
      }
    }
  }
  augment "/ncs:devices/ncs:device/ncs:config/aaa:aaa/aaa:domains/aaa:domain/bras-basic-access:bas" {
    description
      "Bras local backup domain configuration.";
    container local-backup {
      tailf:ncs-device-type "netconf";
      tailf:display-when "not(../../../../../../ncs:module) or ../../../../../../ncs:module[ncs:name='huawei-bras-local-backup']";
      description
        "Configure local backup domain.";
      container local-user-backup {
        description
          "Configure local user information backup in a domain.";
        leaf enable {
          type boolean;
          default "true";
          description
            "Enable/disable local user information backup in a domain.";
        }
      }
    }
  }
}
