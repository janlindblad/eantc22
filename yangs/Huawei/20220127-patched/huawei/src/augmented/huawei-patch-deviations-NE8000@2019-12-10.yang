module huawei-patch-deviations-NE8000 {
  // Generated by yanger -t ncs
  tailf:mount-id "huawei-nc-1.0:huawei-nc-1.0";
  tailf:ncs-device-type "netconf";

  namespace "urn:huawei:yang:huawei-patch-deviations-NE8000";
  prefix patch-devs-NE8000;

  import huawei-patch {
    prefix patch;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Patch deviations.";

  revision 2019-12-10 {
    description
      "Initial revision.";
    reference "Huawei private.";
  }

  deviation "/ncs:devices/ncs:device/ncs:live-status/patch:patch/patch:next-startup-patchs" {
    deviate not-supported;
  }
  deviation "/ncs:devices/ncs:device/ncs:live-status/patch:patch/patch:operation-schedules/patch:operation-schedule/patch:name" {
    deviate not-supported;
  }
  deviation "/ncs:devices/ncs:device/ncs:live-status/patch:patch/patch:download-package-schedule" {
    deviate not-supported;
  }
  deviation "/ncs:devices/ncs:device/ncs:live-status/patch:patch/patch:download-package-load-path" {
    deviate not-supported;
  }
  deviation "/ncs:devices/ncs:device/ncs:rpc/patch:rpc-download-patch-file/patch:download-patch-file" {
    deviate not-supported;
  }
}
