module openconfig-igmp {
  // Generated by yanger -t ncs
  tailf:mount-id "huawei-nc-1.0:huawei-nc-1.0";
  tailf:ncs-device-type "netconf";

  yang-version 1;
  namespace "http://openconfig.net/yang/igmp";
  prefix oc-igmp;

  import openconfig-igmp-types {
    prefix oc-igmp-types;
  }
  import openconfig-types {
    prefix oc-types;
  }
  import openconfig-acl {
    prefix oc-acl;
  }
  import openconfig-extensions {
    prefix oc-ext;
  }
  import openconfig-interfaces {
    prefix oc-if;
  }
  import ietf-inet-types {
    prefix inet;
  }
  import tailf-common {
    prefix tailf;
  }
  import tailf-ncs {
    prefix ncs;
  }

  organization
    "OpenConfig working group";
  contact
    "OpenConfig working group
     www.openconfig.net";
  description
    "An OpenConfig model for Internet Group Management Protocol (IGMP).";
  oc-ext:openconfig-version "0.2.0";

  revision 2019-07-09 {
    description
      "Re-indent module to two spaces.
       Normalise timeticks64 usage to nanoseconds.";
    reference "0.2.0";
  }
  revision 2018-11-21 {
    description
      "Add OpenConfig module metadata extensions.";
    reference "0.1.1";
  }
  revision 2018-02-19 {
    description
      "Initial revision.";
    reference "0.1.0";
  }
  oc-ext:regexp-posix;
  oc-ext:catalog-organization "openconfig";
  oc-ext:origin "openconfig";

  grouping ncs_template_admin-config {
    description
      "Re-usable grouping to enable or disable a particular feature.";
    leaf enabled {
      type string;
      // NCS drop default statement
      description
        "When set to true, the functionality within which this
         leaf is defined is enabled, when set to false it is
         explicitly disabled.";
    }
  }

  grouping ncs_template_igmp-interface-config {
    description
      "Configuration data for IGMP on each interface.";
    leaf interface-id {
      type oc-if:ncs_template_interface-id;
      description
        "Reference to an interface on which IGMP is enabled.";
    }
    uses ncs_template_admin-config;
    leaf version {
      type oc-igmp-types:ncs_template_igmp-version;
      description
        "IGMP Version.";
    }
    leaf query-interval {
      type oc-igmp-types:ncs_template_igmp-interval-type;
      description
        "Interval at which the router sends the IGMP membership
         queries.";
    }
    leaf filter-prefixes {
      type string;
      description
        "List used to filter joins.";
    }
  }

  grouping ncs_template_igmp-counters-per-version {
    description
      "Counters for each IGMP protocol version.";
    // NCS drop config false container state
  }

  grouping ncs_template_igmp-interface-counters {
    description
      "State and session data for IGMP on each interface.";
    container counters {
      description
        "Counters avaiable on a per interface bases for IGMP.";
      container queries {
        description
          "IGMP membership queries.";
        container sent {
          description
            "Number of IGMP membership queries sent.";
          uses ncs_template_igmp-counters-per-version;
        }
        container received {
          description
            "Number of IGMP membership queries received.";
          uses ncs_template_igmp-counters-per-version;
        }
      }
      container reports {
        description
          "Number of IGMP membership reports received.";
        uses ncs_template_igmp-counters-per-version;
      }
    }
  }

  grouping ncs_template_igmp-snooping-state {
    description
      "IGMP membership snooping state.";
    leaf group {
      type string;
      description
        "Multicast address.";
    }
    leaf source {
      type string;
      description
        "Source address of multicast.";
    }
    leaf reporter {
      type string;
      description
        "Address of the last reporter.";
    }
  }

  grouping ncs_template_igmp-snooping-structural {
    description
      "IGMP membership information determined through snooping.";
    container membership-groups {
      description
        "List of IGMP Membership information.";
      // NCS drop config false list group
    }
  }

  grouping ncs_template_igmp-interface-state {
    description
      "IGMP interface state.";
    leaf query-expires {
      type oc-types:ncs_template_timeticks64;
      description
        "This timestamp indicates the time that the next query is sent
         expressed relative to the Unix Epoch (Jan 1, 1970 00:00:00 UTC).";
    }
  }

  grouping ncs_template_igmp-interface-top {
    description
      "Configuration and state data for IGMP on each interface.";
    container interfaces {
      description
        "The interfaces on which IGMP is configured.";
      list interface {
        // NCS patched for predictable order
        ordered-by user;
        key "interface-id";
        description
          "This container defines interface IGMP configuration and
           state information.";
        leaf interface-id {
          type string;
          description
            "Reference to an interface on which IGMP is enabled.";
        }
        container config {
          description
            "IGMP interface configuration.";
          uses ncs_template_igmp-interface-config;
        }
        // NCS drop config false container state
        uses ncs_template_igmp-interface-counters;
        uses ncs_template_igmp-snooping-structural;
        uses oc-if:ncs_template_interface-ref;
      }
    }
  }

  grouping ncs_template_igmp-ssm-maps-config {
    description
      "A Source Specific Multicast (SSM) mapping. This allows
       IGMP v2 hosts to be able to join in SSM environments
       by translating IGMP v2 reports into IGMP v3 reports.
       The request in an IGMP v2 join is sent toward the source
       address found by matching the multicast address.";
    leaf source {
      type string;
      description
        "Multicast source address.";
    }
    leaf ssm-ranges {
      type string;
      description
        "List of accepted source specific multicast (SSM) address
         ranges.";
    }
  }

  grouping ncs_template_igmp-global-config {
    description
      "This grouping defines global config options for IGMP.";
  }

  grouping ncs_template_igmp-global-top {
    description
      "Top level grouping for global IGMP configuration.";
    container ssm {
      description
        "Source specific multicast (SSM).";
      container mappings {
        description
          "A list of source specific multicast (SSM) mappings.";
        list mapping {
          // NCS patched for predictable order
          ordered-by user;
          key "source";
          description
            "A Source Specific Multicast (SSM) mapping. This allows
             IGMP v2 hosts to be able to join in SSM environments
             by translating IGMP v2 reports into IGMP v3 reports.
             The request in an IGMP v2 join is sent toward the source
             address found by matching the multicast address.";
          leaf source {
            type string;
            description
              "Multicast source address.";
          }
          container config {
            description
              "Configuration for SSM maps.";
            uses ncs_template_igmp-ssm-maps-config;
          }
          // NCS drop config false container state
        }
      }
    }
  }

  grouping ncs_template_igmp-top {
    description
      "Top-level grouping for IGMP.";
    container igmp {
      description
        "Top-level IGMP configuration and operational state.";
      container global {
        description
          "Global IGMP configuration and operational state.";
        uses ncs_template_igmp-global-top;
      }
      uses ncs_template_igmp-interface-top;
    }
  }

  grouping ncs_rpc_notif_admin-config {
    description
      "Re-usable grouping to enable or disable a particular feature.";
    leaf enabled {
      type boolean;
      default "false";
      description
        "When set to true, the functionality within which this
         leaf is defined is enabled, when set to false it is
         explicitly disabled.";
    }
  }

  grouping ncs_rpc_notif_igmp-interface-config {
    description
      "Configuration data for IGMP on each interface.";
    leaf interface-id {
      type oc-if:ncs_rpc_notif_interface-id;
      description
        "Reference to an interface on which IGMP is enabled.";
    }
    uses ncs_rpc_notif_admin-config;
    leaf version {
      type oc-igmp-types:ncs_rpc_notif_igmp-version;
      description
        "IGMP Version.";
    }
    leaf query-interval {
      type oc-igmp-types:ncs_rpc_notif_igmp-interval-type;
      description
        "Interval at which the router sends the IGMP membership
         queries.";
    }
    leaf filter-prefixes {
      type string;
      description
        "List used to filter joins.";
    }
  }

  grouping ncs_rpc_notif_igmp-counters-per-version {
    description
      "Counters for each IGMP protocol version.";
    container state {
      config false;
      description
        "Counters for each IGMP protocol version.";
      leaf v1 {
        type uint32;
        description
          "IGMP v1.";
      }
      leaf v2 {
        type uint32;
        description
          "IGMP v2.";
      }
      leaf v3 {
        type uint32;
        description
          "IGMP v3.";
      }
    }
  }

  grouping ncs_rpc_notif_igmp-interface-counters {
    description
      "State and session data for IGMP on each interface.";
    container counters {
      description
        "Counters avaiable on a per interface bases for IGMP.";
      container queries {
        description
          "IGMP membership queries.";
        container sent {
          description
            "Number of IGMP membership queries sent.";
          uses ncs_rpc_notif_igmp-counters-per-version;
        }
        container received {
          description
            "Number of IGMP membership queries received.";
          uses ncs_rpc_notif_igmp-counters-per-version;
        }
      }
      container reports {
        description
          "Number of IGMP membership reports received.";
        uses ncs_rpc_notif_igmp-counters-per-version;
      }
    }
  }

  grouping ncs_rpc_notif_igmp-snooping-state {
    description
      "IGMP membership snooping state.";
    leaf group {
      type inet:ipv4-address;
      description
        "Multicast address.";
    }
    leaf source {
      type inet:ipv4-address;
      description
        "Source address of multicast.";
    }
    leaf reporter {
      type inet:ipv4-address;
      description
        "Address of the last reporter.";
    }
  }

  grouping ncs_rpc_notif_igmp-snooping-structural {
    description
      "IGMP membership information determined through snooping.";
    container membership-groups {
      description
        "List of IGMP Membership information.";
      list group {
        key "group";
        config false;
        description
          "Multicast group membership.";
        leaf group {
          type leafref {
            path "../state/group";
          }
          description
            "Multicast address.";
        }
        container state {
          config false;
          description
            "Multicast group membership.";
          uses ncs_rpc_notif_igmp-snooping-state;
        }
      }
    }
  }

  grouping ncs_rpc_notif_igmp-interface-state {
    description
      "IGMP interface state.";
    leaf query-expires {
      type oc-types:ncs_rpc_notif_timeticks64;
      description
        "This timestamp indicates the time that the next query is sent
         expressed relative to the Unix Epoch (Jan 1, 1970 00:00:00 UTC).";
    }
  }

  grouping ncs_rpc_notif_igmp-interface-top {
    description
      "Configuration and state data for IGMP on each interface.";
    container interfaces {
      description
        "The interfaces on which IGMP is configured.";
      list interface {
        key "interface-id";
        description
          "This container defines interface IGMP configuration and
           state information.";
        leaf interface-id {
          type leafref {
            path "../config/interface-id";
          }
          description
            "Reference to an interface on which IGMP is enabled.";
        }
        container config {
          description
            "IGMP interface configuration.";
          uses ncs_rpc_notif_igmp-interface-config;
        }
        container state {
          config false;
          description
            "This container defines state information for IGMP
             interfaces.";
          uses ncs_rpc_notif_igmp-interface-state;
          uses ncs_rpc_notif_igmp-interface-config;
        }
        uses ncs_rpc_notif_igmp-interface-counters;
        uses ncs_rpc_notif_igmp-snooping-structural;
        uses oc-if:ncs_rpc_notif_interface-ref;
      }
    }
  }

  grouping ncs_rpc_notif_igmp-ssm-maps-config {
    description
      "A Source Specific Multicast (SSM) mapping. This allows
       IGMP v2 hosts to be able to join in SSM environments
       by translating IGMP v2 reports into IGMP v3 reports.
       The request in an IGMP v2 join is sent toward the source
       address found by matching the multicast address.";
    leaf source {
      type inet:ipv4-address;
      description
        "Multicast source address.";
    }
    leaf ssm-ranges {
      type string;
      description
        "List of accepted source specific multicast (SSM) address
         ranges.";
    }
  }

  grouping ncs_rpc_notif_igmp-global-config {
    description
      "This grouping defines global config options for IGMP.";
  }

  grouping ncs_rpc_notif_igmp-global-top {
    description
      "Top level grouping for global IGMP configuration.";
    container ssm {
      description
        "Source specific multicast (SSM).";
      container mappings {
        description
          "A list of source specific multicast (SSM) mappings.";
        list mapping {
          key "source";
          description
            "A Source Specific Multicast (SSM) mapping. This allows
             IGMP v2 hosts to be able to join in SSM environments
             by translating IGMP v2 reports into IGMP v3 reports.
             The request in an IGMP v2 join is sent toward the source
             address found by matching the multicast address.";
          leaf source {
            type leafref {
              path "../config/source";
            }
            description
              "Multicast source address.";
          }
          container config {
            description
              "Configuration for SSM maps.";
            uses ncs_rpc_notif_igmp-ssm-maps-config;
          }
          container state {
            config false;
            description
              "State for SSM maps.";
            uses ncs_rpc_notif_igmp-ssm-maps-config;
          }
        }
      }
    }
  }

  grouping ncs_rpc_notif_igmp-top {
    description
      "Top-level grouping for IGMP.";
    container igmp {
      description
        "Top-level IGMP configuration and operational state.";
      container global {
        description
          "Global IGMP configuration and operational state.";
        uses ncs_rpc_notif_igmp-global-top;
      }
      uses ncs_rpc_notif_igmp-interface-top;
    }
  }

  grouping live_ncs_admin-config {
    description
      "Re-usable grouping to enable or disable a particular feature.";
    leaf enabled {
      type boolean;
      // NCS drop default statement
      description
        "When set to true, the functionality within which this
         leaf is defined is enabled, when set to false it is
         explicitly disabled.";
    }
  }

  grouping live_ncs_igmp-interface-config {
    description
      "Configuration data for IGMP on each interface.";
    leaf interface-id {
      type oc-if:live_ncs_interface-id;
      description
        "Reference to an interface on which IGMP is enabled.";
    }
    uses live_ncs_admin-config;
    leaf version {
      type oc-igmp-types:live_ncs_igmp-version;
      description
        "IGMP Version.";
    }
    leaf query-interval {
      type oc-igmp-types:live_ncs_igmp-interval-type;
      description
        "Interval at which the router sends the IGMP membership
         queries.";
    }
    leaf filter-prefixes {
      type string;
      description
        "List used to filter joins.";
    }
  }

  grouping live_ncs_igmp-counters-per-version {
    description
      "Counters for each IGMP protocol version.";
    container state {
      description
        "Counters for each IGMP protocol version.";
      leaf v1 {
        type uint32;
        description
          "IGMP v1.";
      }
      leaf v2 {
        type uint32;
        description
          "IGMP v2.";
      }
      leaf v3 {
        type uint32;
        description
          "IGMP v3.";
      }
    }
  }

  grouping live_ncs_igmp-interface-counters {
    description
      "State and session data for IGMP on each interface.";
    container counters {
      description
        "Counters avaiable on a per interface bases for IGMP.";
      container queries {
        description
          "IGMP membership queries.";
        container sent {
          description
            "Number of IGMP membership queries sent.";
          uses live_ncs_igmp-counters-per-version;
        }
        container received {
          description
            "Number of IGMP membership queries received.";
          uses live_ncs_igmp-counters-per-version;
        }
      }
      container reports {
        description
          "Number of IGMP membership reports received.";
        uses live_ncs_igmp-counters-per-version;
      }
    }
  }

  grouping live_ncs_igmp-snooping-state {
    description
      "IGMP membership snooping state.";
    leaf group {
      type inet:ipv4-address;
      description
        "Multicast address.";
    }
    leaf source {
      type inet:ipv4-address;
      description
        "Source address of multicast.";
    }
    leaf reporter {
      type inet:ipv4-address;
      description
        "Address of the last reporter.";
    }
  }

  grouping live_ncs_igmp-snooping-structural {
    description
      "IGMP membership information determined through snooping.";
    container membership-groups {
      description
        "List of IGMP Membership information.";
      list group {
        key "group";
        description
          "Multicast group membership.";
        leaf group {
          type leafref {
            path "../state/group";
          }
          description
            "Multicast address.";
        }
        container state {
          description
            "Multicast group membership.";
          uses live_ncs_igmp-snooping-state;
        }
      }
    }
  }

  grouping live_ncs_igmp-interface-state {
    description
      "IGMP interface state.";
    leaf query-expires {
      type oc-types:live_ncs_timeticks64;
      description
        "This timestamp indicates the time that the next query is sent
         expressed relative to the Unix Epoch (Jan 1, 1970 00:00:00 UTC).";
    }
  }

  grouping live_ncs_igmp-interface-top {
    description
      "Configuration and state data for IGMP on each interface.";
    container interfaces {
      description
        "The interfaces on which IGMP is configured.";
      list interface {
        key "interface-id";
        description
          "This container defines interface IGMP configuration and
           state information.";
        leaf interface-id {
          type leafref {
            path "../config/interface-id";
          }
          description
            "Reference to an interface on which IGMP is enabled.";
        }
        container config {
          description
            "IGMP interface configuration.";
          uses live_ncs_igmp-interface-config;
        }
        container state {
          description
            "This container defines state information for IGMP
             interfaces.";
          uses live_ncs_igmp-interface-state;
          uses live_ncs_igmp-interface-config;
        }
        uses live_ncs_igmp-interface-counters;
        uses live_ncs_igmp-snooping-structural;
        uses oc-if:live_ncs_interface-ref;
      }
    }
  }

  grouping live_ncs_igmp-ssm-maps-config {
    description
      "A Source Specific Multicast (SSM) mapping. This allows
       IGMP v2 hosts to be able to join in SSM environments
       by translating IGMP v2 reports into IGMP v3 reports.
       The request in an IGMP v2 join is sent toward the source
       address found by matching the multicast address.";
    leaf source {
      type inet:ipv4-address;
      description
        "Multicast source address.";
    }
    leaf ssm-ranges {
      type leafref {
        path "/ncs:devices/ncs:device/ncs:live-status/oc-acl:acl/oc-acl:acl-sets/oc-acl:acl-set/oc-acl:config/oc-acl:name" {
          tailf:xpath-root 3;
        }
      }
      description
        "List of accepted source specific multicast (SSM) address
         ranges.";
    }
  }

  grouping live_ncs_igmp-global-config {
    description
      "This grouping defines global config options for IGMP.";
  }

  grouping live_ncs_igmp-global-top {
    description
      "Top level grouping for global IGMP configuration.";
    container ssm {
      description
        "Source specific multicast (SSM).";
      container mappings {
        description
          "A list of source specific multicast (SSM) mappings.";
        list mapping {
          key "source";
          description
            "A Source Specific Multicast (SSM) mapping. This allows
             IGMP v2 hosts to be able to join in SSM environments
             by translating IGMP v2 reports into IGMP v3 reports.
             The request in an IGMP v2 join is sent toward the source
             address found by matching the multicast address.";
          leaf source {
            type leafref {
              path "../config/source";
            }
            description
              "Multicast source address.";
          }
          container config {
            description
              "Configuration for SSM maps.";
            uses live_ncs_igmp-ssm-maps-config;
          }
          container state {
            description
              "State for SSM maps.";
            uses live_ncs_igmp-ssm-maps-config;
          }
        }
      }
    }
  }

  grouping live_ncs_igmp-top {
    description
      "Top-level grouping for IGMP.";
    container igmp {
      description
        "Top-level IGMP configuration and operational state.";
      container global {
        description
          "Global IGMP configuration and operational state.";
        uses live_ncs_igmp-global-top;
      }
      uses live_ncs_igmp-interface-top;
    }
  }

  grouping admin-config {
    description
      "Re-usable grouping to enable or disable a particular feature.";
    leaf enabled {
      type boolean;
      default "false";
      description
        "When set to true, the functionality within which this
         leaf is defined is enabled, when set to false it is
         explicitly disabled.";
    }
  }

  grouping igmp-interface-config {
    description
      "Configuration data for IGMP on each interface.";
    leaf interface-id {
      type oc-if:interface-id;
      description
        "Reference to an interface on which IGMP is enabled.";
    }
    uses admin-config;
    leaf version {
      type oc-igmp-types:igmp-version;
      description
        "IGMP Version.";
    }
    leaf query-interval {
      type oc-igmp-types:igmp-interval-type;
      description
        "Interval at which the router sends the IGMP membership
         queries.";
    }
    leaf filter-prefixes {
      type string;
      description
        "List used to filter joins.";
    }
  }

  grouping igmp-counters-per-version {
    description
      "Counters for each IGMP protocol version.";
    // NCS drop config false container state
  }

  grouping igmp-interface-counters {
    description
      "State and session data for IGMP on each interface.";
    container counters {
      description
        "Counters avaiable on a per interface bases for IGMP.";
      container queries {
        description
          "IGMP membership queries.";
        container sent {
          description
            "Number of IGMP membership queries sent.";
          uses igmp-counters-per-version;
        }
        container received {
          description
            "Number of IGMP membership queries received.";
          uses igmp-counters-per-version;
        }
      }
      container reports {
        description
          "Number of IGMP membership reports received.";
        uses igmp-counters-per-version;
      }
    }
  }

  grouping igmp-snooping-state {
    description
      "IGMP membership snooping state.";
    leaf group {
      type inet:ipv4-address;
      description
        "Multicast address.";
    }
    leaf source {
      type inet:ipv4-address;
      description
        "Source address of multicast.";
    }
    leaf reporter {
      type inet:ipv4-address;
      description
        "Address of the last reporter.";
    }
  }

  grouping igmp-snooping-structural {
    description
      "IGMP membership information determined through snooping.";
    container membership-groups {
      description
        "List of IGMP Membership information.";
      // NCS drop config false list group
    }
  }

  grouping igmp-interface-state {
    description
      "IGMP interface state.";
    leaf query-expires {
      type oc-types:timeticks64;
      description
        "This timestamp indicates the time that the next query is sent
         expressed relative to the Unix Epoch (Jan 1, 1970 00:00:00 UTC).";
    }
  }

  grouping igmp-interface-top {
    description
      "Configuration and state data for IGMP on each interface.";
    container interfaces {
      description
        "The interfaces on which IGMP is configured.";
      list interface {
        key "interface-id";
        description
          "This container defines interface IGMP configuration and
           state information.";
        leaf interface-id {
          type leafref {
            path "../config/interface-id";
          }
          description
            "Reference to an interface on which IGMP is enabled.";
        }
        container config {
          description
            "IGMP interface configuration.";
          uses igmp-interface-config;
        }
        // NCS drop config false container state
        uses igmp-interface-counters;
        uses igmp-snooping-structural;
        uses oc-if:interface-ref;
      }
    }
  }

  grouping igmp-ssm-maps-config {
    description
      "A Source Specific Multicast (SSM) mapping. This allows
       IGMP v2 hosts to be able to join in SSM environments
       by translating IGMP v2 reports into IGMP v3 reports.
       The request in an IGMP v2 join is sent toward the source
       address found by matching the multicast address.";
    leaf source {
      type inet:ipv4-address;
      description
        "Multicast source address.";
    }
    leaf ssm-ranges {
      type leafref {
        path "/ncs:devices/ncs:device/ncs:config/oc-acl:acl/oc-acl:acl-sets/oc-acl:acl-set/oc-acl:config/oc-acl:name" {
          tailf:xpath-root 3;
        }
      }
      description
        "List of accepted source specific multicast (SSM) address
         ranges.";
    }
  }

  grouping igmp-global-config {
    description
      "This grouping defines global config options for IGMP.";
  }

  grouping igmp-global-top {
    description
      "Top level grouping for global IGMP configuration.";
    container ssm {
      description
        "Source specific multicast (SSM).";
      container mappings {
        description
          "A list of source specific multicast (SSM) mappings.";
        list mapping {
          key "source";
          description
            "A Source Specific Multicast (SSM) mapping. This allows
             IGMP v2 hosts to be able to join in SSM environments
             by translating IGMP v2 reports into IGMP v3 reports.
             The request in an IGMP v2 join is sent toward the source
             address found by matching the multicast address.";
          leaf source {
            type leafref {
              path "../config/source";
            }
            description
              "Multicast source address.";
          }
          container config {
            description
              "Configuration for SSM maps.";
            uses igmp-ssm-maps-config;
          }
          // NCS drop config false container state
        }
      }
    }
  }

  grouping igmp-top {
    description
      "Top-level grouping for IGMP.";
    container igmp {
      description
        "Top-level IGMP configuration and operational state.";
      container global {
        description
          "Global IGMP configuration and operational state.";
        uses igmp-global-top;
      }
      uses igmp-interface-top;
    }
  }
}
