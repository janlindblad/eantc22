submodule huawei-diagnostic-tools-tcp {
  // Generated by yanger -t ncs
  tailf:mount-id "huawei-nc-1.0:huawei-nc-1.0";

  yang-version 1;
  belongs-to huawei-diagnostic-tools {
    prefix diagnostic-tools;
  }

  import huawei-pub-type {
    prefix pub-type;
  }
  import ietf-inet-types {
    prefix inet;
  }
  import huawei-network-instance {
    prefix ni;
  }
  import huawei-extension {
    prefix ext;
  }
  include huawei-diagnostic-tools-common;
  include huawei-diagnostic-tools-type;
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "TCP diagnosis tool.";

  revision 2019-04-13 {
    description
      "Initial revision.";
    reference "Huawei private.";
  }

  grouping ncs_template_tcp-test-result-type {
    description
      "TCP test results.";
    // NCS drop config false container 'ping-results'
  }

  grouping ncs_rpc_notif_tcp-test-result-type {
    description
      "TCP test results.";
    container ping-results {
      config false;
      description
        "List of TCP ping results.";
      list ping-result {
        key "test-name";
        config false;
        description
          "Statistics of TCP ping result.";
        leaf test-name {
          type string {
            length "1..32";
          }
          config false;
          description
            "Test name.";
        }
        leaf packet-send {
          type uint32;
          units "packet";
          config false;
          description
            "Total number of sent packets.";
        }
        leaf packet-receive {
          type uint32;
          units "packet";
          config false;
          description
            "Total number of received packets.";
        }
        leaf loss-ratio {
          type pub-type:ncs_rpc_notif_percent;
          units "%";
          config false;
          description
            "Packet loss ratio of a test.";
        }
        leaf rtt-min {
          type uint32;
          units "ms";
          config false;
          description
            "Minimum RTT of all test packets.";
        }
        leaf rtt-max {
          type uint32;
          units "ms";
          config false;
          description
            "Maximum RTT of all test packets.";
        }
        leaf rtt-average {
          type uint32;
          units "ms";
          config false;
          description
            "Average RTT of all test packets.";
        }
        leaf status {
          type ncs_rpc_notif_dgntl-test-status-type;
          config false;
          description
            "Test status.";
        }
        container probes {
          config false;
          description
            "List of ping results of all packets in a test.";
          list probe {
            key "sequence";
            config false;
            description
              "Statistics of ping result of a single packet in a test.";
            leaf sequence {
              type uint32;
              config false;
              description
                "Serial number of a test packet received.";
            }
            leaf replier {
              type inet:ipv4-address-no-zone;
              config false;
              description
                "Destination address of the related hop in a test.";
            }
            leaf rtt {
              type uint32;
              units "ms";
              config false;
              description
                "RTT of test packets.";
            }
            leaf result-type {
              type ncs_rpc_notif_probe-result-type;
              config false;
              description
                "Result of packet sending.";
            }
            leaf is-delete {
              type boolean;
              config false;
              description
                "Enable/disable the function of deleting test results.";
            }
          }
        }
      }
    }
  }

  grouping live_ncs_tcp-test-result-type {
    description
      "TCP test results.";
    container ping-results {
      description
        "List of TCP ping results.";
      list ping-result {
        key "test-name";
        description
          "Statistics of TCP ping result.";
        leaf test-name {
          type string {
            length "1..32";
          }
          description
            "Test name.";
        }
        leaf packet-send {
          type uint32;
          units "packet";
          description
            "Total number of sent packets.";
        }
        leaf packet-receive {
          type uint32;
          units "packet";
          description
            "Total number of received packets.";
        }
        leaf loss-ratio {
          type pub-type:live_ncs_percent;
          units "%";
          description
            "Packet loss ratio of a test.";
        }
        leaf rtt-min {
          type uint32;
          units "ms";
          description
            "Minimum RTT of all test packets.";
        }
        leaf rtt-max {
          type uint32;
          units "ms";
          description
            "Maximum RTT of all test packets.";
        }
        leaf rtt-average {
          type uint32;
          units "ms";
          description
            "Average RTT of all test packets.";
        }
        leaf status {
          type live_ncs_dgntl-test-status-type;
          description
            "Test status.";
        }
        container probes {
          description
            "List of ping results of all packets in a test.";
          list probe {
            key "sequence";
            description
              "Statistics of ping result of a single packet in a test.";
            leaf sequence {
              type uint32;
              description
                "Serial number of a test packet received.";
            }
            leaf replier {
              type inet:ipv4-address-no-zone;
              description
                "Destination address of the related hop in a test.";
            }
            leaf rtt {
              type uint32;
              units "ms";
              description
                "RTT of test packets.";
            }
            leaf result-type {
              type live_ncs_probe-result-type;
              description
                "Result of packet sending.";
            }
            leaf is-delete {
              type boolean;
              description
                "Enable/disable the function of deleting test results.";
            }
          }
        }
      }
    }
  }

  grouping tcp-test-result-type {
    description
      "TCP test results.";
    // NCS drop config false container 'ping-results'
  }

  augment "/ncs:devices/ncs:device/ncs:rpc" {
    container rpc-tcp-delete-ping {
      tailf:ncs-device-type "netconf";
      tailf:display-when "not(../../ncs:module) or ../../ncs:module[ncs:name='huawei-diagnostic-tools']";
      tailf:action tcp-delete-ping {
        tailf:actionpoint ncsproxy {
          tailf:internal;
        }
        description
          "Delete TCP ping.";
        ext:node-ref "/diagnostic-tools:diagnostic-tools/diagnostic-tools:tcp/diagnostic-tools:ping-results/diagnostic-tools:ping-result";
        input {
          leaf test-name {
            type string;
            mandatory true;
            description
              "Test name.";
          }
        }
      }
    }
  }
  augment "/ncs:devices/ncs:device-group/ncs:ned-id/ncs:rpc" {
    container rpc-tcp-delete-ping {
      tailf:ncs-device-type "netconf";
      tailf:display-when "/ncs:devices/ncs:device[ncs:name=current()/../../../ncs:member]/ncs:module[ncs:name='huawei-diagnostic-tools']";
      tailf:action tcp-delete-ping {
        tailf:actionpoint ncsproxy {
          tailf:internal;
        }
        description
          "Delete TCP ping.";
        ext:node-ref "/diagnostic-tools:diagnostic-tools/diagnostic-tools:tcp/diagnostic-tools:ping-results/diagnostic-tools:ping-result";
        input {
          leaf test-name {
            type string;
            mandatory true;
            description
              "Test name.";
          }
        }
      }
    }
  }
  augment "/ncs:devices/ncs:device/ncs:rpc" {
    container rpc-tcp-stop-ping {
      tailf:ncs-device-type "netconf";
      tailf:display-when "not(../../ncs:module) or ../../ncs:module[ncs:name='huawei-diagnostic-tools']";
      tailf:action tcp-stop-ping {
        tailf:actionpoint ncsproxy {
          tailf:internal;
        }
        description
          "Stop TCP ping.";
        ext:node-ref "/diagnostic-tools:diagnostic-tools/diagnostic-tools:tcp/diagnostic-tools:ping-results/diagnostic-tools:ping-result";
        input {
          leaf test-name {
            type string;
            mandatory true;
            description
              "Test name.";
          }
        }
      }
    }
  }
  augment "/ncs:devices/ncs:device-group/ncs:ned-id/ncs:rpc" {
    container rpc-tcp-stop-ping {
      tailf:ncs-device-type "netconf";
      tailf:display-when "/ncs:devices/ncs:device[ncs:name=current()/../../../ncs:member]/ncs:module[ncs:name='huawei-diagnostic-tools']";
      tailf:action tcp-stop-ping {
        tailf:actionpoint ncsproxy {
          tailf:internal;
        }
        description
          "Stop TCP ping.";
        ext:node-ref "/diagnostic-tools:diagnostic-tools/diagnostic-tools:tcp/diagnostic-tools:ping-results/diagnostic-tools:ping-result";
        input {
          leaf test-name {
            type string;
            mandatory true;
            description
              "Test name.";
          }
        }
      }
    }
  }
  augment "/ncs:devices/ncs:device/ncs:rpc" {
    container rpc-tcp-start-ping {
      tailf:ncs-device-type "netconf";
      tailf:display-when "not(../../ncs:module) or ../../ncs:module[ncs:name='huawei-diagnostic-tools']";
      tailf:action tcp-start-ping {
        tailf:actionpoint ncsproxy {
          tailf:internal;
        }
        description
          "Start TCP ping.";
        input {
          leaf test-name {
            type string {
              length "1..32";
            }
            mandatory true;
            description
              "Test name.";
          }
          leaf destination {
            type pub-type:ncs_rpc_notif_host-name;
            mandatory true;
            description
              "Destination address of the string type.";
          }
          leaf timeout {
            type uint32 {
              range "0..65535";
            }
            units "ms";
            default "2000";
            description
              "Time to wait for a response packet after a test packet is sent.";
          }
          leaf count {
            type uint32 {
              range "1..4294967295";
            }
            units "packet";
            default "5";
            description
              "Number of sent test packets.";
          }
          leaf interval {
            type uint32 {
              range "1..10000";
            }
            units "ms";
            default "500";
            description
              "Interval for sending test packets.";
          }
          leaf ttl {
            type uint32 {
              range "1..255";
            }
            default "30";
            description
              "Time to live.";
          }
          leaf pass-route {
            type boolean;
            default "false";
            description
              "Send packet pass route.";
          }
          leaf ni-name {
            type string;
            description
              "Name of a VPN instance.";
          }
          leaf dest-port {
            type uint32 {
              range "1..65535";
            }
            default "7";
            description
              "Destination TCP port.";
          }
          leaf source-address {
            type inet:ipv4-address-no-zone;
            description
              "Source address.";
          }
        }
      }
    }
  }
  augment "/ncs:devices/ncs:device-group/ncs:ned-id/ncs:rpc" {
    container rpc-tcp-start-ping {
      tailf:ncs-device-type "netconf";
      tailf:display-when "/ncs:devices/ncs:device[ncs:name=current()/../../../ncs:member]/ncs:module[ncs:name='huawei-diagnostic-tools']";
      tailf:action tcp-start-ping {
        tailf:actionpoint ncsproxy {
          tailf:internal;
        }
        description
          "Start TCP ping.";
        input {
          leaf test-name {
            type string {
              length "1..32";
            }
            mandatory true;
            description
              "Test name.";
          }
          leaf destination {
            type pub-type:ncs_rpc_notif_host-name;
            mandatory true;
            description
              "Destination address of the string type.";
          }
          leaf timeout {
            type uint32 {
              range "0..65535";
            }
            units "ms";
            default "2000";
            description
              "Time to wait for a response packet after a test packet is sent.";
          }
          leaf count {
            type uint32 {
              range "1..4294967295";
            }
            units "packet";
            default "5";
            description
              "Number of sent test packets.";
          }
          leaf interval {
            type uint32 {
              range "1..10000";
            }
            units "ms";
            default "500";
            description
              "Interval for sending test packets.";
          }
          leaf ttl {
            type uint32 {
              range "1..255";
            }
            default "30";
            description
              "Time to live.";
          }
          leaf pass-route {
            type boolean;
            default "false";
            description
              "Send packet pass route.";
          }
          leaf ni-name {
            type string;
            description
              "Name of a VPN instance.";
          }
          leaf dest-port {
            type uint32 {
              range "1..65535";
            }
            default "7";
            description
              "Destination TCP port.";
          }
          leaf source-address {
            type inet:ipv4-address-no-zone;
            description
              "Source address.";
          }
        }
      }
    }
  }
  augment "/ncs:devices/ncs:device/ncs:live-status/diagnostic-tools:diagnostic-tools" {
    description
      "List of TCP tests.";
    container tcp {
      tailf:ncs-device-type "netconf";
      tailf:display-when "not(../../../ncs:module) or ../../../ncs:module[ncs:name='huawei-diagnostic-tools'] or (../../../ncs:live-status-protocol[not(ncs:capability)]) or (../../../ncs:live-status-protocol/ncs:capability/ncs:module[.='huawei-diagnostic-tools'])";
      description
        "Statistics of TCP tests.";
      uses live_ncs_tcp-test-result-type;
    }
  }
}
