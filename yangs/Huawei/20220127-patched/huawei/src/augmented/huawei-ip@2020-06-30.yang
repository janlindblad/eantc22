module huawei-ip {
  // Generated by yanger -t ncs
  tailf:mount-id "huawei-nc-1.0:huawei-nc-1.0";
  tailf:ncs-device-type "netconf";

  namespace "urn:huawei:yang:huawei-ip";
  prefix ip;

  import ietf-inet-types {
    prefix inet;
  }
  import huawei-ifm {
    prefix ifm;
  }
  import huawei-extension {
    prefix ext;
  }
  import huawei-network-instance {
    prefix ni;
  }
  import huawei-l3vpn {
    prefix l3vpn;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "This module contains a collection of YANG definitions for
     configuring IP implementations.
     Copyright (C) 2019 Huawei Technologies Co., Ltd. All rights reserved.";

  revision 2020-06-30 {
    description
      "Add units attribute.";
    reference "Huawei private.";
  }
  revision 2020-02-14 {
    description
      "Modify the description of nodes.";
    reference "Huawei private.";
  }
  revision 2019-11-10 {
    description
      "Modify the must statements of IPv4 and IPv6 containers.";
    reference "Huawei private.";
  }
  revision 2019-04-15 {
    description
      "Initial revision.";
    reference "Huawei private.";
  }
  ext:task-name "interface-mgr";

  typedef ncs_template_ipv4-address-config-type {
    type string;
    description
      "IPv4 address type.";
  }

  typedef ncs_template_ipv4-address-state-type {
    type string;
    description
      "IPv4 address type.";
  }

  typedef ncs_template_ipv4-netmask {
    type string;
    description
      "IPv4 mask support mask format.";
  }

  typedef ncs_template_negotiation-type {
    type string;
    description
      "Negotiation address type.";
  }

  typedef ncs_template_ipv6-address-config-type {
    type string;
    description
      "IPv6 address type.";
  }

  typedef ncs_template_ipv6-address-state-type {
    type string;
    description
      "IPv6 address type.";
  }

  typedef ncs_template_ipv6-address-algorithm-type {
    type string;
    description
      "IPv6 address algorithm type.";
  }

  typedef ncs_template_ipv6-status-type {
    type string;
    description
      "The status of an address.";
  }

  typedef ncs_rpc_notif_ipv4-address-config-type {
    type enumeration {
      enum "main" {
        value 1;
        description
          "Primary address of an interface.";
      }
      enum "sub" {
        value 32;
        description
          "Secondary address of an interface.";
      }
    }
    description
      "IPv4 address type.";
  }

  typedef ncs_rpc_notif_ipv4-address-state-type {
    type enumeration {
      enum "main" {
        value 1;
        description
          "Primary address of an interface.";
      }
      enum "sub" {
        value 32;
        description
          "Secondary address of an interface.";
      }
      enum "neg" {
        value 4;
        description
          "Negotiated address of an interface.";
      }
      enum "unnumber" {
        value 2;
        description
          "Unnumbered address of an interface.";
      }
      enum "dhcp" {
        value 256;
        description
          "Unnumbered address of an interface.";
      }
    }
    description
      "IPv4 address type.";
  }

  typedef ncs_rpc_notif_ipv4-netmask {
    type string {
      length "9..15";
      pattern '((([1-9]?[0-9]|1[0-9][0-9]|2[0-4][0-9]|25[0-5])\.){3}([1-9]?[0-9]|1[0-9][0-9]|2[0-4][0-9]|25[0-5]))';
    }
    description
      "IPv4 mask support mask format.";
  }

  typedef ncs_rpc_notif_negotiation-type {
    type enumeration {
      enum "ppp-negotiate" {
        value 0;
        description
          "PPP negotiation type.";
      }
    }
    description
      "Negotiation address type.";
  }

  typedef ncs_rpc_notif_ipv6-address-config-type {
    type enumeration {
      enum "global" {
        value 1;
        description
          "Global unicast address.";
      }
      enum "link-local" {
        value 2;
        description
          "Link local address.";
      }
      enum "anycast" {
        value 6;
        description
          "Anycast address.";
      }
    }
    description
      "IPv6 address type.";
  }

  typedef ncs_rpc_notif_ipv6-address-state-type {
    type enumeration {
      enum "global" {
        value 1;
        description
          "Global unicast address.";
      }
      enum "link-local" {
        value 2;
        description
          "Link local address.";
      }
      enum "auto-link-local" {
        value 3;
        description
          "Auto link local address.";
      }
      enum "anycast" {
        value 6;
        description
          "Anycast address.";
      }
    }
    description
      "IPv6 address type.";
  }

  typedef ncs_rpc_notif_ipv6-address-algorithm-type {
    type enumeration {
      enum "none" {
        value 0;
        description
          "None.";
      }
      enum "cga" {
        value 1;
        description
          "Cga type.";
      }
      enum "eui64" {
        value 2;
        description
          "EUI-64 type.";
      }
    }
    description
      "IPv6 address algorithm type.";
  }

  typedef ncs_rpc_notif_ipv6-status-type {
    type enumeration {
      enum "preferred" {
        value 1;
        description
          "This is a valid address that can appear as the destination or source address of a packet.";
      }
      enum "inaccessible" {
        value 4;
        description
          "The address is not accessible because the interface to which this address is assigned is not operational.";
      }
      enum "unknown" {
        value 5;
        description
          "The status cannot be determined for some reason.";
      }
      enum "tentative" {
        value 6;
        description
          "The uniqueness of the address on the link is being verified. Addresses in this state should not be used for general communication and should only be used to determine the uniqueness of the address.";
      }
      enum "duplicate" {
        value 7;
        description
          "The address has been determined to be non-unique on the link and so must not be used.";
      }
    }
    description
      "The status of an address.";
  }

  typedef live_ncs_ipv4-address-config-type {
    type enumeration {
      enum "main" {
        value 1;
        description
          "Primary address of an interface.";
      }
      enum "sub" {
        value 32;
        description
          "Secondary address of an interface.";
      }
    }
    description
      "IPv4 address type.";
  }

  typedef live_ncs_ipv4-address-state-type {
    type enumeration {
      enum "main" {
        value 1;
        description
          "Primary address of an interface.";
      }
      enum "sub" {
        value 32;
        description
          "Secondary address of an interface.";
      }
      enum "neg" {
        value 4;
        description
          "Negotiated address of an interface.";
      }
      enum "unnumber" {
        value 2;
        description
          "Unnumbered address of an interface.";
      }
      enum "dhcp" {
        value 256;
        description
          "Unnumbered address of an interface.";
      }
    }
    description
      "IPv4 address type.";
  }

  typedef live_ncs_ipv4-netmask {
    type string {
      length "9..15";
      pattern '((([1-9]?[0-9]|1[0-9][0-9]|2[0-4][0-9]|25[0-5])\.){3}([1-9]?[0-9]|1[0-9][0-9]|2[0-4][0-9]|25[0-5]))';
    }
    description
      "IPv4 mask support mask format.";
  }

  typedef live_ncs_negotiation-type {
    type enumeration {
      enum "ppp-negotiate" {
        value 0;
        description
          "PPP negotiation type.";
      }
    }
    description
      "Negotiation address type.";
  }

  typedef live_ncs_ipv6-address-config-type {
    type enumeration {
      enum "global" {
        value 1;
        description
          "Global unicast address.";
      }
      enum "link-local" {
        value 2;
        description
          "Link local address.";
      }
      enum "anycast" {
        value 6;
        description
          "Anycast address.";
      }
    }
    description
      "IPv6 address type.";
  }

  typedef live_ncs_ipv6-address-state-type {
    type enumeration {
      enum "global" {
        value 1;
        description
          "Global unicast address.";
      }
      enum "link-local" {
        value 2;
        description
          "Link local address.";
      }
      enum "auto-link-local" {
        value 3;
        description
          "Auto link local address.";
      }
      enum "anycast" {
        value 6;
        description
          "Anycast address.";
      }
    }
    description
      "IPv6 address type.";
  }

  typedef live_ncs_ipv6-address-algorithm-type {
    type enumeration {
      enum "none" {
        value 0;
        description
          "None.";
      }
      enum "cga" {
        value 1;
        description
          "Cga type.";
      }
      enum "eui64" {
        value 2;
        description
          "EUI-64 type.";
      }
    }
    description
      "IPv6 address algorithm type.";
  }

  typedef live_ncs_ipv6-status-type {
    type enumeration {
      enum "preferred" {
        value 1;
        description
          "This is a valid address that can appear as the destination or source address of a packet.";
      }
      enum "inaccessible" {
        value 4;
        description
          "The address is not accessible because the interface to which this address is assigned is not operational.";
      }
      enum "unknown" {
        value 5;
        description
          "The status cannot be determined for some reason.";
      }
      enum "tentative" {
        value 6;
        description
          "The uniqueness of the address on the link is being verified. Addresses in this state should not be used for general communication and should only be used to determine the uniqueness of the address.";
      }
      enum "duplicate" {
        value 7;
        description
          "The address has been determined to be non-unique on the link and so must not be used.";
      }
    }
    description
      "The status of an address.";
  }

  typedef ipv4-address-config-type {
    type enumeration {
      enum "main" {
        value 1;
        description
          "Primary address of an interface.";
      }
      enum "sub" {
        value 32;
        description
          "Secondary address of an interface.";
      }
    }
    description
      "IPv4 address type.";
  }

  typedef ipv4-address-state-type {
    type enumeration {
      enum "main" {
        value 1;
        description
          "Primary address of an interface.";
      }
      enum "sub" {
        value 32;
        description
          "Secondary address of an interface.";
      }
      enum "neg" {
        value 4;
        description
          "Negotiated address of an interface.";
      }
      enum "unnumber" {
        value 2;
        description
          "Unnumbered address of an interface.";
      }
      enum "dhcp" {
        value 256;
        description
          "Unnumbered address of an interface.";
      }
    }
    description
      "IPv4 address type.";
  }

  typedef ipv4-netmask {
    type string {
      length "9..15";
      pattern '((([1-9]?[0-9]|1[0-9][0-9]|2[0-4][0-9]|25[0-5])\.){3}([1-9]?[0-9]|1[0-9][0-9]|2[0-4][0-9]|25[0-5]))';
    }
    description
      "IPv4 mask support mask format.";
  }

  typedef negotiation-type {
    type enumeration {
      enum "ppp-negotiate" {
        value 0;
        description
          "PPP negotiation type.";
      }
    }
    description
      "Negotiation address type.";
  }

  typedef ipv6-address-config-type {
    type enumeration {
      enum "global" {
        value 1;
        description
          "Global unicast address.";
      }
      enum "link-local" {
        value 2;
        description
          "Link local address.";
      }
      enum "anycast" {
        value 6;
        description
          "Anycast address.";
      }
    }
    description
      "IPv6 address type.";
  }

  typedef ipv6-address-state-type {
    type enumeration {
      enum "global" {
        value 1;
        description
          "Global unicast address.";
      }
      enum "link-local" {
        value 2;
        description
          "Link local address.";
      }
      enum "auto-link-local" {
        value 3;
        description
          "Auto link local address.";
      }
      enum "anycast" {
        value 6;
        description
          "Anycast address.";
      }
    }
    description
      "IPv6 address type.";
  }

  typedef ipv6-address-algorithm-type {
    type enumeration {
      enum "none" {
        value 0;
        description
          "None.";
      }
      enum "cga" {
        value 1;
        description
          "Cga type.";
      }
      enum "eui64" {
        value 2;
        description
          "EUI-64 type.";
      }
    }
    description
      "IPv6 address algorithm type.";
  }

  typedef ipv6-status-type {
    type enumeration {
      enum "preferred" {
        value 1;
        description
          "This is a valid address that can appear as the destination or source address of a packet.";
      }
      enum "inaccessible" {
        value 4;
        description
          "The address is not accessible because the interface to which this address is assigned is not operational.";
      }
      enum "unknown" {
        value 5;
        description
          "The status cannot be determined for some reason.";
      }
      enum "tentative" {
        value 6;
        description
          "The uniqueness of the address on the link is being verified. Addresses in this state should not be used for general communication and should only be used to determine the uniqueness of the address.";
      }
      enum "duplicate" {
        value 7;
        description
          "The address has been determined to be non-unique on the link and so must not be used.";
      }
    }
    description
      "The status of an address.";
  }

  augment "/ncs:devices/ncs:template/ncs:ned-id/ncs:config/ifm:ifm/ifm:interfaces/ifm:interface" {
    description
      "Policies for selecting source and destination IPv6 addresses and parameters for configuring IP on interfaces.";
    container ipv4 {
      // NCS drop must statement
      description
        "Configure IPv4 addresses.";
      choice address {
        description
          "The IPv4 address can be specified as negotiated or unnumbered or ordinarily address.";
        case common-address {
          description
            "Configure address.";
          container addresses {
            // NCS drop must statement
            description
              "List of common addresses. The IPv4 address of the DCN interface cannot be created, modified, or deleted.";
            list address {
              // NCS patched for predictable order
              ordered-by user;
              key "ip";
              description
                "Configure IPv4 address.";
              leaf ip {
                type string;
                description
                  "IPv4 address.";
              }
              leaf mask {
                type ncs_template_ipv4-netmask;
                // NCS drop mandatory statement
                description
                  "IPv4 address mask.";
              }
              leaf type {
                type ncs_template_ipv4-address-config-type;
                // NCS drop mandatory statement
                description
                  "IPv4 address type.";
              }
            }
          }
        }
        case unnumbered-address {
          description
            "Unnumbered address.";
          container unnumbered-address {
            description
              "Configure unnumbered interface. The address borrowing relationship of the DCN interface cannot be created, modified, or deleted.";
            leaf unnumbered-if-name {
              type string;
              // NCS drop must statement
              // NCS drop mandatory statement
              description
                "Name of an unnumbered interface.";
            }
          }
        }
        case negotiate-address {
          description
            "Negotiate address.";
          container negotiation-address {
            description
              "Configure negotiate address.";
            leaf negotiation-type {
              type ncs_template_negotiation-type;
              // NCS drop mandatory statement
              description
                "Enable negotiation address on interface.";
            }
          }
        }
      }
      // NCS drop config false container state
    }
    container ipv6 {
      presence "Enable/disable the IPv6 capability on an interface.";
      description
        "Enable/disable the IPv6 capability on an interface.";
      leaf mtu6 {
        type string;
        units "Byte";
        ext:dynamic-default;
        description
          "IPv6 maximum transmission unit of an interface.
           Special explanation:
           Range: The server may restrict the allowed values for this leaf, depending on the interface's type.";
      }
      leaf spread-mtu-flag {
        type string;
        // NCS drop default statement
        description
          "Enable/disable the function of spreading the IPv6 MTU of main interface to subinterface.";
      }
      leaf auto-link-local {
        type string;
        // NCS drop must statement
        // NCS drop default statement
        description
          "Enable/disable an interface with the auto linklocal address function.";
      }
      choice address {
        description
          "IPv6 address configurations.";
        case common-address {
          description
            "Configure address.";
          container addresses {
            // NCS drop must statement
            description
              "List of IPv6 addresses.";
            list address {
              // NCS patched for predictable order
              ordered-by user;
              key "ip";
              description
                "Configure IPv6 address.";
              leaf ip {
                type string;
                description
                  "IPv6 address.";
              }
              leaf prefix-length {
                type string;
                // NCS drop mandatory statement
                description
                  "Length of the IPv6 address prefix.";
              }
              leaf type {
                type ncs_template_ipv6-address-config-type;
                // NCS drop mandatory statement
                description
                  "IPv6 address type.";
              }
              leaf algorithm-type {
                type ncs_template_ipv6-address-algorithm-type;
                // NCS drop must statement
                // NCS drop default statement
                description
                  "Address algorithm type.";
              }
            }
          }
        }
      }
      container nd-prefixs {
        // NCS drop must statement
        description
          "List of nd prefix.";
        list nd-prefix {
          // NCS patched for predictable order
          ordered-by user;
          key "prefix";
          description
            "Configure nd prefix.";
          leaf prefix {
            type string;
            description
              "IPv6 address of the prefix.";
          }
          leaf prefix-len {
            type string;
            // NCS drop mandatory statement
            description
              "Length of the prefix address.";
          }
          leaf valid-lifetime {
            type string;
            units "s";
            // NCS drop must statement
            // NCS drop mandatory statement
            description
              "Valid life time.";
          }
          leaf preferred-lifetime {
            type string;
            units "s";
            // NCS drop must statement
            // NCS drop mandatory statement
            description
              "Preferred life time.";
          }
          leaf auto-flag {
            type string;
            // NCS drop default statement
            description
              "Enable/disable the autonomous address-configuration.";
          }
          leaf on-link-flag {
            type string;
            // NCS drop default statement
            description
              "Enable/disable the on-link flag.";
          }
        }
      }
      // NCS drop config false container state
    }
  }
  augment "/ncs:devices/ncs:device/ncs:live-status/ifm:ifm/ifm:interfaces/ifm:interface" {
    description
      "Policies for selecting source and destination IPv6 addresses and parameters for configuring IP on interfaces.";
    container ipv4 {
      tailf:ncs-device-type "netconf";
      tailf:display-when "not(../../../../../ncs:module) or ../../../../../ncs:module[ncs:name='huawei-ip'] or (../../../../../ncs:live-status-protocol[not(ncs:capability)]) or (../../../../../ncs:live-status-protocol/ncs:capability/ncs:module[.='huawei-ip'])";
      // NCS drop must statement
      description
        "Configure IPv4 addresses.";
      choice address {
        description
          "The IPv4 address can be specified as negotiated or unnumbered or ordinarily address.";
        case common-address {
          description
            "Configure address.";
          container addresses {
            // NCS drop must statement
            description
              "List of common addresses. The IPv4 address of the DCN interface cannot be created, modified, or deleted.";
            list address {
              key "ip";
              description
                "Configure IPv4 address.";
              leaf ip {
                type inet:ipv4-address-no-zone;
                description
                  "IPv4 address.";
              }
              leaf mask {
                type live_ncs_ipv4-netmask;
                // NCS drop mandatory statement
                description
                  "IPv4 address mask.";
              }
              leaf type {
                type live_ncs_ipv4-address-config-type;
                // NCS drop mandatory statement
                description
                  "IPv4 address type.";
              }
            }
          }
        }
        case unnumbered-address {
          description
            "Unnumbered address.";
          container unnumbered-address {
            description
              "Configure unnumbered interface. The address borrowing relationship of the DCN interface cannot be created, modified, or deleted.";
            leaf unnumbered-if-name {
              type leafref {
                path "/ncs:devices/ncs:device/ncs:live-status/ifm:ifm/ifm:interfaces/ifm:interface/ifm:name" {
                  tailf:xpath-root 3;
                }
              }
              // NCS drop must statement
              // NCS drop mandatory statement
              description
                "Name of an unnumbered interface.";
            }
          }
        }
        case negotiate-address {
          description
            "Negotiate address.";
          container negotiation-address {
            description
              "Configure negotiate address.";
            leaf negotiation-type {
              type live_ncs_negotiation-type;
              // NCS drop mandatory statement
              description
                "Enable negotiation address on interface.";
            }
          }
        }
      }
      container state {
        description
          "Operational state of IPv4 addresses.";
        container addresses {
          description
            "List of addresses.";
          list address {
            key "ip";
            description
              "Operational state of IPv4 address.";
            leaf ip {
              type inet:ipv4-address-no-zone;
              description
                "IPv4 address.";
            }
            leaf mask {
              type live_ncs_ipv4-netmask;
              description
                "IPv4 address mask.";
            }
            leaf type {
              type live_ncs_ipv4-address-state-type;
              description
                "IPv4 address type.";
            }
            leaf is-block {
              type boolean;
              description
                "IPv4 address is blocked or not.";
            }
          }
        }
        container gateways {
          description
            "List of gateway addresses.";
          list gateway {
            key "gateway";
            description
              "Operational state of gateway addresses.";
            leaf gateway {
              type inet:ipv4-address;
              description
                "Gateway of interface.";
            }
          }
        }
      }
    }
    container ipv6 {
      tailf:ncs-device-type "netconf";
      tailf:display-when "not(../../../../../ncs:module) or ../../../../../ncs:module[ncs:name='huawei-ip'] or (../../../../../ncs:live-status-protocol[not(ncs:capability)]) or (../../../../../ncs:live-status-protocol/ncs:capability/ncs:module[.='huawei-ip'])";
      presence "Enable/disable the IPv6 capability on an interface.";
      description
        "Enable/disable the IPv6 capability on an interface.";
      leaf mtu6 {
        type uint32 {
          range "0..50000";
        }
        units "Byte";
        ext:dynamic-default;
        description
          "IPv6 maximum transmission unit of an interface.
           Special explanation:
           Range: The server may restrict the allowed values for this leaf, depending on the interface's type.";
      }
      leaf spread-mtu-flag {
        type boolean;
        // NCS drop default statement
        description
          "Enable/disable the function of spreading the IPv6 MTU of main interface to subinterface.";
      }
      leaf auto-link-local {
        type boolean;
        // NCS drop must statement
        // NCS drop default statement
        description
          "Enable/disable an interface with the auto linklocal address function.";
      }
      choice address {
        description
          "IPv6 address configurations.";
        case common-address {
          description
            "Configure address.";
          container addresses {
            // NCS drop must statement
            description
              "List of IPv6 addresses.";
            list address {
              key "ip";
              description
                "Configure IPv6 address.";
              leaf ip {
                type inet:ipv6-address-no-zone;
                description
                  "IPv6 address.";
              }
              leaf prefix-length {
                type uint32 {
                  range "1..128";
                }
                // NCS drop mandatory statement
                description
                  "Length of the IPv6 address prefix.";
              }
              leaf type {
                type live_ncs_ipv6-address-config-type;
                // NCS drop mandatory statement
                description
                  "IPv6 address type.";
              }
              leaf algorithm-type {
                type live_ncs_ipv6-address-algorithm-type;
                // NCS drop must statement
                // NCS drop default statement
                description
                  "Address algorithm type.";
              }
            }
          }
        }
      }
      container nd-prefixs {
        // NCS drop must statement
        description
          "List of nd prefix.";
        list nd-prefix {
          key "prefix";
          description
            "Configure nd prefix.";
          leaf prefix {
            type inet:ipv6-address-no-zone;
            description
              "IPv6 address of the prefix.";
          }
          leaf prefix-len {
            type int32 {
              range "0..128";
            }
            // NCS drop mandatory statement
            description
              "Length of the prefix address.";
          }
          leaf valid-lifetime {
            type uint32 {
              range "0..4294967295";
            }
            units "s";
            // NCS drop must statement
            // NCS drop mandatory statement
            description
              "Valid life time.";
          }
          leaf preferred-lifetime {
            type uint32 {
              range "0..4294967295";
            }
            units "s";
            // NCS drop must statement
            // NCS drop mandatory statement
            description
              "Preferred life time.";
          }
          leaf auto-flag {
            type boolean;
            // NCS drop default statement
            description
              "Enable/disable the autonomous address-configuration.";
          }
          leaf on-link-flag {
            type boolean;
            // NCS drop default statement
            description
              "Enable/disable the on-link flag.";
          }
        }
      }
      container state {
        description
          "Operational state of IPv6 addresses.";
        leaf mtu6 {
          type uint32 {
            range "0..50000";
          }
          units "Byte";
          description
            "IPv6 maximum transmission unit of an interface.
             Special explanation:
             Range: The server may restrict the allowed values for this leaf, depending on the interface's type.";
        }
        container addresses {
          description
            "List of IPv6 addresses.";
          list address {
            key "ip";
            description
              "Operational state of IPv6 addresses.";
            leaf ip {
              type inet:ipv6-address-no-zone;
              description
                "IPv6 address.";
            }
            leaf prefix-length {
              type uint32 {
                range "1..128";
              }
              description
                "Length of the IPv6 address prefix.";
            }
            leaf type {
              type live_ncs_ipv6-address-state-type;
              description
                "IPv6 address type.";
            }
            leaf algorithm-type {
              type live_ncs_ipv6-address-algorithm-type;
              description
                "Address algorithm type.";
            }
            leaf collision-count {
              type uint8 {
                range "0..3";
              }
              description
                "Number of IPv6 address collisions.";
            }
            leaf is-block {
              type boolean;
              description
                "IPv6 address is blocked or not.";
            }
            leaf status {
              type live_ncs_ipv6-status-type;
              description
                "IPv6 address status.";
            }
          }
        }
      }
    }
  }
  augment "/ncs:devices/ncs:device/ncs:config/ifm:ifm/ifm:interfaces/ifm:interface" {
    description
      "Policies for selecting source and destination IPv6 addresses and parameters for configuring IP on interfaces.";
    container ipv4 {
      tailf:ncs-device-type "netconf";
      tailf:display-when "not(../../../../../ncs:module) or ../../../../../ncs:module[ncs:name='huawei-ip']";
      must "/ni:network-instance/ni:instances/ni:instance[ni:name=current()/../ifm:vrf-name]/l3vpn:afs/l3vpn:af[l3vpn:type='ipv4-unicast']" {
        tailf:xpath-root 3;
      }
      description
        "Configure IPv4 addresses.";
      choice address {
        description
          "The IPv4 address can be specified as negotiated or unnumbered or ordinarily address.";
        case common-address {
          description
            "Configure address.";
          container addresses {
            must "count(address)=0 or count(address[type='main'])=1" {
              tailf:xpath-root 3;
            }
            description
              "List of common addresses. The IPv4 address of the DCN interface cannot be created, modified, or deleted.";
            list address {
              key "ip";
              description
                "Configure IPv4 address.";
              leaf ip {
                type inet:ipv4-address-no-zone;
                description
                  "IPv4 address.";
              }
              leaf mask {
                type ipv4-netmask;
                mandatory true;
                description
                  "IPv4 address mask.";
              }
              leaf type {
                type ipv4-address-config-type;
                mandatory true;
                description
                  "IPv4 address type.";
              }
            }
          }
        }
        case unnumbered-address {
          description
            "Unnumbered address.";
          container unnumbered-address {
            description
              "Configure unnumbered interface. The address borrowing relationship of the DCN interface cannot be created, modified, or deleted.";
            leaf unnumbered-if-name {
              type leafref {
                path "/ncs:devices/ncs:device/ncs:config/ifm:ifm/ifm:interfaces/ifm:interface/ifm:name" {
                  tailf:xpath-root 3;
                }
              }
              must '(../../../ifm:name!=../unnumbered-if-name) and (/ifm:ifm/ifm:interfaces/ifm:interface[ifm:name=current()]/ifm:vrf-name = ../../../ifm:vrf-name)' {
                tailf:xpath-root 3;
              }
              mandatory true;
              description
                "Name of an unnumbered interface.";
            }
          }
        }
        case negotiate-address {
          description
            "Negotiate address.";
          container negotiation-address {
            description
              "Configure negotiate address.";
            leaf negotiation-type {
              type negotiation-type;
              mandatory true;
              description
                "Enable negotiation address on interface.";
            }
          }
        }
      }
      // NCS drop config false container state
    }
    container ipv6 {
      tailf:ncs-device-type "netconf";
      tailf:display-when "not(../../../../../ncs:module) or ../../../../../ncs:module[ncs:name='huawei-ip']";
      presence "Enable/disable the IPv6 capability on an interface.";
      description
        "Enable/disable the IPv6 capability on an interface.";
      leaf mtu6 {
        type uint32 {
          range "0..50000";
        }
        units "Byte";
        ext:dynamic-default;
        description
          "IPv6 maximum transmission unit of an interface.
           Special explanation:
           Range: The server may restrict the allowed values for this leaf, depending on the interface's type.";
      }
      leaf spread-mtu-flag {
        type boolean;
        default "false";
        description
          "Enable/disable the function of spreading the IPv6 MTU of main interface to subinterface.";
      }
      leaf auto-link-local {
        type boolean;
        must "../auto-link-local='false' or (../auto-link-local='true' and /ni:network-instance/ni:instances/ni:instance[ni:name=current()/../../ifm:vrf-name]/l3vpn:afs/l3vpn:af[l3vpn:type='ipv6-unicast'])" {
          tailf:xpath-root 3;
        }
        default "false";
        description
          "Enable/disable an interface with the auto linklocal address function.";
      }
      choice address {
        description
          "IPv6 address configurations.";
        case common-address {
          description
            "Configure address.";
          container addresses {
            must "/ni:network-instance/ni:instances/ni:instance[ni:name=current()/../../ifm:vrf-name]/l3vpn:afs/l3vpn:af[l3vpn:type='ipv6-unicast']" {
              tailf:xpath-root 3;
            }
            description
              "List of IPv6 addresses.";
            list address {
              key "ip";
              description
                "Configure IPv6 address.";
              leaf ip {
                type inet:ipv6-address-no-zone;
                description
                  "IPv6 address.";
              }
              leaf prefix-length {
                type uint32 {
                  range "1..128";
                }
                mandatory true;
                description
                  "Length of the IPv6 address prefix.";
              }
              leaf type {
                type ipv6-address-config-type;
                mandatory true;
                description
                  "IPv6 address type.";
              }
              leaf algorithm-type {
                type ipv6-address-algorithm-type;
                must "(../type='global' and (../algorithm-type='none' or ../algorithm-type='cga' or ../algorithm-type='eui64') ) or (../type='link-local' and (../algorithm-type='none' or ../algorithm-type='cga') ) or (../type='anycast' and ../algorithm-type='none')" {
                  tailf:xpath-root 3;
                }
                default "none";
                description
                  "Address algorithm type.";
              }
            }
          }
        }
      }
      container nd-prefixs {
        must "(count(nd-prefix)> 0 and /ni:network-instance/ni:instances/ni:instance[ni:name=current()/../../ifm:vrf-name]/l3vpn:afs/l3vpn:af[l3vpn:type='ipv6-unicast']) or (count(nd-prefix)= 0)" {
          tailf:xpath-root 3;
        }
        description
          "List of nd prefix.";
        list nd-prefix {
          key "prefix";
          description
            "Configure nd prefix.";
          leaf prefix {
            type inet:ipv6-address-no-zone;
            description
              "IPv6 address of the prefix.";
          }
          leaf prefix-len {
            type int32 {
              range "0..128";
            }
            mandatory true;
            description
              "Length of the prefix address.";
          }
          leaf valid-lifetime {
            type uint32 {
              range "0..4294967295";
            }
            units "s";
            must '(../valid-lifetime>=../preferred-lifetime)' {
              tailf:xpath-root 3;
            }
            mandatory true;
            description
              "Valid life time.";
          }
          leaf preferred-lifetime {
            type uint32 {
              range "0..4294967295";
            }
            units "s";
            must '(../preferred-lifetime<=../valid-lifetime)' {
              tailf:xpath-root 3;
            }
            mandatory true;
            description
              "Preferred life time.";
          }
          leaf auto-flag {
            type boolean;
            default "true";
            description
              "Enable/disable the autonomous address-configuration.";
          }
          leaf on-link-flag {
            type boolean;
            default "true";
            description
              "Enable/disable the on-link flag.";
          }
        }
      }
      // NCS drop config false container state
    }
  }
}
