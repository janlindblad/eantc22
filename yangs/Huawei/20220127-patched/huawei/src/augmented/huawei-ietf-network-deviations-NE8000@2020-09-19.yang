module huawei-ietf-network-deviations-NE8000 {
  // Generated by yanger -t ncs
  tailf:mount-id "huawei-nc-1.0:huawei-nc-1.0";
  tailf:ncs-device-type "netconf";

  yang-version 1.1;
  namespace "urn:huawei:yang:huawei-ietf-network-deviations-NE8000";
  prefix nw-devs-NE8000;

  import ietf-network {
    prefix nw;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Deviations for ietf-network model.";

  revision 2020-09-19 {
    description
      "Initial revision.";
    reference "Huawei private.";
  }

  deviation "/ncs:devices/ncs:template/ncs:ned-id/ncs:config/nw:networks" {
    deviate not-supported;
  }
  deviation "/ncs:devices/ncs:device/ncs:live-status/nw:networks" {
    deviate not-supported;
  }
  deviation "/ncs:devices/ncs:device/ncs:config/nw:networks" {
    deviate not-supported;
  }
}
