module huawei-fim-devm {
  // Generated by yanger -t ncs
  tailf:mount-id "huawei-nc-1.0:huawei-nc-1.0";
  tailf:ncs-device-type "netconf";

  namespace "urn:huawei:yang:huawei-fim-devm";
  prefix fim-devm;

  import huawei-extension {
    prefix ext;
  }
  import huawei-pub-type {
    prefix pub-type;
  }
  import huawei-devm {
    prefix devm;
  }
  import huawei-fim-ifm {
    prefix fim-ifm;
  }
  import huawei-ifm {
    prefix ifm;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Global configuration.";

  revision 2020-03-11 {
    description
      "Initial revision.";
    reference "Huawei private.";
  }
  ext:task-name "forwarding";

  typedef ncs_template_enable-type {
    type string;
    description
      "Enable type.";
  }

  typedef ncs_template_forward-mode-type {
    type string;
    description
      "Slot forward mode.";
  }

  typedef ncs_rpc_notif_enable-type {
    type enumeration {
      enum "disable" {
        value 0;
        description
          "Disable.";
      }
      enum "enable" {
        value 1;
        description
          "Enable.";
      }
    }
    description
      "Enable type.";
  }

  typedef ncs_rpc_notif_forward-mode-type {
    type enumeration {
      enum "loopback" {
        value 0;
        description
          "Loopback forward type.";
      }
      enum "through" {
        value 1;
        description
          "Through forward type.";
      }
    }
    description
      "Slot forward mode.";
  }

  typedef live_ncs_enable-type {
    type enumeration {
      enum "disable" {
        value 0;
        description
          "Disable.";
      }
      enum "enable" {
        value 1;
        description
          "Enable.";
      }
    }
    description
      "Enable type.";
  }

  typedef live_ncs_forward-mode-type {
    type enumeration {
      enum "loopback" {
        value 0;
        description
          "Loopback forward type.";
      }
      enum "through" {
        value 1;
        description
          "Through forward type.";
      }
    }
    description
      "Slot forward mode.";
  }

  typedef enable-type {
    type enumeration {
      enum "disable" {
        value 0;
        description
          "Disable.";
      }
      enum "enable" {
        value 1;
        description
          "Enable.";
      }
    }
    description
      "Enable type.";
  }

  typedef forward-mode-type {
    type enumeration {
      enum "loopback" {
        value 0;
        description
          "Loopback forward type.";
      }
      enum "through" {
        value 1;
        description
          "Through forward type.";
      }
    }
    description
      "Slot forward mode.";
  }

  augment "/ncs:devices/ncs:template/ncs:ned-id/ncs:config/devm:devm/devm:lpu-boards/devm:lpu-board" {
    description
      "FIM configuration to the DEVM lpu-board module.";
    container fim {
      description
        "Configure the forward configuration to the DEVM lpu-board module.";
      leaf forward-mode {
        type ncs_template_forward-mode-type;
        // NCS drop default statement
        description
          "Forward mode.";
      }
      leaf vlan-miss-enable {
        type ncs_template_enable-type;
        // NCS drop default statement
        description
          "VLAN-miss to-cpu enable.";
      }
      leaf scan-period {
        // NCS drop when statement
        type string;
        units "min";
        // NCS drop default statement
        description
          "Scan period.";
      }
      leaf cpu-threshold {
        // NCS drop when statement
        type string;
        units "%";
        // NCS drop default statement
        description
          "CPU usage threshold.";
      }
      leaf cpu-detect {
        // NCS drop when statement
        type string;
        units "min";
        // NCS drop default statement
        description
          "CPU usage detection period.";
      }
      leaf cpu-restore {
        // NCS drop when statement
        type string;
        units "%";
        // NCS drop default statement
        description
          "Restore dynamically adjusted CPU usage threshold.";
      }
    }
    // NCS drop config false container 'macmtu-discard-statistics'
    container ve-mac-address {
      description
        "Configure the VE MAC address.";
      leaf l2-ve-mac {
        type pub-type:ncs_template_mac-address;
        description
          "L2 VE MAC address.";
      }
      leaf access-ve-mac {
        type pub-type:ncs_template_mac-address;
        description
          "Access VE MAC address.";
      }
    }
  }
  augment "/ncs:devices/ncs:device/ncs:live-status/devm:devm/devm:lpu-boards/devm:lpu-board" {
    description
      "FIM configuration to the DEVM lpu-board module.";
    container fim {
      tailf:ncs-device-type "netconf";
      tailf:display-when "not(../../../../../ncs:module) or ../../../../../ncs:module[ncs:name='huawei-fim-devm'] or (../../../../../ncs:live-status-protocol[not(ncs:capability)]) or (../../../../../ncs:live-status-protocol/ncs:capability/ncs:module[.='huawei-fim-devm'])";
      description
        "Configure the forward configuration to the DEVM lpu-board module.";
      leaf forward-mode {
        type live_ncs_forward-mode-type;
        // NCS drop default statement
        description
          "Forward mode.";
      }
      leaf vlan-miss-enable {
        type live_ncs_enable-type;
        // NCS drop default statement
        description
          "VLAN-miss to-cpu enable.";
      }
      leaf scan-period {
        // NCS drop when statement
        type uint32 {
          range "2..720";
        }
        units "min";
        // NCS drop default statement
        description
          "Scan period.";
      }
      leaf cpu-threshold {
        // NCS drop when statement
        type uint32 {
          range "10..100";
        }
        units "%";
        // NCS drop default statement
        description
          "CPU usage threshold.";
      }
      leaf cpu-detect {
        // NCS drop when statement
        type uint32 {
          range "1..10";
        }
        units "min";
        // NCS drop default statement
        description
          "CPU usage detection period.";
      }
      leaf cpu-restore {
        // NCS drop when statement
        type uint32 {
          range "10..100";
        }
        units "%";
        // NCS drop default statement
        description
          "Restore dynamically adjusted CPU usage threshold.";
      }
    }
    container macmtu-discard-statistics {
      tailf:ncs-device-type "netconf";
      tailf:display-when "not(../../../../../ncs:module) or ../../../../../ncs:module[ncs:name='huawei-fim-devm'] or (../../../../../ncs:live-status-protocol[not(ncs:capability)]) or (../../../../../ncs:live-status-protocol/ncs:capability/ncs:module[.='huawei-fim-devm'])";
      description
        "MAC&MTU error statistics.";
      leaf mtu-ipv4 {
        type uint64;
        description
          "IPv4 MTU error statistics.";
      }
      leaf mtu-ipv6 {
        type uint64;
        description
          "IPv6 MTU error statistics.";
      }
      leaf mac-ipv4 {
        type uint64;
        description
          "IPv4 MAC error statistics.";
      }
      leaf mac-ipv6 {
        type uint64;
        description
          "IPv6 MAC error statistics.";
      }
    }
    container ve-mac-address {
      tailf:ncs-device-type "netconf";
      tailf:display-when "not(../../../../../ncs:module) or ../../../../../ncs:module[ncs:name='huawei-fim-devm'] or (../../../../../ncs:live-status-protocol[not(ncs:capability)]) or (../../../../../ncs:live-status-protocol/ncs:capability/ncs:module[.='huawei-fim-devm'])";
      description
        "Configure the VE MAC address.";
      leaf l2-ve-mac {
        type pub-type:live_ncs_mac-address;
        description
          "L2 VE MAC address.";
      }
      leaf access-ve-mac {
        type pub-type:live_ncs_mac-address;
        description
          "Access VE MAC address.";
      }
    }
  }
  augment "/ncs:devices/ncs:device/ncs:config/devm:devm/devm:lpu-boards/devm:lpu-board" {
    description
      "FIM configuration to the DEVM lpu-board module.";
    container fim {
      tailf:ncs-device-type "netconf";
      tailf:display-when "not(../../../../../ncs:module) or ../../../../../ncs:module[ncs:name='huawei-fim-devm']";
      description
        "Configure the forward configuration to the DEVM lpu-board module.";
      leaf forward-mode {
        type forward-mode-type;
        default "loopback";
        description
          "Forward mode.";
      }
      leaf vlan-miss-enable {
        type enable-type;
        default "disable";
        description
          "VLAN-miss to-cpu enable.";
      }
      leaf scan-period {
        when "/ifm:ifm/ifm:global/fim-ifm:fim-ifm-global/fim-ifm:trunk-adjust-enable='enable'" {
          tailf:xpath-root 3;
        }
        type uint32 {
          range "2..720";
        }
        units "min";
        default "60";
        description
          "Scan period.";
      }
      leaf cpu-threshold {
        when "/ifm:ifm/ifm:global/fim-ifm:fim-ifm-global/fim-ifm:trunk-adjust-enable='enable'" {
          tailf:xpath-root 3;
        }
        type uint32 {
          range "10..100";
        }
        units "%";
        default "60";
        description
          "CPU usage threshold.";
      }
      leaf cpu-detect {
        when "/ifm:ifm/ifm:global/fim-ifm:fim-ifm-global/fim-ifm:trunk-adjust-enable='enable'" {
          tailf:xpath-root 3;
        }
        type uint32 {
          range "1..10";
        }
        units "min";
        default "10";
        description
          "CPU usage detection period.";
      }
      leaf cpu-restore {
        when "/ifm:ifm/ifm:global/fim-ifm:fim-ifm-global/fim-ifm:trunk-adjust-enable='enable'" {
          tailf:xpath-root 3;
        }
        type uint32 {
          range "10..100";
        }
        units "%";
        default "55";
        description
          "Restore dynamically adjusted CPU usage threshold.";
      }
    }
    // NCS drop config false container 'macmtu-discard-statistics'
    container ve-mac-address {
      tailf:ncs-device-type "netconf";
      tailf:display-when "not(../../../../../ncs:module) or ../../../../../ncs:module[ncs:name='huawei-fim-devm']";
      description
        "Configure the VE MAC address.";
      leaf l2-ve-mac {
        type pub-type:mac-address;
        description
          "L2 VE MAC address.";
      }
      leaf access-ve-mac {
        type pub-type:mac-address;
        description
          "Access VE MAC address.";
      }
    }
  }
  augment "/ncs:devices/ncs:template/ncs:ned-id/ncs:config/devm:devm/devm:mpu-boards/devm:mpu-board" {
    description
      "FIM configuration to the DEVM mpu-board module.";
    container fim {
      description
        "Configure the forward configuration to the DEVM mpu-board module.";
      leaf forward-mode {
        type ncs_template_forward-mode-type;
        // NCS drop default statement
        description
          "Forward mode.";
      }
      leaf vlan-miss-enable {
        type ncs_template_enable-type;
        // NCS drop default statement
        description
          "VLAN-miss to-cpu enable.";
      }
      leaf scan-period {
        // NCS drop when statement
        type string;
        units "min";
        // NCS drop default statement
        description
          "Scan period.";
      }
      leaf cpu-threshold {
        // NCS drop when statement
        type string;
        units "%";
        // NCS drop default statement
        description
          "CPU usage threshold.";
      }
      leaf cpu-detect {
        // NCS drop when statement
        type string;
        units "min";
        // NCS drop default statement
        description
          "CPU usage detection period.";
      }
      leaf cpu-restore {
        // NCS drop when statement
        type string;
        units "%";
        // NCS drop default statement
        description
          "Restore dynamically adjusted CPU usage threshold.";
      }
    }
    // NCS drop config false container 'macmtu-discard-statistics'
    container ve-mac-address {
      description
        "Configure the VE MAC address.";
      leaf l2-ve-mac {
        type pub-type:ncs_template_mac-address;
        description
          "L2 VE MAC address.";
      }
      leaf access-ve-mac {
        type pub-type:ncs_template_mac-address;
        description
          "Access VE MAC address.";
      }
    }
  }
  augment "/ncs:devices/ncs:device/ncs:live-status/devm:devm/devm:mpu-boards/devm:mpu-board" {
    description
      "FIM configuration to the DEVM mpu-board module.";
    container fim {
      tailf:ncs-device-type "netconf";
      tailf:display-when "not(../../../../../ncs:module) or ../../../../../ncs:module[ncs:name='huawei-fim-devm'] or (../../../../../ncs:live-status-protocol[not(ncs:capability)]) or (../../../../../ncs:live-status-protocol/ncs:capability/ncs:module[.='huawei-fim-devm'])";
      description
        "Configure the forward configuration to the DEVM mpu-board module.";
      leaf forward-mode {
        type live_ncs_forward-mode-type;
        // NCS drop default statement
        description
          "Forward mode.";
      }
      leaf vlan-miss-enable {
        type live_ncs_enable-type;
        // NCS drop default statement
        description
          "VLAN-miss to-cpu enable.";
      }
      leaf scan-period {
        // NCS drop when statement
        type uint32 {
          range "2..720";
        }
        units "min";
        // NCS drop default statement
        description
          "Scan period.";
      }
      leaf cpu-threshold {
        // NCS drop when statement
        type uint32 {
          range "10..100";
        }
        units "%";
        // NCS drop default statement
        description
          "CPU usage threshold.";
      }
      leaf cpu-detect {
        // NCS drop when statement
        type uint32 {
          range "1..10";
        }
        units "min";
        // NCS drop default statement
        description
          "CPU usage detection period.";
      }
      leaf cpu-restore {
        // NCS drop when statement
        type uint32 {
          range "10..100";
        }
        units "%";
        // NCS drop default statement
        description
          "Restore dynamically adjusted CPU usage threshold.";
      }
    }
    container macmtu-discard-statistics {
      tailf:ncs-device-type "netconf";
      tailf:display-when "not(../../../../../ncs:module) or ../../../../../ncs:module[ncs:name='huawei-fim-devm'] or (../../../../../ncs:live-status-protocol[not(ncs:capability)]) or (../../../../../ncs:live-status-protocol/ncs:capability/ncs:module[.='huawei-fim-devm'])";
      description
        "MAC&MTU error statistics.";
      leaf mtu-ipv4 {
        type uint64;
        description
          "IPv4 MTU error statistics.";
      }
      leaf mtu-ipv6 {
        type uint64;
        description
          "IPv6 MTU error statistics.";
      }
      leaf mac-ipv4 {
        type uint64;
        description
          "IPv4 MAC error statistics.";
      }
      leaf mac-ipv6 {
        type uint64;
        description
          "IPv6 MAC error statistics.";
      }
    }
    container ve-mac-address {
      tailf:ncs-device-type "netconf";
      tailf:display-when "not(../../../../../ncs:module) or ../../../../../ncs:module[ncs:name='huawei-fim-devm'] or (../../../../../ncs:live-status-protocol[not(ncs:capability)]) or (../../../../../ncs:live-status-protocol/ncs:capability/ncs:module[.='huawei-fim-devm'])";
      description
        "Configure the VE MAC address.";
      leaf l2-ve-mac {
        type pub-type:live_ncs_mac-address;
        description
          "L2 VE MAC address.";
      }
      leaf access-ve-mac {
        type pub-type:live_ncs_mac-address;
        description
          "Access VE MAC address.";
      }
    }
  }
  augment "/ncs:devices/ncs:device/ncs:config/devm:devm/devm:mpu-boards/devm:mpu-board" {
    description
      "FIM configuration to the DEVM mpu-board module.";
    container fim {
      tailf:ncs-device-type "netconf";
      tailf:display-when "not(../../../../../ncs:module) or ../../../../../ncs:module[ncs:name='huawei-fim-devm']";
      description
        "Configure the forward configuration to the DEVM mpu-board module.";
      leaf forward-mode {
        type forward-mode-type;
        default "loopback";
        description
          "Forward mode.";
      }
      leaf vlan-miss-enable {
        type enable-type;
        default "disable";
        description
          "VLAN-miss to-cpu enable.";
      }
      leaf scan-period {
        when "/ifm:ifm/ifm:global/fim-ifm:fim-ifm-global/fim-ifm:trunk-adjust-enable='enable'" {
          tailf:xpath-root 3;
        }
        type uint32 {
          range "2..720";
        }
        units "min";
        default "60";
        description
          "Scan period.";
      }
      leaf cpu-threshold {
        when "/ifm:ifm/ifm:global/fim-ifm:fim-ifm-global/fim-ifm:trunk-adjust-enable='enable'" {
          tailf:xpath-root 3;
        }
        type uint32 {
          range "10..100";
        }
        units "%";
        default "60";
        description
          "CPU usage threshold.";
      }
      leaf cpu-detect {
        when "/ifm:ifm/ifm:global/fim-ifm:fim-ifm-global/fim-ifm:trunk-adjust-enable='enable'" {
          tailf:xpath-root 3;
        }
        type uint32 {
          range "1..10";
        }
        units "min";
        default "10";
        description
          "CPU usage detection period.";
      }
      leaf cpu-restore {
        when "/ifm:ifm/ifm:global/fim-ifm:fim-ifm-global/fim-ifm:trunk-adjust-enable='enable'" {
          tailf:xpath-root 3;
        }
        type uint32 {
          range "10..100";
        }
        units "%";
        default "55";
        description
          "Restore dynamically adjusted CPU usage threshold.";
      }
    }
    // NCS drop config false container 'macmtu-discard-statistics'
    container ve-mac-address {
      tailf:ncs-device-type "netconf";
      tailf:display-when "not(../../../../../ncs:module) or ../../../../../ncs:module[ncs:name='huawei-fim-devm']";
      description
        "Configure the VE MAC address.";
      leaf l2-ve-mac {
        type pub-type:mac-address;
        description
          "L2 VE MAC address.";
      }
      leaf access-ve-mac {
        type pub-type:mac-address;
        description
          "Access VE MAC address.";
      }
    }
  }
}
