module huawei-fim-ifm {
  // Generated by yanger -t ncs
  tailf:mount-id "huawei-nc-1.0:huawei-nc-1.0";
  tailf:ncs-device-type "netconf";

  namespace "urn:huawei:yang:huawei-fim-ifm";
  prefix fim-ifm;

  import huawei-pub-type {
    prefix pub-type;
  }
  import huawei-ifm {
    prefix ifm;
  }
  import huawei-extension {
    prefix ext;
  }
  import huawei-ethernet {
    prefix ethernet;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Common interface management, which includes the public configuration of interfaces.";
  reference "Huawei private.";

  revision 2020-03-23 {
    description
      "Initial revision.";
    reference "Huawei private.";
  }
  ext:task-name "forwarding";

  typedef ncs_template_enable-type {
    type string;
    description
      "Enable type.";
  }

  typedef ncs_template_statistic-mode-type {
    type string;
    description
      "Ip Statistic Mode Type.";
  }

  typedef ncs_template_ve-mode-type {
    type string;
    description
      "VE Forward Mode Type.";
  }

  typedef ncs_template_ve-interface-type {
    type string;
    description
      "VE Interface Type.";
  }

  typedef ncs_template_local-forward-type {
    type string;
    description
      "Trunk Local Forward Type.";
  }

  typedef ncs_template_reset-ipversion-type {
    type string;
    description
      "Reset IP vertion type.";
  }

  typedef ncs_template_reset-dispcard-type {
    type string;
    description
      "Reset discard vertion type.";
  }

  typedef ncs_rpc_notif_enable-type {
    type enumeration {
      enum "disable" {
        value 0;
        description
          "Disable.";
      }
      enum "enable" {
        value 1;
        description
          "Enable.";
      }
    }
    description
      "Enable type.";
  }

  typedef ncs_rpc_notif_statistic-mode-type {
    type enumeration {
      enum "forward" {
        value 1;
        description
          "Forward mode statistics.";
      }
      enum "mac" {
        value 0;
        description
          "MAC mode statistics.";
      }
    }
    description
      "Ip Statistic Mode Type.";
  }

  typedef ncs_rpc_notif_ve-mode-type {
    type enumeration {
      enum "through" {
        value 1;
        description
          "Software loopback.";
      }
      enum "loopback" {
        value 0;
        description
          "Hardware loopback.";
      }
      enum "half-through" {
        value 3;
        description
          "Software switch hardware loopback.";
      }
    }
    description
      "VE Forward Mode Type.";
  }

  typedef ncs_rpc_notif_ve-interface-type {
    type enumeration {
      enum "L2VE" {
        value 1;
        description
          "Layer 2 Terminate Virtual-Ethernet interface.";
      }
      enum "L3VE" {
        value 2;
        description
          "Layer 3 Access Virtual-Ethernet interface.";
      }
      enum "terminate-ve" {
        value 7;
        description
          "Layer 3 Terminate Virtual-Ethernet interface.";
      }
    }
    description
      "VE Interface Type.";
  }

  typedef ncs_rpc_notif_local-forward-type {
    type enumeration {
      enum "unicast" {
        value 1;
        description
          "Unicast Local Forward.";
      }
    }
    description
      "Trunk Local Forward Type.";
  }

  typedef ncs_rpc_notif_reset-ipversion-type {
    type enumeration {
      enum "ipv4" {
        value 1;
        description
          "IPv4 reset.";
      }
      enum "ipv6" {
        value 2;
        description
          "IPv6 reset.";
      }
    }
    description
      "Reset IP vertion type.";
  }

  typedef ncs_rpc_notif_reset-dispcard-type {
    type enumeration {
      enum "mac" {
        value 1;
        description
          "MAC reset.";
      }
      enum "mtu" {
        value 2;
        description
          "MTU reset.";
      }
    }
    description
      "Reset discard vertion type.";
  }

  typedef live_ncs_enable-type {
    type enumeration {
      enum "disable" {
        value 0;
        description
          "Disable.";
      }
      enum "enable" {
        value 1;
        description
          "Enable.";
      }
    }
    description
      "Enable type.";
  }

  typedef live_ncs_statistic-mode-type {
    type enumeration {
      enum "forward" {
        value 1;
        description
          "Forward mode statistics.";
      }
      enum "mac" {
        value 0;
        description
          "MAC mode statistics.";
      }
    }
    description
      "Ip Statistic Mode Type.";
  }

  typedef live_ncs_ve-mode-type {
    type enumeration {
      enum "through" {
        value 1;
        description
          "Software loopback.";
      }
      enum "loopback" {
        value 0;
        description
          "Hardware loopback.";
      }
      enum "half-through" {
        value 3;
        description
          "Software switch hardware loopback.";
      }
    }
    description
      "VE Forward Mode Type.";
  }

  typedef live_ncs_ve-interface-type {
    type enumeration {
      enum "L2VE" {
        value 1;
        description
          "Layer 2 Terminate Virtual-Ethernet interface.";
      }
      enum "L3VE" {
        value 2;
        description
          "Layer 3 Access Virtual-Ethernet interface.";
      }
      enum "terminate-ve" {
        value 7;
        description
          "Layer 3 Terminate Virtual-Ethernet interface.";
      }
    }
    description
      "VE Interface Type.";
  }

  typedef live_ncs_local-forward-type {
    type enumeration {
      enum "unicast" {
        value 1;
        description
          "Unicast Local Forward.";
      }
    }
    description
      "Trunk Local Forward Type.";
  }

  typedef live_ncs_reset-ipversion-type {
    type enumeration {
      enum "ipv4" {
        value 1;
        description
          "IPv4 reset.";
      }
      enum "ipv6" {
        value 2;
        description
          "IPv6 reset.";
      }
    }
    description
      "Reset IP vertion type.";
  }

  typedef live_ncs_reset-dispcard-type {
    type enumeration {
      enum "mac" {
        value 1;
        description
          "MAC reset.";
      }
      enum "mtu" {
        value 2;
        description
          "MTU reset.";
      }
    }
    description
      "Reset discard vertion type.";
  }

  typedef enable-type {
    type enumeration {
      enum "disable" {
        value 0;
        description
          "Disable.";
      }
      enum "enable" {
        value 1;
        description
          "Enable.";
      }
    }
    description
      "Enable type.";
  }

  typedef statistic-mode-type {
    type enumeration {
      enum "forward" {
        value 1;
        description
          "Forward mode statistics.";
      }
      enum "mac" {
        value 0;
        description
          "MAC mode statistics.";
      }
    }
    description
      "Ip Statistic Mode Type.";
  }

  typedef ve-mode-type {
    type enumeration {
      enum "through" {
        value 1;
        description
          "Software loopback.";
      }
      enum "loopback" {
        value 0;
        description
          "Hardware loopback.";
      }
      enum "half-through" {
        value 3;
        description
          "Software switch hardware loopback.";
      }
    }
    description
      "VE Forward Mode Type.";
  }

  typedef ve-interface-type {
    type enumeration {
      enum "L2VE" {
        value 1;
        description
          "Layer 2 Terminate Virtual-Ethernet interface.";
      }
      enum "L3VE" {
        value 2;
        description
          "Layer 3 Access Virtual-Ethernet interface.";
      }
      enum "terminate-ve" {
        value 7;
        description
          "Layer 3 Terminate Virtual-Ethernet interface.";
      }
    }
    description
      "VE Interface Type.";
  }

  typedef local-forward-type {
    type enumeration {
      enum "unicast" {
        value 1;
        description
          "Unicast Local Forward.";
      }
    }
    description
      "Trunk Local Forward Type.";
  }

  typedef reset-ipversion-type {
    type enumeration {
      enum "ipv4" {
        value 1;
        description
          "IPv4 reset.";
      }
      enum "ipv6" {
        value 2;
        description
          "IPv6 reset.";
      }
    }
    description
      "Reset IP vertion type.";
  }

  typedef reset-dispcard-type {
    type enumeration {
      enum "mac" {
        value 1;
        description
          "MAC reset.";
      }
      enum "mtu" {
        value 2;
        description
          "MTU reset.";
      }
    }
    description
      "Reset discard vertion type.";
  }

  augment "/ncs:devices/ncs:device/ncs:rpc" {
    container rpc-rst-mru-discard {
      tailf:ncs-device-type "netconf";
      tailf:display-when "not(../../ncs:module) or ../../ncs:module[ncs:name='huawei-fim-ifm']";
      tailf:action rst-mru-discard {
        tailf:actionpoint ncsproxy {
          tailf:internal;
        }
        description
          "Clear interface MRU discard statistics.";
        ext:node-ref "/ifm/interfaces/interface";
        input {
          leaf interface-name {
            type string {
              length "1..63";
            }
            mandatory true;
            description
              "Interface name of clear interface MRU discard statistics.";
          }
        }
      }
    }
  }
  augment "/ncs:devices/ncs:device-group/ncs:ned-id/ncs:rpc" {
    container rpc-rst-mru-discard {
      tailf:ncs-device-type "netconf";
      tailf:display-when "/ncs:devices/ncs:device[ncs:name=current()/../../../ncs:member]/ncs:module[ncs:name='huawei-fim-ifm']";
      tailf:action rst-mru-discard {
        tailf:actionpoint ncsproxy {
          tailf:internal;
        }
        description
          "Clear interface MRU discard statistics.";
        ext:node-ref "/ifm/interfaces/interface";
        input {
          leaf interface-name {
            type string {
              length "1..63";
            }
            mandatory true;
            description
              "Interface name of clear interface MRU discard statistics.";
          }
        }
      }
    }
  }
  augment "/ncs:devices/ncs:device/ncs:rpc" {
    container rpc-rst-macmtu-slot {
      tailf:ncs-device-type "netconf";
      tailf:display-when "not(../../ncs:module) or ../../ncs:module[ncs:name='huawei-fim-ifm']";
      tailf:action rst-macmtu-slot {
        tailf:actionpoint ncsproxy {
          tailf:internal;
        }
        description
          "Clear MAC&MTU error statistics.";
        ext:node-ref "/ifm/interfaces/interface";
        input {
          leaf board-position {
            type string {
              length "1..32";
            }
            mandatory true;
            description
              "Board position.";
          }
          leaf discard-type {
            type ncs_rpc_notif_reset-dispcard-type;
            description
              "Configure the discard type.";
          }
          leaf ip-version {
            type ncs_rpc_notif_reset-ipversion-type;
            description
              "Configure the discard IP version.";
          }
        }
      }
    }
  }
  augment "/ncs:devices/ncs:device-group/ncs:ned-id/ncs:rpc" {
    container rpc-rst-macmtu-slot {
      tailf:ncs-device-type "netconf";
      tailf:display-when "/ncs:devices/ncs:device[ncs:name=current()/../../../ncs:member]/ncs:module[ncs:name='huawei-fim-ifm']";
      tailf:action rst-macmtu-slot {
        tailf:actionpoint ncsproxy {
          tailf:internal;
        }
        description
          "Clear MAC&MTU error statistics.";
        ext:node-ref "/ifm/interfaces/interface";
        input {
          leaf board-position {
            type string {
              length "1..32";
            }
            mandatory true;
            description
              "Board position.";
          }
          leaf discard-type {
            type ncs_rpc_notif_reset-dispcard-type;
            description
              "Configure the discard type.";
          }
          leaf ip-version {
            type ncs_rpc_notif_reset-ipversion-type;
            description
              "Configure the discard IP version.";
          }
        }
      }
    }
  }
  augment "/ncs:devices/ncs:device/ncs:rpc" {
    container rpc-rst-macmtu-intf {
      tailf:ncs-device-type "netconf";
      tailf:display-when "not(../../ncs:module) or ../../ncs:module[ncs:name='huawei-fim-ifm']";
      tailf:action rst-macmtu-intf {
        tailf:actionpoint ncsproxy {
          tailf:internal;
        }
        description
          "Clear MAC and MTU error statistics.";
        ext:node-ref "/ifm/interfaces/interface";
        input {
          leaf interface-name {
            type string {
              length "1..63";
            }
            mandatory true;
            description
              "Interface name.";
          }
          leaf discard-type {
            type ncs_rpc_notif_reset-dispcard-type;
            description
              "Configure the discard type.";
          }
          leaf ip-version {
            type ncs_rpc_notif_reset-ipversion-type;
            description
              "Configure the discard IP version.";
          }
        }
      }
    }
  }
  augment "/ncs:devices/ncs:device-group/ncs:ned-id/ncs:rpc" {
    container rpc-rst-macmtu-intf {
      tailf:ncs-device-type "netconf";
      tailf:display-when "/ncs:devices/ncs:device[ncs:name=current()/../../../ncs:member]/ncs:module[ncs:name='huawei-fim-ifm']";
      tailf:action rst-macmtu-intf {
        tailf:actionpoint ncsproxy {
          tailf:internal;
        }
        description
          "Clear MAC and MTU error statistics.";
        ext:node-ref "/ifm/interfaces/interface";
        input {
          leaf interface-name {
            type string {
              length "1..63";
            }
            mandatory true;
            description
              "Interface name.";
          }
          leaf discard-type {
            type ncs_rpc_notif_reset-dispcard-type;
            description
              "Configure the discard type.";
          }
          leaf ip-version {
            type ncs_rpc_notif_reset-ipversion-type;
            description
              "Configure the discard IP version.";
          }
        }
      }
    }
  }
  augment "/ncs:devices/ncs:template/ncs:ned-id/ncs:config/ifm:ifm/ifm:interfaces/ifm:interface" {
    description
      "Interface forward configuration to the interface management module.";
    container fim {
      description
        "Configure the function of statistic to main interface.";
      leaf statistic-enable {
        // NCS drop when statement
        type ncs_template_enable-type;
        // NCS drop default statement
        description
          "Enable the function of traffic statistics.";
      }
      leaf statistic-mode {
        // NCS drop when statement
        type ncs_template_statistic-mode-type;
        // NCS drop default statement
        description
          "Configure the traffic statistics mode.";
      }
      leaf mac-statistic-enable {
        // NCS drop when statement
        type ncs_template_enable-type;
        // NCS drop default statement
        description
          "Enable the function of bit per seconds (bps) statistics.";
      }
    }
    container fim-ifm-mru {
      description
        "Configure the maximum receive unit.";
      leaf mru {
        // NCS drop when statement
        type string;
        units "Byte";
        // NCS drop must statement
        description
          "Maximum receive unit of an interface.";
      }
      leaf mru-statistic-enable {
        // NCS drop when statement
        type ncs_template_enable-type;
        // NCS drop default statement
        description
          "Enable discard statistics of maximum receive unit of an interface.";
      }
    }
    container fim-tcp-mss {
      description
        "Configure Tcp mss.";
      leaf tcp-mss {
        // NCS drop when statement
        type string;
        units "Byte";
        // NCS drop must statement
        description
          "Maxitum Segment Size of an interface.";
      }
    }
    container fim-ifm-bdifint {
      // NCS drop when statement
      description
        "Configure forward configurations to VBDIF interface.";
      leaf vbdif-loopback-enable {
        type string;
        // NCS drop default statement
        description
          "Enable/disable the VBDIF loopback forward mode.";
      }
    }
    container fim-ifm-veint {
      description
        "Configure Virtual-Ethernet interface information.";
      leaf ve-forward-mode {
        // NCS drop when statement
        type ncs_template_ve-mode-type;
        // NCS drop default statement
        description
          "Virtual-Ethernet forward mode type.";
      }
      leaf ve-slot-id {
        // NCS drop when statement
        type string;
        description
          "Remove boards from a global VE interface.";
      }
    }
    container ve-group {
      // NCS drop when statement
      presence "configure ve-group.";
      description
        "Enable/disable a Virtual-Ethernet Group.";
      leaf type {
        type ncs_template_ve-interface-type;
        // NCS drop mandatory statement
        description
          "Virtual-Ethernet interface type.";
        ext:operation-exclude "update" {
          description
            "The node cannot be modified when ve-group is configured.";
        }
      }
      leaf id {
        type string;
        // NCS drop mandatory statement
        description
          "Virtual-Ethernet group ID.";
        ext:operation-exclude "update" {
          description
            "The node cannot be modified when ve-group is configured.";
        }
      }
    }
    // NCS drop config false container 'mru-discard-statistic'
    // NCS drop config false container 'macmtu-discard-stat'
  }
  augment "/ncs:devices/ncs:device/ncs:live-status/ifm:ifm/ifm:interfaces/ifm:interface" {
    description
      "Interface forward configuration to the interface management module.";
    container fim {
      tailf:ncs-device-type "netconf";
      tailf:display-when "not(../../../../../ncs:module) or ../../../../../ncs:module[ncs:name='huawei-fim-ifm'] or (../../../../../ncs:live-status-protocol[not(ncs:capability)]) or (../../../../../ncs:live-status-protocol/ncs:capability/ncs:module[.='huawei-fim-ifm'])";
      description
        "Configure the function of statistic to main interface.";
      leaf statistic-enable {
        // NCS drop when statement
        type live_ncs_enable-type;
        // NCS drop default statement
        description
          "Enable the function of traffic statistics.";
      }
      leaf statistic-mode {
        // NCS drop when statement
        type live_ncs_statistic-mode-type;
        // NCS drop default statement
        description
          "Configure the traffic statistics mode.";
      }
      leaf mac-statistic-enable {
        // NCS drop when statement
        type live_ncs_enable-type;
        // NCS drop default statement
        description
          "Enable the function of bit per seconds (bps) statistics.";
      }
    }
    container fim-ifm-mru {
      tailf:ncs-device-type "netconf";
      tailf:display-when "not(../../../../../ncs:module) or ../../../../../ncs:module[ncs:name='huawei-fim-ifm'] or (../../../../../ncs:live-status-protocol[not(ncs:capability)]) or (../../../../../ncs:live-status-protocol/ncs:capability/ncs:module[.='huawei-fim-ifm'])";
      description
        "Configure the maximum receive unit.";
      leaf mru {
        // NCS drop when statement
        type uint16 {
          range "46..9600";
        }
        units "Byte";
        // NCS drop must statement
        description
          "Maximum receive unit of an interface.";
      }
      leaf mru-statistic-enable {
        // NCS drop when statement
        type live_ncs_enable-type;
        // NCS drop default statement
        description
          "Enable discard statistics of maximum receive unit of an interface.";
      }
    }
    container fim-tcp-mss {
      tailf:ncs-device-type "netconf";
      tailf:display-when "not(../../../../../ncs:module) or ../../../../../ncs:module[ncs:name='huawei-fim-ifm'] or (../../../../../ncs:live-status-protocol[not(ncs:capability)]) or (../../../../../ncs:live-status-protocol/ncs:capability/ncs:module[.='huawei-fim-ifm'])";
      description
        "Configure Tcp mss.";
      leaf tcp-mss {
        // NCS drop when statement
        type uint16 {
          range "32..9500";
        }
        units "Byte";
        // NCS drop must statement
        description
          "Maxitum Segment Size of an interface.";
      }
    }
    container fim-ifm-bdifint {
      tailf:ncs-device-type "netconf";
      tailf:display-when "not(../../../../../ncs:module) or ../../../../../ncs:module[ncs:name='huawei-fim-ifm'] or (../../../../../ncs:live-status-protocol[not(ncs:capability)]) or (../../../../../ncs:live-status-protocol/ncs:capability/ncs:module[.='huawei-fim-ifm'])";
      // NCS drop when statement
      description
        "Configure forward configurations to VBDIF interface.";
      leaf vbdif-loopback-enable {
        type boolean;
        // NCS drop default statement
        description
          "Enable/disable the VBDIF loopback forward mode.";
      }
    }
    container fim-ifm-veint {
      tailf:ncs-device-type "netconf";
      tailf:display-when "not(../../../../../ncs:module) or ../../../../../ncs:module[ncs:name='huawei-fim-ifm'] or (../../../../../ncs:live-status-protocol[not(ncs:capability)]) or (../../../../../ncs:live-status-protocol/ncs:capability/ncs:module[.='huawei-fim-ifm'])";
      description
        "Configure Virtual-Ethernet interface information.";
      leaf ve-forward-mode {
        // NCS drop when statement
        type live_ncs_ve-mode-type;
        // NCS drop default statement
        description
          "Virtual-Ethernet forward mode type.";
      }
      leaf ve-slot-id {
        // NCS drop when statement
        type string {
          length "1..512";
        }
        description
          "Remove boards from a global VE interface.";
      }
    }
    container ve-group {
      tailf:ncs-device-type "netconf";
      tailf:display-when "not(../../../../../ncs:module) or ../../../../../ncs:module[ncs:name='huawei-fim-ifm'] or (../../../../../ncs:live-status-protocol[not(ncs:capability)]) or (../../../../../ncs:live-status-protocol/ncs:capability/ncs:module[.='huawei-fim-ifm'])";
      // NCS drop when statement
      presence "configure ve-group.";
      description
        "Enable/disable a Virtual-Ethernet Group.";
      leaf type {
        type live_ncs_ve-interface-type;
        // NCS drop mandatory statement
        description
          "Virtual-Ethernet interface type.";
        ext:operation-exclude "update" {
          description
            "The node cannot be modified when ve-group is configured.";
        }
      }
      leaf id {
        type uint32 {
          range "1..8192";
        }
        // NCS drop mandatory statement
        description
          "Virtual-Ethernet group ID.";
        ext:operation-exclude "update" {
          description
            "The node cannot be modified when ve-group is configured.";
        }
      }
    }
    container mru-discard-statistic {
      tailf:ncs-device-type "netconf";
      tailf:display-when "not(../../../../../ncs:module) or ../../../../../ncs:module[ncs:name='huawei-fim-ifm'] or (../../../../../ncs:live-status-protocol[not(ncs:capability)]) or (../../../../../ncs:live-status-protocol/ncs:capability/ncs:module[.='huawei-fim-ifm'])";
      description
        "Statistics of maximum receive unit of an interface.";
      leaf packet {
        type uint64;
        description
          "Display the packets of discarded statistics of maximum receive unit of an interface.";
      }
      leaf byte {
        type uint64;
        units "Byte";
        description
          "Display the bytes of discarded statistics of maximum receive unit of an interface.";
      }
    }
    container macmtu-discard-stat {
      tailf:ncs-device-type "netconf";
      tailf:display-when "not(../../../../../ncs:module) or ../../../../../ncs:module[ncs:name='huawei-fim-ifm'] or (../../../../../ncs:live-status-protocol[not(ncs:capability)]) or (../../../../../ncs:live-status-protocol/ncs:capability/ncs:module[.='huawei-fim-ifm'])";
      description
        "MAC&MTU error statistics.";
      leaf mtu-ipv4 {
        type uint64;
        description
          "IPv4 MTU error statistics.";
      }
      leaf mtu-ipv6 {
        type uint64;
        description
          "IPv6 MTU error statistics.";
      }
      leaf mac-ipv4 {
        type uint64;
        // NCS drop default statement
        description
          "IPv4 MAC error statistics.";
      }
      leaf mac-ipv6 {
        type uint64;
        description
          "IPv6 MAC error statistics.";
      }
    }
  }
  augment "/ncs:devices/ncs:device/ncs:config/ifm:ifm/ifm:interfaces/ifm:interface" {
    description
      "Interface forward configuration to the interface management module.";
    container fim {
      tailf:ncs-device-type "netconf";
      tailf:display-when "not(../../../../../ncs:module) or ../../../../../ncs:module[ncs:name='huawei-fim-ifm']";
      description
        "Configure the function of statistic to main interface.";
      leaf statistic-enable {
        when "../../ifm:class='main-interface' and ../../ifm:type!='Virtual-Ethernet' and ../../ifm:type!='Tunnel' and ../../ifm:type!='NULL' and ../../ifm:type!='LoopBack' and ../../ifm:type!='Global-VE' and ../../ifm:type!='Nve' and ../../ifm:type!='Vlanif' and ../../ifm:type!='PW-VE' and ../../ifm:type!='Vbdif'" {
          tailf:xpath-root 3;
        }
        type enable-type;
        default "disable";
        description
          "Enable the function of traffic statistics.";
      }
      leaf statistic-mode {
        when "not(../../ifm:type='Virtual-Ethernet' or ../../ifm:type='Tunnel' or ../../ifm:type='NULL' or ../../ifm:type='LoopBack' or ../../ifm:type='Global-VE' or ../../ifm:type='Nve' or ../../ifm:type='Vlanif' or  ((../../ifm:type='PW-VE') and (../../ifm:class='main-interface')))" {
          tailf:xpath-root 3;
        }
        type statistic-mode-type;
        default "mac";
        description
          "Configure the traffic statistics mode.";
      }
      leaf mac-statistic-enable {
        when "../../ifm:class='main-interface' and ../../ifm:type!='Virtual-Ethernet' and ../../ifm:type!='Tunnel' and ../../ifm:type!='NULL' and ../../ifm:type!='LoopBack' and ../../ifm:type!='Global-VE' and ../../ifm:type!='Nve' and ../../ifm:type!='Vbdif' and ../../ifm:type!='Vlanif' and ../../ifm:type!='PW-VE'" {
          tailf:xpath-root 3;
        }
        type enable-type;
        default "disable";
        description
          "Enable the function of bit per seconds (bps) statistics.";
      }
    }
    container fim-ifm-mru {
      tailf:ncs-device-type "netconf";
      tailf:display-when "not(../../../../../ncs:module) or ../../../../../ncs:module[ncs:name='huawei-fim-ifm']";
      description
        "Configure the maximum receive unit.";
      leaf mru {
        when "../../ifm:type!='Virtual-Ethernet' and ../../ifm:type!='Tunnel' and ../../ifm:type!='NULL' and ../../ifm:type!='LoopBack' and ../../ifm:type!='Global-VE' and ../../ifm:type!='Nve' and ../../ifm:type!='FlexE-200GE' and ../../ifm:type!='FlexE-50G' and ../../ifm:type!='FlexE-100G' and ../../ifm:type!='FlexE-400G' and ../../ifm:type!='FlexE-50|100G'" {
          tailf:xpath-root 3;
        }
        type uint16 {
          range "46..9600";
        }
        units "Byte";
        must 'not(/ifm:ifm/ifm:interfaces/ifm:interface/fim-ifm:fim-tcp-mss/fim-ifm:tcp-mss)' {
          tailf:xpath-root 3;
        }
        description
          "Maximum receive unit of an interface.";
      }
      leaf mru-statistic-enable {
        when '../mru' {
          tailf:xpath-root 3;
        }
        type enable-type;
        default "disable";
        description
          "Enable discard statistics of maximum receive unit of an interface.";
      }
    }
    container fim-tcp-mss {
      tailf:ncs-device-type "netconf";
      tailf:display-when "not(../../../../../ncs:module) or ../../../../../ncs:module[ncs:name='huawei-fim-ifm']";
      description
        "Configure Tcp mss.";
      leaf tcp-mss {
        when "../../ifm:type!='Virtual-Ethernet' and ../../ifm:type!='Tunnel' and ../../ifm:type!='NULL' and ../../ifm:type!='LoopBack' and ../../ifm:type!='Global-VE' and ../../ifm:type!='Nve'" {
          tailf:xpath-root 3;
        }
        type uint16 {
          range "32..9500";
        }
        units "Byte";
        must '(not(/ifm:ifm/ifm:interfaces/ifm:interface/ethernet:ethernet/ethernet:main-interface/ethernet:l2-attribute) or not(../tcp-mss)) and not(/ifm:ifm/ifm:interfaces/ifm:interface/fim-ifm:fim-ifm-mru/fim-ifm:mru)' {
          tailf:xpath-root 3;
        }
        description
          "Maxitum Segment Size of an interface.";
      }
    }
    container fim-ifm-bdifint {
      tailf:ncs-device-type "netconf";
      tailf:display-when "not(../../../../../ncs:module) or ../../../../../ncs:module[ncs:name='huawei-fim-ifm']";
      when "../ifm:type='Vbdif'" {
        tailf:xpath-root 3;
      }
      description
        "Configure forward configurations to VBDIF interface.";
      leaf vbdif-loopback-enable {
        type boolean;
        default "false";
        description
          "Enable/disable the VBDIF loopback forward mode.";
      }
    }
    container fim-ifm-veint {
      tailf:ncs-device-type "netconf";
      tailf:display-when "not(../../../../../ncs:module) or ../../../../../ncs:module[ncs:name='huawei-fim-ifm']";
      description
        "Configure Virtual-Ethernet interface information.";
      leaf ve-forward-mode {
        when "(../../ifm:type='Virtual-Ethernet' and ../../fim-ifm:ve-group/fim-ifm:type='L2VE') or (../../ifm:type='Global-VE' and ../../fim-ifm:ve-group/fim-ifm:type='L2VE')" {
          tailf:xpath-root 3;
        }
        type ve-mode-type;
        default "loopback";
        description
          "Virtual-Ethernet forward mode type.";
      }
      leaf ve-slot-id {
        when "../../ifm:type='Global-VE' and ../../fim-ifm:ve-group/fim-ifm:type='L2VE'" {
          tailf:xpath-root 3;
        }
        type string {
          length "1..512";
        }
        description
          "Remove boards from a global VE interface.";
      }
    }
    container ve-group {
      tailf:ncs-device-type "netconf";
      tailf:display-when "not(../../../../../ncs:module) or ../../../../../ncs:module[ncs:name='huawei-fim-ifm']";
      when "../ifm:type='Virtual-Ethernet' or ../ifm:type='Global-VE'" {
        tailf:xpath-root 3;
      }
      presence "configure ve-group.";
      description
        "Enable/disable a Virtual-Ethernet Group.";
      leaf type {
        type ve-interface-type;
        mandatory true;
        description
          "Virtual-Ethernet interface type.";
        ext:operation-exclude "update" {
          description
            "The node cannot be modified when ve-group is configured.";
        }
      }
      leaf id {
        type uint32 {
          range "1..8192";
        }
        mandatory true;
        description
          "Virtual-Ethernet group ID.";
        ext:operation-exclude "update" {
          description
            "The node cannot be modified when ve-group is configured.";
        }
      }
    }
    // NCS drop config false container 'mru-discard-statistic'
    // NCS drop config false container 'macmtu-discard-stat'
  }
  augment "/ncs:devices/ncs:template/ncs:ned-id/ncs:config/ifm:ifm/ifm:global" {
    description
      "Global configuration to the interface management module.";
    container fim-ifm-global {
      description
        "Configure FIM global configurations.";
      leaf global-strict-filter {
        type ncs_template_enable-type;
        // NCS drop default statement
        description
          "Global filter enable status.";
      }
      leaf dual-stat-enable {
        type ncs_template_enable-type;
        // NCS drop default statement
        description
          "Set forward mode statistic for all interfaces.";
      }
      leaf trunk-delaysend-time {
        type string;
        units "ms";
        // NCS drop default statement
        description
          "Configure the delay time for an ETH-Trunk interface to join a member interface in a unicast scenario.";
      }
      leaf trunk-adjust-enable {
        type ncs_template_enable-type;
        // NCS drop default statement
        description
          "Enable the function of trunk load-blance dynamic-adjust.";
      }
      leaf qinq-transport-enable {
        type ncs_template_enable-type;
        // NCS drop default statement
        description
          "Configures Ethernet interfaces to retain the outer TPID EtherType value in received QinQ packets.";
      }
    }
    container fim-trunk-localfwd {
      description
        "Configure the function of trunk local forward.";
      leaf enable {
        type ncs_template_enable-type;
        // NCS drop default statement
        description
          "Trunk Local Forward enable status.";
      }
    }
    // NCS drop config false container 've-groups'
  }
  augment "/ncs:devices/ncs:device/ncs:live-status/ifm:ifm/ifm:global" {
    description
      "Global configuration to the interface management module.";
    container fim-ifm-global {
      tailf:ncs-device-type "netconf";
      tailf:display-when "not(../../../../ncs:module) or ../../../../ncs:module[ncs:name='huawei-fim-ifm'] or (../../../../ncs:live-status-protocol[not(ncs:capability)]) or (../../../../ncs:live-status-protocol/ncs:capability/ncs:module[.='huawei-fim-ifm'])";
      description
        "Configure FIM global configurations.";
      leaf global-strict-filter {
        type live_ncs_enable-type;
        // NCS drop default statement
        description
          "Global filter enable status.";
      }
      leaf dual-stat-enable {
        type live_ncs_enable-type;
        // NCS drop default statement
        description
          "Set forward mode statistic for all interfaces.";
      }
      leaf trunk-delaysend-time {
        type uint32 {
          range "1000..300000";
        }
        units "ms";
        // NCS drop default statement
        description
          "Configure the delay time for an ETH-Trunk interface to join a member interface in a unicast scenario.";
      }
      leaf trunk-adjust-enable {
        type live_ncs_enable-type;
        // NCS drop default statement
        description
          "Enable the function of trunk load-blance dynamic-adjust.";
      }
      leaf qinq-transport-enable {
        type live_ncs_enable-type;
        // NCS drop default statement
        description
          "Configures Ethernet interfaces to retain the outer TPID EtherType value in received QinQ packets.";
      }
    }
    container fim-trunk-localfwd {
      tailf:ncs-device-type "netconf";
      tailf:display-when "not(../../../../ncs:module) or ../../../../ncs:module[ncs:name='huawei-fim-ifm'] or (../../../../ncs:live-status-protocol[not(ncs:capability)]) or (../../../../ncs:live-status-protocol/ncs:capability/ncs:module[.='huawei-fim-ifm'])";
      description
        "Configure the function of trunk local forward.";
      leaf enable {
        type live_ncs_enable-type;
        // NCS drop default statement
        description
          "Trunk Local Forward enable status.";
      }
    }
    container ve-groups {
      tailf:ncs-device-type "netconf";
      tailf:display-when "not(../../../../ncs:module) or ../../../../ncs:module[ncs:name='huawei-fim-ifm'] or (../../../../ncs:live-status-protocol[not(ncs:capability)]) or (../../../../ncs:live-status-protocol/ncs:capability/ncs:module[.='huawei-fim-ifm'])";
      description
        "List of the relation of Virtual-Ethernet and ve-group.";
      list ve-group {
        key "ve-group-id slot-id";
        description
          "Operational state of the relation of Virtual-Ethernet and ve-group.";
        leaf ve-group-id {
          type uint32;
          description
            "VE-group id.";
        }
        leaf slot-id {
          type string {
            length "1..24";
          }
          description
            "Slot ID.";
        }
        leaf l2-ve-ifname {
          type pub-type:live_ncs_if-name;
          description
            "Terminate Virtual-Ethernet interface.";
        }
        leaf l3-ve-ifname {
          type pub-type:live_ncs_if-name;
          description
            "Access Virtual-Ethernet interface.";
        }
      }
    }
  }
  augment "/ncs:devices/ncs:device/ncs:config/ifm:ifm/ifm:global" {
    description
      "Global configuration to the interface management module.";
    container fim-ifm-global {
      tailf:ncs-device-type "netconf";
      tailf:display-when "not(../../../../ncs:module) or ../../../../ncs:module[ncs:name='huawei-fim-ifm']";
      description
        "Configure FIM global configurations.";
      leaf global-strict-filter {
        type enable-type;
        default "disable";
        description
          "Global filter enable status.";
      }
      leaf dual-stat-enable {
        type enable-type;
        default "disable";
        description
          "Set forward mode statistic for all interfaces.";
      }
      leaf trunk-delaysend-time {
        type uint32 {
          range "1000..300000";
        }
        units "ms";
        default "1500";
        description
          "Configure the delay time for an ETH-Trunk interface to join a member interface in a unicast scenario.";
      }
      leaf trunk-adjust-enable {
        type enable-type;
        default "disable";
        description
          "Enable the function of trunk load-blance dynamic-adjust.";
      }
      leaf qinq-transport-enable {
        type enable-type;
        default "disable";
        description
          "Configures Ethernet interfaces to retain the outer TPID EtherType value in received QinQ packets.";
      }
    }
    container fim-trunk-localfwd {
      tailf:ncs-device-type "netconf";
      tailf:display-when "not(../../../../ncs:module) or ../../../../ncs:module[ncs:name='huawei-fim-ifm']";
      description
        "Configure the function of trunk local forward.";
      leaf enable {
        type enable-type;
        default "disable";
        description
          "Trunk Local Forward enable status.";
      }
    }
    // NCS drop config false container 've-groups'
  }
}
