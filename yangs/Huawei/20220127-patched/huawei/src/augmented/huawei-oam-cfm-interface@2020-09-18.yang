module huawei-oam-cfm-interface {
  // Generated by yanger -t ncs
  tailf:mount-id "huawei-nc-1.0:huawei-nc-1.0";
  tailf:ncs-device-type "netconf";

  namespace "urn:huawei:yang:huawei-oam-cfm-interface";
  prefix oam-cfm-interface;

  import huawei-extension {
    prefix ext;
  }
  import huawei-oammgr {
    prefix oammgr;
  }
  import huawei-ifm {
    prefix ifm;
  }
  import huawei-y1731 {
    prefix y1731;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Configure the operation, administration and maintenance (OAM) association function.";

  revision 2020-09-18 {
    description
      "Initial revision.";
    reference "Huawei private.";
  }
  ext:task-name "oammgr";

  typedef ncs_template_cfm-bind-interface-type {
    type string;
    description
      "Binding type.";
  }

  typedef ncs_rpc_notif_cfm-bind-interface-type {
    type enumeration {
      enum "CFM-IF" {
        value 1;
        description
          "Type that CFM transfers fault information to interface.";
      }
      enum "IF-CFM" {
        value 2;
        description
          "Type that interface transfers fault information to CFM.";
      }
    }
    description
      "Binding type.";
  }

  typedef live_ncs_cfm-bind-interface-type {
    type enumeration {
      enum "CFM-IF" {
        value 1;
        description
          "Type that CFM transfers fault information to interface.";
      }
      enum "IF-CFM" {
        value 2;
        description
          "Type that interface transfers fault information to CFM.";
      }
    }
    description
      "Binding type.";
  }

  typedef cfm-bind-interface-type {
    type enumeration {
      enum "CFM-IF" {
        value 1;
        description
          "Type that CFM transfers fault information to interface.";
      }
      enum "IF-CFM" {
        value 2;
        description
          "Type that interface transfers fault information to CFM.";
      }
    }
    description
      "Binding type.";
  }

  augment "/ncs:devices/ncs:template/ncs:ned-id/ncs:config/oammgr:oammgr" {
    description
      "Configure the operation, administration and maintenance (OAM) association function.";
    container cfm-bind-interfaces {
      description
        "List of associations between CFM and interface.";
      list cfm-bind-interface {
        // NCS patched for predictable order
        ordered-by user;
        key "md-name ma-name if-name bind-type";
        unique "md-name ma-name bind-type";
        unique "if-name bind-type";
        description
          "Configure an instance of an association between CFM and interface.";
        leaf md-name {
          type string;
          description
            "Configure an MD name.";
        }
        leaf ma-name {
          type string;
          description
            "Configure an MA name.";
        }
        leaf if-name {
          type string;
          description
            "Configure the name of interface.";
        }
        leaf bind-type {
          type ncs_template_cfm-bind-interface-type;
          description
            "Configure a binding type.";
        }
      }
    }
  }
  augment "/ncs:devices/ncs:device/ncs:live-status/oammgr:oammgr" {
    description
      "Configure the operation, administration and maintenance (OAM) association function.";
    container cfm-bind-interfaces {
      tailf:ncs-device-type "netconf";
      tailf:display-when "not(../../../ncs:module) or ../../../ncs:module[ncs:name='huawei-oam-cfm-interface'] or (../../../ncs:live-status-protocol[not(ncs:capability)]) or (../../../ncs:live-status-protocol/ncs:capability/ncs:module[.='huawei-oam-cfm-interface'])";
      description
        "List of associations between CFM and interface.";
      list cfm-bind-interface {
        key "md-name ma-name if-name bind-type";
        unique "md-name ma-name bind-type";
        unique "if-name bind-type";
        description
          "Configure an instance of an association between CFM and interface.";
        leaf md-name {
          type leafref {
            path "/ncs:devices/ncs:device/ncs:live-status/y1731:y1731/y1731:global-enable/y1731:mds/y1731:md/y1731:name" {
              tailf:xpath-root 3;
            }
          }
          description
            "Configure an MD name.";
        }
        leaf ma-name {
          type leafref {
            path "/ncs:devices/ncs:device/ncs:live-status/y1731:y1731/y1731:global-enable/y1731:mds/y1731:md[y1731:name=current()/../md-name]/y1731:mas/y1731:ma/y1731:name" {
              tailf:xpath-root 3;
            }
          }
          description
            "Configure an MA name.";
        }
        leaf if-name {
          type leafref {
            path "/ncs:devices/ncs:device/ncs:live-status/ifm:ifm/ifm:interfaces/ifm:interface/ifm:name" {
              tailf:xpath-root 3;
            }
          }
          description
            "Configure the name of interface.";
        }
        leaf bind-type {
          type live_ncs_cfm-bind-interface-type;
          description
            "Configure a binding type.";
        }
      }
    }
  }
  augment "/ncs:devices/ncs:device/ncs:config/oammgr:oammgr" {
    description
      "Configure the operation, administration and maintenance (OAM) association function.";
    container cfm-bind-interfaces {
      tailf:ncs-device-type "netconf";
      tailf:display-when "not(../../../ncs:module) or ../../../ncs:module[ncs:name='huawei-oam-cfm-interface']";
      description
        "List of associations between CFM and interface.";
      list cfm-bind-interface {
        key "md-name ma-name if-name bind-type";
        unique "md-name ma-name bind-type";
        unique "if-name bind-type";
        description
          "Configure an instance of an association between CFM and interface.";
        leaf md-name {
          type leafref {
            path "/ncs:devices/ncs:device/ncs:config/y1731:y1731/y1731:global-enable/y1731:mds/y1731:md/y1731:name" {
              tailf:xpath-root 3;
            }
          }
          description
            "Configure an MD name.";
        }
        leaf ma-name {
          type leafref {
            path "/ncs:devices/ncs:device/ncs:config/y1731:y1731/y1731:global-enable/y1731:mds/y1731:md[y1731:name=current()/../md-name]/y1731:mas/y1731:ma/y1731:name" {
              tailf:xpath-root 3;
            }
          }
          description
            "Configure an MA name.";
        }
        leaf if-name {
          type leafref {
            path "/ncs:devices/ncs:device/ncs:config/ifm:ifm/ifm:interfaces/ifm:interface/ifm:name" {
              tailf:xpath-root 3;
            }
          }
          description
            "Configure the name of interface.";
        }
        leaf bind-type {
          type cfm-bind-interface-type;
          description
            "Configure a binding type.";
        }
      }
    }
  }
}
