module huawei-mplsoam-deviations-NE8000 {
  // Generated by yanger -t ncs
  tailf:mount-id "huawei-nc-1.0:huawei-nc-1.0";
  tailf:ncs-device-type "netconf";

  yang-version 1;
  namespace "urn:huawei:yang:huawei-mplsoam-deviations-NE8000";
  prefix mplsoam-devs-NE8000;

  import huawei-mplsoam {
    prefix mplsoam;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Multiprotocol Label Switching (MPLS) operations, administration and maintenance (OAM), provides the following functions: fault management, performance monitoring, and protection switching.";

  revision 2019-10-18 {
    description
      "Initial revision.";
    reference "Huawei private.";
  }

  deviation "/ncs:devices/ncs:device/ncs:live-status/mplsoam:mplsoam/mplsoam:global/mplsoam:oam-num" {
    deviate not-supported;
  }
  deviation "/ncs:devices/ncs:template/ncs:ned-id/ncs:config/mplsoam:mplsoam/mplsoam:tunnels" {
    deviate not-supported;
  }
  deviation "/ncs:devices/ncs:device/ncs:live-status/mplsoam:mplsoam/mplsoam:tunnels" {
    deviate not-supported;
  }
  deviation "/ncs:devices/ncs:device/ncs:config/mplsoam:mplsoam/mplsoam:tunnels" {
    deviate not-supported;
  }
  deviation "/ncs:devices/ncs:template/ncs:ned-id/ncs:config/mplsoam:mplsoam/mplsoam:vll-pws" {
    deviate not-supported;
  }
  deviation "/ncs:devices/ncs:device/ncs:live-status/mplsoam:mplsoam/mplsoam:vll-pws" {
    deviate not-supported;
  }
  deviation "/ncs:devices/ncs:device/ncs:config/mplsoam:mplsoam/mplsoam:vll-pws" {
    deviate not-supported;
  }
  deviation "/ncs:devices/ncs:template/ncs:ned-id/ncs:config/mplsoam:mplsoam/mplsoam:vsi-pws" {
    deviate not-supported;
  }
  deviation "/ncs:devices/ncs:device/ncs:live-status/mplsoam:mplsoam/mplsoam:vsi-pws" {
    deviate not-supported;
  }
  deviation "/ncs:devices/ncs:device/ncs:config/mplsoam:mplsoam/mplsoam:vsi-pws" {
    deviate not-supported;
  }
  deviation "/ncs:devices/ncs:device/ncs:rpc/mplsoam:rpc-enable-co-route-tunnel/mplsoam:enable-co-route-tunnel" {
    deviate not-supported;
  }
  deviation "/ncs:devices/ncs:device/ncs:rpc/mplsoam:rpc-disable-co-route-tunnel/mplsoam:disable-co-route-tunnel" {
    deviate not-supported;
  }
  deviation "/ncs:devices/ncs:device/ncs:rpc/mplsoam:rpc-enable-egress-id-tunnel-lsp/mplsoam:enable-egress-id-tunnel-lsp" {
    deviate not-supported;
  }
  deviation "/ncs:devices/ncs:device/ncs:rpc/mplsoam:rpc-disable-egress-id-tunnel-lsp/mplsoam:disable-egress-id-tunnel-lsp" {
    deviate not-supported;
  }
  deviation "/ncs:devices/ncs:device/ncs:rpc/mplsoam:rpc-enable-egress-name-tunnel-lsp/mplsoam:enable-egress-name-tunnel-lsp" {
    deviate not-supported;
  }
  deviation "/ncs:devices/ncs:device/ncs:rpc/mplsoam:rpc-disable-egress-name-tunnel-lsp/mplsoam:disable-egress-name-tunnel-lsp" {
    deviate not-supported;
  }
  deviation "/ncs:devices/ncs:device/ncs:rpc/mplsoam:rpc-enable-ingress-tunnel-lsp/mplsoam:enable-ingress-tunnel-lsp" {
    deviate not-supported;
  }
  deviation "/ncs:devices/ncs:device/ncs:rpc/mplsoam:rpc-disable-ingress-tunnel-lsp/mplsoam:disable-ingress-tunnel-lsp" {
    deviate not-supported;
  }
  deviation "/ncs:devices/ncs:device/ncs:rpc/mplsoam:rpc-enable-co-route-tunnel-lsp/mplsoam:enable-co-route-tunnel-lsp" {
    deviate not-supported;
  }
  deviation "/ncs:devices/ncs:device/ncs:rpc/mplsoam:rpc-disable-co-route-tunnel-lsp/mplsoam:disable-co-route-tunnel-lsp" {
    deviate not-supported;
  }
}
