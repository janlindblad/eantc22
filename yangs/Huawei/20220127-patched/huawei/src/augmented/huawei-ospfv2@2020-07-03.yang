module huawei-ospfv2 {
  // Generated by yanger -t ncs
  tailf:mount-id "huawei-nc-1.0:huawei-nc-1.0";
  tailf:ncs-device-type "netconf";

  namespace "urn:huawei:yang:huawei-ospfv2";
  prefix ospfv2;

  import huawei-ifm {
    prefix ifm;
  }
  import huawei-network-instance {
    prefix ni;
  }
  import huawei-l3vpn {
    prefix l3vpn;
  }
  import huawei-routing-policy {
    prefix rtp;
  }
  import huawei-acl {
    prefix acl;
  }
  import huawei-xpl {
    prefix xpl;
  }
  import huawei-pub-type {
    prefix pub-type;
  }
  import ietf-yang-types {
    prefix yang;
  }
  import huawei-extension {
    prefix ext;
  }
  import ietf-inet-types {
    prefix inet;
  }
  include huawei-ospfv2-type;
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "OSPFv2.";

  revision 2020-07-03 {
    description
      "Modify the must statement.";
    reference "Huawei private.";
  }
  revision 2020-07-01 {
    description
      "Add keychain-name pattern lower-only.";
    reference "Huawei private.";
  }
  revision 2020-03-28 {
    description
      "Add cost-binding and case.";
    reference "Huawei private.";
  }
  revision 2020-03-04 {
    description
      "Modify the description.";
    reference "Huawei private.";
  }
  revision 2020-03-03 {
    description
      "Modify the description.";
    reference "Huawei private.";
  }
  revision 2020-02-27 {
    description
      "Modify session-car and case.";
    reference "Huawei private.";
  }
  revision 2020-02-04 {
    description
      "Add session-car and case.";
    reference "Huawei private.";
  }
  revision 2019-12-26 {
    description
      "Reconstructing Yang file by yin mechanism.";
    reference "Huawei private.";
  }
  revision 2019-12-20 {
    description
      "Reconstructing Yang file by yin mechanism.";
    reference "Huawei private.";
  }
  revision 2019-12-16 {
    description
      "Reconstructing Yang file by yin mechanism.";
    reference "Huawei private.";
  }
  revision 2019-11-22 {
    description
      "Reconstructing Yang file by yin mechanism.";
    reference "Huawei private.";
  }
  revision 2019-11-15 {
    description
      "Reconstructing Yang file by yin mechanism.";
    reference "Huawei private.";
  }
  revision 2019-10-22 {
    description
      "Reconstructing Yang file by yin mechanism.";
    reference "Huawei private.";
  }
  revision 2019-04-04 {
    description
      "Initial revision.";
    reference "Huawei private.";
  }
  ext:task-name "ospf";

  grouping ncs_template_policy-type {
    description
      "Type of a filtering rule. The available options are ACL Name or ACL Number or IP Prefix List or Route policy.";
    choice policy-type {
      // NCS drop mandatory statement
      description
        "Type of a filtering rule.";
      case basic-acl {
        description
          "Apply basic ACL Name or ACL Number.";
        leaf name-or-num {
          type string;
          // NCS drop must statement
          description
            "Apply basic ACL Name or ACL Number.";
        }
      }
      case ip-prefix {
        description
          "Set the name of an IP prefix list.";
        leaf ip-prefix {
          type string;
          description
            "Set the name of an IP prefix list.";
        }
      }
      case route-policy {
        description
          "Set a route policy name.";
        leaf route-policy {
          type string;
          description
            "Set a route policy name.";
        }
      }
      case route-filter {
        description
          "Set a route filter name.";
        leaf route-filter {
          type string;
          description
            "Set a route filter name.";
        }
      }
    }
  }

  grouping ncs_rpc_notif_policy-type {
    description
      "Type of a filtering rule. The available options are ACL Name or ACL Number or IP Prefix List or Route policy.";
    choice policy-type {
      mandatory true;
      description
        "Type of a filtering rule.";
      case basic-acl {
        description
          "Apply basic ACL Name or ACL Number.";
        leaf name-or-num {
          type string;
          must "/acl:acl/acl:groups/acl:group[acl:identity=current()]/acl:type='basic'" {
            tailf:xpath-root 3;
          }
          description
            "Apply basic ACL Name or ACL Number.";
        }
      }
      case ip-prefix {
        description
          "Set the name of an IP prefix list.";
        leaf ip-prefix {
          type string;
          description
            "Set the name of an IP prefix list.";
        }
      }
      case route-policy {
        description
          "Set a route policy name.";
        leaf route-policy {
          type string;
          description
            "Set a route policy name.";
        }
      }
      case route-filter {
        description
          "Set a route filter name.";
        leaf route-filter {
          type string;
          description
            "Set a route filter name.";
        }
      }
    }
  }

  grouping live_ncs_policy-type {
    description
      "Type of a filtering rule. The available options are ACL Name or ACL Number or IP Prefix List or Route policy.";
    choice policy-type {
      // NCS drop mandatory statement
      description
        "Type of a filtering rule.";
      case basic-acl {
        description
          "Apply basic ACL Name or ACL Number.";
        leaf name-or-num {
          type leafref {
            path "/ncs:devices/ncs:device/ncs:live-status/acl:acl/acl:groups/acl:group/acl:identity" {
              tailf:xpath-root 3;
            }
          }
          // NCS drop must statement
          description
            "Apply basic ACL Name or ACL Number.";
        }
      }
      case ip-prefix {
        description
          "Set the name of an IP prefix list.";
        leaf ip-prefix {
          type leafref {
            path "/ncs:devices/ncs:device/ncs:live-status/rtp:routing-policy/rtp:ipv4-prefix-filters/rtp:ipv4-prefix-filter/rtp:name" {
              tailf:xpath-root 3;
            }
          }
          description
            "Set the name of an IP prefix list.";
        }
      }
      case route-policy {
        description
          "Set a route policy name.";
        leaf route-policy {
          type leafref {
            path "/ncs:devices/ncs:device/ncs:live-status/rtp:routing-policy/rtp:policy-definitions/rtp:policy-definition/rtp:name" {
              tailf:xpath-root 3;
            }
          }
          description
            "Set a route policy name.";
        }
      }
      case route-filter {
        description
          "Set a route filter name.";
        leaf route-filter {
          type leafref {
            path "/ncs:devices/ncs:device/ncs:live-status/xpl:xpl/xpl:route-filters/xpl:route-filter/xpl:name" {
              tailf:xpath-root 3;
            }
          }
          description
            "Set a route filter name.";
        }
      }
    }
  }

  grouping policy-type {
    description
      "Type of a filtering rule. The available options are ACL Name or ACL Number or IP Prefix List or Route policy.";
    choice policy-type {
      mandatory true;
      description
        "Type of a filtering rule.";
      case basic-acl {
        description
          "Apply basic ACL Name or ACL Number.";
        leaf name-or-num {
          type leafref {
            path "/ncs:devices/ncs:device/ncs:config/acl:acl/acl:groups/acl:group/acl:identity" {
              tailf:xpath-root 3;
            }
          }
          must "/acl:acl/acl:groups/acl:group[acl:identity=current()]/acl:type='basic'" {
            tailf:xpath-root 3;
          }
          description
            "Apply basic ACL Name or ACL Number.";
        }
      }
      case ip-prefix {
        description
          "Set the name of an IP prefix list.";
        leaf ip-prefix {
          type leafref {
            path "/ncs:devices/ncs:device/ncs:config/rtp:routing-policy/rtp:ipv4-prefix-filters/rtp:ipv4-prefix-filter/rtp:name" {
              tailf:xpath-root 3;
            }
          }
          description
            "Set the name of an IP prefix list.";
        }
      }
      case route-policy {
        description
          "Set a route policy name.";
        leaf route-policy {
          type leafref {
            path "/ncs:devices/ncs:device/ncs:config/rtp:routing-policy/rtp:policy-definitions/rtp:policy-definition/rtp:name" {
              tailf:xpath-root 3;
            }
          }
          description
            "Set a route policy name.";
        }
      }
      case route-filter {
        description
          "Set a route filter name.";
        leaf route-filter {
          type leafref {
            path "/ncs:devices/ncs:device/ncs:config/xpl:xpl/xpl:route-filters/xpl:route-filter/xpl:name" {
              tailf:xpath-root 3;
            }
          }
          description
            "Set a route filter name.";
        }
      }
    }
  }

  augment "/ncs:devices/ncs:device/ncs:rpc" {
    container rpc-clear-loop-detect {
      tailf:ncs-device-type "netconf";
      tailf:display-when "not(../../ncs:module) or ../../ncs:module[ncs:name='huawei-ospfv2']";
      tailf:action clear-loop-detect {
        tailf:actionpoint ncsproxy {
          tailf:internal;
        }
        description
          "Clear OSPF import route loop detect status and alarm.";
      }
    }
  }
  augment "/ncs:devices/ncs:device-group/ncs:ned-id/ncs:rpc" {
    container rpc-clear-loop-detect {
      tailf:ncs-device-type "netconf";
      tailf:display-when "/ncs:devices/ncs:device[ncs:name=current()/../../../ncs:member]/ncs:module[ncs:name='huawei-ospfv2']";
      tailf:action clear-loop-detect {
        tailf:actionpoint ncsproxy {
          tailf:internal;
        }
        description
          "Clear OSPF import route loop detect status and alarm.";
      }
    }
  }
  augment "/ncs:devices/ncs:device/ncs:config" {
    container ospfv2 {
      tailf:ncs-device-type "netconf";
      tailf:display-when "not(../../ncs:module) or ../../ncs:module[ncs:name='huawei-ospfv2']";
      description
        "Configure OSPFv2 config.";
      container check-rt-id {
        description
          "Configure automatic modification of conflicted router IDs. If enable, check and resolve OSPF router ID conflict.";
        leaf conflict-flag {
          type boolean;
          default "true";
          description
            "Enable/disable automatic modification of conflicted router IDs. If enable, check and resolve OSPF router ID conflict.";
        }
      }
      container advertise-max-cost {
        description
          "Configure OSPF LSA advertise max cost globally.";
        leaf enable {
          type boolean;
          default "false";
          description
            "Enable/disable OSPF LSAs to advertise max cost globally.";
        }
      }
      container session-car {
        must 'pir-interval>=cir-interval' {
          tailf:xpath-root 3;
        }
        must 'pbs-interval>=cbs-interval' {
          tailf:xpath-root 3;
        }
        description
          "Configure OSPF Session CAR.";
        leaf enable {
          type boolean;
          default "true";
          description
            "Enable/disable OSPF Session CAR.";
        }
        leaf cir-interval {
          type uint32 {
            range "0..1000000";
          }
          units "kbit/s";
          default "8";
          description
            "Specify the Session CAR CIR interval.";
        }
        leaf cbs-interval {
          type uint32 {
            range "0..1000000";
          }
          units "Byte";
          default "100000";
          description
            "Specify the Session CAR CBS interval.";
        }
        leaf pir-interval {
          type uint32 {
            range "0..1000000";
          }
          units "kbit/s";
          default "16000";
          description
            "Specify the Session CAR PIR interval.";
        }
        leaf pbs-interval {
          type uint32 {
            range "0..10000000";
          }
          units "Byte";
          default "9000000";
          description
            "Specify the Session CAR PBS interval.";
        }
      }
      container maxage-lsa-protect {
        description
          "Configure auto protect of purge LSA error for OSPF.";
        leaf disable {
          type boolean;
          default "false";
          description
            "Enable/disable auto protect of purge LSA error for OSPF.";
        }
      }
      container suppress-flap-intf {
        description
          "Configure OSPF suppress flapping interface.";
        leaf disable {
          type boolean;
          default "false";
          description
            "Enable/disable cancel the current setting or default setting.";
        }
      }
      container mib-binding {
        description
          "Configure MIB binding a OSPF process.";
        leaf process-id {
          type leafref {
            path "/ncs:devices/ncs:device/ncs:config/ni:network-instance/ni:instances/ni:instance/ospfv2:ospfv2/ospfv2:sites/ospfv2:site/ospfv2:process-id" {
              tailf:xpath-root 3;
            }
          }
          description
            "Process ID.";
        }
      }
      container flush-source-trace {
        description
          "Configure OSPF flush source trace globally.";
        leaf enable {
          type boolean;
          default "true";
          description
            "Enable/disable OSPF flush source trace globally.";
        }
        leaf vlink-enable {
          type boolean;
          default "true";
          description
            "Enable/disable OSPF vlink flush source trace globally.";
        }
        leaf port {
          type uint16 {
            range "1025..65535";
          }
          default "50122";
          description
            "Set OSPF flush source trace port allocated by huawei-pp4.The related CLI is 'display ip port info | inc UDP'.";
        }
        leaf vlink-port {
          type uint16 {
            range "1025..65535";
          }
          default "50123";
          description
            "Set OSPF vlink flush source trace port allocated by huawei-pp4.The related CLI is 'display ip port info | inc UDP'.";
        }
      }
      container system-control {
        description
          "Configure memory overload control and cpu overload control.";
        leaf cpu-overload-ctrl-enable {
          type boolean;
          default "true";
          description
            "Enable/disable cpu overload control.";
        }
        leaf mem-overload-ctrl-enable {
          type boolean;
          default "true";
          description
            "Enable/disable memory overload control.";
        }
      }
      container route-loop-detect {
        description
          "Configure OSPF import route loop detect.";
        leaf enable {
          type boolean;
          default "true";
          description
            "Enable/disable OSPF import route loop detect.";
        }
      }
    }
  }
  augment "/ncs:devices/ncs:device/ncs:live-status" {
    container ospfv2 {
      tailf:ncs-device-type "netconf";
      tailf:display-when "not(../../ncs:module) or ../../ncs:module[ncs:name='huawei-ospfv2'] or (../../ncs:live-status-protocol[not(ncs:capability)]) or (../../ncs:live-status-protocol/ncs:capability/ncs:module[.='huawei-ospfv2'])";
      description
        "Configure OSPFv2 config.";
      container check-rt-id {
        description
          "Configure automatic modification of conflicted router IDs. If enable, check and resolve OSPF router ID conflict.";
        leaf conflict-flag {
          type boolean;
          // NCS drop default statement
          description
            "Enable/disable automatic modification of conflicted router IDs. If enable, check and resolve OSPF router ID conflict.";
        }
      }
      container advertise-max-cost {
        description
          "Configure OSPF LSA advertise max cost globally.";
        leaf enable {
          type boolean;
          // NCS drop default statement
          description
            "Enable/disable OSPF LSAs to advertise max cost globally.";
        }
      }
      container session-car {
        // NCS drop must statement
        // NCS drop must statement
        description
          "Configure OSPF Session CAR.";
        leaf enable {
          type boolean;
          // NCS drop default statement
          description
            "Enable/disable OSPF Session CAR.";
        }
        leaf cir-interval {
          type uint32 {
            range "0..1000000";
          }
          units "kbit/s";
          // NCS drop default statement
          description
            "Specify the Session CAR CIR interval.";
        }
        leaf cbs-interval {
          type uint32 {
            range "0..1000000";
          }
          units "Byte";
          // NCS drop default statement
          description
            "Specify the Session CAR CBS interval.";
        }
        leaf pir-interval {
          type uint32 {
            range "0..1000000";
          }
          units "kbit/s";
          // NCS drop default statement
          description
            "Specify the Session CAR PIR interval.";
        }
        leaf pbs-interval {
          type uint32 {
            range "0..10000000";
          }
          units "Byte";
          // NCS drop default statement
          description
            "Specify the Session CAR PBS interval.";
        }
      }
      container maxage-lsa-protect {
        description
          "Configure auto protect of purge LSA error for OSPF.";
        leaf disable {
          type boolean;
          // NCS drop default statement
          description
            "Enable/disable auto protect of purge LSA error for OSPF.";
        }
      }
      container suppress-flap-intf {
        description
          "Configure OSPF suppress flapping interface.";
        leaf disable {
          type boolean;
          // NCS drop default statement
          description
            "Enable/disable cancel the current setting or default setting.";
        }
      }
      container mib-binding {
        description
          "Configure MIB binding a OSPF process.";
        leaf process-id {
          type leafref {
            path "/ncs:devices/ncs:device/ncs:live-status/ni:network-instance/ni:instances/ni:instance/ospfv2:ospfv2/ospfv2:sites/ospfv2:site/ospfv2:process-id" {
              tailf:xpath-root 3;
            }
          }
          description
            "Process ID.";
        }
      }
      container flush-source-trace {
        description
          "Configure OSPF flush source trace globally.";
        leaf enable {
          type boolean;
          // NCS drop default statement
          description
            "Enable/disable OSPF flush source trace globally.";
        }
        leaf vlink-enable {
          type boolean;
          // NCS drop default statement
          description
            "Enable/disable OSPF vlink flush source trace globally.";
        }
        leaf port {
          type uint16 {
            range "1025..65535";
          }
          // NCS drop default statement
          description
            "Set OSPF flush source trace port allocated by huawei-pp4.The related CLI is 'display ip port info | inc UDP'.";
        }
        leaf vlink-port {
          type uint16 {
            range "1025..65535";
          }
          // NCS drop default statement
          description
            "Set OSPF vlink flush source trace port allocated by huawei-pp4.The related CLI is 'display ip port info | inc UDP'.";
        }
      }
      container system-control {
        description
          "Configure memory overload control and cpu overload control.";
        leaf cpu-overload-ctrl-enable {
          type boolean;
          // NCS drop default statement
          description
            "Enable/disable cpu overload control.";
        }
        leaf mem-overload-ctrl-enable {
          type boolean;
          // NCS drop default statement
          description
            "Enable/disable memory overload control.";
        }
      }
      container route-loop-detect {
        description
          "Configure OSPF import route loop detect.";
        leaf enable {
          type boolean;
          // NCS drop default statement
          description
            "Enable/disable OSPF import route loop detect.";
        }
      }
    }
  }
  augment "/ncs:devices/ncs:template/ncs:ned-id/ncs:config" {
    container ospfv2 {
      description
        "Configure OSPFv2 config.";
      container check-rt-id {
        description
          "Configure automatic modification of conflicted router IDs. If enable, check and resolve OSPF router ID conflict.";
        leaf conflict-flag {
          type string;
          // NCS drop default statement
          description
            "Enable/disable automatic modification of conflicted router IDs. If enable, check and resolve OSPF router ID conflict.";
        }
      }
      container advertise-max-cost {
        description
          "Configure OSPF LSA advertise max cost globally.";
        leaf enable {
          type string;
          // NCS drop default statement
          description
            "Enable/disable OSPF LSAs to advertise max cost globally.";
        }
      }
      container session-car {
        // NCS drop must statement
        // NCS drop must statement
        description
          "Configure OSPF Session CAR.";
        leaf enable {
          type string;
          // NCS drop default statement
          description
            "Enable/disable OSPF Session CAR.";
        }
        leaf cir-interval {
          type string;
          units "kbit/s";
          // NCS drop default statement
          description
            "Specify the Session CAR CIR interval.";
        }
        leaf cbs-interval {
          type string;
          units "Byte";
          // NCS drop default statement
          description
            "Specify the Session CAR CBS interval.";
        }
        leaf pir-interval {
          type string;
          units "kbit/s";
          // NCS drop default statement
          description
            "Specify the Session CAR PIR interval.";
        }
        leaf pbs-interval {
          type string;
          units "Byte";
          // NCS drop default statement
          description
            "Specify the Session CAR PBS interval.";
        }
      }
      container maxage-lsa-protect {
        description
          "Configure auto protect of purge LSA error for OSPF.";
        leaf disable {
          type string;
          // NCS drop default statement
          description
            "Enable/disable auto protect of purge LSA error for OSPF.";
        }
      }
      container suppress-flap-intf {
        description
          "Configure OSPF suppress flapping interface.";
        leaf disable {
          type string;
          // NCS drop default statement
          description
            "Enable/disable cancel the current setting or default setting.";
        }
      }
      container mib-binding {
        description
          "Configure MIB binding a OSPF process.";
        leaf process-id {
          type string;
          description
            "Process ID.";
        }
      }
      container flush-source-trace {
        description
          "Configure OSPF flush source trace globally.";
        leaf enable {
          type string;
          // NCS drop default statement
          description
            "Enable/disable OSPF flush source trace globally.";
        }
        leaf vlink-enable {
          type string;
          // NCS drop default statement
          description
            "Enable/disable OSPF vlink flush source trace globally.";
        }
        leaf port {
          type string;
          // NCS drop default statement
          description
            "Set OSPF flush source trace port allocated by huawei-pp4.The related CLI is 'display ip port info | inc UDP'.";
        }
        leaf vlink-port {
          type string;
          // NCS drop default statement
          description
            "Set OSPF vlink flush source trace port allocated by huawei-pp4.The related CLI is 'display ip port info | inc UDP'.";
        }
      }
      container system-control {
        description
          "Configure memory overload control and cpu overload control.";
        leaf cpu-overload-ctrl-enable {
          type string;
          // NCS drop default statement
          description
            "Enable/disable cpu overload control.";
        }
        leaf mem-overload-ctrl-enable {
          type string;
          // NCS drop default statement
          description
            "Enable/disable memory overload control.";
        }
      }
      container route-loop-detect {
        description
          "Configure OSPF import route loop detect.";
        leaf enable {
          type string;
          // NCS drop default statement
          description
            "Enable/disable OSPF import route loop detect.";
        }
      }
    }
  }
  augment "/ncs:devices/ncs:template/ncs:ned-id/ncs:config/ni:network-instance/ni:instances/ni:instance/l3vpn:afs/l3vpn:af" {
    description
      "OSPF augment to L3VPN.";
    container ospf-import-rts {
      description
        "List of import route information from another routing protocol.";
      list ospf-import-rt {
        // NCS patched for predictable order
        ordered-by user;
        key "src-vrf process-id";
        description
          "Configure import route information from another routing protocol.";
        leaf src-vrf {
          type string;
          // NCS drop must statement
          description
            "VPN instance route information.";
        }
        leaf process-id {
          type string;
          description
            "Process ID.";
        }
        leaf valid-route {
          type string;
          // NCS drop default statement
          description
            "Enable/disable the valid routes.";
        }
        choice policy-type {
          description
            "Type of import route rule.";
          case route-policy {
            description
              "Set a route policy name.";
            leaf route-policy {
              type string;
              description
                "Set a route policy name.";
            }
          }
          case route-filter {
            description
              "Set a route filter name.";
            leaf route-filter {
              type string;
              description
                "Set a route filter name.";
            }
          }
        }
      }
    }
  }
  augment "/ncs:devices/ncs:device/ncs:live-status/ni:network-instance/ni:instances/ni:instance/l3vpn:afs/l3vpn:af" {
    description
      "OSPF augment to L3VPN.";
    container ospf-import-rts {
      tailf:ncs-device-type "netconf";
      tailf:display-when "not(../../../../../../../ncs:module) or ../../../../../../../ncs:module[ncs:name='huawei-ospfv2'] or (../../../../../../../ncs:live-status-protocol[not(ncs:capability)]) or (../../../../../../../ncs:live-status-protocol/ncs:capability/ncs:module[.='huawei-ospfv2'])";
      description
        "List of import route information from another routing protocol.";
      list ospf-import-rt {
        key "src-vrf process-id";
        description
          "Configure import route information from another routing protocol.";
        leaf src-vrf {
          type leafref {
            path "/ncs:devices/ncs:device/ncs:live-status/ni:network-instance/ni:instances/ni:instance/ni:name" {
              tailf:xpath-root 3;
            }
          }
          // NCS drop must statement
          description
            "VPN instance route information.";
        }
        leaf process-id {
          type uint32 {
            range "1..4294967295";
          }
          description
            "Process ID.";
        }
        leaf valid-route {
          type boolean;
          // NCS drop default statement
          description
            "Enable/disable the valid routes.";
        }
        choice policy-type {
          description
            "Type of import route rule.";
          case route-policy {
            description
              "Set a route policy name.";
            leaf route-policy {
              type leafref {
                path "/ncs:devices/ncs:device/ncs:live-status/rtp:routing-policy/rtp:policy-definitions/rtp:policy-definition/rtp:name" {
                  tailf:xpath-root 3;
                }
              }
              description
                "Set a route policy name.";
            }
          }
          case route-filter {
            description
              "Set a route filter name.";
            leaf route-filter {
              type leafref {
                path "/ncs:devices/ncs:device/ncs:live-status/xpl:xpl/xpl:route-filters/xpl:route-filter/xpl:name" {
                  tailf:xpath-root 3;
                }
              }
              description
                "Set a route filter name.";
            }
          }
        }
      }
    }
  }
  augment "/ncs:devices/ncs:device/ncs:config/ni:network-instance/ni:instances/ni:instance/l3vpn:afs/l3vpn:af" {
    description
      "OSPF augment to L3VPN.";
    container ospf-import-rts {
      tailf:ncs-device-type "netconf";
      tailf:display-when "not(../../../../../../../ncs:module) or ../../../../../../../ncs:module[ncs:name='huawei-ospfv2']";
      description
        "List of import route information from another routing protocol.";
      list ospf-import-rt {
        key "src-vrf process-id";
        description
          "Configure import route information from another routing protocol.";
        leaf src-vrf {
          type leafref {
            path "/ncs:devices/ncs:device/ncs:config/ni:network-instance/ni:instances/ni:instance/ni:name" {
              tailf:xpath-root 3;
            }
          }
          must '../src-vrf!=../../../../../ni:name' {
            tailf:xpath-root 3;
          }
          description
            "VPN instance route information.";
        }
        leaf process-id {
          type uint32 {
            range "1..4294967295";
          }
          description
            "Process ID.";
        }
        leaf valid-route {
          type boolean;
          default "false";
          description
            "Enable/disable the valid routes.";
        }
        choice policy-type {
          description
            "Type of import route rule.";
          case route-policy {
            description
              "Set a route policy name.";
            leaf route-policy {
              type leafref {
                path "/ncs:devices/ncs:device/ncs:config/rtp:routing-policy/rtp:policy-definitions/rtp:policy-definition/rtp:name" {
                  tailf:xpath-root 3;
                }
              }
              description
                "Set a route policy name.";
            }
          }
          case route-filter {
            description
              "Set a route filter name.";
            leaf route-filter {
              type leafref {
                path "/ncs:devices/ncs:device/ncs:config/xpl:xpl/xpl:route-filters/xpl:route-filter/xpl:name" {
                  tailf:xpath-root 3;
                }
              }
              description
                "Set a route filter name.";
            }
          }
        }
      }
    }
  }
  augment "/ncs:devices/ncs:template/ncs:ned-id/ncs:config/ni:network-instance/ni:instances/ni:instance" {
    description
      "OSPFv2 augment to L3VPN.";
    container ospfv2 {
      description
        "Configure OSPFv2.";
      container gtsm {
        // NCS drop when statement
        presence "Enable gtsm.";
        description
          "Configure the OSPF GTSM.";
        leaf hops {
          type string;
          // NCS drop mandatory statement
          description
            "Specifies the number of TTL hops to be detected.";
        }
        leaf nonstandard-multicast {
          type string;
          // NCS drop default statement
          description
            "Enable/disable sending Multicast packet with TTL as 255 and receive multicast packet TTL should be 1 or 255 to ((255 - configured hop) + 1).";
        }
      }
      container sites {
        // NCS drop when statement
        description
          "List of OSPF instance.";
        list site {
          // NCS patched for predictable order
          ordered-by user;
          key "process-id";
          description
            "Configure OSPF instance.";
          leaf process-id {
            type string;
            description
              "Process ID.";
          }
          leaf description {
            type string;
            description
              "Description of an OSPF process.";
          }
          leaf router-id {
            type string;
            description
              "Router ID. It is used to set the OSPF private ID.";
          }
          leaf opaque {
            type string;
            // NCS drop default statement
            description
              "Enable/disable the opaque LSA capability. After it is enabled, an OSPF process can generate the opaque LSA and receive the opaque LSA from the neighbor device.";
          }
          leaf rfc1583-compatible {
            type string;
            // NCS drop default statement
            description
              "Enable/disable the route selection rule that is compatible with RFC 1583.";
          }
          leaf silent-all-interface {
            type string;
            // NCS drop default statement
            description
              "Enable/disable to suppress all interfaces in an OSPF process from sending or receiving OSPF packets.";
          }
          leaf retransmission-limit {
            type string;
            // NCS drop default statement
            description
              "Enable/disable maximum retransmission.";
          }
          leaf retransmission-limit-value {
            // NCS drop when statement
            type string;
            // NCS drop default statement
            description
              "Maximum retransmission times.";
          }
          leaf safe-sync {
            type string;
            // NCS drop default statement
            description
              "Enable/disable safe synchronization.";
          }
          leaf traffic-adj {
            type string;
            // NCS drop default statement
            description
              "Enable/disable traffic adjust info.";
          }
          leaf traffic-adv {
            // NCS drop when statement
            type string;
            // NCS drop default statement
            description
              "Enable/disable traffic advertise info.";
          }
          leaf local-mt {
            // NCS drop when statement
            type string;
            // NCS drop must statement
            // NCS drop default statement
            description
              "Enable/disable local multicast topology.";
          }
          leaf advertise-mpls-lsr-id {
            type string;
            // NCS drop must statement
            // NCS drop default statement
            description
              "Enable/disable advertise MPLS LSR ID into multiple areas as an intra area route.";
          }
          leaf advertise-mpls-lsr-id-cost {
            // NCS drop when statement
            type string;
            // NCS drop default statement
            description
              "MPLS LSR ID link cost.";
          }
          leaf suppress-reachability {
            type string;
            // NCS drop default statement
            description
              "Enable/disable suppress reachability.";
          }
          leaf lsa-refresh {
            type string;
            // NCS drop default statement
            description
              "Enable/disable refresh the age of LSA with greater lsa age.";
          }
          leaf mpls-ldp-auto-flag {
            type ncs_template_proc-auto-cfg-state;
            // NCS drop default statement
            description
              "Enable LDP automatically on OSPF enabled interfaces, but need to set MPLS first.";
          }
          leaf lsdb-overflow-limit {
            type string;
            description
              "Maximum number of AS external LSAs allowed in the LSDB.";
          }
          leaf peer-flapping-suppress {
            type string;
            // NCS drop default statement
            description
              "Enable/disable peer flapping suppress feature.";
          }
          leaf shutdown {
            type string;
            // NCS drop must statement
            // NCS drop default statement
            description
              "Enable/disable shutdown OSPFv2 service.";
          }
          leaf sham-hello {
            type string;
            // NCS drop default statement
            description
              "Enable/disable peers keep alive by receiving any valid OSPF packet.";
          }
          leaf max-link-cost {
            type string;
            description
              "Set the max value of link cost.";
          }
          leaf maxage-lsa {
            type string;
            units "s";
            // NCS drop default statement
            description
              "Calculation of route delay when the OSPF LSA frequently flaps.";
          }
          container private-net {
            // NCS drop when statement
            description
              "Configure private network configuration of OSPF.";
            leaf eca-route {
              type string;
              // NCS drop default statement
              description
                "Enable/disable route type of the extended community attribute for VPN.";
            }
            choice route-tag {
              description
                "To set route tag value.";
              case disable {
                description
                  "To disable the using of the tag for loop detection.";
                leaf disable {
                  type empty;
                  description
                    "To disable the using of the tag for loop detection.";
                }
              }
              case value {
                description
                  "Tag of an imported VPN route.";
                leaf value {
                  type string;
                  description
                    "Tag of an imported VPN route. By default, the first two bytes of the tag value are fixed to be 0xD000, and the last two bytes are the local AS number of the local BGP. For example, if the AS number of BGP is 100, the default tag value in decimal notation is 3489661028.If not configed, the default is 0.";
                }
              }
            }
            leaf vpn-capability {
              type string;
              // NCS drop default statement
              description
                "Enable/disable route loop detection and directly calculate routes. When VPN multi instance is supported on the multi VPN instance CE (MCE) router, loop detection must be cancelled. It is applicable to only OSPF VPN instances.";
            }
            container domain-id {
              presence "ID of an OSPF domain.";
              description
                "Configure ID of an OSPF domain.";
              leaf domain-id {
                type string;
                // NCS drop mandatory statement
                description
                  "ID of an OSPF domain.";
              }
              leaf type {
                type ncs_template_domain-id-type;
                // NCS drop default statement
                description
                  "Type of an OSPF domain ID.";
              }
              leaf value {
                type pub-type:ncs_template_hex-binary;
                // NCS drop default statement
                description
                  "Value of an OSPF domain ID type.";
              }
            }
            container domain-id-secondarys {
              // NCS drop when statement
              description
                "List of ID of a secondary domain.";
              list domain-id-secondary {
                // NCS patched for predictable order
                ordered-by user;
                key "domain-id type value";
                description
                  "Configure ID of a secondary domain.";
                leaf domain-id {
                  type string;
                  description
                    "ID of an OSPF domain.";
                }
                leaf type {
                  type ncs_template_domain-id-type;
                  description
                    "Type of an OSPF domain ID.";
                }
                leaf value {
                  type pub-type:ncs_template_hex-binary;
                  description
                    "Value of an OSPF domain ID type.";
                }
              }
            }
          }
          container host-name {
            description
              "Configure OSPF host name.";
            leaf enable {
              type string;
              // NCS drop must statement
              // NCS drop default statement
              description
                "Enable/disable host name.";
            }
            leaf value {
              // NCS drop when statement
              type string;
              description
                "Set host name.";
            }
          }
          container bandwidth {
            description
              "Configure bandwidth.";
            leaf config-bw-enable {
              type string;
              // NCS drop default statement
              description
                "Enable/disable bandwidth config.";
            }
            leaf reference-value {
              type string;
              // NCS drop default statement
              description
                "Reference to the calculation of link costs.";
            }
          }
          container timer {
            description
              "Configure timer.";
            container lsa-arrival {
              description
                "Configure interval for receiving LSAs either through an intelligent timer or timer.";
              choice timer-type {
                // NCS drop default statement
                description
                  "Set a value for the LDP and OSPF synchronization timer.";
                case timer {
                  description
                    "Interval for receiving LSAs.";
                  leaf interval {
                    type string;
                    description
                      "Interval for receiving LSAs.";
                  }
                }
                case intelligent-timer {
                  description
                    "Specify an intelligent timer.";
                  leaf max-interval {
                    type string;
                    // NCS drop must statement
                    // NCS drop default statement
                    description
                      "Maximum interval for receiving OSPF LSAs.";
                  }
                  leaf start-interval {
                    type string;
                    // NCS drop must statement
                    // NCS drop default statement
                    description
                      "Initial interval for receiving OSPF LSAs.";
                  }
                  leaf hold-interval {
                    type string;
                    // NCS drop must statement
                    // NCS drop default statement
                    description
                      "Hold interval for receiving OSPF LSAs.";
                  }
                }
              }
            }
            container lsa-arr-supp-flap {
              description
                "Configure the delay timer for LSA acceptance.";
              leaf interval {
                type string;
                units "s";
                // NCS drop default statement
                description
                  "Specifies an interval for suppressing LSA advertising in case of route flapping. The value 0 indicates that LSA advertising is not suppressed.";
              }
              leaf threshold-count {
                type string;
                // NCS drop default statement
                description
                  "Value of the threshold of LSAs to be suppressed.";
              }
            }
            container lsa-originate {
              description
                "Configure interval for receiving LSAs either through an intelligent timer or timer.";
              leaf other-type-interval {
                type string;
                // NCS drop default statement
                description
                  "Specify an updating/originating interval for type3, type4 and type10 LSAs. Interval for updating the LSAs except OSPF router LSAs and network LSAs.";
              }
              choice timer-type {
                // NCS drop default statement
                description
                  "Specify an updating/originating interval for type3, type4 and type10 LSAs.";
                case intelligent-timer {
                  description
                    "Specify an intelligent timer for router LSA, network LSA, external LSA and NSSA LSA.";
                  leaf max-interval {
                    type string;
                    // NCS drop must statement
                    // NCS drop default statement
                    description
                      "Maximum interval for updating OSPF LSAs.";
                  }
                  leaf start-interval {
                    type string;
                    // NCS drop must statement
                    // NCS drop default statement
                    description
                      "Initial interval for updating OSPF LSAs.";
                  }
                  leaf hold-interval {
                    type string;
                    // NCS drop must statement
                    // NCS drop default statement
                    description
                      "Hold interval for updating OSPF LSAs.";
                  }
                }
              }
            }
            container lsa-org-supp-flap {
              description
                "Configure the delay timer for LSA generation.";
              leaf interval {
                type string;
                units "s";
                // NCS drop default statement
                description
                  "Specifies an interval for suppressing LSA advertising in case of route flapping. The value 0 indicates that LSA advertising is not suppressed.";
              }
              leaf threshold-count {
                type string;
                // NCS drop default statement
                description
                  "Value of the threshold of LSAs to be suppressed.";
              }
            }
            container spf-schedule {
              description
                "Configure the interval for SPF calculation.";
              choice schedule-type {
                // NCS drop default statement
                description
                  "SPF schedule interval.";
                case timer {
                  description
                    "Specify an updating/originating interval for type3, type4 and type10 LSAs.";
                  leaf interval {
                    type string;
                    units "s";
                    description
                      "Interval for OSPF SPF calculation. By adjusting the interval for SPF calculation, you can prevent the occupation of too many bandwidth and router resources caused by frequent network changes.";
                  }
                }
                case intelligent-timer {
                  description
                    "Specify an intelligent timer.";
                  leaf max-interval {
                    type string;
                    units "ms";
                    // NCS drop must statement
                    // NCS drop default statement
                    description
                      "Maximum interval for OSPF SPF calculation set through an intelligent timer. By adjusting the interval for SPF calculation, you can prevent the occupation of too many bandwidths and device resources caused by frequent network changes.";
                  }
                  leaf start-interval {
                    type string;
                    units "ms";
                    // NCS drop must statement
                    // NCS drop default statement
                    description
                      "Initial interval for OSPF SPF calculation set through an intelligent timer. By adjusting the interval for SPF calculation, you can prevent the occupation of too many bandwidth and router resources caused by frequent network changes.";
                  }
                  leaf hold-interval {
                    type string;
                    units "ms";
                    // NCS drop must statement
                    // NCS drop default statement
                    description
                      "Hold interval for OSPF SPF calculation set through an intelligent timer. By adjusting the interval for calculating SPF, you can prevent the occupation of too many bandwidth and router resources caused by frequent network changes.";
                  }
                  leaf conserv-flag {
                    type string;
                    // NCS drop default statement
                    description
                      "Enable/disable conservative mode.";
                  }
                }
                case millisecond {
                  description
                    "Specify an interval.";
                  leaf millisecond {
                    type string;
                    units "ms";
                    description
                      "Interval for OSPF SPF calculation. By adjusting the interval for SPF calculation, you can prevent the occupation of too many bandwidths and device resources caused by frequent network changes.";
                  }
                }
              }
            }
          }
          container bfd {
            description
              "Configure BFD in a OSPF process.";
            leaf enable {
              type string;
              // NCS drop default statement
              description
                "Enable/disable BFD in an OSPF process.";
            }
            leaf min-rx {
              type string;
              units "ms";
              description
                "Minimum interval for receiving BFD packets from the peer end. The range and default are based on PAF.";
            }
            leaf min-tx {
              type string;
              units "ms";
              description
                "Minimum interval for sending BFD packets to the peer end. The range and default are based on PAF.";
            }
            leaf detect-multiplier {
              type string;
              // NCS drop default statement
              description
                "Local detection multiplier.";
            }
            leaf incr-cost {
              type string;
              description
                "BFD sync cost.";
            }
            leaf frr-binding {
              type string;
              // NCS drop default statement
              description
                "Enable/disable bind FRR with BFD.";
            }
          }
          container metric-delay {
            // NCS drop when statement
            description
              "Configure metric delay in a OSPF process.";
            leaf adv-enable {
              type string;
              // NCS drop default statement
              description
                "Enable/disable metric delay advertisement.";
            }
            leaf suppress-timer {
              type string;
              units "s";
              // NCS drop default statement
              description
                "Metric delay suppress timer.";
            }
            leaf suppress-percent {
              type string;
              // NCS drop default statement
              description
                "Metric delay suppress percent threshold.";
            }
            leaf suppress-absolute {
              type string;
              // NCS drop default statement
              description
                "Metric delay suppress absolute threshold.";
            }
          }
          container bier {
            // NCS drop when statement
            description
              "Configure the bier.";
            leaf enable {
              type string;
              // NCS drop default statement
              description
                "Enable/disable the bier.";
            }
          }
          container stub-router {
            description
              "Configure stub router is used to configure the router as stub router.";
            leaf flag {
              type ncs_template_stub-router-flag;
              // NCS drop default statement
              description
                "Stub router. The router configured with the stub router command notifies other OSPF routers of not using the stub router to forward data by increasing the metric greater than 65535 of the links in the LSA that is generated by the router.";
            }
            leaf interval {
              // NCS drop when statement
              type string;
              // NCS drop default statement
              description
                "Interval for remaining as the stub router during the active/standby switchover of a router.";
            }
            leaf include-stub {
              // NCS drop when statement
              type string;
              // NCS drop default statement
              description
                "Enable/disable set maximum cost for router lsa stub link.";
            }
            leaf external-lsa {
              // NCS drop when statement
              type string;
              // NCS drop default statement
              description
                "Enable/disable set maximum cost for external lsa.";
            }
            leaf external-cost {
              // NCS drop when statement
              type string;
              // NCS drop default statement
              description
                "Advertise external LSAs with configured/default overriding metric.";
            }
            leaf summary-lsa {
              // NCS drop when statement
              type string;
              // NCS drop default statement
              description
                "Enable/disable set maximum cost for summary lsa.";
            }
            leaf summary-cost {
              // NCS drop when statement
              type string;
              // NCS drop default statement
              description
                "Advertise summary LSAs with configured/default overriding metric.";
            }
          }
          container bgp-ls {
            description
              "Configure BGP LS.";
            leaf enable {
              type string;
              // NCS drop must statement
              // NCS drop default statement
              description
                "Enable/disable BGP LS.";
            }
            leaf identifier {
              // NCS drop when statement
              type string;
              description
                "Topo identifier.";
            }
          }
          container import-limit {
            presence "Enable import-limit";
            description
              "Configure limits the maximum number of routes to be imported.";
            leaf max-number {
              type string;
              // NCS drop mandatory statement
              description
                "Maximum number of external routes that can be imported.";
            }
            leaf threshold-upper {
              type string;
              // NCS drop must statement
              // NCS drop default statement
              description
                "Upper threshold of the maximum number of routes that can be imported.";
            }
            leaf threshold-lower {
              type string;
              // NCS drop must statement
              // NCS drop default statement
              description
                "Lower threshold of the maximum number of routes that can be imported.";
            }
          }
          container spf-control {
            description
              "Configure SPF calculation control.";
            leaf max-load-balancing {
              type string;
              // NCS drop default statement
              description
                "Maximum number of the equal cost routes of the destination address in the routing table. The range and default are based on PAF.";
            }
          }
          container default-para {
            description
              "Configure default parameter.";
            choice cost {
              // NCS drop default statement
              description
                "Cost assigned to the ASE or NSSA LSA generated when an external route is imported.";
              case cost-value {
                description
                  "Default metric of the external routes imported by OSPF.";
                leaf cost-value {
                  type string;
                  // NCS drop default statement
                  description
                    "Default metric of the external routes imported by OSPF.";
                }
              }
              case cost-inherit-metric {
                description
                  "Cost of the imported route is the cost carried in the route. If the cost is not specified, the default cost can be set through the default command.";
                leaf cost-inherit-metric {
                  type empty;
                  description
                    "Cost of the imported route is the cost carried in the route. If the cost is not specified, the default cost can be set through the default command.";
                }
              }
            }
            leaf tag {
              type string;
              // NCS drop default statement
              description
                "Tag of an external route.";
            }
            leaf type {
              type ncs_template_external-route-type;
              // NCS drop default statement
              description
                "Type of an external route.";
            }
          }
          container avoid-micro-loop {
            description
              "Configure OSPF avoid microloop.";
            leaf frr-enable {
              type string;
              // NCS drop default statement
              description
                "Enable/disable avoid microloop.";
            }
            leaf frr-rib-update-delay {
              type string;
              units "ms";
              // NCS drop default statement
              description
                "Set the maximum interval of delay timer.";
            }
            leaf te-tunnel-enable {
              type string;
              // NCS drop default statement
              description
                "Enable/disable TE shortcut tunnel avoid microloop.";
            }
            leaf te-tunnel-rib-update-delay {
              type string;
              units "ms";
              // NCS drop default statement
              description
                "Set the route delivery delay for TE shortcut tunnel.";
            }
          }
          container asbr-summary-prefixs {
            description
              "List of aggregate addresses for OSPF (only for ASBR).";
            list asbr-summary-prefix {
              // NCS patched for predictable order
              ordered-by user;
              key "prefix network-mask";
              description
                "Configure aggregate addresses for OSPF (only for ASBR).";
              leaf prefix {
                type string;
                description
                  "IP address. Prefix is the address after mask.";
              }
              leaf network-mask {
                type string;
                description
                  "IP address mask.";
              }
              leaf cost {
                type string;
                description
                  "Specifies the cost of the aggregated route.";
              }
              leaf distribute-delay {
                type string;
                units "s";
                description
                  "Distribute delay interval.";
              }
              leaf tag {
                type string;
                description
                  "Specifies that the tag is mainly used to control advertisement of routes through the routing policy.";
              }
              leaf advertise {
                type string;
                // NCS drop default statement
                description
                  "Enable/disable the aggregated route is advertised.";
              }
              leaf generate-null-zero {
                // NCS drop when statement
                type string;
                // NCS drop default statement
                description
                  "Enable/disable generate black hole route.";
              }
            }
          }
          choice default-route {
            description
              "Notification of default routes to the OSPF routing area.";
            case summary {
              description
                "Summary.";
              container summary {
                // NCS drop when statement
                presence "Enable default-route-advertise summary.";
                description
                  "Configure advertises the type3 summary LSAs of the specified default route.";
                leaf cost {
                  type string;
                  // NCS drop mandatory statement
                  description
                    "Metric of an ASE LSA.";
                }
              }
            }
            case no-summary {
              description
                "No summary.";
              container no-summary {
                presence "Enable default-route-advertise no-summary.";
                description
                  "Configure default routes to the OSPF routing area.";
                leaf enable {
                  type empty;
                  status deprecated;
                  description
                    "Default Route Enable. The node enable is deprecated. You are advised to use the node no-summary.";
                }
                leaf cost {
                  type string;
                  description
                    "Metric of an ASE LSA.";
                }
                leaf tag {
                  type string;
                  description
                    "Route tag for default imported routes.";
                }
                leaf type {
                  type ncs_template_external-route-type;
                  description
                    "Metric type of an ASE LSA for the default routes.";
                }
                leaf distribute-delay {
                  type string;
                  description
                    "Distribute delay timer used for the local router to calculate the default routes advertised by other routers.";
                }
                choice mode {
                  description
                    "Mode for default route.";
                  case permit-calculate-other {
                    description
                      "Set permit calculate other.";
                    leaf permit-calculate-other {
                      type empty;
                      description
                        "To generate and advertise an ASE LSA that describes the default route only when there are valid default routes of other protocols in the routing table of the host. The router configured with permit calculate other still calculates the default routes of other routers.";
                    }
                    leaf permit-ibgp {
                      type empty;
                      description
                        "Match IBGP default route.";
                    }
                  }
                  case always {
                    description
                      "Set always.";
                    leaf always {
                      type empty;
                      description
                        "The router configured with the always parameter does not calculate the default routes of other routers.";
                    }
                  }
                }
                choice policy-type {
                  description
                    "Mode of the policy used for default route.";
                  case route-policy-name {
                    description
                      "Set a route policy name.";
                    leaf route-policy-name {
                      type string;
                      description
                        "Name of a routing policy. Through the routing policy, the device matches the default routing entry generated by the device that does not run OSPF in the routing table, and advertises the default route according to the parameters set through the routing policy.";
                    }
                  }
                  case route-filter-name {
                    description
                      "Set a route filter name.";
                    leaf route-filter-name {
                      type string;
                      description
                        "Name of a routing Filter.";
                    }
                  }
                }
              }
            }
          }
          container route-preferences {
            description
              "List of preference of an OSPF route.";
            list route-preference {
              // NCS patched for predictable order
              ordered-by user;
              key "route-type";
              // NCS drop max-elements statement
              ext:generated-by "system" {
                ext:filter "route-type='default' or route-type='ase'";
              }
              description
                "Configure preference of an OSPF route.";
              leaf route-type {
                type ncs_template_ospf-route-type;
                description
                  "Router type.";
              }
              leaf preference {
                type string;
                ext:dynamic-default {
                  ext:default-value "10" {
                    // NCS drop when statement
                    description
                      "The default value is 10 when route type is not ase.";
                  }
                  ext:default-value "150" {
                    // NCS drop when statement
                    description
                      "The default value is 150 when route type is ase.";
                  }
                }
                description
                  "Preference of an OSPF route. The default of intra and inter area is 10.And The default of external is 150.";
              }
              choice policy-type {
                description
                  "Type of a filtering rule.";
                case route-policy-name {
                  description
                    "Name of a routing policy.";
                  leaf route-policy-name {
                    type string;
                    description
                      "Name of a routing policy.";
                  }
                }
                case route-filter-name {
                  description
                    "Name of a routing Filter.";
                  leaf route-filter-name {
                    type string;
                    description
                      "Name of a routing Filter.";
                  }
                }
              }
            }
          }
          container nexthop-weights {
            description
              "List of preference of an equal cost route.";
            list nexthop-weight {
              // NCS patched for predictable order
              ordered-by user;
              key "ip-address";
              description
                "Configure preference of an equal cost route.";
              leaf ip-address {
                type string;
                description
                  "IP address of the next hop.";
              }
              leaf weight {
                type string;
                // NCS drop mandatory statement
                description
                  "Weight of the next hop. After OSPF calculates the equal cost routes, the next hop is chosen from these equal cost routes based on the value of weight. The smaller the value is, the higher the preference is. By default, the weight is 255. This indicates that load balancing is carried out among equal cost routes and packets are forwarded at the same time without the preference being set.";
              }
            }
          }
          container prefix-prioritys {
            description
              "List of priority of OSPF route.";
            list prefix-priority {
              // NCS patched for predictable order
              ordered-by user;
              key "priority";
              description
                "Configure priority of OSPF route.";
              leaf priority {
                type ncs_template_prefix-priority;
                description
                  "Convergence priority of OSPF routes.";
              }
              leaf ip-prefix {
                type string;
                // NCS drop mandatory statement
                description
                  "Name of the IP prefix list. The value is a string of 1 to 169 characters without spaces. The prefix priority command sets the convergence priority of OSPF routes according to the specified IP prefix list name, and takes effect on the public network only.
                   By default, the convergence priority of public OSPF host routes is medium, the convergence priority of directly connected routes is high, the convergence priority of static routes is medium, and the convergence priority of the routes of other protocols (such as BGP and RIP) is low. On the private network, OSPF 32 bit host routes are globally identified as medium.";
              }
            }
          }
          container ecmp-prefer {
            description
              "Configure equal cost multipath preference of OSPF routes.";
            leaf te-tunnel {
              type string;
              // NCS drop must statement
              // NCS drop default statement
              description
                "Enable/disable TE tunnel interface nexthops.";
            }
            leaf intact {
              type string;
              // NCS drop must statement
              // NCS drop default statement
              description
                "Enable/disable IGP native nexthop.";
            }
          }
          container frr {
            description
              "Configure OSPF fast rerouting.";
            leaf enable {
              type string;
              // NCS drop default statement
              description
                "Enable/disable FRR for this particular process.";
            }
            leaf lfa-enable {
              type string;
              // NCS drop must statement
              // NCS drop default statement
              description
                "Enable/disable loop free alternate.";
            }
            leaf rlfa-enable {
              type string;
              // NCS drop must statement
              // NCS drop default statement
              description
                "Enable/disable remote lfa.";
            }
            leaf rlfa-max-cost {
              // NCS drop when statement
              type string;
              // NCS drop default statement
              description
                "Remote lfa tunnel ldp maximum-reachable-cost.";
            }
            leaf tilfa-enable {
              type string;
              // NCS drop must statement
              // NCS drop default statement
              description
                "Enable/disable TILFA.";
            }
            container tiebreaker {
              // NCS drop when statement
              // NCS drop must statement
              // NCS drop must statement
              // NCS drop must statement
              description
                "Configure tiebreaker for multiple backups.";
              leaf node-protect {
                type string;
                // NCS drop default statement
                description
                  "Set the value of node protect preference. The preference value 5 is reserved for SRLG disjoint type, cannot be configured.";
              }
              leaf lowest-cost {
                type string;
                // NCS drop default statement
                description
                  "Set the value of lowcost preference.";
              }
              leaf ldp-sync {
                type string;
                // NCS drop default statement
                description
                  "Prefer backup nexthop with ldp sync.";
              }
            }
            container route-policy {
              // NCS drop when statement
              description
                "Configure FRR route policy.";
              choice policy-type {
                description
                  "Type of a filtering rule.";
                case route-policy-name {
                  description
                    "Name of a routing policy.";
                  leaf route-policy-name {
                    type string;
                    description
                      "Name of a routing policy.";
                  }
                }
                case route-filter-name {
                  description
                    "Name of a routing filter.";
                  leaf route-filter-name {
                    type string;
                    description
                      "Name of a routing filter.";
                  }
                }
              }
            }
            container rlfa-tunnel {
              // NCS drop when statement
              description
                "Configure remote LFA ip prefix.";
              choice policy-type {
                description
                  "Name of a routing policy.";
                case ip-prefix-name {
                  description
                    "Set a route policy name.";
                  leaf ip-prefix-name {
                    type string;
                    description
                      "To filter PQ node. Those nodes which don't pass filter can't be PQ node.";
                  }
                }
              }
            }
          }
          container local-mt-filter {
            // NCS drop when statement
            description
              "Configure OSPF local multicast topology filtering in routing updates.";
            choice filter-policy {
              description
                "Type of a filtering rule.";
              case acl-name-or-num {
                description
                  "ACL name or ACL number. ACL name: specify the ACL name. ACL num: apply basic ACL.";
                leaf acl-name-or-num {
                  type string;
                  // NCS drop must statement
                  description
                    "ACL name or ACL number. ACL name: specify the ACL name. ACL num: apply basic ACL.";
                }
              }
              case ip-prefix {
                description
                  "Ip prefix name.";
                leaf ip-prefix {
                  type string;
                  description
                    "Ip prefix name.";
                }
              }
              case route-policy-name {
                description
                  "Name of a routing policy.";
                leaf route-policy-name {
                  type string;
                  description
                    "Name of a routing policy.";
                }
              }
              case route-filter-name {
                description
                  "Name of a routing filter.";
                leaf route-filter-name {
                  type string;
                  description
                    "Name of a routing filter.";
                }
              }
            }
          }
          container peers {
            description
              "List of the IP address and DR priority of the neighbor router on the NBMA network.";
            list peer {
              // NCS patched for predictable order
              ordered-by user;
              key "ip-address";
              description
                "Configure the IP address and DR priority of the neighbor router on the NBMA network.";
              leaf ip-address {
                type string;
                description
                  "IP address of the neighbor router.";
              }
              leaf priority {
                type string;
                // NCS drop default statement
                description
                  "To set the IP address and DR priority of the neighbor router on the NBMA network.";
              }
            }
          }
          container filter-lsa-outs {
            description
              "List of LSA filter policy.";
            list filter-lsa-out {
              // NCS patched for predictable order
              ordered-by user;
              key "peer-ip-addr";
              // NCS drop max-elements statement
              description
                "Configure LSA filter policy.";
              leaf peer-ip-addr {
                type string;
                description
                  "IP address of the P2MP neighbor.";
              }
              choice type {
                // NCS drop mandatory statement
                description
                  "Set filter lsa out type.";
                case total {
                  description
                    "Filter total types of LSAs.";
                  leaf all-flag {
                    type empty;
                    description
                      "Filter all types of LSAs.";
                  }
                }
                case other {
                  description
                    "Filter other types of LSAs.";
                  leaf sum-flag {
                    type empty;
                    description
                      "Filter type 3 Summary LSAs.";
                  }
                  choice sum-filter {
                    description
                      "Type of a filtering rule.";
                    case sum-acl-name {
                      description
                        "ACL Name or ACL Number. ACL Name: specify the ACL name. ACL Num: apply basic ACL.";
                      leaf sum-acl-name {
                        // NCS drop when statement
                        type string;
                        // NCS drop must statement
                        description
                          "ACL Name or ACL Number. ACL Name: specify the ACL name. ACL Num: apply basic ACL.";
                      }
                    }
                  }
                  leaf ase-flag {
                    type empty;
                    description
                      "Filter type-5 ASE LSAs.";
                  }
                  choice ase-filter {
                    description
                      "Type of a filtering rule.";
                    case ase-acl-name {
                      description
                        "ACL Name or ACL Number. ACL Name: specify the ACL name. ACL Num: apply basic ACL.";
                      leaf ase-acl-name {
                        // NCS drop when statement
                        type string;
                        // NCS drop must statement
                        description
                          "ACL Name or ACL Number. ACL Name: specify the ACL name. ACL Num: apply basic ACL.";
                      }
                    }
                  }
                  leaf nssa-flag {
                    type empty;
                    description
                      "Filter type7 NSSA LSAs.";
                  }
                  choice nssa-filter {
                    description
                      "Type of a filtering rule.";
                    case nssa-acl-name {
                      description
                        "ACL Name or ACL Number. ACL Name: specify the ACL name. ACL Num: apply basic ACL.";
                      leaf nssa-acl-name {
                        // NCS drop when statement
                        type string;
                        // NCS drop must statement
                        description
                          "ACL Name or ACL Number. ACL Name: specify the ACL name. ACL Num: apply basic ACL.";
                      }
                    }
                  }
                }
              }
            }
          }
          choice graceful-restart {
            description
              "Information about OSPF GR.";
            case gr-ietf {
              description
                "Information about OSPF IETF GR.";
              container gr-ietf {
                // NCS drop when statement
                presence "Enable OSPF IETF GR.";
                description
                  "Configure OSPF IETF GR.";
                choice helper-role-mode {
                  description
                    "Information about OSPF IETF GR helper role.";
                  case never {
                    description
                      "Forbid to support enable mode.";
                    leaf never {
                      type empty;
                      description
                        "Forbid to support enable mode.";
                    }
                  }
                  case work-mode {
                    description
                      "Information about OSPF IETF GR.";
                    leaf planned-only {
                      type empty;
                      description
                        "To support only planned GR on routers.";
                    }
                    leaf ignore-external-lsa {
                      type empty;
                      description
                        "Ignore external lsa check (type5 and type7 LSAs).";
                    }
                    choice match-mode {
                      description
                        "Name of a routing policy.";
                      case acl-name-or-num {
                        description
                          "Specify the basic ACL number or ACL name for filtering peer.";
                        leaf acl-name-or-num {
                          type string;
                          // NCS drop must statement
                          description
                            "Specify the basic ACL number or ACL name for filtering peer.";
                        }
                      }
                      case ip-prefix-name {
                        description
                          "Specify the IP prefix name for filtering peers.";
                        leaf ip-prefix-name {
                          type string;
                          description
                            "Specify the IP prefix name for filtering peers.";
                        }
                      }
                    }
                  }
                }
              }
            }
            case gr-non-ietf {
              description
                "Information about OSPF NON IETF GR.";
              container gr-non-ietf {
                // NCS drop when statement
                presence "Enable OSPF NON IETF GR.";
                description
                  "Configure OSPF NON IETF GR.";
              }
            }
          }
          container flood-control {
            presence "Enable flood-control";
            description
              "Configure OSPF flooding control.";
            leaf number {
              type string;
              // NCS drop default statement
              description
                "Specify the update packet number to send.";
            }
            leaf interval {
              type string;
              // NCS drop default statement
              description
                "Specify the update packet timer interval to send.";
            }
          }
          container dn-bit {
            // NCS drop when statement
            description
              "Configure VPN optionA feature will help PEs in inter AS exchange routes through OSPF. VPN optionA provide two ways to suppress DN bit so that so that inter AS can exchange routes through OSPF. First way dose not set DN bit while import routes from BGP, second way dose not check DN bit while learning the routes from neighbor router. In both the scenario PE will be able to learn route and propagate the route in the new VPN cloud.";
            leaf set-ase {
              type string;
              // NCS drop default statement
              description
                "Enable/disable setting of DN bit in all ASE LSA, applicable in private network.";
            }
            leaf set-nssa {
              type string;
              // NCS drop default statement
              description
                "Enable/disable setting of DN bit in all NSSA LSA, applicable in private network.";
            }
            leaf set-summary {
              type string;
              // NCS drop default statement
              description
                "Enable/disable setting of DN bit in all summary LSA, applicable in private network.";
            }
            leaf check-ase {
              type string;
              // NCS drop default statement
              description
                "Enable/disable checking of DN bit in all ASE LSA, applicable in private network.";
            }
            leaf check-nssa {
              type string;
              // NCS drop default statement
              description
                "Enable/disable checking of DN bit in all NSSA LSA, applicable in private network.";
            }
            leaf check-summary {
              type string;
              // NCS drop default statement
              description
                "Enable/disable checking of DN bit in all summary LSA, applicable in private network.";
            }
            container summary-router-ids {
              // NCS drop when statement
              description
                "List of router ID for which checking for DN bit summary LSA is disabled, applicable in private network.";
              list summary-router-id {
                // NCS patched for predictable order
                ordered-by user;
                key "router-id";
                description
                  "Configure router ID for which checking for DN bit summary LSA is disabled, applicable in private network.";
                leaf router-id {
                  type string;
                  description
                    "Router ID for which checking for DN bit summary LSA is disabled, applicable in private network.";
                }
              }
            }
          }
          container filter-import {
            presence "filter policy import";
            description
              "Configure the filter policy import command. You can set the rules for filtering intra area, inter area, and AS external routes of an OSPF process.";
            choice policy-type {
              // NCS drop mandatory statement
              description
                "Type of a filtering rule.";
              case basic-acl {
                description
                  "Apply basic ACL name or ACL number.";
                leaf name-or-num {
                  type string;
                  // NCS drop must statement
                  description
                    "Apply basic ACL name or ACL number.";
                }
              }
              case ip-prefix {
                description
                  "Set the name of an IP prefix list.";
                leaf ip-prefix {
                  type string;
                  description
                    "Set the name of an IP prefix list.";
                }
              }
              case route-policy {
                description
                  "Set a route policy name.";
                leaf route-policy {
                  type string;
                  description
                    "Set a route policy name.";
                }
              }
              case route-filter {
                description
                  "Set a route filter name.";
                leaf route-filter {
                  type string;
                  description
                    "Set a route filter name.";
                }
              }
            }
            leaf secondary {
              type string;
              // NCS drop must statement
              // NCS drop default statement
              description
                "Enable/disable secondary flag.";
            }
          }
          container filter-exports {
            description
              "List of the filter policy export command. You can set the rules for filtering the routes imported through the import route (OSPF) command when the routes are advertised in type5 LSAs to the OSPF AS.";
            list filter-export {
              // NCS patched for predictable order
              ordered-by user;
              key "protocol protocol-id";
              description
                "Configure the filter policy export command. You can set the rules for filtering the routes imported through the import route (OSPF) command when the routes are advertised in type5 LSAs to the OSPF AS.";
              leaf protocol {
                type ncs_template_filter-rt-protocol;
                description
                  "Protocol that advertises routes.";
              }
              leaf protocol-id {
                type string;
                // NCS drop must statement
                description
                  "Process ID when the advertised protocol is RIP, ISIS, or OSPF.";
              }
              choice policy-type {
                // NCS drop mandatory statement
                description
                  "Type of a filtering rule.";
                case basic-acl {
                  description
                    "Apply basic ACL name or ACL number.";
                  leaf name-or-num {
                    type string;
                    // NCS drop must statement
                    description
                      "Apply basic ACL name or ACL number.";
                  }
                }
                case ip-prefix {
                  description
                    "Set the name of an IP prefix list.";
                  leaf ip-prefix {
                    type string;
                    description
                      "Set the name of an IP prefix list.";
                  }
                }
                case route-policy {
                  description
                    "Set a route policy name.";
                  leaf route-policy {
                    type string;
                    description
                      "Set a route policy name.";
                  }
                }
              }
            }
          }
          container import-routes {
            description
              "List of import the routes learned from other routing protocols.";
            list import-route {
              // NCS patched for predictable order
              ordered-by user;
              key "protocol process-id";
              description
                "Configure import the routes learned from other routing protocols.";
              leaf protocol {
                type ncs_template_import-rt-protocol;
                description
                  "Routing protocol whose routes are imported.";
              }
              leaf process-id {
                type string;
                // NCS drop must statement
                description
                  "Process ID of the routing protocol whose routes are imported. It needs to be set only when the protocol is RIP, OSPF, or ISIS.";
              }
              leaf cost {
                type string;
                description
                  "Route cost.";
              }
              leaf tag {
                type string;
                description
                  "Route tag of an external LSA.";
              }
              leaf type {
                type ncs_template_external-route-type;
                description
                  "Metric type of an external LSA.";
              }
              leaf permit-ibgp {
                type string;
                // NCS drop must statement
                // NCS drop default statement
                description
                  "Enable/disable to import IBGP routes.";
              }
              choice policy-type {
                description
                  "Type of a filtering rule.";
                case route-policy-name {
                  description
                    "Name of a routing policy.";
                  leaf route-policy-name {
                    type string;
                    description
                      "Name of a routing policy.";
                  }
                }
              }
            }
          }
          container silent-interfaces {
            // NCS drop when statement
            description
              "List of interface. To prevent the OSPF routing information from being received by routers in a network segment and forbid the local router to receive the routing update information that is advertised by other routers in the network segment, you can use the silent interface command to suppress the interface to receive or send the OSPF packets.";
            list silent-interface {
              // NCS patched for predictable order
              ordered-by user;
              key "if-name";
              description
                "Configure interface. To prevent the OSPF routing information from being received by routers in a network segment and forbid the local router to receive the routing update information that is advertised by other routers in the network segment, you can use the silent interface command to suppress the interface to receive or send the OSPF packets.";
              leaf if-name {
                type string;
                description
                  "Interface name.";
              }
            }
          }
          container undo-silent-interfaces {
            // NCS drop when statement
            description
              "List of interface. Enables sending and receiving packet on this interface when true. This information is useful when sending and receiving packet is suppressed on all interface on process level and user want it to be enabled on certain interface.";
            list undo-silent-interface {
              // NCS patched for predictable order
              ordered-by user;
              key "if-name";
              description
                "Configure interface. Enables sending and receiving packet on this interface when true. This information is useful when sending and receiving packet is suppressed on all interface on process level and user want it to be enabled on certain interface.";
              leaf if-name {
                type string;
                description
                  "Interface name.";
              }
            }
          }
          container cost-bindings {
            description
              "List of cost-binding. Indicate cost of routing from indicated router source ID binding interface.";
            list cost-binding {
              // NCS patched for predictable order
              ordered-by user;
              key "router-id if-name";
              description
                "Configure cost-binding. Indicate cost of routing from indicated router source ID binding interface.";
              leaf router-id {
                type string;
                description
                  "Source router ID.";
              }
              leaf if-name {
                type string;
                description
                  "Interface name.";
              }
            }
          }
          container areas {
            description
              "List of OSPF area.";
            list area {
              // NCS patched for predictable order
              ordered-by user;
              key "area-id";
              description
                "Configure OSPF area.";
              leaf area-id {
                type string;
                description
                  "Area ID.";
              }
              leaf area-type {
                type ncs_template_area-type;
                // NCS drop default statement
                description
                  "Area type.";
              }
              leaf description {
                type string;
                description
                  "Description of an OSPF area.";
              }
              container networks {
                description
                  "List of the interface that runs OSPF and the area to which the interface belongs to.";
                list network {
                  // NCS patched for predictable order
                  ordered-by user;
                  key "ip-address mask";
                  description
                    "Configure the interface that runs OSPF and the area to which the interface belongs to.";
                  leaf ip-address {
                    type string;
                    description
                      "Specifies the address of the network segment where the interface resides.";
                  }
                  leaf mask {
                    type string;
                    description
                      "Specifies the wildcard mask of IP address.";
                  }
                  leaf description {
                    type string;
                    description
                      "Specifies the description of the specified OSPF network segment.";
                  }
                }
              }
              container stub {
                // NCS drop when statement
                description
                  "Configure stub area.";
                leaf backbone-peer-ignore {
                  type string;
                  // NCS drop default statement
                  description
                    "Enable/disable ignore backbone peer for Stub area.";
                }
                leaf no-summary {
                  type string;
                  // NCS drop default statement
                  description
                    "Enable/disable forbid an ABR to Send Summary LSAs to the Stub Area.";
                }
                leaf default-cost {
                  type string;
                  // NCS drop default statement
                  description
                    "Cost of the default Type3 routes that are sent by an OSPF process to a stub area or an NSSA area. The value is an integer ranging from 1 to 16777214. This parameter takes effect only when it is configured on the ABR connected to a stub area or an NSSA area. The default is 1.";
                }
              }
              container nssa {
                // NCS drop when statement
                description
                  "Configure nssa area.";
                leaf no-summary {
                  type string;
                  // NCS drop default statement
                  description
                    "Enable/disable forbid an ABR to Send Summary LSAs to the NSSA Area.";
                }
                leaf translator-always {
                  type string;
                  // NCS drop default statement
                  description
                    "Enable/disable the router to act as translator always for NSSA Area.";
                }
                leaf default-route-advertise {
                  type string;
                  // NCS drop default statement
                  description
                    "Enable/disable originate Type 7 default into NSSA area.";
                }
                leaf backbone-peer-ignore {
                  // NCS drop when statement
                  type string;
                  // NCS drop default statement
                  description
                    "Enable/disable ignore backbone peer for Nssa area.";
                }
                leaf no-import-route {
                  type string;
                  // NCS drop default statement
                  description
                    "Enable/disable redistribute type 7 LSA into this area.";
                }
                leaf set-n-bit {
                  type string;
                  // NCS drop default statement
                  description
                    "Enable/disable setting of 'N' bit in the DD packet.";
                }
                leaf suppress-fa {
                  type string;
                  // NCS drop default statement
                  description
                    "Enable/disable the forwarding address as 0 for all translated type 5 LSAs.";
                }
                leaf zero-address-forwarding {
                  type string;
                  // NCS drop default statement
                  description
                    "Enable/disable allow zero forwarding address for redistributed type 7 LSA.";
                }
                leaf translator-interval {
                  type string;
                  // NCS drop default statement
                  description
                    "Translator interval.";
                }
                leaf default-cost {
                  type string;
                  // NCS drop default statement
                  description
                    "Cost of the default Type3 routes that are sent by an OSPF process to a stub area or an NSSA area. This parameter takes effect only when it is configured on the ABR connected to a stub area or an NSSA area.";
                }
              }
              container ldp-sync {
                description
                  "Configure timer ldp sync.";
                leaf enable {
                  type string;
                  // NCS drop default statement
                  description
                    "Enable/disable LDP and OSPF synchronization on area.";
                }
                choice hold-cost-max {
                  // NCS drop default statement
                  description
                    "Set timer ldp sync.";
                  case timer {
                    description
                      "Set timer ldp sync.";
                    leaf timer {
                      type string;
                      units "s";
                      description
                        "The interval for sending OSPF LSAs to advertise the maximum metric on the local device.";
                    }
                  }
                  case infinite {
                    description
                      "Always advertise the maximum cost.";
                    leaf infinite {
                      type string;
                      // NCS drop must statement
                      // NCS drop default statement
                      description
                        "Enable/disable always advertise the maximum cost.";
                    }
                  }
                }
              }
              container mpls-te {
                // NCS drop when statement
                description
                  "Configure OSPF processes enabled with the TE capability.";
                leaf enable {
                  type string;
                  // NCS drop must statement
                  // NCS drop default statement
                  description
                    "Enable/disable TE capability of the OSPF process in the specified area.";
                }
                leaf standard-complying {
                  type string;
                  // NCS drop must statement
                  // NCS drop default statement
                  description
                    "Enable/disable accept the LSAs in standard format only.";
                }
              }
              container authentication {
                // NCS drop must statement
                description
                  "Configure authentication. The encryption algorithm MD5 has a low security, which may bring security risks. Using more secure authentication is recommended.";
                leaf mode {
                  type ncs_template_area-authen-mode;
                  // NCS drop default statement
                  description
                    "Set authentication type.";
                }
                leaf auth-text-simple {
                  // NCS drop when statement
                  type pub-type:ncs_template_password;
                  description
                    "Simple authentication key. The password is a string ranging from 1 to 8 characters for a unencrypted password and 24 to 128 characters for a encrypted password.";
                }
                leaf key-id {
                  // NCS drop when statement
                  type string;
                  description
                    "Authentication identifier.";
                }
                leaf auth-text-md5 {
                  // NCS drop when statement
                  type pub-type:ncs_template_password-extend;
                  description
                    "Encrypted authentication password.";
                }
                leaf key-chain-name {
                  // NCS drop when statement
                  type string;
                  ext:case-sensitivity "lower-only";
                  // NCS drop mandatory statement
                  description
                    "Keychain name.";
                }
              }
              container abr-summary-prefixs {
                description
                  "List of ABR route aggregation method.";
                list abr-summary-prefix {
                  // NCS patched for predictable order
                  ordered-by user;
                  key "prefix network-mask";
                  description
                    "Configure ABR route aggregation method.";
                  leaf prefix {
                    type string;
                    description
                      "Specifies the IP address in dotted decimal notation.";
                  }
                  leaf network-mask {
                    type string;
                    description
                      "Specifies the mask of the IP address. The mask address is in dotted decimal notation.";
                  }
                  choice cost {
                    description
                      "Set the cost.";
                    case cost-value {
                      description
                        "Specifies the cost of the aggregated route. By default, the maximal cost in that of all the routes which are aggregated serves as the cost of the aggregated route.";
                      leaf cost-value {
                        type string;
                        description
                          "Specifies the cost of the aggregated route. By default, the maximal cost in that of all the routes which are aggregated serves as the cost of the aggregated route.";
                      }
                    }
                    case cost-inherit-min {
                      description
                        "Indicates if minimum cost should be inherited. By default, maximum cost is inherited.";
                      leaf cost-inherit-min {
                        // NCS drop when statement
                        type empty;
                        description
                          "Indicates if minimum cost should be inherited. By default, maximum cost is inherited.";
                      }
                    }
                  }
                  leaf hold-max-cost {
                    type string;
                    description
                      "Hold max cost duration.";
                  }
                  leaf advertise {
                    type string;
                    // NCS drop default statement
                    description
                      "Enable/disable the aggregated route is advertised.";
                  }
                  leaf generate-null-zero {
                    // NCS drop when statement
                    type string;
                    // NCS drop default statement
                    description
                      "Enable/disable generate black hole route.";
                  }
                }
              }
              container vlink-peers {
                // NCS drop when statement
                description
                  "List of virtual link and its parameters.";
                list vlink-peer {
                  // NCS patched for predictable order
                  ordered-by user;
                  key "router-id";
                  description
                    "Configure virtual link and its parameters.";
                  leaf router-id {
                    type string;
                    description
                      "Neighbor Router ID.";
                  }
                  leaf retransmit-interval {
                    type string;
                    // NCS drop default statement
                    description
                      "Interval for retransmitting LSAs.";
                  }
                  leaf smart-discover {
                    type string;
                    // NCS drop default statement
                    description
                      "Enable/disable smart discover feature.";
                  }
                  container timer {
                    // NCS drop must statement
                    description
                      "Configure timer.";
                    leaf hello-interval {
                      type string;
                      // NCS drop default statement
                      description
                        "Time between Hello packets.";
                    }
                    leaf dead-interval {
                      type string;
                      // NCS drop default statement
                      description
                        "Interval after which a neighbor is declared dead.";
                    }
                    leaf trans-delay-interval {
                      type string;
                      // NCS drop default statement
                      description
                        "Delay for transmitting LSAs.";
                    }
                  }
                  container authentication {
                    description
                      "Configure authentication. The encryption algorithm MD5 has a low security, which may bring security risks. Using more secure authentication is recommended.";
                    leaf mode {
                      type ncs_template_intf-authen-mode;
                      // NCS drop default statement
                      description
                        "Set authentication type: Simple authentication type, Md5/HMAC MD5/HMAC SHA256 authentication type.";
                    }
                    leaf auth-text-simple {
                      // NCS drop when statement
                      type pub-type:ncs_template_password;
                      description
                        "Simple authentication key. The password is a string ranging from 1 to 8 characters for a unencrypted password and 24 to 128 characters for a encrypted password.";
                    }
                    leaf key-id {
                      // NCS drop when statement
                      type string;
                      // NCS drop must statement
                      description
                        "Authentication identifier.";
                    }
                    leaf auth-text-md5 {
                      // NCS drop when statement
                      type pub-type:ncs_template_password-extend;
                      // NCS drop must statement
                      description
                        "MD5/HMAC MD5/HMAC SHA256 authentication password.";
                    }
                    leaf key-chain-name {
                      // NCS drop when statement
                      type string;
                      ext:case-sensitivity "lower-only";
                      // NCS drop mandatory statement
                      description
                        "Keychain name.";
                    }
                  }
                }
              }
              container sham-links {
                // NCS drop when statement
                description
                  "List of sham link and its parameters.";
                list sham-link {
                  // NCS patched for predictable order
                  ordered-by user;
                  key "src-addr dest-addr";
                  description
                    "Configure sham link and its parameters.";
                  leaf src-addr {
                    type string;
                    description
                      "Source address.";
                  }
                  leaf dest-addr {
                    type string;
                    // NCS drop must statement
                    description
                      "Destination address.";
                  }
                  leaf cost {
                    type string;
                    // NCS drop default statement
                    description
                      "Cost.";
                  }
                  leaf retransmit-interval {
                    type string;
                    // NCS drop default statement
                    description
                      "Interval for retransmitting LSAs.";
                  }
                  leaf smart-discover {
                    type string;
                    // NCS drop default statement
                    description
                      "Enable/disable smart discover feature.";
                  }
                  container timer {
                    // NCS drop must statement
                    description
                      "Configure timer.";
                    leaf hello-interval {
                      type string;
                      // NCS drop default statement
                      description
                        "Time between Hello packets.";
                    }
                    leaf dead-interval {
                      type string;
                      // NCS drop default statement
                      description
                        "Interval after which a neighbor is declared dead.";
                    }
                    leaf trans-delay-interval {
                      type string;
                      // NCS drop default statement
                      description
                        "Delay for transmitting LSAs.";
                    }
                  }
                  container authentication {
                    description
                      "Configure authentication. The encryption algorithm MD5 has a low security, which may bring security risks. Using more secure authentication is recommended.";
                    leaf mode {
                      type ncs_template_intf-authen-mode;
                      // NCS drop default statement
                      description
                        "Set authentication type: Simple authentication type, Md5/HMAC MD5/HMAC SHA256 authentication type.";
                    }
                    leaf auth-text-simple {
                      // NCS drop when statement
                      type pub-type:ncs_template_password;
                      description
                        "Simple authentication key. The password is a string ranging from 1 to 8 characters for a unencrypted password and 24 to 128 characters for a encrypted password.";
                    }
                    leaf key-id {
                      // NCS drop when statement
                      type string;
                      // NCS drop must statement
                      description
                        "Authentication identifier.";
                    }
                    leaf auth-text-md5 {
                      // NCS drop when statement
                      type pub-type:ncs_template_password-extend;
                      // NCS drop must statement
                      description
                        "MD5/HMAC MD5/HMAC SHA256 authentication password.";
                    }
                    leaf key-chain-name {
                      // NCS drop when statement
                      type string;
                      ext:case-sensitivity "lower-only";
                      // NCS drop mandatory statement
                      description
                        "Keychain name.";
                    }
                  }
                }
              }
              container filters {
                description
                  "List of ABR to filter outgoing or incoming summary LSAs of the local area.";
                list filter {
                  // NCS patched for predictable order
                  ordered-by user;
                  key "mode";
                  description
                    "Configure ABR to filter outgoing or incoming summary LSAs of the local area.";
                  leaf mode {
                    type ncs_template_area-filter-mode;
                    description
                      "Using the filter export command, you can configure an ABR to filter outgoing summary LSAs of the local area. Using the filter import command, you can configure an ABR to filter incoming summary LSAs of the local area.";
                  }
                  uses ncs_template_policy-type;
                  leaf include-abr-summary {
                    // NCS drop when statement
                    type string;
                    // NCS drop default statement
                    description
                      "Enable/disable include abr summary flag.";
                  }
                }
              }
              container interfaces {
                description
                  "List of the interface enabled with OSPF.";
                list interface {
                  // NCS patched for predictable order
                  ordered-by user;
                  key "name";
                  description
                    "Configure the interface enabled with OSPF.";
                  leaf name {
                    type string;
                    // NCS drop must statement
                    description
                      "Interface name. OSPF does not support the configuration of a NULL/LMP/MTUNNEL/RPR/STACKPORT/SIP/ATMBUNDLE/IMAGROUP/Remote-Ap/VBridge interface types.";
                  }
                  leaf network-type {
                    type ncs_template_network-type;
                    ext:dynamic-default;
                    description
                      "Network type of an OSPF interface. By default, the network type of an interface is determined by the physical interface.
                       In the same network segment, if only two routers run OSPF, you can change the network type of an interface to P2P.";
                  }
                  leaf peer-ip-ignore {
                    type ncs_template_peer-ip-ignore-type;
                    // NCS drop must statement
                    // NCS drop default statement
                    description
                      "Ignores the subnet match check in multi access interface when network type P2P is configured along with this option.";
                  }
                  leaf transmit-delay {
                    type string;
                    // NCS drop default statement
                    description
                      "Delay for transmitting LSAs on an interface.";
                  }
                  leaf mtu-enable {
                    type string;
                    // NCS drop default statement
                    description
                      "Enable/disable MTU filled in a DD packet when the packet is sent. The default MTU in the DD packet is 0. Using the command, you can manually configure the interface to fill in the MTU field (actual MTU of the interface) when the interface sends DD packets.
                       After a virtual connection is established through the virtual template or tunnel, different vendors may use different MTUs as default settings. To ensure consistency, the MTU is set to 0 by default when the interface sends DD packets. Thus, the ospf mtu-enable command usually does not need to be configured.
                       OSPF does not support the preceding configuration on a null interface.";
                  }
                  leaf dr-priority {
                    type string;
                    // NCS drop default statement
                    description
                      "Priority of the interface that participates in the DR and BDR election. The greater the value is, the higher the priority is. The router whose priority is 0 cannot be elected as a DR or a BDR.";
                  }
                  leaf cost {
                    type string;
                    description
                      "To set the cost of an interface. The default value is 1. But the default of Loopback is 0.";
                  }
                  leaf smart-discover {
                    type string;
                    // NCS drop default statement
                    description
                      "Enable/disable smart discover on an interface. When the neighbor status of a router or a DR or BDR on the multi address network of the broadcast or NBMA type changes, the router can send hello packets to the neighbor actively rather than wait for the expiration of the hello timer.";
                  }
                  leaf p2mp-mask-ignore {
                    type string;
                    // NCS drop default statement
                    description
                      "Enable/disable to ignore the check of network masks on a P2MP network. On a P2MP network, when the lengths of device masks are inconsistent, the check of network masks in hello packets can be ignored through this command. In this case, the OSPF neighbor relationship can be normally established.";
                  }
                  leaf ldp-sync-block {
                    type string;
                    // NCS drop must statement
                    // NCS drop default statement
                    description
                      "Enable/disable LDP sync on this interface.";
                  }
                  leaf ldp-sync-enable {
                    type string;
                    // NCS drop must statement
                    // NCS drop default statement
                    description
                      "Enable/disable LDP and OSPF synchronization on an interface.";
                  }
                  leaf link-cost {
                    type string;
                    description
                      "Link cost to be incremented when link quality is low. The default of Loopback is 0,others is 1.";
                  }
                  leaf suppress-reachability {
                    type ncs_template_suppr-reach;
                    // NCS drop default statement
                    description
                      "Suppress its own prefixes and ignore the suppressed prefixes.";
                  }
                  leaf mpls-ldp-auto-flag {
                    type ncs_template_if-auto-cfg-state;
                    // NCS drop default statement
                    description
                      "Block MPLS LDP auto configuration on the interface.";
                  }
                  leaf dcn-opq-blk-enable {
                    type string;
                    // NCS drop default statement
                    description
                      "Enable/disable filter type-10 dcn opaque LSAs.";
                  }
                  leaf peer-hold-max-timer {
                    type string;
                    units "ms";
                    description
                      "Config peer hold max cost interval.";
                  }
                  leaf fallback-cost {
                    // NCS drop when statement
                    type string;
                    description
                      "Fallback cost.";
                  }
                  leaf fallback-bw {
                    // NCS drop when statement
                    type string;
                    units "Mbit/s";
                    // NCS drop mandatory statement
                    description
                      "Fallback bandwidth threshold.";
                  }
                  leaf source-sub-ip-address {
                    type string;
                    description
                      "Source address indicating a subordinate IP address.";
                  }
                  container frr {
                    description
                      "Configure FRR.";
                    leaf frr-disable {
                      type string;
                      // NCS drop default statement
                      description
                        "Enable/disable not use this interface for FRR calculation.";
                    }
                    leaf rlfa-disable {
                      type string;
                      // NCS drop default statement
                      description
                        "Enable/disable remote LFA of the Interface.";
                    }
                    container ti-lfa {
                      description
                        "Configure topology independent loop free alternate (TILFA) computation using segment routing.";
                      leaf disable {
                        type string;
                        // NCS drop default statement
                        description
                          "Enable/disable topology independent LFA on the interface except Loopback.";
                      }
                    }
                  }
                  container timer {
                    description
                      "Configure timer.";
                    leaf hello-interval {
                      type string;
                      ext:dynamic-default {
                        ext:default-value "10" {
                          // NCS drop when statement
                          description
                            "The default value is 10 when network-type is p2p or broadcast.";
                        }
                        ext:default-value "30" {
                          // NCS drop when statement
                          description
                            "The default value is 30 when network-type is p2mp or nbma.";
                        }
                      }
                      description
                        "Interval for sending hello packets on an interface.";
                    }
                    leaf hello-conser {
                      type string;
                      // NCS drop default statement
                      description
                        "Enable/disable the compensation mechanism of controling the deadtimer to enable.";
                    }
                    leaf dead-interval {
                      type string;
                      // NCS drop must statement
                      ext:dynamic-default {
                        ext:default-value "4*(../hello-interval)" {
                          description
                            "The default value of dead interval is 4 times that of hello interval.";
                        }
                      }
                      description
                        "Dead interval of an OSPF neighbor.";
                    }
                    leaf wait-interval {
                      type string;
                      ext:dynamic-default {
                        ext:default-value "../dead-interval" {
                          description
                            "The default value of wait interval is equal to dead interval.";
                        }
                      }
                      description
                        "Wait time.";
                    }
                    leaf poll-interval {
                      type string;
                      // NCS drop default statement
                      description
                        "Poll interval for sending hello packets. On the NBMA network, after the neighbor is invalid, the router sends hello packets periodically according to the interval set through the ospf timer poll command. The poll interval should be at least four times of the interval for sending hello packets.";
                    }
                    leaf retransmit-interval {
                      type string;
                      // NCS drop default statement
                      description
                        "Interval for retransmitting LSAs on an interface.";
                    }
                  }
                  container ldp-sync {
                    description
                      "Configure timer ldp sync.";
                    leaf hold-down-timer {
                      type string;
                      units "s";
                      // NCS drop default statement
                      description
                        "Hold down interval.";
                    }
                    choice hold-cost-max {
                      description
                        "Set timer ldp sync.";
                      case timer {
                        description
                          "Set max cost interval.";
                        leaf timer {
                          type string;
                          units "s";
                          description
                            "Max cost interval range.";
                        }
                      }
                      case infinite {
                        description
                          "Always advertise the maximum cost.";
                        leaf infinite {
                          type empty;
                          description
                            "Always advertise the maximum cost.";
                        }
                      }
                    }
                  }
                  container bfd {
                    description
                      "Configure BFD.";
                    leaf enable {
                      type string;
                      // NCS drop must statement
                      // NCS drop default statement
                      description
                        "Enable/disable BFD.";
                    }
                    leaf block {
                      type string;
                      // NCS drop must statement
                      // NCS drop default statement
                      description
                        "Enable/disable to prevent the dynamic establishment of a BFD session on an interface.";
                    }
                    leaf detect-multiplier {
                      type string;
                      // NCS drop default statement
                      description
                        "Local detection multiplier.";
                    }
                    leaf min-tx {
                      type string;
                      units "ms";
                      description
                        "Minimum interval for sending BFD packets to the peer end. The ranges and the default value is determined by the PAF.";
                    }
                    leaf min-rx {
                      type string;
                      units "ms";
                      description
                        "Minimum interval for receiving BFD packets from the peer end. The ranges and the default value is determined by the PAF.";
                    }
                    leaf frr-binding {
                      type string;
                      // NCS drop default statement
                      description
                        "Enable/disable bind FRR with BFD.";
                    }
                    choice incr-cost {
                      description
                        "Interface BFD sync cost.";
                      case incr-cost-block {
                        description
                          "Interface BFD sync cost block.";
                        leaf incr-cost-block {
                          type empty;
                          description
                            "Interface BFD sync cost block.";
                        }
                      }
                      case incr-cost-value {
                        description
                          "Interface BFD sync cost.";
                        leaf incr-cost-value {
                          type string;
                          description
                            "Interface BFD sync cost.";
                        }
                      }
                    }
                    leaf per-link-flag {
                      type string;
                      // NCS drop must statement
                      // NCS drop default statement
                      description
                        "Enable/disable BFD session per link, support only VLANif interface.";
                    }
                    leaf one-arm-echo-flag {
                      type string;
                      // NCS drop must statement
                      // NCS drop default statement
                      description
                        "Enable/disable echo detection mode, support only VLANif interface.";
                    }
                  }
                  container authentication {
                    description
                      "Configure authentication. The encryption algorithm MD5 has a low security, which may bring security risks. Using more secure authentication is recommended.";
                    leaf mode {
                      type ncs_template_intf-authen-mode;
                      // NCS drop default statement
                      description
                        "Set Authentication type.";
                    }
                    leaf auth-text-simple {
                      // NCS drop when statement
                      type pub-type:ncs_template_password;
                      description
                        "Simple authentication key. The password is a string ranging from 1 to 8 characters for a unencrypted password and 24 to 128 characters for a encrypted password.";
                    }
                    leaf key-id {
                      // NCS drop when statement
                      type string;
                      // NCS drop must statement
                      description
                        "Authentication identifier.";
                    }
                    leaf auth-text-md5 {
                      // NCS drop when statement
                      type pub-type:ncs_template_password-extend;
                      // NCS drop must statement
                      description
                        "Encrypted authentication password.";
                    }
                    leaf key-chain-name {
                      // NCS drop when statement
                      type string;
                      ext:case-sensitivity "lower-only";
                      // NCS drop mandatory statement
                      description
                        "Keychain name.";
                    }
                  }
                  container filter-lsa-out {
                    description
                      "Configure filter lsa out.";
                    choice type {
                      description
                        "Set filter lsa out type.";
                      case total {
                        description
                          "Filter total types of LSAs.";
                        leaf all-flag {
                          type empty;
                          description
                            "Filter all types of LSAs.";
                        }
                      }
                      case other {
                        description
                          "Filter other types of LSAs.";
                        leaf sum-flag {
                          type empty;
                          description
                            "Filter type3 summary LSAs.";
                        }
                        choice sum-filter {
                          description
                            "Type of a filtering rule.";
                          case acl {
                            description
                              "Basic ACL name or ACL number.";
                            leaf sum-name {
                              // NCS drop when statement
                              type string;
                              // NCS drop must statement
                              description
                                "Basic ACL name or ACL number.";
                            }
                          }
                        }
                        leaf ase-flag {
                          type empty;
                          description
                            "Filter type5 ASE LSAs.";
                        }
                        choice ase-filter {
                          description
                            "Type of a filtering rule.";
                          case acl {
                            description
                              "Basic ACL name or ACL number.";
                            leaf ase-name {
                              // NCS drop when statement
                              type string;
                              // NCS drop must statement
                              description
                                "Basic ACL name or ACL number.";
                            }
                          }
                        }
                        leaf nssa-flag {
                          type empty;
                          description
                            "Filter type7 NSSA LSAs.";
                        }
                        choice nssa-filter {
                          description
                            "Type of a filtering rule.";
                          case acl {
                            description
                              "Basic ACL name or ACL number.";
                            leaf nssa-name {
                              // NCS drop when statement
                              type string;
                              // NCS drop must statement
                              description
                                "Basic ACL name or ACL number.";
                            }
                          }
                        }
                      }
                    }
                  }
                  container suppress-flapping {
                    description
                      "Configure flapping suppression.";
                    container peer {
                      // NCS drop must statement
                      description
                        "Configure flapping suppression peer. Not support Loopback.";
                      leaf enable {
                        type string;
                        // NCS drop default statement
                        description
                          "Enable/disable interface peer flapping suppress.";
                      }
                      leaf detect-interval {
                        type string;
                        // NCS drop default statement
                        description
                          "Detecting interval.";
                      }
                      leaf threshold {
                        type string;
                        // NCS drop default statement
                        description
                          "Threshold.";
                      }
                      leaf resume-interval {
                        type string;
                        // NCS drop default statement
                        description
                          "Resume interval.";
                      }
                      leaf hold-down-interval {
                        type string;
                        description
                          "Hold down interval.";
                      }
                      leaf hold-max-cost {
                        type string;
                        // NCS drop default statement
                        description
                          "Enable/disable hold max cost.";
                      }
                    }
                  }
                  container flush-source-trace {
                    description
                      "Configure OSPF flush source trace function.";
                    leaf block {
                      type string;
                      // NCS drop default statement
                      description
                        "Enable/disable OSPF flush source trace.";
                    }
                  }
                  container mpls-te-peers {
                    description
                      "List of OSPF passive peer.";
                    list mpls-te-peer {
                      // NCS patched for predictable order
                      ordered-by user;
                      key "id router-id intf-ip";
                      description
                        "Configure OSPF passive peer.";
                      leaf id {
                        type string;
                        description
                          "Neighbor ID.";
                      }
                      leaf router-id {
                        type string;
                        description
                          "Configure OSPF passive peer router ID.";
                      }
                      leaf intf-ip {
                        type string;
                        description
                          "Configure interface address of passive peer.";
                      }
                      container procs {
                        description
                          "List of OSPF passive peers area.";
                        list proc {
                          // NCS patched for predictable order
                          ordered-by user;
                          key "pid aid";
                          // NCS drop max-elements statement
                          description
                            "Configure OSPF passive peers area.";
                          leaf pid {
                            type string;
                            description
                              "Process ID.";
                          }
                          leaf aid {
                            type string;
                            description
                              "Area ID.";
                          }
                          leaf cost {
                            type string;
                            // NCS drop default statement
                            description
                              "Configuration cost value.";
                          }
                        }
                      }
                    }
                  }
                  container multi-areas {
                    description
                      "List of the information about the multi-area interface enabled with OSPF.";
                    list multi-area {
                      // NCS patched for predictable order
                      ordered-by user;
                      key "area-id";
                      description
                        "Configure the interface enabled with OSPF.";
                      leaf area-id {
                        type string;
                        // NCS drop must statement
                        description
                          "Multi area id.";
                      }
                      leaf transmit-delay {
                        type string;
                        units "s";
                        // NCS drop default statement
                        description
                          "Delay for transmitting LSAs on an interface.";
                      }
                      leaf mtu-enable {
                        type string;
                        // NCS drop default statement
                        description
                          "Enable/disable MTU.Configure the interface to fill in the MTU field (actual MTU of the interface) when the interface sends DD packets.
                           After a virtual connection is established through the virtual template or tunnel, different vendors may use different MTUs as default settings. To ensure consistency, the MTU is set to 0 by default when the interface sends DD packets. Thus, the ospf mtu-enable command usually does not need to be configured. OSPF does not support the preceding configuration on a null interface.";
                      }
                      leaf cost {
                        type string;
                        description
                          "To set the cost of an interface. The default value is 1. But the default of Loopback is 0.";
                      }
                      leaf smart-discover {
                        type string;
                        // NCS drop default statement
                        description
                          "Enable/disable smart discover on an interface. When the neighbor status of a router or a DR or BDR on the multi-address network of the broadcast or NBMA type changes, the router can send Hello packets to the neighbor actively rather than wait for the expiration of the Hello timer.";
                      }
                      leaf ldp-sync-block {
                        type string;
                        // NCS drop must statement
                        // NCS drop default statement
                        description
                          "Enable/disable ldp sync on this interface.";
                      }
                      leaf ldp-sync-enable {
                        type string;
                        // NCS drop must statement
                        // NCS drop default statement
                        description
                          "Enable/disable LDP and OSPF synchronization on an interface.";
                      }
                      leaf fallback-cost {
                        // NCS drop when statement
                        type string;
                        description
                          "Fallback cost.";
                      }
                      leaf fallback-bw {
                        // NCS drop when statement
                        type string;
                        units "Mbit/s";
                        // NCS drop mandatory statement
                        description
                          "Fallback bandwidth threshold.";
                      }
                      container frr {
                        description
                          "Configure frr.";
                        leaf frr-disable {
                          type string;
                          // NCS drop default statement
                          description
                            "Enable/disable use this interface for FRR calculation.";
                        }
                        leaf rlfa-disable {
                          type string;
                          // NCS drop default statement
                          description
                            "Enable/disable remote LFA of the Interface.";
                        }
                        leaf ti-lfa-disable {
                          type string;
                          // NCS drop default statement
                          description
                            "Enable/disable Topology Independent LFA on the interface except Loopback.";
                        }
                      }
                      container timer {
                        description
                          "Configure timer.";
                        leaf hello-interval {
                          type string;
                          units "s";
                          ext:dynamic-default {
                            ext:default-value "10" {
                              // NCS drop when statement
                              description
                                "The default value is 10 when network-type is p2p or broadcast.";
                            }
                            ext:default-value "30" {
                              // NCS drop when statement
                              description
                                "The default value is 30 when network-type is p2mp or nbma.";
                            }
                          }
                          description
                            "Interval for sending Hello packets on an interface. The default value of p2p and broadcast is 10.The default of p2mp and NBMA is 30.";
                        }
                        leaf dead-interval {
                          type string;
                          units "s";
                          // NCS drop must statement
                          ext:dynamic-default {
                            ext:default-value "4*(../hello-interval)" {
                              description
                                "The default value of dead interval is 4 times that of hello interval.";
                            }
                          }
                          description
                            "Dead interval of an OSPF neighbor. The default value of p2p and broadcast is 40.The default of p2mp and NBMA is 120.";
                        }
                        leaf retransmit-interval {
                          type string;
                          // NCS drop default statement
                          description
                            "Interval for Retransmitting LSAs on an Interface.";
                        }
                      }
                      container ldp-sync {
                        description
                          "Configure timer ldp sync.";
                        leaf hold-down-timer {
                          type string;
                          units "s";
                          // NCS drop default statement
                          description
                            "Hold down interval range.";
                        }
                        choice hold-cost-max {
                          description
                            "Set timer ldp-sync.";
                          case timer {
                            description
                              "Set max cost interval.";
                            leaf timer {
                              type string;
                              units "s";
                              description
                                "Max cost interval range.";
                            }
                          }
                          case infinite {
                            description
                              "Always advertise the maximum cost.";
                            leaf infinite {
                              type empty;
                              description
                                "Always advertise the maximum cost.";
                            }
                          }
                        }
                      }
                      container bfd {
                        description
                          "Configure BFD.";
                        leaf block {
                          type string;
                          // NCS drop default statement
                          description
                            "Enable/disable prevent the dynamic establishment of a BFD session on an interface.";
                        }
                      }
                      container authentication {
                        // NCS drop must statement
                        description
                          "Configure authentication. The encryption algorithm MD5 has a low security, which may bring security risks. Using more secure authentication is recommended.";
                        leaf mode {
                          type ncs_template_intf-authen-mode;
                          // NCS drop default statement
                          description
                            "Set Authentication type.";
                        }
                        leaf auth-text-simple {
                          // NCS drop when statement
                          type pub-type:ncs_template_password;
                          description
                            "Simple authentication key. The password is a string ranging from 1 to 8 characters for a unencrypted password and 24 to 128 characters for a encrypted password.";
                        }
                        leaf key-id {
                          // NCS drop when statement
                          type string;
                          description
                            "Authentication identifier.";
                        }
                        leaf auth-text-md5 {
                          // NCS drop when statement
                          type pub-type:ncs_template_password-extend;
                          description
                            "MD5/HMAC-MD5/HMAC-SHA256 Authentication Password.";
                        }
                        leaf key-chain-name {
                          // NCS drop when statement
                          type string;
                          ext:case-sensitivity "lower-only";
                          // NCS drop mandatory statement
                          description
                            "Keychain Name.";
                        }
                      }
                      container filter-lsa-out {
                        presence "Enable multi area filter lsa out.";
                        description
                          "Configure filter-lsa-out.";
                        choice type {
                          // NCS drop mandatory statement
                          description
                            "Set filter-lsa-out type.";
                          case total {
                            description
                              "Filter total types of LSAs.";
                            leaf all-flag {
                              type empty;
                              description
                                "Filter all types of LSAs.";
                            }
                          }
                          case other {
                            description
                              "Filter other types of LSAs.";
                            leaf sum-flag {
                              type empty;
                              description
                                "Filter type-3 Summary LSAs.";
                            }
                            choice sum-filter {
                              description
                                "Type of a filtering rule.";
                              case acl {
                                description
                                  "ACL-Name or ACL-Number.";
                                leaf sum-name {
                                  // NCS drop when statement
                                  type string;
                                  description
                                    "ACL-Name or ACL-Number.";
                                }
                              }
                            }
                            leaf ase-flag {
                              type empty;
                              description
                                "Filter type-5 ASE LSAs.";
                            }
                            choice ase-filter {
                              description
                                "Type of a filtering rule.";
                              case acl {
                                description
                                  "ACL-Name or ACL-Number.";
                                leaf ase-name {
                                  // NCS drop when statement
                                  type string;
                                  description
                                    "ACL-Name or ACL-Number.";
                                }
                              }
                            }
                            leaf nssa-flag {
                              type empty;
                              description
                                "Filter type-7 NSSA LSAs.";
                            }
                            choice nssa-filter {
                              description
                                "Type of a filtering rule.";
                              case acl {
                                description
                                  "ACL-Name or ACL-Number.";
                                leaf nssa-name {
                                  // NCS drop when statement
                                  type string;
                                  description
                                    "ACL-Name or ACL-Number.";
                                }
                              }
                            }
                          }
                        }
                      }
                      container suppress-flapping {
                        description
                          "Configure flapping suppression.";
                        container peer {
                          // NCS drop must statement
                          description
                            "Configure flapping suppression peer. Not support Loopback.";
                          leaf enable {
                            type string;
                            // NCS drop default statement
                            description
                              "Enable/disable interface peer flapping suppress.";
                          }
                          leaf detect-interval {
                            type string;
                            // NCS drop default statement
                            description
                              "Detecting-interval.";
                          }
                          leaf threshold {
                            type string;
                            // NCS drop default statement
                            description
                              "Threshold.";
                          }
                          leaf resume-interval {
                            type string;
                            // NCS drop default statement
                            description
                              "Resume-interval.";
                          }
                          leaf hold-down-interval {
                            type string;
                            description
                              "Hold-down-interval.";
                          }
                          leaf hold-max-cost {
                            type string;
                            // NCS drop default statement
                            description
                              "Enable/disable hold max cost.";
                          }
                        }
                      }
                    }
                  }
                  // NCS drop config false container 'disp-data'
                  // NCS drop config false container 'nbr-statistics'
                  // NCS drop config false container 'error-data'
                }
              }
              // NCS drop config false container 'disp-data'
            }
          }
          // NCS drop config false container 'disp-data'
          // NCS drop config false container 'migp-routings'
          // NCS drop config false container 'abr-asbr-statistics'
          // NCS drop config false container 'nexthop-paras'
          // NCS drop config false container 'lsdb-statistics'
          // NCS drop config false container 'lsdb-briefs'
          // NCS drop config false container 'last-down-nbrs'
          // NCS drop config false container 'disp-graceful-restart'
          // NCS drop config false container 'error-process-data'
          // NCS drop config false container 'as-lsdb-brief'
          // NCS drop config false container neighbors
          // NCS drop config false container routings
          // NCS drop config false container 'vlink-nbr-statistics'
        }
      }
    }
  }
  augment "/ncs:devices/ncs:device/ncs:live-status/ni:network-instance/ni:instances/ni:instance" {
    description
      "OSPFv2 augment to L3VPN.";
    container ospfv2 {
      tailf:ncs-device-type "netconf";
      tailf:display-when "not(../../../../../ncs:module) or ../../../../../ncs:module[ncs:name='huawei-ospfv2'] or (../../../../../ncs:live-status-protocol[not(ncs:capability)]) or (../../../../../ncs:live-status-protocol/ncs:capability/ncs:module[.='huawei-ospfv2'])";
      description
        "Configure OSPFv2.";
      container gtsm {
        // NCS drop when statement
        presence "Enable gtsm.";
        description
          "Configure the OSPF GTSM.";
        leaf hops {
          type uint8 {
            range "1..255";
          }
          // NCS drop mandatory statement
          description
            "Specifies the number of TTL hops to be detected.";
        }
        leaf nonstandard-multicast {
          type boolean;
          // NCS drop default statement
          description
            "Enable/disable sending Multicast packet with TTL as 255 and receive multicast packet TTL should be 1 or 255 to ((255 - configured hop) + 1).";
        }
      }
      container sites {
        // NCS drop when statement
        description
          "List of OSPF instance.";
        list site {
          key "process-id";
          description
            "Configure OSPF instance.";
          leaf process-id {
            type uint32 {
              range "1..4294967295";
            }
            description
              "Process ID.";
          }
          leaf description {
            type string {
              length "1..80";
              pattern '([^?]*)';
            }
            description
              "Description of an OSPF process.";
          }
          leaf router-id {
            type inet:ipv4-address-no-zone;
            description
              "Router ID. It is used to set the OSPF private ID.";
          }
          leaf opaque {
            type boolean;
            // NCS drop default statement
            description
              "Enable/disable the opaque LSA capability. After it is enabled, an OSPF process can generate the opaque LSA and receive the opaque LSA from the neighbor device.";
          }
          leaf rfc1583-compatible {
            type boolean;
            // NCS drop default statement
            description
              "Enable/disable the route selection rule that is compatible with RFC 1583.";
          }
          leaf silent-all-interface {
            type boolean;
            // NCS drop default statement
            description
              "Enable/disable to suppress all interfaces in an OSPF process from sending or receiving OSPF packets.";
          }
          leaf retransmission-limit {
            type boolean;
            // NCS drop default statement
            description
              "Enable/disable maximum retransmission.";
          }
          leaf retransmission-limit-value {
            // NCS drop when statement
            type uint32 {
              range "2..255";
            }
            // NCS drop default statement
            description
              "Maximum retransmission times.";
          }
          leaf safe-sync {
            type boolean;
            // NCS drop default statement
            description
              "Enable/disable safe synchronization.";
          }
          leaf traffic-adj {
            type boolean;
            // NCS drop default statement
            description
              "Enable/disable traffic adjust info.";
          }
          leaf traffic-adv {
            // NCS drop when statement
            type boolean;
            // NCS drop default statement
            description
              "Enable/disable traffic advertise info.";
          }
          leaf local-mt {
            // NCS drop when statement
            type boolean;
            // NCS drop must statement
            // NCS drop default statement
            description
              "Enable/disable local multicast topology.";
          }
          leaf advertise-mpls-lsr-id {
            type boolean;
            // NCS drop must statement
            // NCS drop default statement
            description
              "Enable/disable advertise MPLS LSR ID into multiple areas as an intra area route.";
          }
          leaf advertise-mpls-lsr-id-cost {
            // NCS drop when statement
            type uint32 {
              range "0..65535";
            }
            // NCS drop default statement
            description
              "MPLS LSR ID link cost.";
          }
          leaf suppress-reachability {
            type boolean;
            // NCS drop default statement
            description
              "Enable/disable suppress reachability.";
          }
          leaf lsa-refresh {
            type boolean;
            // NCS drop default statement
            description
              "Enable/disable refresh the age of LSA with greater lsa age.";
          }
          leaf mpls-ldp-auto-flag {
            type live_ncs_proc-auto-cfg-state;
            // NCS drop default statement
            description
              "Enable LDP automatically on OSPF enabled interfaces, but need to set MPLS first.";
          }
          leaf lsdb-overflow-limit {
            type uint32 {
              range "1..1000000";
            }
            description
              "Maximum number of AS external LSAs allowed in the LSDB.";
          }
          leaf peer-flapping-suppress {
            type boolean;
            // NCS drop default statement
            description
              "Enable/disable peer flapping suppress feature.";
          }
          leaf shutdown {
            type boolean;
            // NCS drop must statement
            // NCS drop default statement
            description
              "Enable/disable shutdown OSPFv2 service.";
          }
          leaf sham-hello {
            type boolean;
            // NCS drop default statement
            description
              "Enable/disable peers keep alive by receiving any valid OSPF packet.";
          }
          leaf max-link-cost {
            type uint16 {
              range "1..65534";
            }
            description
              "Set the max value of link cost.";
          }
          leaf maxage-lsa {
            type uint32 {
              range "0..65535";
            }
            units "s";
            // NCS drop default statement
            description
              "Calculation of route delay when the OSPF LSA frequently flaps.";
          }
          container private-net {
            // NCS drop when statement
            description
              "Configure private network configuration of OSPF.";
            leaf eca-route {
              type boolean;
              // NCS drop default statement
              description
                "Enable/disable route type of the extended community attribute for VPN.";
            }
            choice route-tag {
              description
                "To set route tag value.";
              case disable {
                description
                  "To disable the using of the tag for loop detection.";
                leaf disable {
                  type empty;
                  description
                    "To disable the using of the tag for loop detection.";
                }
              }
              case value {
                description
                  "Tag of an imported VPN route.";
                leaf value {
                  type uint32 {
                    range "0..4294967295";
                  }
                  description
                    "Tag of an imported VPN route. By default, the first two bytes of the tag value are fixed to be 0xD000, and the last two bytes are the local AS number of the local BGP. For example, if the AS number of BGP is 100, the default tag value in decimal notation is 3489661028.If not configed, the default is 0.";
                }
              }
            }
            leaf vpn-capability {
              type boolean;
              // NCS drop default statement
              description
                "Enable/disable route loop detection and directly calculate routes. When VPN multi instance is supported on the multi VPN instance CE (MCE) router, loop detection must be cancelled. It is applicable to only OSPF VPN instances.";
            }
            container domain-id {
              presence "ID of an OSPF domain.";
              description
                "Configure ID of an OSPF domain.";
              leaf domain-id {
                type inet:ipv4-address-no-zone;
                // NCS drop mandatory statement
                description
                  "ID of an OSPF domain.";
              }
              leaf type {
                type live_ncs_domain-id-type;
                // NCS drop default statement
                description
                  "Type of an OSPF domain ID.";
              }
              leaf value {
                type pub-type:live_ncs_hex-binary;
                // NCS drop default statement
                description
                  "Value of an OSPF domain ID type.";
              }
            }
            container domain-id-secondarys {
              // NCS drop when statement
              description
                "List of ID of a secondary domain.";
              list domain-id-secondary {
                key "domain-id type value";
                description
                  "Configure ID of a secondary domain.";
                leaf domain-id {
                  type inet:ipv4-address-no-zone;
                  description
                    "ID of an OSPF domain.";
                }
                leaf type {
                  type live_ncs_domain-id-type;
                  description
                    "Type of an OSPF domain ID.";
                }
                leaf value {
                  type pub-type:live_ncs_hex-binary;
                  description
                    "Value of an OSPF domain ID type.";
                }
              }
            }
          }
          container host-name {
            description
              "Configure OSPF host name.";
            leaf enable {
              type boolean;
              // NCS drop must statement
              // NCS drop default statement
              description
                "Enable/disable host name.";
            }
            leaf value {
              // NCS drop when statement
              type string {
                length "1..255";
              }
              description
                "Set host name.";
            }
          }
          container bandwidth {
            description
              "Configure bandwidth.";
            leaf config-bw-enable {
              type boolean;
              // NCS drop default statement
              description
                "Enable/disable bandwidth config.";
            }
            leaf reference-value {
              type uint32 {
                range "1..2147483648";
              }
              // NCS drop default statement
              description
                "Reference to the calculation of link costs.";
            }
          }
          container timer {
            description
              "Configure timer.";
            container lsa-arrival {
              description
                "Configure interval for receiving LSAs either through an intelligent timer or timer.";
              choice timer-type {
                // NCS drop default statement
                description
                  "Set a value for the LDP and OSPF synchronization timer.";
                case timer {
                  description
                    "Interval for receiving LSAs.";
                  leaf interval {
                    type uint32 {
                      range "0..10000";
                    }
                    description
                      "Interval for receiving LSAs.";
                  }
                }
                case intelligent-timer {
                  description
                    "Specify an intelligent timer.";
                  leaf max-interval {
                    type uint32 {
                      range "1..300000";
                    }
                    // NCS drop must statement
                    // NCS drop default statement
                    description
                      "Maximum interval for receiving OSPF LSAs.";
                  }
                  leaf start-interval {
                    type uint32 {
                      range "0..60000";
                    }
                    // NCS drop must statement
                    // NCS drop default statement
                    description
                      "Initial interval for receiving OSPF LSAs.";
                  }
                  leaf hold-interval {
                    type uint32 {
                      range "1..60000";
                    }
                    // NCS drop must statement
                    // NCS drop default statement
                    description
                      "Hold interval for receiving OSPF LSAs.";
                  }
                }
              }
            }
            container lsa-arr-supp-flap {
              description
                "Configure the delay timer for LSA acceptance.";
              leaf interval {
                type uint32 {
                  range "0..600";
                }
                units "s";
                // NCS drop default statement
                description
                  "Specifies an interval for suppressing LSA advertising in case of route flapping. The value 0 indicates that LSA advertising is not suppressed.";
              }
              leaf threshold-count {
                type uint32 {
                  range "3..100";
                }
                // NCS drop default statement
                description
                  "Value of the threshold of LSAs to be suppressed.";
              }
            }
            container lsa-originate {
              description
                "Configure interval for receiving LSAs either through an intelligent timer or timer.";
              leaf other-type-interval {
                type uint32 {
                  range "0..10";
                }
                // NCS drop default statement
                description
                  "Specify an updating/originating interval for type3, type4 and type10 LSAs. Interval for updating the LSAs except OSPF router LSAs and network LSAs.";
              }
              choice timer-type {
                // NCS drop default statement
                description
                  "Specify an updating/originating interval for type3, type4 and type10 LSAs.";
                case intelligent-timer {
                  description
                    "Specify an intelligent timer for router LSA, network LSA, external LSA and NSSA LSA.";
                  leaf max-interval {
                    type uint32 {
                      range "1..300000";
                    }
                    // NCS drop must statement
                    // NCS drop default statement
                    description
                      "Maximum interval for updating OSPF LSAs.";
                  }
                  leaf start-interval {
                    type uint32 {
                      range "0..60000";
                    }
                    // NCS drop must statement
                    // NCS drop default statement
                    description
                      "Initial interval for updating OSPF LSAs.";
                  }
                  leaf hold-interval {
                    type uint32 {
                      range "1..60000";
                    }
                    // NCS drop must statement
                    // NCS drop default statement
                    description
                      "Hold interval for updating OSPF LSAs.";
                  }
                }
              }
            }
            container lsa-org-supp-flap {
              description
                "Configure the delay timer for LSA generation.";
              leaf interval {
                type uint32 {
                  range "0..600";
                }
                units "s";
                // NCS drop default statement
                description
                  "Specifies an interval for suppressing LSA advertising in case of route flapping. The value 0 indicates that LSA advertising is not suppressed.";
              }
              leaf threshold-count {
                type uint32 {
                  range "3..100";
                }
                // NCS drop default statement
                description
                  "Value of the threshold of LSAs to be suppressed.";
              }
            }
            container spf-schedule {
              description
                "Configure the interval for SPF calculation.";
              choice schedule-type {
                // NCS drop default statement
                description
                  "SPF schedule interval.";
                case timer {
                  description
                    "Specify an updating/originating interval for type3, type4 and type10 LSAs.";
                  leaf interval {
                    type uint32 {
                      range "1..10";
                    }
                    units "s";
                    description
                      "Interval for OSPF SPF calculation. By adjusting the interval for SPF calculation, you can prevent the occupation of too many bandwidth and router resources caused by frequent network changes.";
                  }
                }
                case intelligent-timer {
                  description
                    "Specify an intelligent timer.";
                  leaf max-interval {
                    type uint32 {
                      range "1..300000";
                    }
                    units "ms";
                    // NCS drop must statement
                    // NCS drop default statement
                    description
                      "Maximum interval for OSPF SPF calculation set through an intelligent timer. By adjusting the interval for SPF calculation, you can prevent the occupation of too many bandwidths and device resources caused by frequent network changes.";
                  }
                  leaf start-interval {
                    type uint32 {
                      range "1..60000";
                    }
                    units "ms";
                    // NCS drop must statement
                    // NCS drop default statement
                    description
                      "Initial interval for OSPF SPF calculation set through an intelligent timer. By adjusting the interval for SPF calculation, you can prevent the occupation of too many bandwidth and router resources caused by frequent network changes.";
                  }
                  leaf hold-interval {
                    type uint32 {
                      range "1..60000";
                    }
                    units "ms";
                    // NCS drop must statement
                    // NCS drop default statement
                    description
                      "Hold interval for OSPF SPF calculation set through an intelligent timer. By adjusting the interval for calculating SPF, you can prevent the occupation of too many bandwidth and router resources caused by frequent network changes.";
                  }
                  leaf conserv-flag {
                    type boolean;
                    // NCS drop default statement
                    description
                      "Enable/disable conservative mode.";
                  }
                }
                case millisecond {
                  description
                    "Specify an interval.";
                  leaf millisecond {
                    type uint32 {
                      range "1..10000";
                    }
                    units "ms";
                    description
                      "Interval for OSPF SPF calculation. By adjusting the interval for SPF calculation, you can prevent the occupation of too many bandwidths and device resources caused by frequent network changes.";
                  }
                }
              }
            }
          }
          container bfd {
            description
              "Configure BFD in a OSPF process.";
            leaf enable {
              type boolean;
              // NCS drop default statement
              description
                "Enable/disable BFD in an OSPF process.";
            }
            leaf min-rx {
              type uint32 {
                range "3..20000";
              }
              units "ms";
              description
                "Minimum interval for receiving BFD packets from the peer end. The range and default are based on PAF.";
            }
            leaf min-tx {
              type uint32 {
                range "3..20000";
              }
              units "ms";
              description
                "Minimum interval for sending BFD packets to the peer end. The range and default are based on PAF.";
            }
            leaf detect-multiplier {
              type uint32 {
                range "3..50";
              }
              // NCS drop default statement
              description
                "Local detection multiplier.";
            }
            leaf incr-cost {
              type uint32 {
                range "1..65535";
              }
              description
                "BFD sync cost.";
            }
            leaf frr-binding {
              type boolean;
              // NCS drop default statement
              description
                "Enable/disable bind FRR with BFD.";
            }
          }
          container metric-delay {
            // NCS drop when statement
            description
              "Configure metric delay in a OSPF process.";
            leaf adv-enable {
              type boolean;
              // NCS drop default statement
              description
                "Enable/disable metric delay advertisement.";
            }
            leaf suppress-timer {
              type uint32 {
                range "0..600";
              }
              units "s";
              // NCS drop default statement
              description
                "Metric delay suppress timer.";
            }
            leaf suppress-percent {
              type uint8 {
                range "0..100";
              }
              // NCS drop default statement
              description
                "Metric delay suppress percent threshold.";
            }
            leaf suppress-absolute {
              type uint32 {
                range "0..10000";
              }
              // NCS drop default statement
              description
                "Metric delay suppress absolute threshold.";
            }
          }
          container bier {
            // NCS drop when statement
            description
              "Configure the bier.";
            leaf enable {
              type boolean;
              // NCS drop default statement
              description
                "Enable/disable the bier.";
            }
          }
          container stub-router {
            description
              "Configure stub router is used to configure the router as stub router.";
            leaf flag {
              type live_ncs_stub-router-flag;
              // NCS drop default statement
              description
                "Stub router. The router configured with the stub router command notifies other OSPF routers of not using the stub router to forward data by increasing the metric greater than 65535 of the links in the LSA that is generated by the router.";
            }
            leaf interval {
              // NCS drop when statement
              type uint32 {
                range "5..65535";
              }
              // NCS drop default statement
              description
                "Interval for remaining as the stub router during the active/standby switchover of a router.";
            }
            leaf include-stub {
              // NCS drop when statement
              type boolean;
              // NCS drop default statement
              description
                "Enable/disable set maximum cost for router lsa stub link.";
            }
            leaf external-lsa {
              // NCS drop when statement
              type boolean;
              // NCS drop default statement
              description
                "Enable/disable set maximum cost for external lsa.";
            }
            leaf external-cost {
              // NCS drop when statement
              type uint32 {
                range "1..16777215";
              }
              // NCS drop default statement
              description
                "Advertise external LSAs with configured/default overriding metric.";
            }
            leaf summary-lsa {
              // NCS drop when statement
              type boolean;
              // NCS drop default statement
              description
                "Enable/disable set maximum cost for summary lsa.";
            }
            leaf summary-cost {
              // NCS drop when statement
              type uint32 {
                range "1..16777215";
              }
              // NCS drop default statement
              description
                "Advertise summary LSAs with configured/default overriding metric.";
            }
          }
          container bgp-ls {
            description
              "Configure BGP LS.";
            leaf enable {
              type boolean;
              // NCS drop must statement
              // NCS drop default statement
              description
                "Enable/disable BGP LS.";
            }
            leaf identifier {
              // NCS drop when statement
              type uint32 {
                range "2..65535";
              }
              description
                "Topo identifier.";
            }
          }
          container import-limit {
            presence "Enable import-limit";
            description
              "Configure limits the maximum number of routes to be imported.";
            leaf max-number {
              type uint32 {
                range "1..4294967295";
              }
              // NCS drop mandatory statement
              description
                "Maximum number of external routes that can be imported.";
            }
            leaf threshold-upper {
              type uint32 {
                range "1..100";
              }
              // NCS drop must statement
              // NCS drop default statement
              description
                "Upper threshold of the maximum number of routes that can be imported.";
            }
            leaf threshold-lower {
              type uint32 {
                range "1..100";
              }
              // NCS drop must statement
              // NCS drop default statement
              description
                "Lower threshold of the maximum number of routes that can be imported.";
            }
          }
          container spf-control {
            description
              "Configure SPF calculation control.";
            leaf max-load-balancing {
              type uint32 {
                range "1..128";
              }
              // NCS drop default statement
              description
                "Maximum number of the equal cost routes of the destination address in the routing table. The range and default are based on PAF.";
            }
          }
          container default-para {
            description
              "Configure default parameter.";
            choice cost {
              // NCS drop default statement
              description
                "Cost assigned to the ASE or NSSA LSA generated when an external route is imported.";
              case cost-value {
                description
                  "Default metric of the external routes imported by OSPF.";
                leaf cost-value {
                  type uint32 {
                    range "0..16777214";
                  }
                  // NCS drop default statement
                  description
                    "Default metric of the external routes imported by OSPF.";
                }
              }
              case cost-inherit-metric {
                description
                  "Cost of the imported route is the cost carried in the route. If the cost is not specified, the default cost can be set through the default command.";
                leaf cost-inherit-metric {
                  type empty;
                  description
                    "Cost of the imported route is the cost carried in the route. If the cost is not specified, the default cost can be set through the default command.";
                }
              }
            }
            leaf tag {
              type uint32 {
                range "0..4294967295";
              }
              // NCS drop default statement
              description
                "Tag of an external route.";
            }
            leaf type {
              type live_ncs_external-route-type;
              // NCS drop default statement
              description
                "Type of an external route.";
            }
          }
          container avoid-micro-loop {
            description
              "Configure OSPF avoid microloop.";
            leaf frr-enable {
              type boolean;
              // NCS drop default statement
              description
                "Enable/disable avoid microloop.";
            }
            leaf frr-rib-update-delay {
              type uint32 {
                range "100..5000";
              }
              units "ms";
              // NCS drop default statement
              description
                "Set the maximum interval of delay timer.";
            }
            leaf te-tunnel-enable {
              type boolean;
              // NCS drop default statement
              description
                "Enable/disable TE shortcut tunnel avoid microloop.";
            }
            leaf te-tunnel-rib-update-delay {
              type uint32 {
                range "100..30000";
              }
              units "ms";
              // NCS drop default statement
              description
                "Set the route delivery delay for TE shortcut tunnel.";
            }
          }
          container asbr-summary-prefixs {
            description
              "List of aggregate addresses for OSPF (only for ASBR).";
            list asbr-summary-prefix {
              key "prefix network-mask";
              description
                "Configure aggregate addresses for OSPF (only for ASBR).";
              leaf prefix {
                type inet:ipv4-address-no-zone;
                description
                  "IP address. Prefix is the address after mask.";
              }
              leaf network-mask {
                type inet:ipv4-address-no-zone;
                description
                  "IP address mask.";
              }
              leaf cost {
                type uint32 {
                  range "0..16777214";
                }
                description
                  "Specifies the cost of the aggregated route.";
              }
              leaf distribute-delay {
                type uint32 {
                  range "1..65535";
                }
                units "s";
                description
                  "Distribute delay interval.";
              }
              leaf tag {
                type uint32 {
                  range "0..4294967295";
                }
                description
                  "Specifies that the tag is mainly used to control advertisement of routes through the routing policy.";
              }
              leaf advertise {
                type boolean;
                // NCS drop default statement
                description
                  "Enable/disable the aggregated route is advertised.";
              }
              leaf generate-null-zero {
                // NCS drop when statement
                type boolean;
                // NCS drop default statement
                description
                  "Enable/disable generate black hole route.";
              }
            }
          }
          choice default-route {
            description
              "Notification of default routes to the OSPF routing area.";
            case summary {
              description
                "Summary.";
              container summary {
                // NCS drop when statement
                presence "Enable default-route-advertise summary.";
                description
                  "Configure advertises the type3 summary LSAs of the specified default route.";
                leaf cost {
                  type uint32 {
                    range "0..16777214";
                  }
                  // NCS drop mandatory statement
                  description
                    "Metric of an ASE LSA.";
                }
              }
            }
            case no-summary {
              description
                "No summary.";
              container no-summary {
                presence "Enable default-route-advertise no-summary.";
                description
                  "Configure default routes to the OSPF routing area.";
                leaf enable {
                  type empty;
                  status deprecated;
                  description
                    "Default Route Enable. The node enable is deprecated. You are advised to use the node no-summary.";
                }
                leaf cost {
                  type uint32 {
                    range "0..16777214";
                  }
                  description
                    "Metric of an ASE LSA.";
                }
                leaf tag {
                  type uint32 {
                    range "0..4294967295";
                  }
                  description
                    "Route tag for default imported routes.";
                }
                leaf type {
                  type live_ncs_external-route-type;
                  description
                    "Metric type of an ASE LSA for the default routes.";
                }
                leaf distribute-delay {
                  type uint32 {
                    range "1..65535";
                  }
                  description
                    "Distribute delay timer used for the local router to calculate the default routes advertised by other routers.";
                }
                choice mode {
                  description
                    "Mode for default route.";
                  case permit-calculate-other {
                    description
                      "Set permit calculate other.";
                    leaf permit-calculate-other {
                      type empty;
                      description
                        "To generate and advertise an ASE LSA that describes the default route only when there are valid default routes of other protocols in the routing table of the host. The router configured with permit calculate other still calculates the default routes of other routers.";
                    }
                    leaf permit-ibgp {
                      type empty;
                      description
                        "Match IBGP default route.";
                    }
                  }
                  case always {
                    description
                      "Set always.";
                    leaf always {
                      type empty;
                      description
                        "The router configured with the always parameter does not calculate the default routes of other routers.";
                    }
                  }
                }
                choice policy-type {
                  description
                    "Mode of the policy used for default route.";
                  case route-policy-name {
                    description
                      "Set a route policy name.";
                    leaf route-policy-name {
                      type leafref {
                        path "/ncs:devices/ncs:device/ncs:live-status/rtp:routing-policy/rtp:policy-definitions/rtp:policy-definition/rtp:name" {
                          tailf:xpath-root 3;
                        }
                      }
                      description
                        "Name of a routing policy. Through the routing policy, the device matches the default routing entry generated by the device that does not run OSPF in the routing table, and advertises the default route according to the parameters set through the routing policy.";
                    }
                  }
                  case route-filter-name {
                    description
                      "Set a route filter name.";
                    leaf route-filter-name {
                      type leafref {
                        path "/ncs:devices/ncs:device/ncs:live-status/xpl:xpl/xpl:route-filters/xpl:route-filter/xpl:name" {
                          tailf:xpath-root 3;
                        }
                      }
                      description
                        "Name of a routing Filter.";
                    }
                  }
                }
              }
            }
          }
          container route-preferences {
            description
              "List of preference of an OSPF route.";
            list route-preference {
              key "route-type";
              // NCS drop max-elements statement
              ext:generated-by "system" {
                ext:filter "route-type='default' or route-type='ase'";
              }
              description
                "Configure preference of an OSPF route.";
              leaf route-type {
                type live_ncs_ospf-route-type;
                description
                  "Router type.";
              }
              leaf preference {
                type uint32 {
                  range "1..255";
                }
                ext:dynamic-default {
                  ext:default-value "10" {
                    // NCS drop when statement
                    description
                      "The default value is 10 when route type is not ase.";
                  }
                  ext:default-value "150" {
                    // NCS drop when statement
                    description
                      "The default value is 150 when route type is ase.";
                  }
                }
                description
                  "Preference of an OSPF route. The default of intra and inter area is 10.And The default of external is 150.";
              }
              choice policy-type {
                description
                  "Type of a filtering rule.";
                case route-policy-name {
                  description
                    "Name of a routing policy.";
                  leaf route-policy-name {
                    type leafref {
                      path "/ncs:devices/ncs:device/ncs:live-status/rtp:routing-policy/rtp:policy-definitions/rtp:policy-definition/rtp:name" {
                        tailf:xpath-root 3;
                      }
                    }
                    description
                      "Name of a routing policy.";
                  }
                }
                case route-filter-name {
                  description
                    "Name of a routing Filter.";
                  leaf route-filter-name {
                    type leafref {
                      path "/ncs:devices/ncs:device/ncs:live-status/xpl:xpl/xpl:route-filters/xpl:route-filter/xpl:name" {
                        tailf:xpath-root 3;
                      }
                    }
                    description
                      "Name of a routing Filter.";
                  }
                }
              }
            }
          }
          container nexthop-weights {
            description
              "List of preference of an equal cost route.";
            list nexthop-weight {
              key "ip-address";
              description
                "Configure preference of an equal cost route.";
              leaf ip-address {
                type inet:ipv4-address-no-zone;
                description
                  "IP address of the next hop.";
              }
              leaf weight {
                type uint32 {
                  range "1..254";
                }
                // NCS drop mandatory statement
                description
                  "Weight of the next hop. After OSPF calculates the equal cost routes, the next hop is chosen from these equal cost routes based on the value of weight. The smaller the value is, the higher the preference is. By default, the weight is 255. This indicates that load balancing is carried out among equal cost routes and packets are forwarded at the same time without the preference being set.";
              }
            }
          }
          container prefix-prioritys {
            description
              "List of priority of OSPF route.";
            list prefix-priority {
              key "priority";
              description
                "Configure priority of OSPF route.";
              leaf priority {
                type live_ncs_prefix-priority;
                description
                  "Convergence priority of OSPF routes.";
              }
              leaf ip-prefix {
                type leafref {
                  path "/ncs:devices/ncs:device/ncs:live-status/rtp:routing-policy/rtp:ipv4-prefix-filters/rtp:ipv4-prefix-filter/rtp:name" {
                    tailf:xpath-root 3;
                  }
                }
                // NCS drop mandatory statement
                description
                  "Name of the IP prefix list. The value is a string of 1 to 169 characters without spaces. The prefix priority command sets the convergence priority of OSPF routes according to the specified IP prefix list name, and takes effect on the public network only.
                   By default, the convergence priority of public OSPF host routes is medium, the convergence priority of directly connected routes is high, the convergence priority of static routes is medium, and the convergence priority of the routes of other protocols (such as BGP and RIP) is low. On the private network, OSPF 32 bit host routes are globally identified as medium.";
              }
            }
          }
          container ecmp-prefer {
            description
              "Configure equal cost multipath preference of OSPF routes.";
            leaf te-tunnel {
              type boolean;
              // NCS drop must statement
              // NCS drop default statement
              description
                "Enable/disable TE tunnel interface nexthops.";
            }
            leaf intact {
              type boolean;
              // NCS drop must statement
              // NCS drop default statement
              description
                "Enable/disable IGP native nexthop.";
            }
          }
          container frr {
            description
              "Configure OSPF fast rerouting.";
            leaf enable {
              type boolean;
              // NCS drop default statement
              description
                "Enable/disable FRR for this particular process.";
            }
            leaf lfa-enable {
              type boolean;
              // NCS drop must statement
              // NCS drop default statement
              description
                "Enable/disable loop free alternate.";
            }
            leaf rlfa-enable {
              type boolean;
              // NCS drop must statement
              // NCS drop default statement
              description
                "Enable/disable remote lfa.";
            }
            leaf rlfa-max-cost {
              // NCS drop when statement
              type uint32 {
                range "1..4294967295";
              }
              // NCS drop default statement
              description
                "Remote lfa tunnel ldp maximum-reachable-cost.";
            }
            leaf tilfa-enable {
              type boolean;
              // NCS drop must statement
              // NCS drop default statement
              description
                "Enable/disable TILFA.";
            }
            container tiebreaker {
              // NCS drop when statement
              // NCS drop must statement
              // NCS drop must statement
              // NCS drop must statement
              description
                "Configure tiebreaker for multiple backups.";
              leaf node-protect {
                type uint8 {
                  range "1..255";
                }
                // NCS drop default statement
                description
                  "Set the value of node protect preference. The preference value 5 is reserved for SRLG disjoint type, cannot be configured.";
              }
              leaf lowest-cost {
                type uint8 {
                  range "1..255";
                }
                // NCS drop default statement
                description
                  "Set the value of lowcost preference.";
              }
              leaf ldp-sync {
                type uint8 {
                  range "1..255";
                }
                // NCS drop default statement
                description
                  "Prefer backup nexthop with ldp sync.";
              }
            }
            container route-policy {
              // NCS drop when statement
              description
                "Configure FRR route policy.";
              choice policy-type {
                description
                  "Type of a filtering rule.";
                case route-policy-name {
                  description
                    "Name of a routing policy.";
                  leaf route-policy-name {
                    type leafref {
                      path "/ncs:devices/ncs:device/ncs:live-status/rtp:routing-policy/rtp:policy-definitions/rtp:policy-definition/rtp:name" {
                        tailf:xpath-root 3;
                      }
                    }
                    description
                      "Name of a routing policy.";
                  }
                }
                case route-filter-name {
                  description
                    "Name of a routing filter.";
                  leaf route-filter-name {
                    type leafref {
                      path "/ncs:devices/ncs:device/ncs:live-status/xpl:xpl/xpl:route-filters/xpl:route-filter/xpl:name" {
                        tailf:xpath-root 3;
                      }
                    }
                    description
                      "Name of a routing filter.";
                  }
                }
              }
            }
            container rlfa-tunnel {
              // NCS drop when statement
              description
                "Configure remote LFA ip prefix.";
              choice policy-type {
                description
                  "Name of a routing policy.";
                case ip-prefix-name {
                  description
                    "Set a route policy name.";
                  leaf ip-prefix-name {
                    type leafref {
                      path "/ncs:devices/ncs:device/ncs:live-status/rtp:routing-policy/rtp:ipv4-prefix-filters/rtp:ipv4-prefix-filter/rtp:name" {
                        tailf:xpath-root 3;
                      }
                    }
                    description
                      "To filter PQ node. Those nodes which don't pass filter can't be PQ node.";
                  }
                }
              }
            }
          }
          container local-mt-filter {
            // NCS drop when statement
            description
              "Configure OSPF local multicast topology filtering in routing updates.";
            choice filter-policy {
              description
                "Type of a filtering rule.";
              case acl-name-or-num {
                description
                  "ACL name or ACL number. ACL name: specify the ACL name. ACL num: apply basic ACL.";
                leaf acl-name-or-num {
                  type leafref {
                    path "/ncs:devices/ncs:device/ncs:live-status/acl:acl/acl:groups/acl:group/acl:identity" {
                      tailf:xpath-root 3;
                    }
                  }
                  // NCS drop must statement
                  description
                    "ACL name or ACL number. ACL name: specify the ACL name. ACL num: apply basic ACL.";
                }
              }
              case ip-prefix {
                description
                  "Ip prefix name.";
                leaf ip-prefix {
                  type leafref {
                    path "/ncs:devices/ncs:device/ncs:live-status/rtp:routing-policy/rtp:ipv4-prefix-filters/rtp:ipv4-prefix-filter/rtp:name" {
                      tailf:xpath-root 3;
                    }
                  }
                  description
                    "Ip prefix name.";
                }
              }
              case route-policy-name {
                description
                  "Name of a routing policy.";
                leaf route-policy-name {
                  type leafref {
                    path "/ncs:devices/ncs:device/ncs:live-status/rtp:routing-policy/rtp:policy-definitions/rtp:policy-definition/rtp:name" {
                      tailf:xpath-root 3;
                    }
                  }
                  description
                    "Name of a routing policy.";
                }
              }
              case route-filter-name {
                description
                  "Name of a routing filter.";
                leaf route-filter-name {
                  type leafref {
                    path "/ncs:devices/ncs:device/ncs:live-status/xpl:xpl/xpl:route-filters/xpl:route-filter/xpl:name" {
                      tailf:xpath-root 3;
                    }
                  }
                  description
                    "Name of a routing filter.";
                }
              }
            }
          }
          container peers {
            description
              "List of the IP address and DR priority of the neighbor router on the NBMA network.";
            list peer {
              key "ip-address";
              description
                "Configure the IP address and DR priority of the neighbor router on the NBMA network.";
              leaf ip-address {
                type inet:ipv4-address-no-zone;
                description
                  "IP address of the neighbor router.";
              }
              leaf priority {
                type uint8 {
                  range "0..255";
                }
                // NCS drop default statement
                description
                  "To set the IP address and DR priority of the neighbor router on the NBMA network.";
              }
            }
          }
          container filter-lsa-outs {
            description
              "List of LSA filter policy.";
            list filter-lsa-out {
              key "peer-ip-addr";
              // NCS drop max-elements statement
              description
                "Configure LSA filter policy.";
              leaf peer-ip-addr {
                type inet:ipv4-address-no-zone;
                description
                  "IP address of the P2MP neighbor.";
              }
              choice type {
                // NCS drop mandatory statement
                description
                  "Set filter lsa out type.";
                case total {
                  description
                    "Filter total types of LSAs.";
                  leaf all-flag {
                    type empty;
                    description
                      "Filter all types of LSAs.";
                  }
                }
                case other {
                  description
                    "Filter other types of LSAs.";
                  leaf sum-flag {
                    type empty;
                    description
                      "Filter type 3 Summary LSAs.";
                  }
                  choice sum-filter {
                    description
                      "Type of a filtering rule.";
                    case sum-acl-name {
                      description
                        "ACL Name or ACL Number. ACL Name: specify the ACL name. ACL Num: apply basic ACL.";
                      leaf sum-acl-name {
                        // NCS drop when statement
                        type leafref {
                          path "/ncs:devices/ncs:device/ncs:live-status/acl:acl/acl:groups/acl:group/acl:identity" {
                            tailf:xpath-root 3;
                          }
                        }
                        // NCS drop must statement
                        description
                          "ACL Name or ACL Number. ACL Name: specify the ACL name. ACL Num: apply basic ACL.";
                      }
                    }
                  }
                  leaf ase-flag {
                    type empty;
                    description
                      "Filter type-5 ASE LSAs.";
                  }
                  choice ase-filter {
                    description
                      "Type of a filtering rule.";
                    case ase-acl-name {
                      description
                        "ACL Name or ACL Number. ACL Name: specify the ACL name. ACL Num: apply basic ACL.";
                      leaf ase-acl-name {
                        // NCS drop when statement
                        type leafref {
                          path "/ncs:devices/ncs:device/ncs:live-status/acl:acl/acl:groups/acl:group/acl:identity" {
                            tailf:xpath-root 3;
                          }
                        }
                        // NCS drop must statement
                        description
                          "ACL Name or ACL Number. ACL Name: specify the ACL name. ACL Num: apply basic ACL.";
                      }
                    }
                  }
                  leaf nssa-flag {
                    type empty;
                    description
                      "Filter type7 NSSA LSAs.";
                  }
                  choice nssa-filter {
                    description
                      "Type of a filtering rule.";
                    case nssa-acl-name {
                      description
                        "ACL Name or ACL Number. ACL Name: specify the ACL name. ACL Num: apply basic ACL.";
                      leaf nssa-acl-name {
                        // NCS drop when statement
                        type leafref {
                          path "/ncs:devices/ncs:device/ncs:live-status/acl:acl/acl:groups/acl:group/acl:identity" {
                            tailf:xpath-root 3;
                          }
                        }
                        // NCS drop must statement
                        description
                          "ACL Name or ACL Number. ACL Name: specify the ACL name. ACL Num: apply basic ACL.";
                      }
                    }
                  }
                }
              }
            }
          }
          choice graceful-restart {
            description
              "Information about OSPF GR.";
            case gr-ietf {
              description
                "Information about OSPF IETF GR.";
              container gr-ietf {
                // NCS drop when statement
                presence "Enable OSPF IETF GR.";
                description
                  "Configure OSPF IETF GR.";
                choice helper-role-mode {
                  description
                    "Information about OSPF IETF GR helper role.";
                  case never {
                    description
                      "Forbid to support enable mode.";
                    leaf never {
                      type empty;
                      description
                        "Forbid to support enable mode.";
                    }
                  }
                  case work-mode {
                    description
                      "Information about OSPF IETF GR.";
                    leaf planned-only {
                      type empty;
                      description
                        "To support only planned GR on routers.";
                    }
                    leaf ignore-external-lsa {
                      type empty;
                      description
                        "Ignore external lsa check (type5 and type7 LSAs).";
                    }
                    choice match-mode {
                      description
                        "Name of a routing policy.";
                      case acl-name-or-num {
                        description
                          "Specify the basic ACL number or ACL name for filtering peer.";
                        leaf acl-name-or-num {
                          type leafref {
                            path "/ncs:devices/ncs:device/ncs:live-status/acl:acl/acl:groups/acl:group/acl:identity" {
                              tailf:xpath-root 3;
                            }
                          }
                          // NCS drop must statement
                          description
                            "Specify the basic ACL number or ACL name for filtering peer.";
                        }
                      }
                      case ip-prefix-name {
                        description
                          "Specify the IP prefix name for filtering peers.";
                        leaf ip-prefix-name {
                          type leafref {
                            path "/ncs:devices/ncs:device/ncs:live-status/rtp:routing-policy/rtp:ipv4-prefix-filters/rtp:ipv4-prefix-filter/rtp:name" {
                              tailf:xpath-root 3;
                            }
                          }
                          description
                            "Specify the IP prefix name for filtering peers.";
                        }
                      }
                    }
                  }
                }
              }
            }
            case gr-non-ietf {
              description
                "Information about OSPF NON IETF GR.";
              container gr-non-ietf {
                // NCS drop when statement
                presence "Enable OSPF NON IETF GR.";
                description
                  "Configure OSPF NON IETF GR.";
              }
            }
          }
          container flood-control {
            presence "Enable flood-control";
            description
              "Configure OSPF flooding control.";
            leaf number {
              type uint32 {
                range "1..1000";
              }
              // NCS drop default statement
              description
                "Specify the update packet number to send.";
            }
            leaf interval {
              type uint32 {
                range "30..100000";
              }
              // NCS drop default statement
              description
                "Specify the update packet timer interval to send.";
            }
          }
          container dn-bit {
            // NCS drop when statement
            description
              "Configure VPN optionA feature will help PEs in inter AS exchange routes through OSPF. VPN optionA provide two ways to suppress DN bit so that so that inter AS can exchange routes through OSPF. First way dose not set DN bit while import routes from BGP, second way dose not check DN bit while learning the routes from neighbor router. In both the scenario PE will be able to learn route and propagate the route in the new VPN cloud.";
            leaf set-ase {
              type boolean;
              // NCS drop default statement
              description
                "Enable/disable setting of DN bit in all ASE LSA, applicable in private network.";
            }
            leaf set-nssa {
              type boolean;
              // NCS drop default statement
              description
                "Enable/disable setting of DN bit in all NSSA LSA, applicable in private network.";
            }
            leaf set-summary {
              type boolean;
              // NCS drop default statement
              description
                "Enable/disable setting of DN bit in all summary LSA, applicable in private network.";
            }
            leaf check-ase {
              type boolean;
              // NCS drop default statement
              description
                "Enable/disable checking of DN bit in all ASE LSA, applicable in private network.";
            }
            leaf check-nssa {
              type boolean;
              // NCS drop default statement
              description
                "Enable/disable checking of DN bit in all NSSA LSA, applicable in private network.";
            }
            leaf check-summary {
              type boolean;
              // NCS drop default statement
              description
                "Enable/disable checking of DN bit in all summary LSA, applicable in private network.";
            }
            container summary-router-ids {
              // NCS drop when statement
              description
                "List of router ID for which checking for DN bit summary LSA is disabled, applicable in private network.";
              list summary-router-id {
                key "router-id";
                description
                  "Configure router ID for which checking for DN bit summary LSA is disabled, applicable in private network.";
                leaf router-id {
                  type inet:ipv4-address-no-zone;
                  description
                    "Router ID for which checking for DN bit summary LSA is disabled, applicable in private network.";
                }
              }
            }
          }
          container filter-import {
            presence "filter policy import";
            description
              "Configure the filter policy import command. You can set the rules for filtering intra area, inter area, and AS external routes of an OSPF process.";
            choice policy-type {
              // NCS drop mandatory statement
              description
                "Type of a filtering rule.";
              case basic-acl {
                description
                  "Apply basic ACL name or ACL number.";
                leaf name-or-num {
                  type leafref {
                    path "/ncs:devices/ncs:device/ncs:live-status/acl:acl/acl:groups/acl:group/acl:identity" {
                      tailf:xpath-root 3;
                    }
                  }
                  // NCS drop must statement
                  description
                    "Apply basic ACL name or ACL number.";
                }
              }
              case ip-prefix {
                description
                  "Set the name of an IP prefix list.";
                leaf ip-prefix {
                  type leafref {
                    path "/ncs:devices/ncs:device/ncs:live-status/rtp:routing-policy/rtp:ipv4-prefix-filters/rtp:ipv4-prefix-filter/rtp:name" {
                      tailf:xpath-root 3;
                    }
                  }
                  description
                    "Set the name of an IP prefix list.";
                }
              }
              case route-policy {
                description
                  "Set a route policy name.";
                leaf route-policy {
                  type leafref {
                    path "/ncs:devices/ncs:device/ncs:live-status/rtp:routing-policy/rtp:policy-definitions/rtp:policy-definition/rtp:name" {
                      tailf:xpath-root 3;
                    }
                  }
                  description
                    "Set a route policy name.";
                }
              }
              case route-filter {
                description
                  "Set a route filter name.";
                leaf route-filter {
                  type leafref {
                    path "/ncs:devices/ncs:device/ncs:live-status/xpl:xpl/xpl:route-filters/xpl:route-filter/xpl:name" {
                      tailf:xpath-root 3;
                    }
                  }
                  description
                    "Set a route filter name.";
                }
              }
            }
            leaf secondary {
              type boolean;
              // NCS drop must statement
              // NCS drop default statement
              description
                "Enable/disable secondary flag.";
            }
          }
          container filter-exports {
            description
              "List of the filter policy export command. You can set the rules for filtering the routes imported through the import route (OSPF) command when the routes are advertised in type5 LSAs to the OSPF AS.";
            list filter-export {
              key "protocol protocol-id";
              description
                "Configure the filter policy export command. You can set the rules for filtering the routes imported through the import route (OSPF) command when the routes are advertised in type5 LSAs to the OSPF AS.";
              leaf protocol {
                type live_ncs_filter-rt-protocol;
                description
                  "Protocol that advertises routes.";
              }
              leaf protocol-id {
                type uint32 {
                  range "1..4294967295";
                }
                // NCS drop must statement
                description
                  "Process ID when the advertised protocol is RIP, ISIS, or OSPF.";
              }
              choice policy-type {
                // NCS drop mandatory statement
                description
                  "Type of a filtering rule.";
                case basic-acl {
                  description
                    "Apply basic ACL name or ACL number.";
                  leaf name-or-num {
                    type leafref {
                      path "/ncs:devices/ncs:device/ncs:live-status/acl:acl/acl:groups/acl:group/acl:identity" {
                        tailf:xpath-root 3;
                      }
                    }
                    // NCS drop must statement
                    description
                      "Apply basic ACL name or ACL number.";
                  }
                }
                case ip-prefix {
                  description
                    "Set the name of an IP prefix list.";
                  leaf ip-prefix {
                    type leafref {
                      path "/ncs:devices/ncs:device/ncs:live-status/rtp:routing-policy/rtp:ipv4-prefix-filters/rtp:ipv4-prefix-filter/rtp:name" {
                        tailf:xpath-root 3;
                      }
                    }
                    description
                      "Set the name of an IP prefix list.";
                  }
                }
                case route-policy {
                  description
                    "Set a route policy name.";
                  leaf route-policy {
                    type leafref {
                      path "/ncs:devices/ncs:device/ncs:live-status/rtp:routing-policy/rtp:policy-definitions/rtp:policy-definition/rtp:name" {
                        tailf:xpath-root 3;
                      }
                    }
                    description
                      "Set a route policy name.";
                  }
                }
              }
            }
          }
          container import-routes {
            description
              "List of import the routes learned from other routing protocols.";
            list import-route {
              key "protocol process-id";
              description
                "Configure import the routes learned from other routing protocols.";
              leaf protocol {
                type live_ncs_import-rt-protocol;
                description
                  "Routing protocol whose routes are imported.";
              }
              leaf process-id {
                type uint32 {
                  range "0..4294967295";
                }
                // NCS drop must statement
                description
                  "Process ID of the routing protocol whose routes are imported. It needs to be set only when the protocol is RIP, OSPF, or ISIS.";
              }
              leaf cost {
                type uint32 {
                  range "0..16777214";
                }
                description
                  "Route cost.";
              }
              leaf tag {
                type uint32 {
                  range "0..4294967295";
                }
                description
                  "Route tag of an external LSA.";
              }
              leaf type {
                type live_ncs_external-route-type;
                description
                  "Metric type of an external LSA.";
              }
              leaf permit-ibgp {
                type boolean;
                // NCS drop must statement
                // NCS drop default statement
                description
                  "Enable/disable to import IBGP routes.";
              }
              choice policy-type {
                description
                  "Type of a filtering rule.";
                case route-policy-name {
                  description
                    "Name of a routing policy.";
                  leaf route-policy-name {
                    type leafref {
                      path "/ncs:devices/ncs:device/ncs:live-status/rtp:routing-policy/rtp:policy-definitions/rtp:policy-definition/rtp:name" {
                        tailf:xpath-root 3;
                      }
                    }
                    description
                      "Name of a routing policy.";
                  }
                }
              }
            }
          }
          container silent-interfaces {
            // NCS drop when statement
            description
              "List of interface. To prevent the OSPF routing information from being received by routers in a network segment and forbid the local router to receive the routing update information that is advertised by other routers in the network segment, you can use the silent interface command to suppress the interface to receive or send the OSPF packets.";
            list silent-interface {
              key "if-name";
              description
                "Configure interface. To prevent the OSPF routing information from being received by routers in a network segment and forbid the local router to receive the routing update information that is advertised by other routers in the network segment, you can use the silent interface command to suppress the interface to receive or send the OSPF packets.";
              leaf if-name {
                type leafref {
                  path "/ncs:devices/ncs:device/ncs:live-status/ifm:ifm/ifm:interfaces/ifm:interface/ifm:name" {
                    tailf:xpath-root 3;
                  }
                }
                description
                  "Interface name.";
              }
            }
          }
          container undo-silent-interfaces {
            // NCS drop when statement
            description
              "List of interface. Enables sending and receiving packet on this interface when true. This information is useful when sending and receiving packet is suppressed on all interface on process level and user want it to be enabled on certain interface.";
            list undo-silent-interface {
              key "if-name";
              description
                "Configure interface. Enables sending and receiving packet on this interface when true. This information is useful when sending and receiving packet is suppressed on all interface on process level and user want it to be enabled on certain interface.";
              leaf if-name {
                type leafref {
                  path "/ncs:devices/ncs:device/ncs:live-status/ifm:ifm/ifm:interfaces/ifm:interface/ifm:name" {
                    tailf:xpath-root 3;
                  }
                }
                description
                  "Interface name.";
              }
            }
          }
          container cost-bindings {
            description
              "List of cost-binding. Indicate cost of routing from indicated router source ID binding interface.";
            list cost-binding {
              key "router-id if-name";
              description
                "Configure cost-binding. Indicate cost of routing from indicated router source ID binding interface.";
              leaf router-id {
                type inet:ipv4-address-no-zone;
                description
                  "Source router ID.";
              }
              leaf if-name {
                type leafref {
                  path "/ncs:devices/ncs:device/ncs:live-status/ifm:ifm/ifm:interfaces/ifm:interface/ifm:name" {
                    tailf:xpath-root 3;
                  }
                }
                description
                  "Interface name.";
              }
            }
          }
          container areas {
            description
              "List of OSPF area.";
            list area {
              key "area-id";
              description
                "Configure OSPF area.";
              leaf area-id {
                type inet:ipv4-address-no-zone;
                description
                  "Area ID.";
              }
              leaf area-type {
                type live_ncs_area-type;
                // NCS drop default statement
                description
                  "Area type.";
              }
              leaf description {
                type string {
                  length "1..80";
                  pattern '([^?]*)';
                }
                description
                  "Description of an OSPF area.";
              }
              container networks {
                description
                  "List of the interface that runs OSPF and the area to which the interface belongs to.";
                list network {
                  key "ip-address mask";
                  description
                    "Configure the interface that runs OSPF and the area to which the interface belongs to.";
                  leaf ip-address {
                    type inet:ipv4-address-no-zone;
                    description
                      "Specifies the address of the network segment where the interface resides.";
                  }
                  leaf mask {
                    type inet:ipv4-address-no-zone;
                    description
                      "Specifies the wildcard mask of IP address.";
                  }
                  leaf description {
                    type string {
                      length "1..80";
                      pattern '([^?]*)';
                    }
                    description
                      "Specifies the description of the specified OSPF network segment.";
                  }
                }
              }
              container stub {
                // NCS drop when statement
                description
                  "Configure stub area.";
                leaf backbone-peer-ignore {
                  type boolean;
                  // NCS drop default statement
                  description
                    "Enable/disable ignore backbone peer for Stub area.";
                }
                leaf no-summary {
                  type boolean;
                  // NCS drop default statement
                  description
                    "Enable/disable forbid an ABR to Send Summary LSAs to the Stub Area.";
                }
                leaf default-cost {
                  type int32 {
                    range "0..16777214";
                  }
                  // NCS drop default statement
                  description
                    "Cost of the default Type3 routes that are sent by an OSPF process to a stub area or an NSSA area. The value is an integer ranging from 1 to 16777214. This parameter takes effect only when it is configured on the ABR connected to a stub area or an NSSA area. The default is 1.";
                }
              }
              container nssa {
                // NCS drop when statement
                description
                  "Configure nssa area.";
                leaf no-summary {
                  type boolean;
                  // NCS drop default statement
                  description
                    "Enable/disable forbid an ABR to Send Summary LSAs to the NSSA Area.";
                }
                leaf translator-always {
                  type boolean;
                  // NCS drop default statement
                  description
                    "Enable/disable the router to act as translator always for NSSA Area.";
                }
                leaf default-route-advertise {
                  type boolean;
                  // NCS drop default statement
                  description
                    "Enable/disable originate Type 7 default into NSSA area.";
                }
                leaf backbone-peer-ignore {
                  // NCS drop when statement
                  type boolean;
                  // NCS drop default statement
                  description
                    "Enable/disable ignore backbone peer for Nssa area.";
                }
                leaf no-import-route {
                  type boolean;
                  // NCS drop default statement
                  description
                    "Enable/disable redistribute type 7 LSA into this area.";
                }
                leaf set-n-bit {
                  type boolean;
                  // NCS drop default statement
                  description
                    "Enable/disable setting of 'N' bit in the DD packet.";
                }
                leaf suppress-fa {
                  type boolean;
                  // NCS drop default statement
                  description
                    "Enable/disable the forwarding address as 0 for all translated type 5 LSAs.";
                }
                leaf zero-address-forwarding {
                  type boolean;
                  // NCS drop default statement
                  description
                    "Enable/disable allow zero forwarding address for redistributed type 7 LSA.";
                }
                leaf translator-interval {
                  type uint32 {
                    range "1..120";
                  }
                  // NCS drop default statement
                  description
                    "Translator interval.";
                }
                leaf default-cost {
                  type int32 {
                    range "0..16777214";
                  }
                  // NCS drop default statement
                  description
                    "Cost of the default Type3 routes that are sent by an OSPF process to a stub area or an NSSA area. This parameter takes effect only when it is configured on the ABR connected to a stub area or an NSSA area.";
                }
              }
              container ldp-sync {
                description
                  "Configure timer ldp sync.";
                leaf enable {
                  type boolean;
                  // NCS drop default statement
                  description
                    "Enable/disable LDP and OSPF synchronization on area.";
                }
                choice hold-cost-max {
                  // NCS drop default statement
                  description
                    "Set timer ldp sync.";
                  case timer {
                    description
                      "Set timer ldp sync.";
                    leaf timer {
                      type uint32 {
                        range "0..65535";
                      }
                      units "s";
                      description
                        "The interval for sending OSPF LSAs to advertise the maximum metric on the local device.";
                    }
                  }
                  case infinite {
                    description
                      "Always advertise the maximum cost.";
                    leaf infinite {
                      type boolean;
                      // NCS drop must statement
                      // NCS drop default statement
                      description
                        "Enable/disable always advertise the maximum cost.";
                    }
                  }
                }
              }
              container mpls-te {
                // NCS drop when statement
                description
                  "Configure OSPF processes enabled with the TE capability.";
                leaf enable {
                  type boolean;
                  // NCS drop must statement
                  // NCS drop default statement
                  description
                    "Enable/disable TE capability of the OSPF process in the specified area.";
                }
                leaf standard-complying {
                  type boolean;
                  // NCS drop must statement
                  // NCS drop default statement
                  description
                    "Enable/disable accept the LSAs in standard format only.";
                }
              }
              container authentication {
                // NCS drop must statement
                description
                  "Configure authentication. The encryption algorithm MD5 has a low security, which may bring security risks. Using more secure authentication is recommended.";
                leaf mode {
                  type live_ncs_area-authen-mode;
                  // NCS drop default statement
                  description
                    "Set authentication type.";
                }
                leaf auth-text-simple {
                  // NCS drop when statement
                  type pub-type:live_ncs_password;
                  description
                    "Simple authentication key. The password is a string ranging from 1 to 8 characters for a unencrypted password and 24 to 128 characters for a encrypted password.";
                }
                leaf key-id {
                  // NCS drop when statement
                  type uint32 {
                    range "1..255";
                  }
                  description
                    "Authentication identifier.";
                }
                leaf auth-text-md5 {
                  // NCS drop when statement
                  type pub-type:live_ncs_password-extend;
                  description
                    "Encrypted authentication password.";
                }
                leaf key-chain-name {
                  // NCS drop when statement
                  type string {
                    length "1..47";
                    pattern '[^A-Z]+';
                  }
                  ext:case-sensitivity "lower-only";
                  // NCS drop mandatory statement
                  description
                    "Keychain name.";
                }
              }
              container abr-summary-prefixs {
                description
                  "List of ABR route aggregation method.";
                list abr-summary-prefix {
                  key "prefix network-mask";
                  description
                    "Configure ABR route aggregation method.";
                  leaf prefix {
                    type inet:ipv4-address-no-zone;
                    description
                      "Specifies the IP address in dotted decimal notation.";
                  }
                  leaf network-mask {
                    type inet:ipv4-address-no-zone;
                    description
                      "Specifies the mask of the IP address. The mask address is in dotted decimal notation.";
                  }
                  choice cost {
                    description
                      "Set the cost.";
                    case cost-value {
                      description
                        "Specifies the cost of the aggregated route. By default, the maximal cost in that of all the routes which are aggregated serves as the cost of the aggregated route.";
                      leaf cost-value {
                        type uint32 {
                          range "0..16777214";
                        }
                        description
                          "Specifies the cost of the aggregated route. By default, the maximal cost in that of all the routes which are aggregated serves as the cost of the aggregated route.";
                      }
                    }
                    case cost-inherit-min {
                      description
                        "Indicates if minimum cost should be inherited. By default, maximum cost is inherited.";
                      leaf cost-inherit-min {
                        // NCS drop when statement
                        type empty;
                        description
                          "Indicates if minimum cost should be inherited. By default, maximum cost is inherited.";
                      }
                    }
                  }
                  leaf hold-max-cost {
                    type uint16 {
                      range "10..1800";
                    }
                    description
                      "Hold max cost duration.";
                  }
                  leaf advertise {
                    type boolean;
                    // NCS drop default statement
                    description
                      "Enable/disable the aggregated route is advertised.";
                  }
                  leaf generate-null-zero {
                    // NCS drop when statement
                    type boolean;
                    // NCS drop default statement
                    description
                      "Enable/disable generate black hole route.";
                  }
                }
              }
              container vlink-peers {
                // NCS drop when statement
                description
                  "List of virtual link and its parameters.";
                list vlink-peer {
                  key "router-id";
                  description
                    "Configure virtual link and its parameters.";
                  leaf router-id {
                    type inet:ipv4-address-no-zone;
                    description
                      "Neighbor Router ID.";
                  }
                  leaf retransmit-interval {
                    type uint32 {
                      range "1..3600";
                    }
                    // NCS drop default statement
                    description
                      "Interval for retransmitting LSAs.";
                  }
                  leaf smart-discover {
                    type boolean;
                    // NCS drop default statement
                    description
                      "Enable/disable smart discover feature.";
                  }
                  container timer {
                    // NCS drop must statement
                    description
                      "Configure timer.";
                    leaf hello-interval {
                      type uint32 {
                        range "1..65535";
                      }
                      // NCS drop default statement
                      description
                        "Time between Hello packets.";
                    }
                    leaf dead-interval {
                      type uint32 {
                        range "1..235926000";
                      }
                      // NCS drop default statement
                      description
                        "Interval after which a neighbor is declared dead.";
                    }
                    leaf trans-delay-interval {
                      type uint32 {
                        range "1..3600";
                      }
                      // NCS drop default statement
                      description
                        "Delay for transmitting LSAs.";
                    }
                  }
                  container authentication {
                    description
                      "Configure authentication. The encryption algorithm MD5 has a low security, which may bring security risks. Using more secure authentication is recommended.";
                    leaf mode {
                      type live_ncs_intf-authen-mode;
                      // NCS drop default statement
                      description
                        "Set authentication type: Simple authentication type, Md5/HMAC MD5/HMAC SHA256 authentication type.";
                    }
                    leaf auth-text-simple {
                      // NCS drop when statement
                      type pub-type:live_ncs_password;
                      description
                        "Simple authentication key. The password is a string ranging from 1 to 8 characters for a unencrypted password and 24 to 128 characters for a encrypted password.";
                    }
                    leaf key-id {
                      // NCS drop when statement
                      type uint32 {
                        range "1..255";
                      }
                      // NCS drop must statement
                      description
                        "Authentication identifier.";
                    }
                    leaf auth-text-md5 {
                      // NCS drop when statement
                      type pub-type:live_ncs_password-extend;
                      // NCS drop must statement
                      description
                        "MD5/HMAC MD5/HMAC SHA256 authentication password.";
                    }
                    leaf key-chain-name {
                      // NCS drop when statement
                      type string {
                        length "1..47";
                        pattern '[^A-Z]+';
                      }
                      ext:case-sensitivity "lower-only";
                      // NCS drop mandatory statement
                      description
                        "Keychain name.";
                    }
                  }
                }
              }
              container sham-links {
                // NCS drop when statement
                description
                  "List of sham link and its parameters.";
                list sham-link {
                  key "src-addr dest-addr";
                  description
                    "Configure sham link and its parameters.";
                  leaf src-addr {
                    type inet:ipv4-address-no-zone;
                    description
                      "Source address.";
                  }
                  leaf dest-addr {
                    type inet:ipv4-address-no-zone;
                    // NCS drop must statement
                    description
                      "Destination address.";
                  }
                  leaf cost {
                    type uint32 {
                      range "1..65535";
                    }
                    // NCS drop default statement
                    description
                      "Cost.";
                  }
                  leaf retransmit-interval {
                    type uint32 {
                      range "1..3600";
                    }
                    // NCS drop default statement
                    description
                      "Interval for retransmitting LSAs.";
                  }
                  leaf smart-discover {
                    type boolean;
                    // NCS drop default statement
                    description
                      "Enable/disable smart discover feature.";
                  }
                  container timer {
                    // NCS drop must statement
                    description
                      "Configure timer.";
                    leaf hello-interval {
                      type uint32 {
                        range "1..65535";
                      }
                      // NCS drop default statement
                      description
                        "Time between Hello packets.";
                    }
                    leaf dead-interval {
                      type uint32 {
                        range "1..235926000";
                      }
                      // NCS drop default statement
                      description
                        "Interval after which a neighbor is declared dead.";
                    }
                    leaf trans-delay-interval {
                      type uint32 {
                        range "1..3600";
                      }
                      // NCS drop default statement
                      description
                        "Delay for transmitting LSAs.";
                    }
                  }
                  container authentication {
                    description
                      "Configure authentication. The encryption algorithm MD5 has a low security, which may bring security risks. Using more secure authentication is recommended.";
                    leaf mode {
                      type live_ncs_intf-authen-mode;
                      // NCS drop default statement
                      description
                        "Set authentication type: Simple authentication type, Md5/HMAC MD5/HMAC SHA256 authentication type.";
                    }
                    leaf auth-text-simple {
                      // NCS drop when statement
                      type pub-type:live_ncs_password;
                      description
                        "Simple authentication key. The password is a string ranging from 1 to 8 characters for a unencrypted password and 24 to 128 characters for a encrypted password.";
                    }
                    leaf key-id {
                      // NCS drop when statement
                      type uint32 {
                        range "1..255";
                      }
                      // NCS drop must statement
                      description
                        "Authentication identifier.";
                    }
                    leaf auth-text-md5 {
                      // NCS drop when statement
                      type pub-type:live_ncs_password-extend;
                      // NCS drop must statement
                      description
                        "MD5/HMAC MD5/HMAC SHA256 authentication password.";
                    }
                    leaf key-chain-name {
                      // NCS drop when statement
                      type string {
                        length "1..47";
                        pattern '[^A-Z]+';
                      }
                      ext:case-sensitivity "lower-only";
                      // NCS drop mandatory statement
                      description
                        "Keychain name.";
                    }
                  }
                }
              }
              container filters {
                description
                  "List of ABR to filter outgoing or incoming summary LSAs of the local area.";
                list filter {
                  key "mode";
                  description
                    "Configure ABR to filter outgoing or incoming summary LSAs of the local area.";
                  leaf mode {
                    type live_ncs_area-filter-mode;
                    description
                      "Using the filter export command, you can configure an ABR to filter outgoing summary LSAs of the local area. Using the filter import command, you can configure an ABR to filter incoming summary LSAs of the local area.";
                  }
                  uses live_ncs_policy-type;
                  leaf include-abr-summary {
                    // NCS drop when statement
                    type boolean;
                    // NCS drop default statement
                    description
                      "Enable/disable include abr summary flag.";
                  }
                }
              }
              container interfaces {
                description
                  "List of the interface enabled with OSPF.";
                list interface {
                  key "name";
                  description
                    "Configure the interface enabled with OSPF.";
                  leaf name {
                    type leafref {
                      path "/ncs:devices/ncs:device/ncs:live-status/ifm:ifm/ifm:interfaces/ifm:interface/ifm:name" {
                        tailf:xpath-root 3;
                      }
                    }
                    // NCS drop must statement
                    description
                      "Interface name. OSPF does not support the configuration of a NULL/LMP/MTUNNEL/RPR/STACKPORT/SIP/ATMBUNDLE/IMAGROUP/Remote-Ap/VBridge interface types.";
                  }
                  leaf network-type {
                    type live_ncs_network-type;
                    ext:dynamic-default;
                    description
                      "Network type of an OSPF interface. By default, the network type of an interface is determined by the physical interface.
                       In the same network segment, if only two routers run OSPF, you can change the network type of an interface to P2P.";
                  }
                  leaf peer-ip-ignore {
                    type live_ncs_peer-ip-ignore-type;
                    // NCS drop must statement
                    // NCS drop default statement
                    description
                      "Ignores the subnet match check in multi access interface when network type P2P is configured along with this option.";
                  }
                  leaf transmit-delay {
                    type int32 {
                      range "1..500";
                    }
                    // NCS drop default statement
                    description
                      "Delay for transmitting LSAs on an interface.";
                  }
                  leaf mtu-enable {
                    type boolean;
                    // NCS drop default statement
                    description
                      "Enable/disable MTU filled in a DD packet when the packet is sent. The default MTU in the DD packet is 0. Using the command, you can manually configure the interface to fill in the MTU field (actual MTU of the interface) when the interface sends DD packets.
                       After a virtual connection is established through the virtual template or tunnel, different vendors may use different MTUs as default settings. To ensure consistency, the MTU is set to 0 by default when the interface sends DD packets. Thus, the ospf mtu-enable command usually does not need to be configured.
                       OSPF does not support the preceding configuration on a null interface.";
                  }
                  leaf dr-priority {
                    type int32 {
                      range "0..255";
                    }
                    // NCS drop default statement
                    description
                      "Priority of the interface that participates in the DR and BDR election. The greater the value is, the higher the priority is. The router whose priority is 0 cannot be elected as a DR or a BDR.";
                  }
                  leaf cost {
                    type uint32 {
                      range "1..65535";
                    }
                    description
                      "To set the cost of an interface. The default value is 1. But the default of Loopback is 0.";
                  }
                  leaf smart-discover {
                    type boolean;
                    // NCS drop default statement
                    description
                      "Enable/disable smart discover on an interface. When the neighbor status of a router or a DR or BDR on the multi address network of the broadcast or NBMA type changes, the router can send hello packets to the neighbor actively rather than wait for the expiration of the hello timer.";
                  }
                  leaf p2mp-mask-ignore {
                    type boolean;
                    // NCS drop default statement
                    description
                      "Enable/disable to ignore the check of network masks on a P2MP network. On a P2MP network, when the lengths of device masks are inconsistent, the check of network masks in hello packets can be ignored through this command. In this case, the OSPF neighbor relationship can be normally established.";
                  }
                  leaf ldp-sync-block {
                    type boolean;
                    // NCS drop must statement
                    // NCS drop default statement
                    description
                      "Enable/disable LDP sync on this interface.";
                  }
                  leaf ldp-sync-enable {
                    type boolean;
                    // NCS drop must statement
                    // NCS drop default statement
                    description
                      "Enable/disable LDP and OSPF synchronization on an interface.";
                  }
                  leaf link-cost {
                    type uint32 {
                      range "1..65535";
                    }
                    description
                      "Link cost to be incremented when link quality is low. The default of Loopback is 0,others is 1.";
                  }
                  leaf suppress-reachability {
                    type live_ncs_suppr-reach;
                    // NCS drop default statement
                    description
                      "Suppress its own prefixes and ignore the suppressed prefixes.";
                  }
                  leaf mpls-ldp-auto-flag {
                    type live_ncs_if-auto-cfg-state;
                    // NCS drop default statement
                    description
                      "Block MPLS LDP auto configuration on the interface.";
                  }
                  leaf dcn-opq-blk-enable {
                    type boolean;
                    // NCS drop default statement
                    description
                      "Enable/disable filter type-10 dcn opaque LSAs.";
                  }
                  leaf peer-hold-max-timer {
                    type uint32 {
                      range "100..1000000";
                    }
                    units "ms";
                    description
                      "Config peer hold max cost interval.";
                  }
                  leaf fallback-cost {
                    // NCS drop when statement
                    type uint32 {
                      range "1..65535";
                    }
                    description
                      "Fallback cost.";
                  }
                  leaf fallback-bw {
                    // NCS drop when statement
                    type uint32 {
                      range "1..4294967295";
                    }
                    units "Mbit/s";
                    // NCS drop mandatory statement
                    description
                      "Fallback bandwidth threshold.";
                  }
                  leaf source-sub-ip-address {
                    type inet:ipv4-address-no-zone;
                    description
                      "Source address indicating a subordinate IP address.";
                  }
                  container frr {
                    description
                      "Configure FRR.";
                    leaf frr-disable {
                      type boolean;
                      // NCS drop default statement
                      description
                        "Enable/disable not use this interface for FRR calculation.";
                    }
                    leaf rlfa-disable {
                      type boolean;
                      // NCS drop default statement
                      description
                        "Enable/disable remote LFA of the Interface.";
                    }
                    container ti-lfa {
                      description
                        "Configure topology independent loop free alternate (TILFA) computation using segment routing.";
                      leaf disable {
                        type boolean;
                        // NCS drop default statement
                        description
                          "Enable/disable topology independent LFA on the interface except Loopback.";
                      }
                    }
                  }
                  container timer {
                    description
                      "Configure timer.";
                    leaf hello-interval {
                      type int32 {
                        range "1..65535";
                      }
                      ext:dynamic-default {
                        ext:default-value "10" {
                          // NCS drop when statement
                          description
                            "The default value is 10 when network-type is p2p or broadcast.";
                        }
                        ext:default-value "30" {
                          // NCS drop when statement
                          description
                            "The default value is 30 when network-type is p2mp or nbma.";
                        }
                      }
                      description
                        "Interval for sending hello packets on an interface.";
                    }
                    leaf hello-conser {
                      type boolean;
                      // NCS drop default statement
                      description
                        "Enable/disable the compensation mechanism of controling the deadtimer to enable.";
                    }
                    leaf dead-interval {
                      type int32 {
                        range "1..235926000";
                      }
                      // NCS drop must statement
                      ext:dynamic-default {
                        ext:default-value "4*(../hello-interval)" {
                          description
                            "The default value of dead interval is 4 times that of hello interval.";
                        }
                      }
                      description
                        "Dead interval of an OSPF neighbor.";
                    }
                    leaf wait-interval {
                      type uint32 {
                        range "1..235926000";
                      }
                      ext:dynamic-default {
                        ext:default-value "../dead-interval" {
                          description
                            "The default value of wait interval is equal to dead interval.";
                        }
                      }
                      description
                        "Wait time.";
                    }
                    leaf poll-interval {
                      type int32 {
                        range "1..3600";
                      }
                      // NCS drop default statement
                      description
                        "Poll interval for sending hello packets. On the NBMA network, after the neighbor is invalid, the router sends hello packets periodically according to the interval set through the ospf timer poll command. The poll interval should be at least four times of the interval for sending hello packets.";
                    }
                    leaf retransmit-interval {
                      type int32 {
                        range "1..3600";
                      }
                      // NCS drop default statement
                      description
                        "Interval for retransmitting LSAs on an interface.";
                    }
                  }
                  container ldp-sync {
                    description
                      "Configure timer ldp sync.";
                    leaf hold-down-timer {
                      type uint16 {
                        range "0..65535";
                      }
                      units "s";
                      // NCS drop default statement
                      description
                        "Hold down interval.";
                    }
                    choice hold-cost-max {
                      description
                        "Set timer ldp sync.";
                      case timer {
                        description
                          "Set max cost interval.";
                        leaf timer {
                          type uint16 {
                            range "0..65535";
                          }
                          units "s";
                          description
                            "Max cost interval range.";
                        }
                      }
                      case infinite {
                        description
                          "Always advertise the maximum cost.";
                        leaf infinite {
                          type empty;
                          description
                            "Always advertise the maximum cost.";
                        }
                      }
                    }
                  }
                  container bfd {
                    description
                      "Configure BFD.";
                    leaf enable {
                      type boolean;
                      // NCS drop must statement
                      // NCS drop default statement
                      description
                        "Enable/disable BFD.";
                    }
                    leaf block {
                      type boolean;
                      // NCS drop must statement
                      // NCS drop default statement
                      description
                        "Enable/disable to prevent the dynamic establishment of a BFD session on an interface.";
                    }
                    leaf detect-multiplier {
                      type uint32 {
                        range "3..50";
                      }
                      // NCS drop default statement
                      description
                        "Local detection multiplier.";
                    }
                    leaf min-tx {
                      type uint32 {
                        range "3..20000";
                      }
                      units "ms";
                      description
                        "Minimum interval for sending BFD packets to the peer end. The ranges and the default value is determined by the PAF.";
                    }
                    leaf min-rx {
                      type uint32 {
                        range "3..20000";
                      }
                      units "ms";
                      description
                        "Minimum interval for receiving BFD packets from the peer end. The ranges and the default value is determined by the PAF.";
                    }
                    leaf frr-binding {
                      type boolean;
                      // NCS drop default statement
                      description
                        "Enable/disable bind FRR with BFD.";
                    }
                    choice incr-cost {
                      description
                        "Interface BFD sync cost.";
                      case incr-cost-block {
                        description
                          "Interface BFD sync cost block.";
                        leaf incr-cost-block {
                          type empty;
                          description
                            "Interface BFD sync cost block.";
                        }
                      }
                      case incr-cost-value {
                        description
                          "Interface BFD sync cost.";
                        leaf incr-cost-value {
                          type uint32 {
                            range "1..65535";
                          }
                          description
                            "Interface BFD sync cost.";
                        }
                      }
                    }
                    leaf per-link-flag {
                      type boolean;
                      // NCS drop must statement
                      // NCS drop default statement
                      description
                        "Enable/disable BFD session per link, support only VLANif interface.";
                    }
                    leaf one-arm-echo-flag {
                      type boolean;
                      // NCS drop must statement
                      // NCS drop default statement
                      description
                        "Enable/disable echo detection mode, support only VLANif interface.";
                    }
                  }
                  container authentication {
                    description
                      "Configure authentication. The encryption algorithm MD5 has a low security, which may bring security risks. Using more secure authentication is recommended.";
                    leaf mode {
                      type live_ncs_intf-authen-mode;
                      // NCS drop default statement
                      description
                        "Set Authentication type.";
                    }
                    leaf auth-text-simple {
                      // NCS drop when statement
                      type pub-type:live_ncs_password;
                      description
                        "Simple authentication key. The password is a string ranging from 1 to 8 characters for a unencrypted password and 24 to 128 characters for a encrypted password.";
                    }
                    leaf key-id {
                      // NCS drop when statement
                      type uint32 {
                        range "1..255";
                      }
                      // NCS drop must statement
                      description
                        "Authentication identifier.";
                    }
                    leaf auth-text-md5 {
                      // NCS drop when statement
                      type pub-type:live_ncs_password-extend;
                      // NCS drop must statement
                      description
                        "Encrypted authentication password.";
                    }
                    leaf key-chain-name {
                      // NCS drop when statement
                      type string {
                        length "1..47";
                        pattern '[^A-Z]+';
                      }
                      ext:case-sensitivity "lower-only";
                      // NCS drop mandatory statement
                      description
                        "Keychain name.";
                    }
                  }
                  container filter-lsa-out {
                    description
                      "Configure filter lsa out.";
                    choice type {
                      description
                        "Set filter lsa out type.";
                      case total {
                        description
                          "Filter total types of LSAs.";
                        leaf all-flag {
                          type empty;
                          description
                            "Filter all types of LSAs.";
                        }
                      }
                      case other {
                        description
                          "Filter other types of LSAs.";
                        leaf sum-flag {
                          type empty;
                          description
                            "Filter type3 summary LSAs.";
                        }
                        choice sum-filter {
                          description
                            "Type of a filtering rule.";
                          case acl {
                            description
                              "Basic ACL name or ACL number.";
                            leaf sum-name {
                              // NCS drop when statement
                              type leafref {
                                path "/ncs:devices/ncs:device/ncs:live-status/acl:acl/acl:groups/acl:group/acl:identity" {
                                  tailf:xpath-root 3;
                                }
                              }
                              // NCS drop must statement
                              description
                                "Basic ACL name or ACL number.";
                            }
                          }
                        }
                        leaf ase-flag {
                          type empty;
                          description
                            "Filter type5 ASE LSAs.";
                        }
                        choice ase-filter {
                          description
                            "Type of a filtering rule.";
                          case acl {
                            description
                              "Basic ACL name or ACL number.";
                            leaf ase-name {
                              // NCS drop when statement
                              type leafref {
                                path "/ncs:devices/ncs:device/ncs:live-status/acl:acl/acl:groups/acl:group/acl:identity" {
                                  tailf:xpath-root 3;
                                }
                              }
                              // NCS drop must statement
                              description
                                "Basic ACL name or ACL number.";
                            }
                          }
                        }
                        leaf nssa-flag {
                          type empty;
                          description
                            "Filter type7 NSSA LSAs.";
                        }
                        choice nssa-filter {
                          description
                            "Type of a filtering rule.";
                          case acl {
                            description
                              "Basic ACL name or ACL number.";
                            leaf nssa-name {
                              // NCS drop when statement
                              type leafref {
                                path "/ncs:devices/ncs:device/ncs:live-status/acl:acl/acl:groups/acl:group/acl:identity" {
                                  tailf:xpath-root 3;
                                }
                              }
                              // NCS drop must statement
                              description
                                "Basic ACL name or ACL number.";
                            }
                          }
                        }
                      }
                    }
                  }
                  container suppress-flapping {
                    description
                      "Configure flapping suppression.";
                    container peer {
                      // NCS drop must statement
                      description
                        "Configure flapping suppression peer. Not support Loopback.";
                      leaf enable {
                        type boolean;
                        // NCS drop default statement
                        description
                          "Enable/disable interface peer flapping suppress.";
                      }
                      leaf detect-interval {
                        type uint32 {
                          range "1..300";
                        }
                        // NCS drop default statement
                        description
                          "Detecting interval.";
                      }
                      leaf threshold {
                        type uint32 {
                          range "1..1000";
                        }
                        // NCS drop default statement
                        description
                          "Threshold.";
                      }
                      leaf resume-interval {
                        type uint32 {
                          range "2..1000";
                        }
                        // NCS drop default statement
                        description
                          "Resume interval.";
                      }
                      leaf hold-down-interval {
                        type uint32 {
                          range "1..86400";
                        }
                        description
                          "Hold down interval.";
                      }
                      leaf hold-max-cost {
                        type boolean;
                        // NCS drop default statement
                        description
                          "Enable/disable hold max cost.";
                      }
                    }
                  }
                  container flush-source-trace {
                    description
                      "Configure OSPF flush source trace function.";
                    leaf block {
                      type boolean;
                      // NCS drop default statement
                      description
                        "Enable/disable OSPF flush source trace.";
                    }
                  }
                  container mpls-te-peers {
                    description
                      "List of OSPF passive peer.";
                    list mpls-te-peer {
                      key "id router-id intf-ip";
                      description
                        "Configure OSPF passive peer.";
                      leaf id {
                        type uint32 {
                          range "1..255";
                        }
                        description
                          "Neighbor ID.";
                      }
                      leaf router-id {
                        type inet:ipv4-address-no-zone;
                        description
                          "Configure OSPF passive peer router ID.";
                      }
                      leaf intf-ip {
                        type inet:ipv4-address-no-zone;
                        description
                          "Configure interface address of passive peer.";
                      }
                      container procs {
                        description
                          "List of OSPF passive peers area.";
                        list proc {
                          key "pid aid";
                          // NCS drop max-elements statement
                          description
                            "Configure OSPF passive peers area.";
                          leaf pid {
                            type uint32 {
                              range "1..4294967295";
                            }
                            description
                              "Process ID.";
                          }
                          leaf aid {
                            type inet:ipv4-address-no-zone;
                            description
                              "Area ID.";
                          }
                          leaf cost {
                            type uint32 {
                              range "1..65535";
                            }
                            // NCS drop default statement
                            description
                              "Configuration cost value.";
                          }
                        }
                      }
                    }
                  }
                  container multi-areas {
                    description
                      "List of the information about the multi-area interface enabled with OSPF.";
                    list multi-area {
                      key "area-id";
                      description
                        "Configure the interface enabled with OSPF.";
                      leaf area-id {
                        type leafref {
                          path "/ncs:devices/ncs:device/ncs:live-status/ni:network-instance/ni:instances/ni:instance/ospfv2:ospfv2/ospfv2:sites/ospfv2:site/ospfv2:areas/ospfv2:area/ospfv2:area-id" {
                            tailf:xpath-root 3;
                          }
                        }
                        // NCS drop must statement
                        description
                          "Multi area id.";
                      }
                      leaf transmit-delay {
                        type int32 {
                          range "1..500";
                        }
                        units "s";
                        // NCS drop default statement
                        description
                          "Delay for transmitting LSAs on an interface.";
                      }
                      leaf mtu-enable {
                        type boolean;
                        // NCS drop default statement
                        description
                          "Enable/disable MTU.Configure the interface to fill in the MTU field (actual MTU of the interface) when the interface sends DD packets.
                           After a virtual connection is established through the virtual template or tunnel, different vendors may use different MTUs as default settings. To ensure consistency, the MTU is set to 0 by default when the interface sends DD packets. Thus, the ospf mtu-enable command usually does not need to be configured. OSPF does not support the preceding configuration on a null interface.";
                      }
                      leaf cost {
                        type uint32 {
                          range "1..65535";
                        }
                        description
                          "To set the cost of an interface. The default value is 1. But the default of Loopback is 0.";
                      }
                      leaf smart-discover {
                        type boolean;
                        // NCS drop default statement
                        description
                          "Enable/disable smart discover on an interface. When the neighbor status of a router or a DR or BDR on the multi-address network of the broadcast or NBMA type changes, the router can send Hello packets to the neighbor actively rather than wait for the expiration of the Hello timer.";
                      }
                      leaf ldp-sync-block {
                        type boolean;
                        // NCS drop must statement
                        // NCS drop default statement
                        description
                          "Enable/disable ldp sync on this interface.";
                      }
                      leaf ldp-sync-enable {
                        type boolean;
                        // NCS drop must statement
                        // NCS drop default statement
                        description
                          "Enable/disable LDP and OSPF synchronization on an interface.";
                      }
                      leaf fallback-cost {
                        // NCS drop when statement
                        type uint16 {
                          range "1..65535";
                        }
                        description
                          "Fallback cost.";
                      }
                      leaf fallback-bw {
                        // NCS drop when statement
                        type uint32 {
                          range "1..4294967295";
                        }
                        units "Mbit/s";
                        // NCS drop mandatory statement
                        description
                          "Fallback bandwidth threshold.";
                      }
                      container frr {
                        description
                          "Configure frr.";
                        leaf frr-disable {
                          type boolean;
                          // NCS drop default statement
                          description
                            "Enable/disable use this interface for FRR calculation.";
                        }
                        leaf rlfa-disable {
                          type boolean;
                          // NCS drop default statement
                          description
                            "Enable/disable remote LFA of the Interface.";
                        }
                        leaf ti-lfa-disable {
                          type boolean;
                          // NCS drop default statement
                          description
                            "Enable/disable Topology Independent LFA on the interface except Loopback.";
                        }
                      }
                      container timer {
                        description
                          "Configure timer.";
                        leaf hello-interval {
                          type int32 {
                            range "1..65535";
                          }
                          units "s";
                          ext:dynamic-default {
                            ext:default-value "10" {
                              // NCS drop when statement
                              description
                                "The default value is 10 when network-type is p2p or broadcast.";
                            }
                            ext:default-value "30" {
                              // NCS drop when statement
                              description
                                "The default value is 30 when network-type is p2mp or nbma.";
                            }
                          }
                          description
                            "Interval for sending Hello packets on an interface. The default value of p2p and broadcast is 10.The default of p2mp and NBMA is 30.";
                        }
                        leaf dead-interval {
                          type int32 {
                            range "1..235926000";
                          }
                          units "s";
                          // NCS drop must statement
                          ext:dynamic-default {
                            ext:default-value "4*(../hello-interval)" {
                              description
                                "The default value of dead interval is 4 times that of hello interval.";
                            }
                          }
                          description
                            "Dead interval of an OSPF neighbor. The default value of p2p and broadcast is 40.The default of p2mp and NBMA is 120.";
                        }
                        leaf retransmit-interval {
                          type int32 {
                            range "1..3600";
                          }
                          // NCS drop default statement
                          description
                            "Interval for Retransmitting LSAs on an Interface.";
                        }
                      }
                      container ldp-sync {
                        description
                          "Configure timer ldp sync.";
                        leaf hold-down-timer {
                          type uint16 {
                            range "0..65535";
                          }
                          units "s";
                          // NCS drop default statement
                          description
                            "Hold down interval range.";
                        }
                        choice hold-cost-max {
                          description
                            "Set timer ldp-sync.";
                          case timer {
                            description
                              "Set max cost interval.";
                            leaf timer {
                              type uint16 {
                                range "0..65535";
                              }
                              units "s";
                              description
                                "Max cost interval range.";
                            }
                          }
                          case infinite {
                            description
                              "Always advertise the maximum cost.";
                            leaf infinite {
                              type empty;
                              description
                                "Always advertise the maximum cost.";
                            }
                          }
                        }
                      }
                      container bfd {
                        description
                          "Configure BFD.";
                        leaf block {
                          type boolean;
                          // NCS drop default statement
                          description
                            "Enable/disable prevent the dynamic establishment of a BFD session on an interface.";
                        }
                      }
                      container authentication {
                        // NCS drop must statement
                        description
                          "Configure authentication. The encryption algorithm MD5 has a low security, which may bring security risks. Using more secure authentication is recommended.";
                        leaf mode {
                          type live_ncs_intf-authen-mode;
                          // NCS drop default statement
                          description
                            "Set Authentication type.";
                        }
                        leaf auth-text-simple {
                          // NCS drop when statement
                          type pub-type:live_ncs_password;
                          description
                            "Simple authentication key. The password is a string ranging from 1 to 8 characters for a unencrypted password and 24 to 128 characters for a encrypted password.";
                        }
                        leaf key-id {
                          // NCS drop when statement
                          type uint32 {
                            range "1..255";
                          }
                          description
                            "Authentication identifier.";
                        }
                        leaf auth-text-md5 {
                          // NCS drop when statement
                          type pub-type:live_ncs_password-extend;
                          description
                            "MD5/HMAC-MD5/HMAC-SHA256 Authentication Password.";
                        }
                        leaf key-chain-name {
                          // NCS drop when statement
                          type string {
                            length "1..47";
                            pattern '[^A-Z]+';
                          }
                          ext:case-sensitivity "lower-only";
                          // NCS drop mandatory statement
                          description
                            "Keychain Name.";
                        }
                      }
                      container filter-lsa-out {
                        presence "Enable multi area filter lsa out.";
                        description
                          "Configure filter-lsa-out.";
                        choice type {
                          // NCS drop mandatory statement
                          description
                            "Set filter-lsa-out type.";
                          case total {
                            description
                              "Filter total types of LSAs.";
                            leaf all-flag {
                              type empty;
                              description
                                "Filter all types of LSAs.";
                            }
                          }
                          case other {
                            description
                              "Filter other types of LSAs.";
                            leaf sum-flag {
                              type empty;
                              description
                                "Filter type-3 Summary LSAs.";
                            }
                            choice sum-filter {
                              description
                                "Type of a filtering rule.";
                              case acl {
                                description
                                  "ACL-Name or ACL-Number.";
                                leaf sum-name {
                                  // NCS drop when statement
                                  type leafref {
                                    path "/ncs:devices/ncs:device/ncs:live-status/acl:acl/acl:groups/acl:group/acl:identity" {
                                      tailf:xpath-root 3;
                                    }
                                  }
                                  description
                                    "ACL-Name or ACL-Number.";
                                }
                              }
                            }
                            leaf ase-flag {
                              type empty;
                              description
                                "Filter type-5 ASE LSAs.";
                            }
                            choice ase-filter {
                              description
                                "Type of a filtering rule.";
                              case acl {
                                description
                                  "ACL-Name or ACL-Number.";
                                leaf ase-name {
                                  // NCS drop when statement
                                  type leafref {
                                    path "/ncs:devices/ncs:device/ncs:live-status/acl:acl/acl:groups/acl:group/acl:identity" {
                                      tailf:xpath-root 3;
                                    }
                                  }
                                  description
                                    "ACL-Name or ACL-Number.";
                                }
                              }
                            }
                            leaf nssa-flag {
                              type empty;
                              description
                                "Filter type-7 NSSA LSAs.";
                            }
                            choice nssa-filter {
                              description
                                "Type of a filtering rule.";
                              case acl {
                                description
                                  "ACL-Name or ACL-Number.";
                                leaf nssa-name {
                                  // NCS drop when statement
                                  type leafref {
                                    path "/ncs:devices/ncs:device/ncs:live-status/acl:acl/acl:groups/acl:group/acl:identity" {
                                      tailf:xpath-root 3;
                                    }
                                  }
                                  description
                                    "ACL-Name or ACL-Number.";
                                }
                              }
                            }
                          }
                        }
                      }
                      container suppress-flapping {
                        description
                          "Configure flapping suppression.";
                        container peer {
                          // NCS drop must statement
                          description
                            "Configure flapping suppression peer. Not support Loopback.";
                          leaf enable {
                            type boolean;
                            // NCS drop default statement
                            description
                              "Enable/disable interface peer flapping suppress.";
                          }
                          leaf detect-interval {
                            type uint32 {
                              range "1..300";
                            }
                            // NCS drop default statement
                            description
                              "Detecting-interval.";
                          }
                          leaf threshold {
                            type uint32 {
                              range "1..1000";
                            }
                            // NCS drop default statement
                            description
                              "Threshold.";
                          }
                          leaf resume-interval {
                            type uint32 {
                              range "2..1000";
                            }
                            // NCS drop default statement
                            description
                              "Resume-interval.";
                          }
                          leaf hold-down-interval {
                            type uint32 {
                              range "1..86400";
                            }
                            description
                              "Hold-down-interval.";
                          }
                          leaf hold-max-cost {
                            type boolean;
                            // NCS drop default statement
                            description
                              "Enable/disable hold max cost.";
                          }
                        }
                      }
                    }
                  }
                  container disp-data {
                    description
                      "Statistics of OSPF interface.";
                    leaf suppress-reach-block {
                      type boolean;
                      description
                        "Reachability suppression is disabled.";
                    }
                    leaf silent-enable {
                      type boolean;
                      description
                        "To suppress an interface from sending or receiving OSPF packets.";
                    }
                    leaf dr {
                      type inet:ipv4-address-no-zone;
                      description
                        "DR of the network where an interface resides.";
                    }
                    leaf bdr {
                      type inet:ipv4-address-no-zone;
                      description
                        "BDR of the network where an interface resides.";
                    }
                    leaf state {
                      type live_ncs_intf-state;
                      description
                        "Status of an interface, which is determined according to the OSPF interface state machines.";
                    }
                    leaf mtu {
                      type uint32;
                      description
                        "MTU of an interface.";
                    }
                    leaf ip {
                      type inet:ipv4-address-no-zone;
                      description
                        "IP address of an interface.";
                    }
                    leaf cost {
                      type int32;
                      description
                        "Cost of an interface.";
                    }
                    leaf gr-state {
                      type live_ncs_gr-state;
                      description
                        "Status of GR of an interface. The available options are as follows:
                         Normal: The interface is in normal state.
                         Restarter: The interface is in GR state.
                         Helper: The interface is in helper state.";
                    }
                    leaf previous-state {
                      type live_ncs_intf-state;
                      description
                        "Previous status of the interface.";
                    }
                    leaf opaque-id {
                      type uint32;
                      description
                        "Oapque ID of interface.";
                    }
                    leaf mpls-te-link {
                      type boolean;
                      description
                        "MPLS TE link status enabled.";
                    }
                    leaf peer-flap-status {
                      type live_ncs_peer-flapping-status;
                      description
                        "Peer flapping suppress status.";
                    }
                    leaf peer-flap-count {
                      type uint32;
                      description
                        "Peer flapping suppress count.";
                    }
                    leaf peer-flap-threshold {
                      type uint32 {
                        range "1..1000";
                      }
                      description
                        "Peer flapping suppress threshold.";
                    }
                    leaf peer-flap-timer {
                      type string {
                        length "1..40";
                      }
                      description
                        "Peer flapping suppress timer.";
                    }
                    leaf peer-flap-remain-timer {
                      type uint32 {
                        range "0..1000";
                      }
                      units "s";
                      description
                        "Peer flapping suppress remain timer.";
                    }
                    leaf bandwidth {
                      type uint32;
                      description
                        "Current interface bandwidth.";
                    }
                  }
                  container nbr-statistics {
                    description
                      "List of OSPF peer.";
                    list nbr-statistic {
                      key "router-id ip";
                      description
                        "Statistics of OSPF peer.";
                      leaf router-id {
                        type inet:ipv4-address-no-zone;
                        description
                          "ID of a neighbor router.";
                      }
                      leaf ip {
                        type inet:ipv4-address-no-zone;
                        description
                          "Address of a neighbor interface.";
                      }
                      leaf intf-ip {
                        type inet:ipv4-address-no-zone;
                        description
                          "IP address of an interface.";
                      }
                      leaf gr-state {
                        type live_ncs_nbr-gr-state;
                        description
                          "GR state.";
                      }
                      leaf state {
                        type live_ncs_nbr-state;
                        description
                          "Neighbor status.";
                      }
                      leaf mode {
                        type live_ncs_nbr-mode;
                        description
                          "Mode of the DD. The available options are master and slave.";
                      }
                      leaf priority {
                        type int32;
                        description
                          "Priority of a neighbor router.";
                      }
                      leaf dr {
                        type inet:ipv4-address-no-zone;
                        description
                          "Designated router.";
                      }
                      leaf bdr {
                        type inet:ipv4-address-no-zone;
                        description
                          "Backup designated router.";
                      }
                      leaf intf-mtu {
                        type uint32;
                        description
                          "MTU of a neighbor.";
                      }
                      leaf dead-due-timer {
                        type uint32;
                        description
                          "Dead due timer.";
                      }
                      leaf retran-intv {
                        type uint32;
                        description
                          "Neighbor retranIntv.";
                      }
                      leaf up-time {
                        type string {
                          length "1..16";
                        }
                        description
                          "Time when a neighbor goes up.";
                      }
                      leaf up-time-stamp {
                        type yang:date-and-time;
                        description
                          "Neighbor up time stamp.";
                      }
                      leaf auth-sequence {
                        type uint32;
                        description
                          "Neighbor authentication sequence number.";
                      }
                      leaf adj-sid {
                        type uint32;
                        description
                          "Adjacency SID.";
                      }
                      leaf adj-weight {
                        type uint32;
                        description
                          "Adjacency weight.";
                      }
                      leaf adj-flags {
                        type string {
                          length "1..20";
                        }
                        description
                          "Adjacency flags.";
                      }
                    }
                  }
                  container error-data {
                    description
                      "Statistics of error data.";
                    leaf router-id {
                      type inet:ipv4-address-no-zone;
                      description
                        "Router ID.";
                    }
                    leaf same-ip-pkt-cnt {
                      type uint32;
                      description
                        "SameIp packet count.";
                    }
                    leaf bad-pkt-cnt {
                      type uint32;
                      description
                        "Bad packet.";
                    }
                    leaf bad-ver-cnt {
                      type uint32;
                      description
                        "Bad version.";
                    }
                    leaf bad-chksum-pkt-cnt {
                      type uint32;
                      description
                        "Bad checksum.";
                    }
                    leaf bad-area-pkt-cnt {
                      type uint32;
                      description
                        "Bad area ID.";
                    }
                    leaf pkt-rcv-unnumber {
                      type uint32;
                      description
                        "Drop on unnumbered interface.";
                    }
                    leaf bad-virt-link-cnt {
                      type uint32;
                      description
                        "Bad virtual link.";
                    }
                    leaf auth-type-fail-cnt {
                      type uint32;
                      description
                        "Bad authentication type.";
                    }
                    leaf auth-key-fail-cnt {
                      type uint32;
                      description
                        "Bad authentication key.";
                    }
                    leaf short-pkt-cnt {
                      type uint32;
                      description
                        "Packet too small.";
                    }
                    leaf long-pkt-cnt {
                      type uint32;
                      description
                        "Packet size > IP length.";
                    }
                    leaf tx-err-cnt {
                      type uint32;
                      description
                        "Transmit error.";
                    }
                    leaf if-down-cnt {
                      type uint32;
                      description
                        "Interface down.";
                    }
                    leaf no-nbr {
                      type uint32;
                      description
                        "Unknown neighbor.";
                    }
                    leaf mis-netmask-cnt {
                      type uint32;
                      description
                        "Netmask mismatch.";
                    }
                    leaf mis-hello-intl-cnt {
                      type uint32;
                      description
                        "Hello timer mismatch.";
                    }
                    leaf mis-dead-intl-cnt {
                      type uint32;
                      description
                        "Dead timer mismatch.";
                    }
                    leaf mis-ext-cnt {
                      type uint32;
                      description
                        "Extern option mismatch.";
                    }
                    leaf router-id-confusion {
                      type uint32;
                      description
                        "DD router ID confusion.";
                    }
                    leaf vlink-nbr-mis-cnt {
                      type uint32;
                      description
                        "Virtual neighbor unknown.";
                    }
                    leaf nbma-nbr-err-cnt {
                      type uint32;
                      description
                        "NBMA neighbor unknown.";
                    }
                    leaf inval-src-hello-cnt {
                      type uint32;
                      description
                        "Invalid source.";
                    }
                    leaf dd-nbr-low-cnt {
                      type uint32;
                      description
                        "Neighbour state low for DD.";
                    }
                    leaf dd-rtrid-cnt {
                      type uint32;
                      description
                        "DD router ID confusion.";
                    }
                    leaf dd-opt-mismatch-cnt {
                      type uint32;
                      description
                        "Extern option mismatch.";
                    }
                    leaf dd-unknwn-lsa-cnt {
                      type uint32;
                      description
                        "DD packet unknown LSA type.";
                    }
                    leaf dd-mtu-mismatch-cnt {
                      type uint32;
                      description
                        "MTU option mismatch.";
                    }
                    leaf ack-nbr-low-cnt {
                      type uint32;
                      description
                        "Neighbour state low for LS acknowledgement.";
                    }
                    leaf ack-bad-cnt {
                      type uint32;
                      description
                        "Bad ack.";
                    }
                    leaf ack-duplicate-cnt {
                      type uint32;
                      description
                        "Duplicate ack.";
                    }
                    leaf ack-unknwn-lsa-cnt {
                      type uint32;
                      description
                        "LSAck packet unknown LSA type.";
                    }
                    leaf req-nbr-low-cnt {
                      type uint32;
                      description
                        "Neighbour state low for LS request.";
                    }
                    leaf req-empty-cnt {
                      type uint32;
                      description
                        "Empty request.";
                    }
                    leaf req-bad-cnt {
                      type uint32;
                      description
                        "Bad request.";
                    }
                    leaf upd-nbr-low-cnt {
                      type uint32;
                      description
                        "Neighbour state low for LS update.";
                    }
                    leaf upd-self-newr-cnt {
                      type uint32;
                      description
                        "Newer self generate LSA.";
                    }
                    leaf upd-min-lsarr-cnt {
                      type uint32;
                      description
                        "Received LSA within LSA arrival interval.";
                    }
                    leaf upd-ls-chksum-cnt {
                      type uint32;
                      description
                        "LSA checksum bad.";
                    }
                    leaf upd-les-recent-cnt {
                      type uint32;
                      description
                        "Received less recent LSA.";
                    }
                    leaf upd-unknw-lsa-cnt {
                      type uint32;
                      description
                        "LSUpdate packet unknown LSA type.";
                    }
                    leaf opq9-flood-cnt {
                      type uint32;
                      description
                        "Opq9 of flooding scope.";
                    }
                    leaf opq10-flood-cnt {
                      type uint32;
                      description
                        "Opq10 of flooding scope.";
                    }
                    leaf opq11-flood-cnt {
                      type uint32;
                      description
                        "Opq11 of flooding scope.";
                    }
                    leaf rxmt-dd-err-cnt {
                      type uint32;
                      description
                        "Number for DD packet.";
                    }
                    leaf rxmt-req-err-cnt {
                      type uint32;
                      description
                        "Number for request packet.";
                    }
                    leaf rxmt-upd-err-cnt {
                      type uint32;
                      description
                        "Number for update packet.";
                    }
                    leaf gr-invalid-lsa-cnt {
                      type uint32;
                      description
                        "Number of invalid LSAs.";
                    }
                    leaf gr-invalid-pol-cnt {
                      type uint32;
                      description
                        "Number of policy failed LSAs.";
                    }
                    leaf gr-invalid-prd-cnt {
                      type uint32;
                      description
                        "Number of wrong period LSAs.";
                    }
                    leaf tunnel-cost-cnt {
                      type uint32;
                      description
                        "Tunnel cost mistake.";
                    }
                    leaf peer-net-type-cnt {
                      type uint32;
                      description
                        "The network type of the neighbor interface is not consistent.";
                    }
                    leaf hello-dr-mis-cnt {
                      type uint32;
                      description
                        "The DR or BDR in receiving hello packet is not same with the DR or BDR.";
                    }
                    leaf gen-ttl-err-cnt {
                      type uint32;
                      description
                        "The TTL of the packet is error.";
                    }
                    leaf over-max-buffer-length-cnt {
                      type uint32;
                      description
                        "Number of packet that length is more than max buffer length.";
                    }
                    leaf bad-net-segment-packet-cnt {
                      type uint32;
                      description
                        "Number of bad network segment packet.";
                    }
                    leaf bad-routerid-packet-cnt {
                      type uint32;
                      description
                        "Number of non-hello packet that router ID is different.";
                    }
                    leaf destination-ip-error-packet-cnt {
                      type uint32;
                      description
                        "Number of bad destIpAddress packet.";
                    }
                    leaf passive-intf-packet-cnt {
                      type uint32;
                      description
                        "Number of packet that received from silent Interface.";
                    }
                    leaf hello-nbr-reach-limit-cnt {
                      type uint32;
                      description
                        "Number of hello packet that discard because the number of neighbour reached the limit.";
                    }
                    leaf hello-hold-down-cnt {
                      type uint32;
                      description
                        "Number of hello packet that discard because the neighbour is in hold-down state.";
                    }
                    leaf hello-memory-overload-cnt {
                      type uint32;
                      description
                        "Number of hello packet that discard because memory is overload.";
                    }
                    leaf hello-cpu-overload-cnt {
                      type uint32;
                      description
                        "Number of hello packet that discard because cpu is overload.";
                    }
                    leaf dd-nbr-reach-limit-cnt {
                      type uint32;
                      description
                        "Number of dd packet that discard because the number of neighbour reached the limit.";
                    }
                    leaf dd-cpu-overload-cnt {
                      type uint32;
                      description
                        "Number of dd packet that discard because cpu is overload.";
                    }
                    leaf dd-mem-overload-cnt {
                      type uint32;
                      description
                        "Number of dd packet that discard because memory is overload.";
                    }
                    leaf ri-lsa-tlv-error-cnt {
                      type uint32;
                      description
                        "Router information lsa Tlv error.";
                    }
                    leaf ri-lsa-sub-tlv-error-cnt {
                      type uint32;
                      description
                        "Router information lsa sub Tlv error.";
                    }
                    leaf ext-prefix-lsa-tlv-error-cnt {
                      type uint32;
                      description
                        "Extend prefix lsa Tlv error.";
                    }
                    leaf ext-prefix-lsa-sub-tlv-error-cnt {
                      type uint32;
                      description
                        "Extend prefix lsa sub Tlv error.";
                    }
                    leaf ext-link-lsa-tlv-error-cnt {
                      type uint32;
                      description
                        "Extend link lsa Tlv error.";
                    }
                    leaf ext-link-lsa-sub-tlv-error-cnt {
                      type uint32;
                      description
                        "Extend link lsa sub Tlv error.";
                    }
                    leaf bad-sr-algo-cnt {
                      type uint32;
                      description
                        "Bad SR-Algorithm TLV.";
                    }
                    leaf bad-sid-range-cnt {
                      type uint32;
                      description
                        "Bad SID/Label Range TLV.";
                    }
                    leaf bad-sid-cnt {
                      type uint32;
                      description
                        "Bad SID/Label Sub TLV.";
                    }
                    leaf bad-adj-sid-cnt {
                      type uint32;
                      description
                        "Bad Adj-SID Sub TLV.";
                    }
                    leaf bad-prefix-sid-cnt {
                      type uint32;
                      description
                        "Bad Prefix-SID Sub TLV.";
                    }
                    leaf bad-ext-prefix-range-cnt {
                      type uint32;
                      description
                        "Bad Extended Prefix Range TLV.";
                    }
                    leaf bad-lan-adj-sid-cnt {
                      type uint32;
                      description
                        "Bad LAN Adj-SID Sub TLV.";
                    }
                    leaf bad-ext-prefix-cnt {
                      type uint32;
                      description
                        "Bad Extended Prefix TLV.";
                    }
                    leaf bad-ext-link-cnt {
                      type uint32;
                      description
                        "Bad Extended Link TLV.";
                    }
                  }
                }
              }
              container disp-data {
                description
                  "Statistics of OSPF area.";
                leaf spf-schedule-times {
                  type uint32;
                  description
                    "Times of calculating SPF.";
                }
                leaf interface-count {
                  type uint32;
                  description
                    "Number of interfaces.";
                }
                leaf exchange-and-loading-nbr {
                  type uint32;
                  description
                    "Number of neighbors in exchange/loading state.";
                }
                leaf router-id-conflict {
                  type live_ncs_router-id-conflict-state;
                  description
                    "Router ID conflict state.";
                }
                leaf import-limit-status {
                  type live_ncs_import-limit-status;
                  description
                    "Limit status of imported routes.";
                }
                leaf self-nssa-lsa-count {
                  type uint32;
                  description
                    "Number of NSSA LSAs that are generated locally.";
                }
                leaf nssa-trans-state {
                  type live_ncs_nssa-trans-state;
                  description
                    "NSSA translator state.";
                }
                leaf nssa-trans-role {
                  type live_ncs_nssa-trans-role;
                  description
                    "NSSA translator role.";
                }
                leaf nssa-trans-stab-intv {
                  type boolean;
                  description
                    "Continuing NSSA translation duties during stability interval.";
                }
              }
            }
          }
          container disp-data {
            description
              "Statistics of OSPF site.";
            leaf effective-router-id {
              type inet:ipv4-address-no-zone;
              description
                "Effective router ID.";
            }
            leaf border-router {
              type live_ncs_border-router;
              description
                "Router type.";
            }
            leaf ietf-mode {
              type live_ncs_ietf-mode;
              description
                "Global DS TE mode.";
            }
            leaf spf-count {
              type uint32;
              description
                "SPF computation count.";
            }
            leaf area-count {
              type uint32;
              description
                "Number of areas.";
            }
            leaf nssa-count {
              type uint32;
              description
                "Number of NSSA areas.";
            }
            leaf exchange-and-loading-nbr {
              type uint32;
              description
                "Neighbor in exchange/loading state.";
            }
            leaf lsdb-overflow-status {
              type live_ncs_lsdb-overflow-status;
              description
                "LSDB overflow status.";
            }
            leaf non-default-ase-lsa-count {
              type uint32;
              description
                "Number of non default AS external LSAs.";
            }
            leaf lsdb-overflow-remain {
              type uint32;
              description
                "Remaining time of the overflow state.";
            }
            leaf import-limit-status {
              type live_ncs_import-limit-status;
              description
                "Limit status of imported external routes.";
            }
            leaf self-ase-lsa-count {
              type uint32;
              description
                "Number of AS external LSAs that are generated locally.";
            }
          }
          container migp-routings {
            description
              "List of the OSPF MIGP routing table.";
            list migp-routing {
              key "dest-ip mask-length";
              description
                "Statistics of the OSPF MIGP routing table.";
              leaf dest-ip {
                type inet:ipv4-address-no-zone;
                description
                  "Destination IP address.";
              }
              leaf mask-length {
                type uint32 {
                  range "0..32";
                }
                description
                  "Mask length.";
              }
              leaf cost {
                type uint32;
                description
                  "Cost to the destination address.";
              }
              leaf prefix-priority {
                type live_ncs_pre-priority;
                description
                  "Prefix priority.";
              }
              leaf path-type {
                type live_ncs_path-type;
                description
                  "Route type.";
              }
              container nexthop-datas {
                description
                  "List of nexthop data.";
                list nexthop-data {
                  key "ip-addr adv-router-id area-id";
                  description
                    "Statistics of nexthop data.";
                  leaf ip-addr {
                    type inet:ipv4-address-no-zone;
                    description
                      "Nexthop IP address.";
                  }
                  leaf adv-router-id {
                    type inet:ipv4-address-no-zone;
                    description
                      "Next hop advertising router ID.";
                  }
                  leaf area-id {
                    type inet:ipv4-address-no-zone;
                    description
                      "Next hop area ID.";
                  }
                  leaf flags-disp {
                    type string {
                      length "1..8";
                    }
                    description
                      "Next hop flags.";
                  }
                  leaf tag {
                    type uint32;
                    description
                      "Next hop tag.";
                  }
                  leaf if-name {
                    type string {
                      length "1..64";
                    }
                    description
                      "Next hop outgoing interface name.";
                  }
                }
              }
            }
          }
          container abr-asbr-statistics {
            description
              "List of the OSPF ABR and ASBR.";
            list abr-asbr-statistic {
              key "if-index nexthop-ip area-id destination-id";
              description
                "Statistics of the OSPF ABR and ASBR.";
              leaf if-index {
                type uint32;
                description
                  "Abr or asbr interface index.";
              }
              leaf nexthop-ip {
                type inet:ipv4-address-no-zone;
                description
                  "Next hop IP address for sending packets to an ABR or ASBR.";
              }
              leaf area-id {
                type inet:ipv4-address-no-zone;
                description
                  "Abr or asbr area ID.";
              }
              leaf destination-id {
                type inet:ipv4-address-no-zone;
                description
                  "ID of an ABR or ASBR.";
              }
              leaf if-name {
                type string {
                  length "0..64";
                }
                description
                  "Abr or asbr interface name.";
              }
              leaf router-id {
                type inet:ipv4-address-no-zone;
                description
                  "ID of the local router.";
              }
              leaf path-type {
                type live_ncs_path-type;
                description
                  "Inter area or intra area router.";
              }
              leaf cost {
                type uint32;
                description
                  "Cost from a router to an ABR or ASBR.";
              }
              leaf router-type {
                type live_ncs_router-type;
                description
                  "Abr or asbr router type.";
              }
            }
          }
          container nexthop-paras {
            description
              "List of the next hop of an OSPF process.";
            list nexthop-para {
              key "addr rt-source-type if-addr if-name";
              description
                "Statistics of the next hop of an OSPF process.";
              leaf addr {
                type inet:ipv4-address-no-zone;
                description
                  "Details about the next hop.";
              }
              leaf rt-source-type {
                type live_ncs_route-source-type;
                description
                  "Type of route origination.";
              }
              leaf if-addr {
                type inet:ipv4-address-no-zone;
                description
                  "Interface address.";
              }
              leaf if-name {
                type string {
                  length "0..64";
                }
                description
                  "Interface name.";
              }
              leaf referece-count {
                type uint32;
                description
                  "Number of OSPF routes using the next hop.";
              }
              leaf router-id {
                type inet:ipv4-address-no-zone;
                description
                  "ID of the local router.";
              }
            }
          }
          container lsdb-statistics {
            description
              "List of OSPF LSDBs.";
            list lsdb-statistic {
              key "area-id lsa-type link-state-id adv-router-id";
              description
                "Statistics of OSPF LSDBs.";
              leaf area-id {
                type inet:ipv4-address-no-zone;
                description
                  "Area ID.";
              }
              leaf lsa-type {
                type live_ncs_lsa-type;
                description
                  "The value can be router, network, sum net, sum asbr, NSSA, external, opq link, opq area, or opq AS.";
              }
              leaf link-state-id {
                type inet:ipv4-address-no-zone;
                description
                  "Link state ID in the LSA header.";
              }
              leaf adv-router-id {
                type inet:ipv4-address-no-zone;
                description
                  "Router that advertises or generates LSAs.";
              }
              leaf lsa-age {
                type int32;
                description
                  "LSA aging time.";
              }
              leaf lsa-sequence-num {
                type string {
                  length "1..12";
                }
                description
                  "LSA sequence number (from the LSA header).";
              }
              leaf check-sum {
                type string {
                  length "1..10";
                }
                description
                  "Checksum.";
              }
              leaf lsa-length {
                type uint32;
                description
                  "LSA length.";
              }
              leaf options {
                type live_ncs_lsdb-option;
                description
                  "LSA option.";
              }
              leaf option-flag {
                type live_ncs_lsdb-option-flag;
                description
                  "LSA option flag. The available options are V, B, and E.";
              }
              leaf link-count {
                type uint32;
                description
                  "Number of links.";
              }
              leaf network-mask {
                type inet:ipv4-address-no-zone;
                description
                  "Network mask of the network LSA.";
              }
              leaf host-name {
                type string {
                  length "1..255";
                }
                description
                  "Host name.";
              }
              container lsabodys {
                description
                  "List of lsabody.";
                list lsabody {
                  key "link-id link-data link-type attach-router forward-ip";
                  description
                    "Statistics of lsabody.";
                  leaf link-id {
                    type inet:ipv4-address-no-zone;
                    description
                      "Link ID of the router LSA.";
                  }
                  leaf link-data {
                    type inet:ipv4-address-no-zone;
                    description
                      "Link data about the router LSA.";
                  }
                  leaf link-type {
                    type live_ncs_lsdb-link-type;
                    description
                      "Link type of the router LSA. The available options are Point-to-Point, TransNet, StubNet, and Virtual.";
                  }
                  leaf attach-router {
                    type inet:ipv4-address-no-zone;
                    description
                      "Router connected to the network.";
                  }
                  leaf forward-ip {
                    type inet:ipv4-address-no-zone;
                    description
                      "Forwarding IP address.";
                  }
                  leaf tos-id {
                    type uint8;
                    description
                      "ToS ID.";
                  }
                  leaf tos-metric {
                    type uint32;
                    description
                      "ToS metric.";
                  }
                  leaf route-tag {
                    type uint32;
                    description
                      "Route tag, which is used to prevent route Loopback and applicable to Type5 or Type7 LSAs, of 32 bytes.";
                  }
                  leaf opaque-type {
                    type uint32;
                    description
                      "Opaque type.";
                  }
                  leaf opaque-id {
                    type uint32;
                    description
                      "Opaque LSA ID. Opaque type + Opaque ID = Link state ID in the LSA header.";
                  }
                  leaf ext-metric-type {
                    type uint8;
                    description
                      "E type of ASE/NSSA LSAs.";
                  }
                }
              }
              container rilsa {
                description
                  "Statistics of LSA TLV information.";
                leaf host-name {
                  type string {
                    length "1..255";
                  }
                  description
                    "Host name TLV.";
                }
                leaf algorithm {
                  type string {
                    length "1..255";
                  }
                  description
                    "SR algorithm.";
                }
              }
              container prefix-lsas {
                description
                  "List of prefix LSA.";
                list prefix-lsa {
                  key "prefix";
                  description
                    "Statistics of prefix LSA.";
                  leaf prefix {
                    type inet:ipv4-address-no-zone;
                    description
                      "Prefix of the router LSA.";
                  }
                  leaf route-type {
                    type live_ncs_lsdb-route-type;
                    description
                      "Route type.";
                  }
                  leaf af {
                    type string {
                      length "1..256";
                    }
                    description
                      "Address family.";
                  }
                  leaf flags {
                    type string {
                      length "1..21";
                    }
                    description
                      "Tlv flags.";
                  }
                  container redistribute-list {
                    description
                      "Statistics of redistribute-list information.";
                    leaf sub-tlv-flags {
                      type string {
                        length "1..22";
                      }
                      description
                        "Redistribute list sub TLV flags.";
                    }
                    leaf router-ids {
                      type string {
                        length "1..40";
                      }
                      description
                        "Redistribute list sub TLV router ID and process ID.";
                    }
                  }
                }
              }
            }
          }
          container lsdb-briefs {
            description
              "List of LSDB statistics.";
            list lsdb-brief {
              key "area-id";
              description
                "Statistics of LSDB statistics.";
              leaf area-id {
                type inet:ipv4-address-no-zone;
                description
                  "Area ID.";
              }
              leaf router-id {
                type inet:ipv4-address-no-zone;
                description
                  "ID of the local router.";
              }
              leaf stub {
                type uint32;
                description
                  "Number of stubs.";
              }
              leaf router {
                type uint32;
                description
                  "Number of router LSAs.";
              }
              leaf network {
                type uint32;
                description
                  "Number of network LSAs.";
              }
              leaf summary-net {
                type uint32;
                description
                  "Number of summary net LSAs.";
              }
              leaf asbr {
                type uint32;
                description
                  "Number of ASBR LSAs.";
              }
              leaf type7 {
                type uint32;
                description
                  "Number of Type7 LSAs.";
              }
              leaf opaque9 {
                type uint32;
                description
                  "Number of Type9 opaque LSAs.";
              }
              leaf opaque10 {
                type uint32;
                description
                  "Number of Type10 opaque LSAs.";
              }
              leaf sub-total {
                type uint32;
                description
                  "Sub type sum.";
              }
            }
          }
          container last-down-nbrs {
            description
              "List of the OSPF neighbor that goes down for the last time.";
            list last-down-nbr {
              key "list-index area-id ip-addr router-id if-name";
              description
                "Statistics of the OSPF neighbor that goes down for the last time.";
              leaf list-index {
                type uint32;
                description
                  "The serial number of the node for the particular last down neighbor.";
              }
              leaf area-id {
                type inet:ipv4-address-no-zone;
                description
                  "Area to which the neighbor belongs.";
              }
              leaf ip-addr {
                type inet:ipv4-address-no-zone;
                description
                  "Address of the neighbor interface.";
              }
              leaf router-id {
                type inet:ipv4-address-no-zone;
                description
                  "Router ID of the neighbor.";
              }
              leaf if-name {
                type string {
                  length "0..64";
                }
                description
                  "Interface that connects to the neighbor.";
              }
              leaf immediate-reason {
                type live_ncs_nbr-down-imm-reason;
                description
                  "Direct reason that the neighbor goes down.";
              }
              leaf primary-reason {
                type live_ncs_nbr-down-prim-reason;
                description
                  "Primary reason that the neighbor goes down.";
              }
              leaf time {
                type yang:date-and-time;
                description
                  "Time when the neighbor goes down.";
              }
              leaf local-router-id {
                type inet:ipv4-address-no-zone;
                description
                  "ID of the local router.";
              }
              leaf type {
                type live_ncs_nbr-type;
                description
                  "Last down neighbor type.";
              }
            }
          }
          container disp-graceful-restart {
            description
              "Statistics of graceful restart information.";
            leaf capability {
              type live_ncs_helper-capabality;
              description
                "Graceful restart capability.";
            }
            leaf help-role {
              type live_ncs_helper-support;
              description
                "Helper policy support.";
            }
            leaf current-state {
              type live_ncs_gr-state;
              description
                "Current GR status.";
            }
            leaf on-helper {
              type live_ncs_on-helper;
              description
                "Cause for exiting GR by the helper.";
            }
            leaf nbr-num {
              type uint32;
              description
                "Re starting neighbor count.";
            }
          }
          container error-process-data {
            description
              "Statistics of error data.";
            leaf router-id {
              type inet:ipv4-address-no-zone;
              description
                "Router ID.";
            }
            leaf same-ip-pkt-cnt {
              type uint32;
              description
                "Same IP packet count.";
            }
            leaf bad-pkt-cnt {
              type uint32;
              description
                "Bad packet.";
            }
            leaf bad-ver-cnt {
              type uint32;
              description
                "Bad version.";
            }
            leaf bad-chk-sum-pkt-cnt {
              type uint32;
              description
                "Bad checksum.";
            }
            leaf bad-area-pkt-cnt {
              type uint32;
              description
                "Bad area ID.";
            }
            leaf pkt-rcv-unnumber {
              type uint32;
              description
                "Drop on unnumbered interface.";
            }
            leaf bad-virt-link-cnt {
              type uint32;
              description
                "Bad virtual link.";
            }
            leaf auth-type-fail-cnt {
              type uint32;
              description
                "Bad authentication type.";
            }
            leaf auth-key-fail-cnt {
              type uint32;
              description
                "Bad authentication key.";
            }
            leaf short-pkt-cnt {
              type uint32;
              description
                "Packet too small.";
            }
            leaf long-pkt-cnt {
              type uint32;
              description
                "Packet size > ip length.";
            }
            leaf tx-err-cnt {
              type uint32;
              description
                "Transmit error.";
            }
            leaf if-down-cnt {
              type uint32;
              description
                "Interface down.";
            }
            leaf no-nbr {
              type uint32;
              description
                "Unknown neighbor.";
            }
            leaf mis-netmask-cnt {
              type uint32;
              description
                "Netmask mismatch.";
            }
            leaf mis-hello-intl-cnt {
              type uint32;
              description
                "Hello timer mismatch.";
            }
            leaf mis-dead-intl-cnt {
              type uint32;
              description
                "Dead timer mismatch.";
            }
            leaf mis-ext-rou-cap-cnt {
              type uint32;
              description
                "Extern option mismatch.";
            }
            leaf router-id-confusion {
              type uint32;
              description
                "DD router ID confusion.";
            }
            leaf vlink-nbr-mis-cnt {
              type uint32;
              description
                "Virtual neighbor unknown.";
            }
            leaf nbma-nbr-err-cnt {
              type uint32;
              description
                "NBMA neighbor unknown.";
            }
            leaf inval-src-helo-cnt {
              type uint32;
              description
                "Invalid source.";
            }
            leaf dd-nbr-low-cnt {
              type uint32;
              description
                "Neighbour state low for DD.";
            }
            leaf dd-router-id-cnt {
              type uint32;
              description
                "DD router ID confusion.";
            }
            leaf dd-opt-mismatch-cnt {
              type uint32;
              description
                "Extern option mismatch.";
            }
            leaf dd-unknwn-lsa-cnt {
              type uint32;
              description
                "DD packet unknown LSA type.";
            }
            leaf dd-mtu-mismatch-cnt {
              type uint32;
              description
                "MTU option mismatch.";
            }
            leaf ack-nbr-low-cnt {
              type uint32;
              description
                "Neighbour state low for LS acknowledgement.";
            }
            leaf ack-bad-cnt {
              type uint32;
              description
                "Bad ack.";
            }
            leaf ack-duplicate-cnt {
              type uint32;
              description
                "Duplicate ack.";
            }
            leaf ack-unknown-lsa-cnt {
              type uint32;
              description
                "LSAck packet unknown LSA type.";
            }
            leaf req-nbr-low-cnt {
              type uint32;
              description
                "Neighbour state low for LS request.";
            }
            leaf req-empty-cnt {
              type uint32;
              description
                "Empty request.";
            }
            leaf req-bad-cnt {
              type uint32;
              description
                "Bad request.";
            }
            leaf upd-nbr-low-cnt {
              type uint32;
              description
                "Neighbour state low for LS update.";
            }
            leaf upd-self-newr-cnt {
              type uint32;
              description
                "Newer self generate LSA.";
            }
            leaf upd-min-lsa-lsarr-cnt {
              type uint32;
              description
                "Received LSA within LSA arrival interval.";
            }
            leaf upd-ls-checksum-cnt {
              type uint32;
              description
                "LSA checksum bad.";
            }
            leaf upd-les-recent-cnt {
              type uint32;
              description
                "Received less recent LSA.";
            }
            leaf upd-unknow-lsa-cnt {
              type uint32;
              description
                "LSUpdate packet unknown LSA type.";
            }
            leaf opq9-flood-cnt {
              type uint32;
              description
                "Opq9 of flooding scope.";
            }
            leaf opq10-flood-cnt {
              type uint32;
              description
                "Opq10 of flooding scope.";
            }
            leaf opq11-flood-cnt {
              type uint32;
              description
                "Opq11 of flooding scope.";
            }
            leaf unknown-tlv {
              type uint32;
              description
                "Unknown TLV type.";
            }
            leaf rxmt-dd-err-cnt {
              type uint32;
              description
                "Number for DD packet.";
            }
            leaf rxmt-req-err-cnt {
              type uint32;
              description
                "Number for request packet.";
            }
            leaf rxmt-upd-err-cnt {
              type uint32;
              description
                "Number for update packet.";
            }
            leaf gr-invalid-lsa-cnt {
              type uint32;
              description
                "Number of invalid LSAs.";
            }
            leaf gr-invalid-pol-cnt {
              type uint32;
              description
                "Number of policy failed LSAs.";
            }
            leaf gr-invalid-prd-cnt {
              type uint32;
              description
                "Number of wrong period LSAs.";
            }
            leaf tunnel-cost-cnt {
              type uint32;
              description
                "Tunnel cost mistake.";
            }
            leaf peer-net-type-cnt {
              type uint32;
              description
                "The network type of the neighbor interface is not consistent.";
            }
            leaf hello-dr-mis-cnt {
              type uint32;
              description
                "The DR or BDR in receiving hello packet is not same with the DR or BDR.";
            }
            leaf gen-ttl-err-cnt {
              type uint32;
              description
                "The TTL of the packet is error.";
            }
            leaf over-max-buffer-length-cnt {
              type uint32;
              description
                "Number of packet that length is more than max buffer length.";
            }
            leaf bad-net-segment-packet-cnt {
              type uint32;
              description
                "Number of bad network segment packet.";
            }
            leaf bad-routerid-packet-cnt {
              type uint32;
              description
                "Number of non-hello packet that router ID is different.";
            }
            leaf destination-ip-error-packet-cnt {
              type uint32;
              description
                "Number of bad destIpAddress packet.";
            }
            leaf passive-intf-packet-cnt {
              type uint32;
              description
                "Number of packet that received from silent Interface.";
            }
            leaf hello-nbr-reach-limit-cnt {
              type uint32;
              description
                "Number of hello packet that discard because the number of neighbour reached the limit.";
            }
            leaf hello-hold-down-cnt {
              type uint32;
              description
                "Number of hello packet that discard because the neighbour is in hold-down state.";
            }
            leaf hello-memory-overload-cnt {
              type uint32;
              description
                "Number of hello packet that discard because memory is overload.";
            }
            leaf hello-cpu-overload-cnt {
              type uint32;
              description
                "Number of hello packet that discard because cpu is overload.";
            }
            leaf dd-nbr-reach-limit-cnt {
              type uint32;
              description
                "Number of dd packet that discard because the number of neighbour reached the limit.";
            }
            leaf dd-cpu-overload-cnt {
              type uint32;
              description
                "Number of dd packet that discard because cpu is overload.";
            }
            leaf dd-mem-overload-cnt {
              type uint32;
              description
                "Number of dd packet that discard because memory is overload.";
            }
            leaf ri-lsa-tlv-error-cnt {
              type uint32;
              description
                "Router information lsa Tlv error.";
            }
            leaf ri-lsa-sub-tlv-error-cnt {
              type uint32;
              description
                "Router information lsa sub Tlv error.";
            }
            leaf ext-prefix-lsa-tlv-error-cnt {
              type uint32;
              description
                "Extend prefix lsa Tlv error.";
            }
            leaf ext-prefix-lsa-sub-tlv-error-cnt {
              type uint32;
              description
                "Extend prefix lsa sub Tlv error.";
            }
            leaf ext-link-lsa-tlv-error-cnt {
              type uint32;
              description
                "Extend link lsa Tlv error.";
            }
            leaf ext-link-lsa-sub-tlv-error-cnt {
              type uint32;
              description
                "Extend link lsa sub Tlv error.";
            }
            leaf bad-sr-algo-cnt {
              type uint32;
              description
                "Bad SR-Algorithm TLV.";
            }
            leaf bad-sid-range-cnt {
              type uint32;
              description
                "Bad SID/Label Range TLV.";
            }
            leaf bad-sid-cnt {
              type uint32;
              description
                "Bad SID/Label Sub TLV.";
            }
            leaf bad-adj-sid-cnt {
              type uint32;
              description
                "Bad Adj-SID Sub TLV.";
            }
            leaf bad-prefix-sid-cnt {
              type uint32;
              description
                "Bad Prefix-SID Sub TLV.";
            }
            leaf bad-ext-prefix-range-cnt {
              type uint32;
              description
                "Bad Extended Prefix Range TLV.";
            }
            leaf bad-lan-adj-sid-cnt {
              type uint32;
              description
                "Bad LAN Adj-SID Sub TLV.";
            }
            leaf bad-ext-prefix-cnt {
              type uint32;
              description
                "Bad Extended Prefix TLV.";
            }
            leaf bad-ext-link-cnt {
              type uint32;
              description
                "Bad Extended Link TLV.";
            }
          }
          container as-lsdb-brief {
            description
              "Statistics of AS LSDB statistics.";
            leaf router-id {
              type inet:ipv4-address-no-zone;
              description
                "ID of the local router.";
            }
            leaf opaque11 {
              type uint32;
              description
                "Number of Type11 opaque LSAs.";
            }
            leaf ase {
              type uint32;
              description
                "Number of ASE LSAs.";
            }
            leaf sub-total {
              type uint32;
              description
                "Sub type sum.";
            }
          }
          container neighbors {
            description
              "List of neighbor.";
            list neighbor {
              key "area-id if-name router-id ip-addr";
              description
                "Statistics of neighbor.";
              leaf area-id {
                type inet:ipv4-address-no-zone;
                description
                  "Neighbor area ID.";
              }
              leaf if-name {
                type string {
                  length "0..64";
                }
                description
                  "Neighbor interface name.";
              }
              leaf router-id {
                type inet:ipv4-address-no-zone;
                description
                  "Neighbor router ID.";
              }
              leaf ip-addr {
                type inet:ipv4-address-no-zone;
                description
                  "Neighbor IP address.";
              }
              leaf multi-area-flag {
                type boolean;
                description
                  "The symoble of multi area.";
              }
              leaf state {
                type live_ncs_nbr-state;
                description
                  "Neighbor state.";
              }
              leaf host-name {
                type string {
                  length "1..255";
                }
                description
                  "Neighbor host name.";
              }
              container datas {
                description
                  "List of neighbor data.";
                list data {
                  key "if-ip";
                  description
                    "Statistics of neighbor data.";
                  leaf if-ip {
                    type inet:ipv4-address-no-zone;
                    description
                      "Neighbor interface IP address.";
                  }
                  leaf gr-state {
                    type live_ncs_nbr-gr-state;
                    description
                      "Neighbor GR state.";
                  }
                  leaf mode {
                    type live_ncs_nbr-mode;
                    description
                      "Neighbor mode.";
                  }
                  leaf priority {
                    type int32;
                    description
                      "Neighbor priority.";
                  }
                  leaf dr {
                    type inet:ipv4-address-no-zone;
                    description
                      "Neighbor DR.";
                  }
                  leaf bdr {
                    type inet:ipv4-address-no-zone;
                    description
                      "Neighbor BDR.";
                  }
                  leaf if-mtu {
                    type uint32;
                    description
                      "Neighbor interface MTU.";
                  }
                  leaf dead-due-timer {
                    type uint32;
                    description
                      "Neighbor dead due timer.";
                  }
                  leaf retran-interval {
                    type uint32;
                    description
                      "Neighbor retransmit interval.";
                  }
                  leaf up-time {
                    type string {
                      length "1..16";
                    }
                    description
                      "Neighbor up time.";
                  }
                  leaf up-time-stamp {
                    type yang:date-and-time;
                    description
                      "Neighbor up time stamp.";
                  }
                  leaf auth-sequence {
                    type uint32;
                    description
                      "Neighbor authentication sequence number.";
                  }
                }
              }
            }
          }
          container routings {
            description
              "List of the OSPF routing table.";
            list routing {
              key "dest-ip mask-length path-type";
              description
                "Statistics of the OSPF routing table.";
              leaf dest-ip {
                type inet:ipv4-address-no-zone;
                description
                  "Destination IP address.";
              }
              leaf mask-length {
                type uint32 {
                  range "0..32";
                }
                description
                  "Mask length.";
              }
              leaf path-type {
                type live_ncs_path-type;
                description
                  "Route type.";
              }
              leaf cost {
                type uint32;
                description
                  "Cost to the destination address.";
              }
              leaf prefix-priority {
                type live_ncs_pre-priority;
                description
                  "Prefix priority.";
              }
              container nexthop-datas {
                description
                  "List of nexthop data.";
                list nexthop-data {
                  key "ip-addr adv-router-id area-id";
                  description
                    "Statistics of nexthop data.";
                  leaf ip-addr {
                    type inet:ipv4-address-no-zone;
                    description
                      "Nexthop IP address.";
                  }
                  leaf adv-router-id {
                    type inet:ipv4-address-no-zone;
                    description
                      "Next hop advertising router ID.";
                  }
                  leaf area-id {
                    type inet:ipv4-address-no-zone;
                    description
                      "Next hop area ID.";
                  }
                  leaf if-name {
                    type string {
                      length "1..64";
                    }
                    description
                      "Next hop outgoing interface name.";
                  }
                  leaf flags-disp {
                    type string {
                      length "1..8";
                    }
                    description
                      "Next hop flags.";
                  }
                  leaf tag {
                    type uint32;
                    description
                      "Next hop tag.";
                  }
                  leaf bak-if-name {
                    type string {
                      length "1..64";
                    }
                    description
                      "Backup outgoing interface name.";
                  }
                  leaf bak-next-ip {
                    type inet:ipv4-address-no-zone;
                    description
                      "Backup nexthop IP address.";
                  }
                  leaf backup-type {
                    type live_ncs_backup-type;
                    description
                      "Type of backup.";
                  }
                  leaf tunnel-dest {
                    type inet:ipv4-address-no-zone;
                    description
                      "Tunnel destination.";
                  }
                  leaf tunnel-type {
                    type live_ncs_tunnel-type;
                    description
                      "Type of tunnel.";
                  }
                }
              }
            }
          }
          container vlink-nbr-statistics {
            description
              "List of virtual link information.";
            list vlink-nbr-statistic {
              key "area-id router-id";
              description
                "Statistics of virtual link information.";
              leaf area-id {
                type inet:ipv4-address-no-zone;
                description
                  "The transit area identifier.";
              }
              leaf router-id {
                type inet:ipv4-address-no-zone;
                description
                  "A 32-bit integer uniquely identifying the neighboring router in the autonomous system.";
              }
              leaf if-ip-address {
                type inet:ipv4-address-no-zone;
                description
                  "Self/Source IP address of the out going interface.";
              }
              leaf ip-address {
                type inet:ipv4-address-no-zone;
                description
                  "The IP address this virtual neighbor is using.";
              }
              leaf state {
                type live_ncs_nbr-state;
                description
                  "The state of the virtual neighbor relationship.";
              }
              leaf interface-state {
                type live_ncs_intf-state;
                description
                  "OSPF virtual interface states.";
              }
              leaf type {
                type live_ncs_network-type;
                description
                  "Interface type.";
              }
              leaf gr-state {
                type live_ncs_nbr-gr-state;
                description
                  "Status of GR of an interface.";
              }
              leaf hello-interval {
                type uint32;
                units "s";
                description
                  "Time between hello packets.";
              }
              leaf dead-interval {
                type uint32;
                units "s";
                description
                  "Interval after which a neighbor is declared dead.";
              }
              leaf trans-delay-interval {
                type uint32;
                units "s";
                description
                  "Delay for transmitting LSAs.";
              }
              leaf retransmit-interval {
                type uint32;
                units "s";
                description
                  "Interval for retransmitting LSAs.";
              }
              leaf cost {
                type uint32;
                description
                  "Cost to reach the end point of this virtual link or cost to reach the virtual neighbor.";
              }
              leaf smart-discover {
                type boolean;
                description
                  "Indicates whether smart discover feature is enabled or not.";
              }
              leaf options {
                type inet:ipv4-address-no-zone;
                description
                  "Neighbor options.";
              }
              leaf events {
                type uint32;
                description
                  "Neighbor events.";
              }
              leaf ls-rxq-len {
                type uint32;
                description
                  "Neighbor retransmission queue length.";
              }
              leaf hello-suppress {
                type boolean;
                description
                  "Indicates whether Hellos are being suppressed to the neighbor.";
              }
              leaf gr-helper-age {
                type uint32;
                description
                  "Neighbor helper age.";
              }
              leaf helper-ext-reason {
                type live_ncs_helper-extreason;
                description
                  "Neighbor helper exit reason.";
              }
              leaf gr-helper-status {
                type live_ncs_nbr-gr-helper-status;
                description
                  "Neighbor helper status.";
              }
            }
          }
        }
      }
    }
  }
  augment "/ncs:devices/ncs:device/ncs:config/ni:network-instance/ni:instances/ni:instance" {
    description
      "OSPFv2 augment to L3VPN.";
    container ospfv2 {
      tailf:ncs-device-type "netconf";
      tailf:display-when "not(../../../../../ncs:module) or ../../../../../ncs:module[ncs:name='huawei-ospfv2']";
      description
        "Configure OSPFv2.";
      container gtsm {
        when "../../l3vpn:afs/l3vpn:af[l3vpn:type='ipv4-unicast']" {
          tailf:xpath-root 3;
        }
        presence "Enable gtsm.";
        description
          "Configure the OSPF GTSM.";
        leaf hops {
          type uint8 {
            range "1..255";
          }
          mandatory true;
          description
            "Specifies the number of TTL hops to be detected.";
        }
        leaf nonstandard-multicast {
          type boolean;
          default "false";
          description
            "Enable/disable sending Multicast packet with TTL as 255 and receive multicast packet TTL should be 1 or 255 to ((255 - configured hop) + 1).";
        }
      }
      container sites {
        when "../../l3vpn:afs/l3vpn:af[l3vpn:type='ipv4-unicast']" {
          tailf:xpath-root 3;
        }
        description
          "List of OSPF instance.";
        list site {
          key "process-id";
          description
            "Configure OSPF instance.";
          leaf process-id {
            type uint32 {
              range "1..4294967295";
            }
            description
              "Process ID.";
          }
          leaf description {
            type string {
              length "1..80";
              pattern '([^?]*)';
            }
            description
              "Description of an OSPF process.";
          }
          leaf router-id {
            type inet:ipv4-address-no-zone;
            description
              "Router ID. It is used to set the OSPF private ID.";
          }
          leaf opaque {
            type boolean;
            default "true";
            description
              "Enable/disable the opaque LSA capability. After it is enabled, an OSPF process can generate the opaque LSA and receive the opaque LSA from the neighbor device.";
          }
          leaf rfc1583-compatible {
            type boolean;
            default "true";
            description
              "Enable/disable the route selection rule that is compatible with RFC 1583.";
          }
          leaf silent-all-interface {
            type boolean;
            default "false";
            description
              "Enable/disable to suppress all interfaces in an OSPF process from sending or receiving OSPF packets.";
          }
          leaf retransmission-limit {
            type boolean;
            default "false";
            description
              "Enable/disable maximum retransmission.";
          }
          leaf retransmission-limit-value {
            when "../retransmission-limit='true'" {
              tailf:xpath-root 3;
            }
            type uint32 {
              range "2..255";
            }
            default "30";
            description
              "Maximum retransmission times.";
          }
          leaf safe-sync {
            type boolean;
            default "false";
            description
              "Enable/disable safe synchronization.";
          }
          leaf traffic-adj {
            type boolean;
            default "false";
            description
              "Enable/disable traffic adjust info.";
          }
          leaf traffic-adv {
            when "../traffic-adj='true'" {
              tailf:xpath-root 3;
            }
            type boolean;
            default "false";
            description
              "Enable/disable traffic advertise info.";
          }
          leaf local-mt {
            when "../../../../ni:name='_public_'" {
              tailf:xpath-root 3;
            }
            type boolean;
            must "../local-mt='false' or ../traffic-adj='true'" {
              tailf:xpath-root 3;
            }
            default "false";
            description
              "Enable/disable local multicast topology.";
          }
          leaf advertise-mpls-lsr-id {
            type boolean;
            must "../advertise-mpls-lsr-id='false' or ../../../../ni:name='_public_'" {
              tailf:xpath-root 3;
            }
            default "false";
            description
              "Enable/disable advertise MPLS LSR ID into multiple areas as an intra area route.";
          }
          leaf advertise-mpls-lsr-id-cost {
            when "../advertise-mpls-lsr-id='true'" {
              tailf:xpath-root 3;
            }
            type uint32 {
              range "0..65535";
            }
            default "0";
            description
              "MPLS LSR ID link cost.";
          }
          leaf suppress-reachability {
            type boolean;
            default "false";
            description
              "Enable/disable suppress reachability.";
          }
          leaf lsa-refresh {
            type boolean;
            default "true";
            description
              "Enable/disable refresh the age of LSA with greater lsa age.";
          }
          leaf mpls-ldp-auto-flag {
            type proc-auto-cfg-state;
            default "none";
            description
              "Enable LDP automatically on OSPF enabled interfaces, but need to set MPLS first.";
          }
          leaf lsdb-overflow-limit {
            type uint32 {
              range "1..1000000";
            }
            description
              "Maximum number of AS external LSAs allowed in the LSDB.";
          }
          leaf peer-flapping-suppress {
            type boolean;
            default "true";
            description
              "Enable/disable peer flapping suppress feature.";
          }
          leaf shutdown {
            type boolean;
            must "../shutdown='false' or ../../../../ni:name='__dcn_vpn__'" {
              tailf:xpath-root 3;
            }
            default "false";
            description
              "Enable/disable shutdown OSPFv2 service.";
          }
          leaf sham-hello {
            type boolean;
            default "false";
            description
              "Enable/disable peers keep alive by receiving any valid OSPF packet.";
          }
          leaf max-link-cost {
            type uint16 {
              range "1..65534";
            }
            description
              "Set the max value of link cost.";
          }
          leaf maxage-lsa {
            type uint32 {
              range "0..65535";
            }
            units "s";
            default "20";
            description
              "Calculation of route delay when the OSPF LSA frequently flaps.";
          }
          container private-net {
            when "../../../../ni:name!='_public_'" {
              tailf:xpath-root 3;
            }
            description
              "Configure private network configuration of OSPF.";
            leaf eca-route {
              type boolean;
              default "false";
              description
                "Enable/disable route type of the extended community attribute for VPN.";
            }
            choice route-tag {
              description
                "To set route tag value.";
              case disable {
                description
                  "To disable the using of the tag for loop detection.";
                leaf disable {
                  type empty;
                  description
                    "To disable the using of the tag for loop detection.";
                }
              }
              case value {
                description
                  "Tag of an imported VPN route.";
                leaf value {
                  type uint32 {
                    range "0..4294967295";
                  }
                  description
                    "Tag of an imported VPN route. By default, the first two bytes of the tag value are fixed to be 0xD000, and the last two bytes are the local AS number of the local BGP. For example, if the AS number of BGP is 100, the default tag value in decimal notation is 3489661028.If not configed, the default is 0.";
                }
              }
            }
            leaf vpn-capability {
              type boolean;
              default "false";
              description
                "Enable/disable route loop detection and directly calculate routes. When VPN multi instance is supported on the multi VPN instance CE (MCE) router, loop detection must be cancelled. It is applicable to only OSPF VPN instances.";
            }
            container domain-id {
              presence "ID of an OSPF domain.";
              description
                "Configure ID of an OSPF domain.";
              leaf domain-id {
                type inet:ipv4-address-no-zone;
                mandatory true;
                description
                  "ID of an OSPF domain.";
              }
              leaf type {
                type domain-id-type;
                default "0x0005";
                description
                  "Type of an OSPF domain ID.";
              }
              leaf value {
                type pub-type:hex-binary {
                  length "1..6";
                  pattern '((0x|0X)?[0-9a-fA-F]{0,4})';
                }
                default "0x0";
                description
                  "Value of an OSPF domain ID type.";
              }
            }
            container domain-id-secondarys {
              when '../domain-id' {
                tailf:xpath-root 3;
              }
              description
                "List of ID of a secondary domain.";
              list domain-id-secondary {
                key "domain-id type value";
                description
                  "Configure ID of a secondary domain.";
                leaf domain-id {
                  type inet:ipv4-address-no-zone;
                  description
                    "ID of an OSPF domain.";
                }
                leaf type {
                  type domain-id-type;
                  description
                    "Type of an OSPF domain ID.";
                }
                leaf value {
                  type pub-type:hex-binary {
                    length "1..6";
                    pattern '((0x|0X)?[0-9a-fA-F]{0,4})';
                  }
                  description
                    "Value of an OSPF domain ID type.";
                }
              }
            }
          }
          container host-name {
            description
              "Configure OSPF host name.";
            leaf enable {
              type boolean;
              must "../enable='false' or ../../opaque='true'" {
                tailf:xpath-root 3;
              }
              default "false";
              description
                "Enable/disable host name.";
            }
            leaf value {
              when "../enable='true'" {
                tailf:xpath-root 3;
              }
              type string {
                length "1..255";
              }
              description
                "Set host name.";
            }
          }
          container bandwidth {
            description
              "Configure bandwidth.";
            leaf config-bw-enable {
              type boolean;
              default "false";
              description
                "Enable/disable bandwidth config.";
            }
            leaf reference-value {
              type uint32 {
                range "1..2147483648";
              }
              default "100";
              description
                "Reference to the calculation of link costs.";
            }
          }
          container timer {
            description
              "Configure timer.";
            container lsa-arrival {
              description
                "Configure interval for receiving LSAs either through an intelligent timer or timer.";
              choice timer-type {
                default "intelligent-timer";
                description
                  "Set a value for the LDP and OSPF synchronization timer.";
                case timer {
                  description
                    "Interval for receiving LSAs.";
                  leaf interval {
                    type uint32 {
                      range "0..10000";
                    }
                    description
                      "Interval for receiving LSAs.";
                  }
                }
                case intelligent-timer {
                  description
                    "Specify an intelligent timer.";
                  leaf max-interval {
                    type uint32 {
                      range "1..300000";
                    }
                    must '../start-interval<=../max-interval and ../hold-interval<=../max-interval' {
                      tailf:xpath-root 3;
                    }
                    default "1000";
                    description
                      "Maximum interval for receiving OSPF LSAs.";
                  }
                  leaf start-interval {
                    type uint32 {
                      range "0..60000";
                    }
                    must '../start-interval<=../max-interval' {
                      tailf:xpath-root 3;
                    }
                    default "500";
                    description
                      "Initial interval for receiving OSPF LSAs.";
                  }
                  leaf hold-interval {
                    type uint32 {
                      range "1..60000";
                    }
                    must '../hold-interval<=../max-interval' {
                      tailf:xpath-root 3;
                    }
                    default "500";
                    description
                      "Hold interval for receiving OSPF LSAs.";
                  }
                }
              }
            }
            container lsa-arr-supp-flap {
              description
                "Configure the delay timer for LSA acceptance.";
              leaf interval {
                type uint32 {
                  range "0..600";
                }
                units "s";
                default "10";
                description
                  "Specifies an interval for suppressing LSA advertising in case of route flapping. The value 0 indicates that LSA advertising is not suppressed.";
              }
              leaf threshold-count {
                type uint32 {
                  range "3..100";
                }
                default "30";
                description
                  "Value of the threshold of LSAs to be suppressed.";
              }
            }
            container lsa-originate {
              description
                "Configure interval for receiving LSAs either through an intelligent timer or timer.";
              leaf other-type-interval {
                type uint32 {
                  range "0..10";
                }
                default "5";
                description
                  "Specify an updating/originating interval for type3, type4 and type10 LSAs. Interval for updating the LSAs except OSPF router LSAs and network LSAs.";
              }
              choice timer-type {
                default "intelligent-timer";
                description
                  "Specify an updating/originating interval for type3, type4 and type10 LSAs.";
                case intelligent-timer {
                  description
                    "Specify an intelligent timer for router LSA, network LSA, external LSA and NSSA LSA.";
                  leaf max-interval {
                    type uint32 {
                      range "1..300000";
                    }
                    must '../start-interval<=../max-interval and ../hold-interval<=../max-interval' {
                      tailf:xpath-root 3;
                    }
                    default "5000";
                    description
                      "Maximum interval for updating OSPF LSAs.";
                  }
                  leaf start-interval {
                    type uint32 {
                      range "0..60000";
                    }
                    must '../start-interval<=../max-interval' {
                      tailf:xpath-root 3;
                    }
                    default "500";
                    description
                      "Initial interval for updating OSPF LSAs.";
                  }
                  leaf hold-interval {
                    type uint32 {
                      range "1..60000";
                    }
                    must '../hold-interval<=../max-interval' {
                      tailf:xpath-root 3;
                    }
                    default "1000";
                    description
                      "Hold interval for updating OSPF LSAs.";
                  }
                }
              }
            }
            container lsa-org-supp-flap {
              description
                "Configure the delay timer for LSA generation.";
              leaf interval {
                type uint32 {
                  range "0..600";
                }
                units "s";
                default "10";
                description
                  "Specifies an interval for suppressing LSA advertising in case of route flapping. The value 0 indicates that LSA advertising is not suppressed.";
              }
              leaf threshold-count {
                type uint32 {
                  range "3..100";
                }
                default "30";
                description
                  "Value of the threshold of LSAs to be suppressed.";
              }
            }
            container spf-schedule {
              description
                "Configure the interval for SPF calculation.";
              choice schedule-type {
                default "intelligent-timer";
                description
                  "SPF schedule interval.";
                case timer {
                  description
                    "Specify an updating/originating interval for type3, type4 and type10 LSAs.";
                  leaf interval {
                    type uint32 {
                      range "1..10";
                    }
                    units "s";
                    description
                      "Interval for OSPF SPF calculation. By adjusting the interval for SPF calculation, you can prevent the occupation of too many bandwidth and router resources caused by frequent network changes.";
                  }
                }
                case intelligent-timer {
                  description
                    "Specify an intelligent timer.";
                  leaf max-interval {
                    type uint32 {
                      range "1..300000";
                    }
                    units "ms";
                    must '../start-interval<=../max-interval and ../hold-interval<=../max-interval' {
                      tailf:xpath-root 3;
                    }
                    default "5000";
                    description
                      "Maximum interval for OSPF SPF calculation set through an intelligent timer. By adjusting the interval for SPF calculation, you can prevent the occupation of too many bandwidths and device resources caused by frequent network changes.";
                  }
                  leaf start-interval {
                    type uint32 {
                      range "1..60000";
                    }
                    units "ms";
                    must '../start-interval<=../max-interval' {
                      tailf:xpath-root 3;
                    }
                    default "50";
                    description
                      "Initial interval for OSPF SPF calculation set through an intelligent timer. By adjusting the interval for SPF calculation, you can prevent the occupation of too many bandwidth and router resources caused by frequent network changes.";
                  }
                  leaf hold-interval {
                    type uint32 {
                      range "1..60000";
                    }
                    units "ms";
                    must '../hold-interval<=../max-interval' {
                      tailf:xpath-root 3;
                    }
                    default "200";
                    description
                      "Hold interval for OSPF SPF calculation set through an intelligent timer. By adjusting the interval for calculating SPF, you can prevent the occupation of too many bandwidth and router resources caused by frequent network changes.";
                  }
                  leaf conserv-flag {
                    type boolean;
                    default "false";
                    description
                      "Enable/disable conservative mode.";
                  }
                }
                case millisecond {
                  description
                    "Specify an interval.";
                  leaf millisecond {
                    type uint32 {
                      range "1..10000";
                    }
                    units "ms";
                    description
                      "Interval for OSPF SPF calculation. By adjusting the interval for SPF calculation, you can prevent the occupation of too many bandwidths and device resources caused by frequent network changes.";
                  }
                }
              }
            }
          }
          container bfd {
            description
              "Configure BFD in a OSPF process.";
            leaf enable {
              type boolean;
              default "false";
              description
                "Enable/disable BFD in an OSPF process.";
            }
            leaf min-rx {
              type uint32 {
                range "3..20000";
              }
              units "ms";
              description
                "Minimum interval for receiving BFD packets from the peer end. The range and default are based on PAF.";
            }
            leaf min-tx {
              type uint32 {
                range "3..20000";
              }
              units "ms";
              description
                "Minimum interval for sending BFD packets to the peer end. The range and default are based on PAF.";
            }
            leaf detect-multiplier {
              type uint32 {
                range "3..50";
              }
              default "3";
              description
                "Local detection multiplier.";
            }
            leaf incr-cost {
              type uint32 {
                range "1..65535";
              }
              description
                "BFD sync cost.";
            }
            leaf frr-binding {
              type boolean;
              default "false";
              description
                "Enable/disable bind FRR with BFD.";
            }
          }
          container metric-delay {
            when "../opaque='true'" {
              tailf:xpath-root 3;
            }
            description
              "Configure metric delay in a OSPF process.";
            leaf adv-enable {
              type boolean;
              default "false";
              description
                "Enable/disable metric delay advertisement.";
            }
            leaf suppress-timer {
              type uint32 {
                range "0..600";
              }
              units "s";
              default "120";
              description
                "Metric delay suppress timer.";
            }
            leaf suppress-percent {
              type uint8 {
                range "0..100";
              }
              default "10";
              description
                "Metric delay suppress percent threshold.";
            }
            leaf suppress-absolute {
              type uint32 {
                range "0..10000";
              }
              default "1000";
              description
                "Metric delay suppress absolute threshold.";
            }
          }
          container bier {
            when "../opaque='true' and ../../../../ni:name='_public_'" {
              tailf:xpath-root 3;
            }
            description
              "Configure the bier.";
            leaf enable {
              type boolean;
              default "false";
              description
                "Enable/disable the bier.";
            }
          }
          container stub-router {
            description
              "Configure stub router is used to configure the router as stub router.";
            leaf flag {
              type stub-router-flag;
              default "no-config";
              description
                "Stub router. The router configured with the stub router command notifies other OSPF routers of not using the stub router to forward data by increasing the metric greater than 65535 of the links in the LSA that is generated by the router.";
            }
            leaf interval {
              when "../flag='stub-on-boot'" {
                tailf:xpath-root 3;
              }
              type uint32 {
                range "5..65535";
              }
              default "500";
              description
                "Interval for remaining as the stub router during the active/standby switchover of a router.";
            }
            leaf include-stub {
              when "../flag!='no-config'" {
                tailf:xpath-root 3;
              }
              type boolean;
              default "false";
              description
                "Enable/disable set maximum cost for router lsa stub link.";
            }
            leaf external-lsa {
              when "../flag!='no-config'" {
                tailf:xpath-root 3;
              }
              type boolean;
              default "false";
              description
                "Enable/disable set maximum cost for external lsa.";
            }
            leaf external-cost {
              when "../external-lsa='true'" {
                tailf:xpath-root 3;
              }
              type uint32 {
                range "1..16777215";
              }
              default "16711680";
              description
                "Advertise external LSAs with configured/default overriding metric.";
            }
            leaf summary-lsa {
              when "../flag!='no-config'" {
                tailf:xpath-root 3;
              }
              type boolean;
              default "false";
              description
                "Enable/disable set maximum cost for summary lsa.";
            }
            leaf summary-cost {
              when "../summary-lsa='true'" {
                tailf:xpath-root 3;
              }
              type uint32 {
                range "1..16777215";
              }
              default "16711680";
              description
                "Advertise summary LSAs with configured/default overriding metric.";
            }
          }
          container bgp-ls {
            description
              "Configure BGP LS.";
            leaf enable {
              type boolean;
              must "../enable='false' or ../../../../../ni:name='_public_'" {
                tailf:xpath-root 3;
              }
              default "false";
              description
                "Enable/disable BGP LS.";
            }
            leaf identifier {
              when "../enable='true'" {
                tailf:xpath-root 3;
              }
              type uint32 {
                range "2..65535";
              }
              description
                "Topo identifier.";
            }
          }
          container import-limit {
            presence "Enable import-limit";
            description
              "Configure limits the maximum number of routes to be imported.";
            leaf max-number {
              type uint32 {
                range "1..4294967295";
              }
              mandatory true;
              description
                "Maximum number of external routes that can be imported.";
            }
            leaf threshold-upper {
              type uint32 {
                range "1..100";
              }
              must '../threshold-upper>=../threshold-lower' {
                tailf:xpath-root 3;
              }
              default "80";
              description
                "Upper threshold of the maximum number of routes that can be imported.";
            }
            leaf threshold-lower {
              type uint32 {
                range "1..100";
              }
              must '../threshold-upper>=../threshold-lower' {
                tailf:xpath-root 3;
              }
              default "70";
              description
                "Lower threshold of the maximum number of routes that can be imported.";
            }
          }
          container spf-control {
            description
              "Configure SPF calculation control.";
            leaf max-load-balancing {
              type uint32 {
                range "1..128";
              }
              default "128";
              description
                "Maximum number of the equal cost routes of the destination address in the routing table. The range and default are based on PAF.";
            }
          }
          container default-para {
            description
              "Configure default parameter.";
            choice cost {
              default "cost-value";
              description
                "Cost assigned to the ASE or NSSA LSA generated when an external route is imported.";
              case cost-value {
                description
                  "Default metric of the external routes imported by OSPF.";
                leaf cost-value {
                  type uint32 {
                    range "0..16777214";
                  }
                  default "1";
                  description
                    "Default metric of the external routes imported by OSPF.";
                }
              }
              case cost-inherit-metric {
                description
                  "Cost of the imported route is the cost carried in the route. If the cost is not specified, the default cost can be set through the default command.";
                leaf cost-inherit-metric {
                  type empty;
                  description
                    "Cost of the imported route is the cost carried in the route. If the cost is not specified, the default cost can be set through the default command.";
                }
              }
            }
            leaf tag {
              type uint32 {
                range "0..4294967295";
              }
              default "1";
              description
                "Tag of an external route.";
            }
            leaf type {
              type external-route-type;
              default "type2";
              description
                "Type of an external route.";
            }
          }
          container avoid-micro-loop {
            description
              "Configure OSPF avoid microloop.";
            leaf frr-enable {
              type boolean;
              default "false";
              description
                "Enable/disable avoid microloop.";
            }
            leaf frr-rib-update-delay {
              type uint32 {
                range "100..5000";
              }
              units "ms";
              default "100";
              description
                "Set the maximum interval of delay timer.";
            }
            leaf te-tunnel-enable {
              type boolean;
              default "false";
              description
                "Enable/disable TE shortcut tunnel avoid microloop.";
            }
            leaf te-tunnel-rib-update-delay {
              type uint32 {
                range "100..30000";
              }
              units "ms";
              default "1000";
              description
                "Set the route delivery delay for TE shortcut tunnel.";
            }
          }
          container asbr-summary-prefixs {
            description
              "List of aggregate addresses for OSPF (only for ASBR).";
            list asbr-summary-prefix {
              key "prefix network-mask";
              description
                "Configure aggregate addresses for OSPF (only for ASBR).";
              leaf prefix {
                type inet:ipv4-address-no-zone;
                description
                  "IP address. Prefix is the address after mask.";
              }
              leaf network-mask {
                type inet:ipv4-address-no-zone;
                description
                  "IP address mask.";
              }
              leaf cost {
                type uint32 {
                  range "0..16777214";
                }
                description
                  "Specifies the cost of the aggregated route.";
              }
              leaf distribute-delay {
                type uint32 {
                  range "1..65535";
                }
                units "s";
                description
                  "Distribute delay interval.";
              }
              leaf tag {
                type uint32 {
                  range "0..4294967295";
                }
                description
                  "Specifies that the tag is mainly used to control advertisement of routes through the routing policy.";
              }
              leaf advertise {
                type boolean;
                default "true";
                description
                  "Enable/disable the aggregated route is advertised.";
              }
              leaf generate-null-zero {
                when "../advertise = 'true'" {
                  tailf:xpath-root 3;
                }
                type boolean;
                default "false";
                description
                  "Enable/disable generate black hole route.";
              }
            }
          }
          choice default-route {
            description
              "Notification of default routes to the OSPF routing area.";
            case summary {
              description
                "Summary.";
              container summary {
                when "../../../../ni:name!='_public_'" {
                  tailf:xpath-root 3;
                }
                presence "Enable default-route-advertise summary.";
                description
                  "Configure advertises the type3 summary LSAs of the specified default route.";
                leaf cost {
                  type uint32 {
                    range "0..16777214";
                  }
                  mandatory true;
                  description
                    "Metric of an ASE LSA.";
                }
              }
            }
            case no-summary {
              description
                "No summary.";
              container no-summary {
                presence "Enable default-route-advertise no-summary.";
                description
                  "Configure default routes to the OSPF routing area.";
                leaf enable {
                  type empty;
                  status deprecated;
                  description
                    "Default Route Enable. The node enable is deprecated. You are advised to use the node no-summary.";
                }
                leaf cost {
                  type uint32 {
                    range "0..16777214";
                  }
                  description
                    "Metric of an ASE LSA.";
                }
                leaf tag {
                  type uint32 {
                    range "0..4294967295";
                  }
                  description
                    "Route tag for default imported routes.";
                }
                leaf type {
                  type external-route-type;
                  description
                    "Metric type of an ASE LSA for the default routes.";
                }
                leaf distribute-delay {
                  type uint32 {
                    range "1..65535";
                  }
                  description
                    "Distribute delay timer used for the local router to calculate the default routes advertised by other routers.";
                }
                choice mode {
                  description
                    "Mode for default route.";
                  case permit-calculate-other {
                    description
                      "Set permit calculate other.";
                    leaf permit-calculate-other {
                      type empty;
                      description
                        "To generate and advertise an ASE LSA that describes the default route only when there are valid default routes of other protocols in the routing table of the host. The router configured with permit calculate other still calculates the default routes of other routers.";
                    }
                    leaf permit-ibgp {
                      type empty;
                      description
                        "Match IBGP default route.";
                    }
                  }
                  case always {
                    description
                      "Set always.";
                    leaf always {
                      type empty;
                      description
                        "The router configured with the always parameter does not calculate the default routes of other routers.";
                    }
                  }
                }
                choice policy-type {
                  description
                    "Mode of the policy used for default route.";
                  case route-policy-name {
                    description
                      "Set a route policy name.";
                    leaf route-policy-name {
                      type leafref {
                        path "/ncs:devices/ncs:device/ncs:config/rtp:routing-policy/rtp:policy-definitions/rtp:policy-definition/rtp:name" {
                          tailf:xpath-root 3;
                        }
                      }
                      description
                        "Name of a routing policy. Through the routing policy, the device matches the default routing entry generated by the device that does not run OSPF in the routing table, and advertises the default route according to the parameters set through the routing policy.";
                    }
                  }
                  case route-filter-name {
                    description
                      "Set a route filter name.";
                    leaf route-filter-name {
                      type leafref {
                        path "/ncs:devices/ncs:device/ncs:config/xpl:xpl/xpl:route-filters/xpl:route-filter/xpl:name" {
                          tailf:xpath-root 3;
                        }
                      }
                      description
                        "Name of a routing Filter.";
                    }
                  }
                }
              }
            }
          }
          container route-preferences {
            description
              "List of preference of an OSPF route.";
            list route-preference {
              key "route-type";
              max-elements 4;
              ext:generated-by "system" {
                ext:filter "route-type='default' or route-type='ase'";
              }
              description
                "Configure preference of an OSPF route.";
              leaf route-type {
                type ospf-route-type;
                description
                  "Router type.";
              }
              leaf preference {
                type uint32 {
                  range "1..255";
                }
                ext:dynamic-default {
                  ext:default-value "10" {
                    when "../route-type != 'ase'" {
                      tailf:xpath-root 3;
                    }
                    description
                      "The default value is 10 when route type is not ase.";
                  }
                  ext:default-value "150" {
                    when "../route-type = 'ase'" {
                      tailf:xpath-root 3;
                    }
                    description
                      "The default value is 150 when route type is ase.";
                  }
                }
                description
                  "Preference of an OSPF route. The default of intra and inter area is 10.And The default of external is 150.";
              }
              choice policy-type {
                description
                  "Type of a filtering rule.";
                case route-policy-name {
                  description
                    "Name of a routing policy.";
                  leaf route-policy-name {
                    type leafref {
                      path "/ncs:devices/ncs:device/ncs:config/rtp:routing-policy/rtp:policy-definitions/rtp:policy-definition/rtp:name" {
                        tailf:xpath-root 3;
                      }
                    }
                    description
                      "Name of a routing policy.";
                  }
                }
                case route-filter-name {
                  description
                    "Name of a routing Filter.";
                  leaf route-filter-name {
                    type leafref {
                      path "/ncs:devices/ncs:device/ncs:config/xpl:xpl/xpl:route-filters/xpl:route-filter/xpl:name" {
                        tailf:xpath-root 3;
                      }
                    }
                    description
                      "Name of a routing Filter.";
                  }
                }
              }
            }
          }
          container nexthop-weights {
            description
              "List of preference of an equal cost route.";
            list nexthop-weight {
              key "ip-address";
              description
                "Configure preference of an equal cost route.";
              leaf ip-address {
                type inet:ipv4-address-no-zone;
                description
                  "IP address of the next hop.";
              }
              leaf weight {
                type uint32 {
                  range "1..254";
                }
                mandatory true;
                description
                  "Weight of the next hop. After OSPF calculates the equal cost routes, the next hop is chosen from these equal cost routes based on the value of weight. The smaller the value is, the higher the preference is. By default, the weight is 255. This indicates that load balancing is carried out among equal cost routes and packets are forwarded at the same time without the preference being set.";
              }
            }
          }
          container prefix-prioritys {
            description
              "List of priority of OSPF route.";
            list prefix-priority {
              key "priority";
              description
                "Configure priority of OSPF route.";
              leaf priority {
                type prefix-priority;
                description
                  "Convergence priority of OSPF routes.";
              }
              leaf ip-prefix {
                type leafref {
                  path "/ncs:devices/ncs:device/ncs:config/rtp:routing-policy/rtp:ipv4-prefix-filters/rtp:ipv4-prefix-filter/rtp:name" {
                    tailf:xpath-root 3;
                  }
                }
                mandatory true;
                description
                  "Name of the IP prefix list. The value is a string of 1 to 169 characters without spaces. The prefix priority command sets the convergence priority of OSPF routes according to the specified IP prefix list name, and takes effect on the public network only.
                   By default, the convergence priority of public OSPF host routes is medium, the convergence priority of directly connected routes is high, the convergence priority of static routes is medium, and the convergence priority of the routes of other protocols (such as BGP and RIP) is low. On the private network, OSPF 32 bit host routes are globally identified as medium.";
              }
            }
          }
          container ecmp-prefer {
            description
              "Configure equal cost multipath preference of OSPF routes.";
            leaf te-tunnel {
              type boolean;
              must "../te-tunnel='false' or ../intact='false'" {
                tailf:xpath-root 3;
              }
              default "false";
              description
                "Enable/disable TE tunnel interface nexthops.";
            }
            leaf intact {
              type boolean;
              must "../intact='false' or ../te-tunnel='false'" {
                tailf:xpath-root 3;
              }
              default "false";
              description
                "Enable/disable IGP native nexthop.";
            }
          }
          container frr {
            description
              "Configure OSPF fast rerouting.";
            leaf enable {
              type boolean;
              default "false";
              description
                "Enable/disable FRR for this particular process.";
            }
            leaf lfa-enable {
              type boolean;
              must "../lfa-enable='false' or ../enable='true'" {
                tailf:xpath-root 3;
              }
              default "false";
              description
                "Enable/disable loop free alternate.";
            }
            leaf rlfa-enable {
              type boolean;
              must "../rlfa-enable='false' or ../lfa-enable='true' and ../../../../../ni:name='_public_'" {
                tailf:xpath-root 3;
              }
              default "false";
              description
                "Enable/disable remote lfa.";
            }
            leaf rlfa-max-cost {
              when "../rlfa-enable='true'" {
                tailf:xpath-root 3;
              }
              type uint32 {
                range "1..4294967295";
              }
              default "4294967295";
              description
                "Remote lfa tunnel ldp maximum-reachable-cost.";
            }
            leaf tilfa-enable {
              type boolean;
              must "../tilfa-enable='false' or ../lfa-enable='true' and ../../../../../ni:name='_public_'" {
                tailf:xpath-root 3;
              }
              default "false";
              description
                "Enable/disable TILFA.";
            }
            container tiebreaker {
              when "../lfa-enable='true'" {
                tailf:xpath-root 3;
              }
              must 'node-protect!=lowest-cost' {
                tailf:xpath-root 3;
              }
              must 'node-protect!=ldp-sync' {
                tailf:xpath-root 3;
              }
              must 'ldp-sync!=lowest-cost' {
                tailf:xpath-root 3;
              }
              description
                "Configure tiebreaker for multiple backups.";
              leaf node-protect {
                type uint8 {
                  range "1..255";
                }
                default "40";
                description
                  "Set the value of node protect preference. The preference value 5 is reserved for SRLG disjoint type, cannot be configured.";
              }
              leaf lowest-cost {
                type uint8 {
                  range "1..255";
                }
                default "20";
                description
                  "Set the value of lowcost preference.";
              }
              leaf ldp-sync {
                type uint8 {
                  range "1..255";
                }
                default "10";
                description
                  "Prefer backup nexthop with ldp sync.";
              }
            }
            container route-policy {
              when "../enable='true'" {
                tailf:xpath-root 3;
              }
              description
                "Configure FRR route policy.";
              choice policy-type {
                description
                  "Type of a filtering rule.";
                case route-policy-name {
                  description
                    "Name of a routing policy.";
                  leaf route-policy-name {
                    type leafref {
                      path "/ncs:devices/ncs:device/ncs:config/rtp:routing-policy/rtp:policy-definitions/rtp:policy-definition/rtp:name" {
                        tailf:xpath-root 3;
                      }
                    }
                    description
                      "Name of a routing policy.";
                  }
                }
                case route-filter-name {
                  description
                    "Name of a routing filter.";
                  leaf route-filter-name {
                    type leafref {
                      path "/ncs:devices/ncs:device/ncs:config/xpl:xpl/xpl:route-filters/xpl:route-filter/xpl:name" {
                        tailf:xpath-root 3;
                      }
                    }
                    description
                      "Name of a routing filter.";
                  }
                }
              }
            }
            container rlfa-tunnel {
              when "../enable='true' and ../../../../../ni:name='_public_'" {
                tailf:xpath-root 3;
              }
              description
                "Configure remote LFA ip prefix.";
              choice policy-type {
                description
                  "Name of a routing policy.";
                case ip-prefix-name {
                  description
                    "Set a route policy name.";
                  leaf ip-prefix-name {
                    type leafref {
                      path "/ncs:devices/ncs:device/ncs:config/rtp:routing-policy/rtp:ipv4-prefix-filters/rtp:ipv4-prefix-filter/rtp:name" {
                        tailf:xpath-root 3;
                      }
                    }
                    description
                      "To filter PQ node. Those nodes which don't pass filter can't be PQ node.";
                  }
                }
              }
            }
          }
          container local-mt-filter {
            when "../../../../ni:name='_public_'" {
              tailf:xpath-root 3;
            }
            description
              "Configure OSPF local multicast topology filtering in routing updates.";
            choice filter-policy {
              description
                "Type of a filtering rule.";
              case acl-name-or-num {
                description
                  "ACL name or ACL number. ACL name: specify the ACL name. ACL num: apply basic ACL.";
                leaf acl-name-or-num {
                  type leafref {
                    path "/ncs:devices/ncs:device/ncs:config/acl:acl/acl:groups/acl:group/acl:identity" {
                      tailf:xpath-root 3;
                    }
                  }
                  must "/acl:acl/acl:groups/acl:group[acl:identity=current()]/acl:type='basic'" {
                    tailf:xpath-root 3;
                  }
                  description
                    "ACL name or ACL number. ACL name: specify the ACL name. ACL num: apply basic ACL.";
                }
              }
              case ip-prefix {
                description
                  "Ip prefix name.";
                leaf ip-prefix {
                  type leafref {
                    path "/ncs:devices/ncs:device/ncs:config/rtp:routing-policy/rtp:ipv4-prefix-filters/rtp:ipv4-prefix-filter/rtp:name" {
                      tailf:xpath-root 3;
                    }
                  }
                  description
                    "Ip prefix name.";
                }
              }
              case route-policy-name {
                description
                  "Name of a routing policy.";
                leaf route-policy-name {
                  type leafref {
                    path "/ncs:devices/ncs:device/ncs:config/rtp:routing-policy/rtp:policy-definitions/rtp:policy-definition/rtp:name" {
                      tailf:xpath-root 3;
                    }
                  }
                  description
                    "Name of a routing policy.";
                }
              }
              case route-filter-name {
                description
                  "Name of a routing filter.";
                leaf route-filter-name {
                  type leafref {
                    path "/ncs:devices/ncs:device/ncs:config/xpl:xpl/xpl:route-filters/xpl:route-filter/xpl:name" {
                      tailf:xpath-root 3;
                    }
                  }
                  description
                    "Name of a routing filter.";
                }
              }
            }
          }
          container peers {
            description
              "List of the IP address and DR priority of the neighbor router on the NBMA network.";
            list peer {
              key "ip-address";
              description
                "Configure the IP address and DR priority of the neighbor router on the NBMA network.";
              leaf ip-address {
                type inet:ipv4-address-no-zone;
                description
                  "IP address of the neighbor router.";
              }
              leaf priority {
                type uint8 {
                  range "0..255";
                }
                default "1";
                description
                  "To set the IP address and DR priority of the neighbor router on the NBMA network.";
              }
            }
          }
          container filter-lsa-outs {
            description
              "List of LSA filter policy.";
            list filter-lsa-out {
              key "peer-ip-addr";
              max-elements 512;
              description
                "Configure LSA filter policy.";
              leaf peer-ip-addr {
                type inet:ipv4-address-no-zone;
                description
                  "IP address of the P2MP neighbor.";
              }
              choice type {
                mandatory true;
                description
                  "Set filter lsa out type.";
                case total {
                  description
                    "Filter total types of LSAs.";
                  leaf all-flag {
                    type empty;
                    description
                      "Filter all types of LSAs.";
                  }
                }
                case other {
                  description
                    "Filter other types of LSAs.";
                  leaf sum-flag {
                    type empty;
                    description
                      "Filter type 3 Summary LSAs.";
                  }
                  choice sum-filter {
                    description
                      "Type of a filtering rule.";
                    case sum-acl-name {
                      description
                        "ACL Name or ACL Number. ACL Name: specify the ACL name. ACL Num: apply basic ACL.";
                      leaf sum-acl-name {
                        when '../sum-flag' {
                          tailf:xpath-root 3;
                        }
                        type leafref {
                          path "/ncs:devices/ncs:device/ncs:config/acl:acl/acl:groups/acl:group/acl:identity" {
                            tailf:xpath-root 3;
                          }
                        }
                        must "/acl:acl/acl:groups/acl:group[acl:identity=current()]/acl:type='basic'" {
                          tailf:xpath-root 3;
                        }
                        description
                          "ACL Name or ACL Number. ACL Name: specify the ACL name. ACL Num: apply basic ACL.";
                      }
                    }
                  }
                  leaf ase-flag {
                    type empty;
                    description
                      "Filter type-5 ASE LSAs.";
                  }
                  choice ase-filter {
                    description
                      "Type of a filtering rule.";
                    case ase-acl-name {
                      description
                        "ACL Name or ACL Number. ACL Name: specify the ACL name. ACL Num: apply basic ACL.";
                      leaf ase-acl-name {
                        when '../ase-flag' {
                          tailf:xpath-root 3;
                        }
                        type leafref {
                          path "/ncs:devices/ncs:device/ncs:config/acl:acl/acl:groups/acl:group/acl:identity" {
                            tailf:xpath-root 3;
                          }
                        }
                        must "/acl:acl/acl:groups/acl:group[acl:identity=current()]/acl:type='basic'" {
                          tailf:xpath-root 3;
                        }
                        description
                          "ACL Name or ACL Number. ACL Name: specify the ACL name. ACL Num: apply basic ACL.";
                      }
                    }
                  }
                  leaf nssa-flag {
                    type empty;
                    description
                      "Filter type7 NSSA LSAs.";
                  }
                  choice nssa-filter {
                    description
                      "Type of a filtering rule.";
                    case nssa-acl-name {
                      description
                        "ACL Name or ACL Number. ACL Name: specify the ACL name. ACL Num: apply basic ACL.";
                      leaf nssa-acl-name {
                        when '../nssa-flag' {
                          tailf:xpath-root 3;
                        }
                        type leafref {
                          path "/ncs:devices/ncs:device/ncs:config/acl:acl/acl:groups/acl:group/acl:identity" {
                            tailf:xpath-root 3;
                          }
                        }
                        must "/acl:acl/acl:groups/acl:group[acl:identity=current()]/acl:type='basic'" {
                          tailf:xpath-root 3;
                        }
                        description
                          "ACL Name or ACL Number. ACL Name: specify the ACL name. ACL Num: apply basic ACL.";
                      }
                    }
                  }
                }
              }
            }
          }
          choice graceful-restart {
            description
              "Information about OSPF GR.";
            case gr-ietf {
              description
                "Information about OSPF IETF GR.";
              container gr-ietf {
                when "../opaque='true'" {
                  tailf:xpath-root 3;
                }
                presence "Enable OSPF IETF GR.";
                description
                  "Configure OSPF IETF GR.";
                choice helper-role-mode {
                  description
                    "Information about OSPF IETF GR helper role.";
                  case never {
                    description
                      "Forbid to support enable mode.";
                    leaf never {
                      type empty;
                      description
                        "Forbid to support enable mode.";
                    }
                  }
                  case work-mode {
                    description
                      "Information about OSPF IETF GR.";
                    leaf planned-only {
                      type empty;
                      description
                        "To support only planned GR on routers.";
                    }
                    leaf ignore-external-lsa {
                      type empty;
                      description
                        "Ignore external lsa check (type5 and type7 LSAs).";
                    }
                    choice match-mode {
                      description
                        "Name of a routing policy.";
                      case acl-name-or-num {
                        description
                          "Specify the basic ACL number or ACL name for filtering peer.";
                        leaf acl-name-or-num {
                          type leafref {
                            path "/ncs:devices/ncs:device/ncs:config/acl:acl/acl:groups/acl:group/acl:identity" {
                              tailf:xpath-root 3;
                            }
                          }
                          must "/acl:acl/acl:groups/acl:group[acl:identity=current()]/acl:type='basic'" {
                            tailf:xpath-root 3;
                          }
                          description
                            "Specify the basic ACL number or ACL name for filtering peer.";
                        }
                      }
                      case ip-prefix-name {
                        description
                          "Specify the IP prefix name for filtering peers.";
                        leaf ip-prefix-name {
                          type leafref {
                            path "/ncs:devices/ncs:device/ncs:config/rtp:routing-policy/rtp:ipv4-prefix-filters/rtp:ipv4-prefix-filter/rtp:name" {
                              tailf:xpath-root 3;
                            }
                          }
                          description
                            "Specify the IP prefix name for filtering peers.";
                        }
                      }
                    }
                  }
                }
              }
            }
            case gr-non-ietf {
              description
                "Information about OSPF NON IETF GR.";
              container gr-non-ietf {
                when "../opaque='true'" {
                  tailf:xpath-root 3;
                }
                presence "Enable OSPF NON IETF GR.";
                description
                  "Configure OSPF NON IETF GR.";
              }
            }
          }
          container flood-control {
            presence "Enable flood-control";
            description
              "Configure OSPF flooding control.";
            leaf number {
              type uint32 {
                range "1..1000";
              }
              default "50";
              description
                "Specify the update packet number to send.";
            }
            leaf interval {
              type uint32 {
                range "30..100000";
              }
              default "30";
              description
                "Specify the update packet timer interval to send.";
            }
          }
          container dn-bit {
            when "../../../../ni:name!='_public_'" {
              tailf:xpath-root 3;
            }
            description
              "Configure VPN optionA feature will help PEs in inter AS exchange routes through OSPF. VPN optionA provide two ways to suppress DN bit so that so that inter AS can exchange routes through OSPF. First way dose not set DN bit while import routes from BGP, second way dose not check DN bit while learning the routes from neighbor router. In both the scenario PE will be able to learn route and propagate the route in the new VPN cloud.";
            leaf set-ase {
              type boolean;
              default "false";
              description
                "Enable/disable setting of DN bit in all ASE LSA, applicable in private network.";
            }
            leaf set-nssa {
              type boolean;
              default "false";
              description
                "Enable/disable setting of DN bit in all NSSA LSA, applicable in private network.";
            }
            leaf set-summary {
              type boolean;
              default "false";
              description
                "Enable/disable setting of DN bit in all summary LSA, applicable in private network.";
            }
            leaf check-ase {
              type boolean;
              default "false";
              description
                "Enable/disable checking of DN bit in all ASE LSA, applicable in private network.";
            }
            leaf check-nssa {
              type boolean;
              default "false";
              description
                "Enable/disable checking of DN bit in all NSSA LSA, applicable in private network.";
            }
            leaf check-summary {
              type boolean;
              default "false";
              description
                "Enable/disable checking of DN bit in all summary LSA, applicable in private network.";
            }
            container summary-router-ids {
              when "../check-summary='false'" {
                tailf:xpath-root 3;
              }
              description
                "List of router ID for which checking for DN bit summary LSA is disabled, applicable in private network.";
              list summary-router-id {
                key "router-id";
                description
                  "Configure router ID for which checking for DN bit summary LSA is disabled, applicable in private network.";
                leaf router-id {
                  type inet:ipv4-address-no-zone;
                  description
                    "Router ID for which checking for DN bit summary LSA is disabled, applicable in private network.";
                }
              }
            }
          }
          container filter-import {
            presence "filter policy import";
            description
              "Configure the filter policy import command. You can set the rules for filtering intra area, inter area, and AS external routes of an OSPF process.";
            choice policy-type {
              mandatory true;
              description
                "Type of a filtering rule.";
              case basic-acl {
                description
                  "Apply basic ACL name or ACL number.";
                leaf name-or-num {
                  type leafref {
                    path "/ncs:devices/ncs:device/ncs:config/acl:acl/acl:groups/acl:group/acl:identity" {
                      tailf:xpath-root 3;
                    }
                  }
                  must "/acl:acl/acl:groups/acl:group[acl:identity=current()]/acl:type='basic'" {
                    tailf:xpath-root 3;
                  }
                  description
                    "Apply basic ACL name or ACL number.";
                }
              }
              case ip-prefix {
                description
                  "Set the name of an IP prefix list.";
                leaf ip-prefix {
                  type leafref {
                    path "/ncs:devices/ncs:device/ncs:config/rtp:routing-policy/rtp:ipv4-prefix-filters/rtp:ipv4-prefix-filter/rtp:name" {
                      tailf:xpath-root 3;
                    }
                  }
                  description
                    "Set the name of an IP prefix list.";
                }
              }
              case route-policy {
                description
                  "Set a route policy name.";
                leaf route-policy {
                  type leafref {
                    path "/ncs:devices/ncs:device/ncs:config/rtp:routing-policy/rtp:policy-definitions/rtp:policy-definition/rtp:name" {
                      tailf:xpath-root 3;
                    }
                  }
                  description
                    "Set a route policy name.";
                }
              }
              case route-filter {
                description
                  "Set a route filter name.";
                leaf route-filter {
                  type leafref {
                    path "/ncs:devices/ncs:device/ncs:config/xpl:xpl/xpl:route-filters/xpl:route-filter/xpl:name" {
                      tailf:xpath-root 3;
                    }
                  }
                  description
                    "Set a route filter name.";
                }
              }
            }
            leaf secondary {
              type boolean;
              must "../secondary='false' or ../route-policy" {
                tailf:xpath-root 3;
              }
              default "false";
              description
                "Enable/disable secondary flag.";
            }
          }
          container filter-exports {
            description
              "List of the filter policy export command. You can set the rules for filtering the routes imported through the import route (OSPF) command when the routes are advertised in type5 LSAs to the OSPF AS.";
            list filter-export {
              key "protocol protocol-id";
              description
                "Configure the filter policy export command. You can set the rules for filtering the routes imported through the import route (OSPF) command when the routes are advertised in type5 LSAs to the OSPF AS.";
              leaf protocol {
                type filter-rt-protocol;
                description
                  "Protocol that advertises routes.";
              }
              leaf protocol-id {
                type uint32 {
                  range "1..4294967295";
                }
                must "../protocol-id=1 or ../protocol='ospf' or ../protocol='isis' or ../protocol='rip'" {
                  tailf:xpath-root 3;
                }
                description
                  "Process ID when the advertised protocol is RIP, ISIS, or OSPF.";
              }
              choice policy-type {
                mandatory true;
                description
                  "Type of a filtering rule.";
                case basic-acl {
                  description
                    "Apply basic ACL name or ACL number.";
                  leaf name-or-num {
                    type leafref {
                      path "/ncs:devices/ncs:device/ncs:config/acl:acl/acl:groups/acl:group/acl:identity" {
                        tailf:xpath-root 3;
                      }
                    }
                    must "/acl:acl/acl:groups/acl:group[acl:identity=current()]/acl:type='basic'" {
                      tailf:xpath-root 3;
                    }
                    description
                      "Apply basic ACL name or ACL number.";
                  }
                }
                case ip-prefix {
                  description
                    "Set the name of an IP prefix list.";
                  leaf ip-prefix {
                    type leafref {
                      path "/ncs:devices/ncs:device/ncs:config/rtp:routing-policy/rtp:ipv4-prefix-filters/rtp:ipv4-prefix-filter/rtp:name" {
                        tailf:xpath-root 3;
                      }
                    }
                    description
                      "Set the name of an IP prefix list.";
                  }
                }
                case route-policy {
                  description
                    "Set a route policy name.";
                  leaf route-policy {
                    type leafref {
                      path "/ncs:devices/ncs:device/ncs:config/rtp:routing-policy/rtp:policy-definitions/rtp:policy-definition/rtp:name" {
                        tailf:xpath-root 3;
                      }
                    }
                    description
                      "Set a route policy name.";
                  }
                }
              }
            }
          }
          container import-routes {
            description
              "List of import the routes learned from other routing protocols.";
            list import-route {
              key "protocol process-id";
              description
                "Configure import the routes learned from other routing protocols.";
              leaf protocol {
                type import-rt-protocol;
                description
                  "Routing protocol whose routes are imported.";
              }
              leaf process-id {
                type uint32 {
                  range "0..4294967295";
                }
                must "(../process-id=0 and (../protocol='direct' or ../protocol='static' or ../protocol='bgp' or ../protocol='unr' or ../protocol='opr')) or (../process-id>0 and (../protocol='ospf' or ../protocol='isis' or ../protocol='rip'))" {
                  tailf:xpath-root 3;
                }
                description
                  "Process ID of the routing protocol whose routes are imported. It needs to be set only when the protocol is RIP, OSPF, or ISIS.";
              }
              leaf cost {
                type uint32 {
                  range "0..16777214";
                }
                description
                  "Route cost.";
              }
              leaf tag {
                type uint32 {
                  range "0..4294967295";
                }
                description
                  "Route tag of an external LSA.";
              }
              leaf type {
                type external-route-type;
                description
                  "Metric type of an external LSA.";
              }
              leaf permit-ibgp {
                type boolean;
                must "../permit-ibgp='false' or ../protocol='bgp'" {
                  tailf:xpath-root 3;
                }
                default "false";
                description
                  "Enable/disable to import IBGP routes.";
              }
              choice policy-type {
                description
                  "Type of a filtering rule.";
                case route-policy-name {
                  description
                    "Name of a routing policy.";
                  leaf route-policy-name {
                    type leafref {
                      path "/ncs:devices/ncs:device/ncs:config/rtp:routing-policy/rtp:policy-definitions/rtp:policy-definition/rtp:name" {
                        tailf:xpath-root 3;
                      }
                    }
                    description
                      "Name of a routing policy.";
                  }
                }
              }
            }
          }
          container silent-interfaces {
            when "../silent-all-interface='false'" {
              tailf:xpath-root 3;
            }
            description
              "List of interface. To prevent the OSPF routing information from being received by routers in a network segment and forbid the local router to receive the routing update information that is advertised by other routers in the network segment, you can use the silent interface command to suppress the interface to receive or send the OSPF packets.";
            list silent-interface {
              key "if-name";
              description
                "Configure interface. To prevent the OSPF routing information from being received by routers in a network segment and forbid the local router to receive the routing update information that is advertised by other routers in the network segment, you can use the silent interface command to suppress the interface to receive or send the OSPF packets.";
              leaf if-name {
                type leafref {
                  path "/ncs:devices/ncs:device/ncs:config/ifm:ifm/ifm:interfaces/ifm:interface/ifm:name" {
                    tailf:xpath-root 3;
                  }
                }
                description
                  "Interface name.";
              }
            }
          }
          container undo-silent-interfaces {
            when "../silent-all-interface='true'" {
              tailf:xpath-root 3;
            }
            description
              "List of interface. Enables sending and receiving packet on this interface when true. This information is useful when sending and receiving packet is suppressed on all interface on process level and user want it to be enabled on certain interface.";
            list undo-silent-interface {
              key "if-name";
              description
                "Configure interface. Enables sending and receiving packet on this interface when true. This information is useful when sending and receiving packet is suppressed on all interface on process level and user want it to be enabled on certain interface.";
              leaf if-name {
                type leafref {
                  path "/ncs:devices/ncs:device/ncs:config/ifm:ifm/ifm:interfaces/ifm:interface/ifm:name" {
                    tailf:xpath-root 3;
                  }
                }
                description
                  "Interface name.";
              }
            }
          }
          container cost-bindings {
            description
              "List of cost-binding. Indicate cost of routing from indicated router source ID binding interface.";
            list cost-binding {
              key "router-id if-name";
              description
                "Configure cost-binding. Indicate cost of routing from indicated router source ID binding interface.";
              leaf router-id {
                type inet:ipv4-address-no-zone;
                description
                  "Source router ID.";
              }
              leaf if-name {
                type leafref {
                  path "/ncs:devices/ncs:device/ncs:config/ifm:ifm/ifm:interfaces/ifm:interface/ifm:name" {
                    tailf:xpath-root 3;
                  }
                }
                description
                  "Interface name.";
              }
            }
          }
          container areas {
            description
              "List of OSPF area.";
            list area {
              key "area-id";
              description
                "Configure OSPF area.";
              leaf area-id {
                type inet:ipv4-address-no-zone;
                description
                  "Area ID.";
              }
              leaf area-type {
                type area-type;
                default "normal";
                description
                  "Area type.";
              }
              leaf description {
                type string {
                  length "1..80";
                  pattern '([^?]*)';
                }
                description
                  "Description of an OSPF area.";
              }
              container networks {
                description
                  "List of the interface that runs OSPF and the area to which the interface belongs to.";
                list network {
                  key "ip-address mask";
                  description
                    "Configure the interface that runs OSPF and the area to which the interface belongs to.";
                  leaf ip-address {
                    type inet:ipv4-address-no-zone;
                    description
                      "Specifies the address of the network segment where the interface resides.";
                  }
                  leaf mask {
                    type inet:ipv4-address-no-zone;
                    description
                      "Specifies the wildcard mask of IP address.";
                  }
                  leaf description {
                    type string {
                      length "1..80";
                      pattern '([^?]*)';
                    }
                    description
                      "Specifies the description of the specified OSPF network segment.";
                  }
                }
              }
              container stub {
                when "../area-type='stub'" {
                  tailf:xpath-root 3;
                }
                description
                  "Configure stub area.";
                leaf backbone-peer-ignore {
                  type boolean;
                  default "false";
                  description
                    "Enable/disable ignore backbone peer for Stub area.";
                }
                leaf no-summary {
                  type boolean;
                  default "false";
                  description
                    "Enable/disable forbid an ABR to Send Summary LSAs to the Stub Area.";
                }
                leaf default-cost {
                  type int32 {
                    range "0..16777214";
                  }
                  default "1";
                  description
                    "Cost of the default Type3 routes that are sent by an OSPF process to a stub area or an NSSA area. The value is an integer ranging from 1 to 16777214. This parameter takes effect only when it is configured on the ABR connected to a stub area or an NSSA area. The default is 1.";
                }
              }
              container nssa {
                when "../area-type='nssa'" {
                  tailf:xpath-root 3;
                }
                description
                  "Configure nssa area.";
                leaf no-summary {
                  type boolean;
                  default "false";
                  description
                    "Enable/disable forbid an ABR to Send Summary LSAs to the NSSA Area.";
                }
                leaf translator-always {
                  type boolean;
                  default "false";
                  description
                    "Enable/disable the router to act as translator always for NSSA Area.";
                }
                leaf default-route-advertise {
                  type boolean;
                  default "false";
                  description
                    "Enable/disable originate Type 7 default into NSSA area.";
                }
                leaf backbone-peer-ignore {
                  when "../default-route-advertise='true'" {
                    tailf:xpath-root 3;
                  }
                  type boolean;
                  default "false";
                  description
                    "Enable/disable ignore backbone peer for Nssa area.";
                }
                leaf no-import-route {
                  type boolean;
                  default "false";
                  description
                    "Enable/disable redistribute type 7 LSA into this area.";
                }
                leaf set-n-bit {
                  type boolean;
                  default "false";
                  description
                    "Enable/disable setting of 'N' bit in the DD packet.";
                }
                leaf suppress-fa {
                  type boolean;
                  default "false";
                  description
                    "Enable/disable the forwarding address as 0 for all translated type 5 LSAs.";
                }
                leaf zero-address-forwarding {
                  type boolean;
                  default "false";
                  description
                    "Enable/disable allow zero forwarding address for redistributed type 7 LSA.";
                }
                leaf translator-interval {
                  type uint32 {
                    range "1..120";
                  }
                  default "40";
                  description
                    "Translator interval.";
                }
                leaf default-cost {
                  type int32 {
                    range "0..16777214";
                  }
                  default "1";
                  description
                    "Cost of the default Type3 routes that are sent by an OSPF process to a stub area or an NSSA area. This parameter takes effect only when it is configured on the ABR connected to a stub area or an NSSA area.";
                }
              }
              container ldp-sync {
                description
                  "Configure timer ldp sync.";
                leaf enable {
                  type boolean;
                  default "false";
                  description
                    "Enable/disable LDP and OSPF synchronization on area.";
                }
                choice hold-cost-max {
                  default "infinite";
                  description
                    "Set timer ldp sync.";
                  case timer {
                    description
                      "Set timer ldp sync.";
                    leaf timer {
                      type uint32 {
                        range "0..65535";
                      }
                      units "s";
                      description
                        "The interval for sending OSPF LSAs to advertise the maximum metric on the local device.";
                    }
                  }
                  case infinite {
                    description
                      "Always advertise the maximum cost.";
                    leaf infinite {
                      type boolean;
                      must "../infinite='true'" {
                        tailf:xpath-root 3;
                      }
                      default "true";
                      description
                        "Enable/disable always advertise the maximum cost.";
                    }
                  }
                }
              }
              container mpls-te {
                when "../../../../../../ni:name!='__dcn_vpn__'" {
                  tailf:xpath-root 3;
                }
                description
                  "Configure OSPF processes enabled with the TE capability.";
                leaf enable {
                  type boolean;
                  must "../../../../opaque='true' or ../enable='false'" {
                    tailf:xpath-root 3;
                  }
                  default "false";
                  description
                    "Enable/disable TE capability of the OSPF process in the specified area.";
                }
                leaf standard-complying {
                  type boolean;
                  must "../standard-complying='false' or ../enable='true'" {
                    tailf:xpath-root 3;
                  }
                  default "false";
                  description
                    "Enable/disable accept the LSAs in standard format only.";
                }
              }
              container authentication {
                must '(key-id and auth-text-md5) or (not(key-id) and not(auth-text-md5))' {
                  tailf:xpath-root 3;
                }
                description
                  "Configure authentication. The encryption algorithm MD5 has a low security, which may bring security risks. Using more secure authentication is recommended.";
                leaf mode {
                  type area-authen-mode;
                  default "none";
                  description
                    "Set authentication type.";
                }
                leaf auth-text-simple {
                  when "../mode='simple'" {
                    tailf:xpath-root 3;
                  }
                  type pub-type:password;
                  description
                    "Simple authentication key. The password is a string ranging from 1 to 8 characters for a unencrypted password and 24 to 128 characters for a encrypted password.";
                }
                leaf key-id {
                  when "../mode='hmac-md5' or ../mode='hmac-sha256' or ../mode='md5'" {
                    tailf:xpath-root 3;
                  }
                  type uint32 {
                    range "1..255";
                  }
                  description
                    "Authentication identifier.";
                }
                leaf auth-text-md5 {
                  when "../mode='hmac-md5' or ../mode='hmac-sha256' or ../mode='md5'" {
                    tailf:xpath-root 3;
                  }
                  type pub-type:password-extend;
                  description
                    "Encrypted authentication password.";
                }
                leaf key-chain-name {
                  when "../mode='keychain'" {
                    tailf:xpath-root 3;
                  }
                  type string {
                    length "1..47";
                    pattern '[^A-Z]+';
                  }
                  ext:case-sensitivity "lower-only";
                  mandatory true;
                  description
                    "Keychain name.";
                }
              }
              container abr-summary-prefixs {
                description
                  "List of ABR route aggregation method.";
                list abr-summary-prefix {
                  key "prefix network-mask";
                  description
                    "Configure ABR route aggregation method.";
                  leaf prefix {
                    type inet:ipv4-address-no-zone;
                    description
                      "Specifies the IP address in dotted decimal notation.";
                  }
                  leaf network-mask {
                    type inet:ipv4-address-no-zone;
                    description
                      "Specifies the mask of the IP address. The mask address is in dotted decimal notation.";
                  }
                  choice cost {
                    description
                      "Set the cost.";
                    case cost-value {
                      description
                        "Specifies the cost of the aggregated route. By default, the maximal cost in that of all the routes which are aggregated serves as the cost of the aggregated route.";
                      leaf cost-value {
                        type uint32 {
                          range "0..16777214";
                        }
                        description
                          "Specifies the cost of the aggregated route. By default, the maximal cost in that of all the routes which are aggregated serves as the cost of the aggregated route.";
                      }
                    }
                    case cost-inherit-min {
                      description
                        "Indicates if minimum cost should be inherited. By default, maximum cost is inherited.";
                      leaf cost-inherit-min {
                        when "../../../../../../../../ni:name!='_public_'" {
                          tailf:xpath-root 3;
                        }
                        type empty;
                        description
                          "Indicates if minimum cost should be inherited. By default, maximum cost is inherited.";
                      }
                    }
                  }
                  leaf hold-max-cost {
                    type uint16 {
                      range "10..1800";
                    }
                    description
                      "Hold max cost duration.";
                  }
                  leaf advertise {
                    type boolean;
                    default "true";
                    description
                      "Enable/disable the aggregated route is advertised.";
                  }
                  leaf generate-null-zero {
                    when "../advertise='true'" {
                      tailf:xpath-root 3;
                    }
                    type boolean;
                    default "false";
                    description
                      "Enable/disable generate black hole route.";
                  }
                }
              }
              container vlink-peers {
                when "../area-type='normal'" {
                  tailf:xpath-root 3;
                }
                description
                  "List of virtual link and its parameters.";
                list vlink-peer {
                  key "router-id";
                  description
                    "Configure virtual link and its parameters.";
                  leaf router-id {
                    type inet:ipv4-address-no-zone;
                    description
                      "Neighbor Router ID.";
                  }
                  leaf retransmit-interval {
                    type uint32 {
                      range "1..3600";
                    }
                    default "5";
                    description
                      "Interval for retransmitting LSAs.";
                  }
                  leaf smart-discover {
                    type boolean;
                    default "false";
                    description
                      "Enable/disable smart discover feature.";
                  }
                  container timer {
                    must 'hello-interval<dead-interval' {
                      tailf:xpath-root 3;
                    }
                    description
                      "Configure timer.";
                    leaf hello-interval {
                      type uint32 {
                        range "1..65535";
                      }
                      default "10";
                      description
                        "Time between Hello packets.";
                    }
                    leaf dead-interval {
                      type uint32 {
                        range "1..235926000";
                      }
                      default "40";
                      description
                        "Interval after which a neighbor is declared dead.";
                    }
                    leaf trans-delay-interval {
                      type uint32 {
                        range "1..3600";
                      }
                      default "1";
                      description
                        "Delay for transmitting LSAs.";
                    }
                  }
                  container authentication {
                    description
                      "Configure authentication. The encryption algorithm MD5 has a low security, which may bring security risks. Using more secure authentication is recommended.";
                    leaf mode {
                      type intf-authen-mode;
                      default "none";
                      description
                        "Set authentication type: Simple authentication type, Md5/HMAC MD5/HMAC SHA256 authentication type.";
                    }
                    leaf auth-text-simple {
                      when "../mode='simple'" {
                        tailf:xpath-root 3;
                      }
                      type pub-type:password;
                      description
                        "Simple authentication key. The password is a string ranging from 1 to 8 characters for a unencrypted password and 24 to 128 characters for a encrypted password.";
                    }
                    leaf key-id {
                      when "../mode='hmac-sha256' or ../mode='md5' or ../mode='hmac-md5'" {
                        tailf:xpath-root 3;
                      }
                      type uint32 {
                        range "1..255";
                      }
                      must '../key-id and ../auth-text-md5' {
                        tailf:xpath-root 3;
                      }
                      description
                        "Authentication identifier.";
                    }
                    leaf auth-text-md5 {
                      when "../mode='hmac-sha256' or ../mode='md5' or ../mode='hmac-md5'" {
                        tailf:xpath-root 3;
                      }
                      type pub-type:password-extend {
                        length "1..432";
                      }
                      must '../key-id and ../auth-text-md5' {
                        tailf:xpath-root 3;
                      }
                      description
                        "MD5/HMAC MD5/HMAC SHA256 authentication password.";
                    }
                    leaf key-chain-name {
                      when "../mode='keychain'" {
                        tailf:xpath-root 3;
                      }
                      type string {
                        length "1..47";
                        pattern '[^A-Z]+';
                      }
                      ext:case-sensitivity "lower-only";
                      mandatory true;
                      description
                        "Keychain name.";
                    }
                  }
                }
              }
              container sham-links {
                when "../../../../../../ni:name!='_public_'" {
                  tailf:xpath-root 3;
                }
                description
                  "List of sham link and its parameters.";
                list sham-link {
                  key "src-addr dest-addr";
                  description
                    "Configure sham link and its parameters.";
                  leaf src-addr {
                    type inet:ipv4-address-no-zone;
                    description
                      "Source address.";
                  }
                  leaf dest-addr {
                    type inet:ipv4-address-no-zone;
                    must '../dest-addr!=../src-addr' {
                      tailf:xpath-root 3;
                    }
                    description
                      "Destination address.";
                  }
                  leaf cost {
                    type uint32 {
                      range "1..65535";
                    }
                    default "1";
                    description
                      "Cost.";
                  }
                  leaf retransmit-interval {
                    type uint32 {
                      range "1..3600";
                    }
                    default "5";
                    description
                      "Interval for retransmitting LSAs.";
                  }
                  leaf smart-discover {
                    type boolean;
                    default "false";
                    description
                      "Enable/disable smart discover feature.";
                  }
                  container timer {
                    must 'hello-interval<dead-interval' {
                      tailf:xpath-root 3;
                    }
                    description
                      "Configure timer.";
                    leaf hello-interval {
                      type uint32 {
                        range "1..65535";
                      }
                      default "10";
                      description
                        "Time between Hello packets.";
                    }
                    leaf dead-interval {
                      type uint32 {
                        range "1..235926000";
                      }
                      default "40";
                      description
                        "Interval after which a neighbor is declared dead.";
                    }
                    leaf trans-delay-interval {
                      type uint32 {
                        range "1..3600";
                      }
                      default "1";
                      description
                        "Delay for transmitting LSAs.";
                    }
                  }
                  container authentication {
                    description
                      "Configure authentication. The encryption algorithm MD5 has a low security, which may bring security risks. Using more secure authentication is recommended.";
                    leaf mode {
                      type intf-authen-mode;
                      default "none";
                      description
                        "Set authentication type: Simple authentication type, Md5/HMAC MD5/HMAC SHA256 authentication type.";
                    }
                    leaf auth-text-simple {
                      when "../mode='simple'" {
                        tailf:xpath-root 3;
                      }
                      type pub-type:password;
                      description
                        "Simple authentication key. The password is a string ranging from 1 to 8 characters for a unencrypted password and 24 to 128 characters for a encrypted password.";
                    }
                    leaf key-id {
                      when "../mode='hmac-sha256' or ../mode='md5' or ../mode='hmac-md5'" {
                        tailf:xpath-root 3;
                      }
                      type uint32 {
                        range "1..255";
                      }
                      must '../key-id and ../auth-text-md5' {
                        tailf:xpath-root 3;
                      }
                      description
                        "Authentication identifier.";
                    }
                    leaf auth-text-md5 {
                      when "../mode='hmac-sha256' or ../mode='md5' or ../mode='hmac-md5'" {
                        tailf:xpath-root 3;
                      }
                      type pub-type:password-extend {
                        length "1..432";
                      }
                      must '../key-id and ../auth-text-md5' {
                        tailf:xpath-root 3;
                      }
                      description
                        "MD5/HMAC MD5/HMAC SHA256 authentication password.";
                    }
                    leaf key-chain-name {
                      when "../mode='keychain'" {
                        tailf:xpath-root 3;
                      }
                      type string {
                        length "1..47";
                        pattern '[^A-Z]+';
                      }
                      ext:case-sensitivity "lower-only";
                      mandatory true;
                      description
                        "Keychain name.";
                    }
                  }
                }
              }
              container filters {
                description
                  "List of ABR to filter outgoing or incoming summary LSAs of the local area.";
                list filter {
                  key "mode";
                  description
                    "Configure ABR to filter outgoing or incoming summary LSAs of the local area.";
                  leaf mode {
                    type area-filter-mode;
                    description
                      "Using the filter export command, you can configure an ABR to filter outgoing summary LSAs of the local area. Using the filter import command, you can configure an ABR to filter incoming summary LSAs of the local area.";
                  }
                  uses policy-type;
                  leaf include-abr-summary {
                    when "../mode='filter-import'" {
                      tailf:xpath-root 3;
                    }
                    type boolean;
                    default "false";
                    description
                      "Enable/disable include abr summary flag.";
                  }
                }
              }
              container interfaces {
                description
                  "List of the interface enabled with OSPF.";
                list interface {
                  key "name";
                  description
                    "Configure the interface enabled with OSPF.";
                  leaf name {
                    type leafref {
                      path "/ncs:devices/ncs:device/ncs:config/ifm:ifm/ifm:interfaces/ifm:interface/ifm:name" {
                        tailf:xpath-root 3;
                      }
                    }
                    must '../../../../../../../../ni:name=/ifm:ifm/ifm:interfaces/ifm:interface[ifm:name=current()]/ifm:vrf-name' {
                      tailf:xpath-root 3;
                    }
                    description
                      "Interface name. OSPF does not support the configuration of a NULL/LMP/MTUNNEL/RPR/STACKPORT/SIP/ATMBUNDLE/IMAGROUP/Remote-Ap/VBridge interface types.";
                  }
                  leaf network-type {
                    type network-type;
                    ext:dynamic-default;
                    description
                      "Network type of an OSPF interface. By default, the network type of an interface is determined by the physical interface.
                       In the same network segment, if only two routers run OSPF, you can change the network type of an interface to P2P.";
                  }
                  leaf peer-ip-ignore {
                    type peer-ip-ignore-type;
                    must "../peer-ip-ignore='enable' and ../network-type='p2p' or ../peer-ip-ignore='disable'" {
                      tailf:xpath-root 3;
                    }
                    default "disable";
                    description
                      "Ignores the subnet match check in multi access interface when network type P2P is configured along with this option.";
                  }
                  leaf transmit-delay {
                    type int32 {
                      range "1..500";
                    }
                    default "1";
                    description
                      "Delay for transmitting LSAs on an interface.";
                  }
                  leaf mtu-enable {
                    type boolean;
                    default "false";
                    description
                      "Enable/disable MTU filled in a DD packet when the packet is sent. The default MTU in the DD packet is 0. Using the command, you can manually configure the interface to fill in the MTU field (actual MTU of the interface) when the interface sends DD packets.
                       After a virtual connection is established through the virtual template or tunnel, different vendors may use different MTUs as default settings. To ensure consistency, the MTU is set to 0 by default when the interface sends DD packets. Thus, the ospf mtu-enable command usually does not need to be configured.
                       OSPF does not support the preceding configuration on a null interface.";
                  }
                  leaf dr-priority {
                    type int32 {
                      range "0..255";
                    }
                    default "1";
                    description
                      "Priority of the interface that participates in the DR and BDR election. The greater the value is, the higher the priority is. The router whose priority is 0 cannot be elected as a DR or a BDR.";
                  }
                  leaf cost {
                    type uint32 {
                      range "1..65535";
                    }
                    description
                      "To set the cost of an interface. The default value is 1. But the default of Loopback is 0.";
                  }
                  leaf smart-discover {
                    type boolean;
                    default "false";
                    description
                      "Enable/disable smart discover on an interface. When the neighbor status of a router or a DR or BDR on the multi address network of the broadcast or NBMA type changes, the router can send hello packets to the neighbor actively rather than wait for the expiration of the hello timer.";
                  }
                  leaf p2mp-mask-ignore {
                    type boolean;
                    default "false";
                    description
                      "Enable/disable to ignore the check of network masks on a P2MP network. On a P2MP network, when the lengths of device masks are inconsistent, the check of network masks in hello packets can be ignored through this command. In this case, the OSPF neighbor relationship can be normally established.";
                  }
                  leaf ldp-sync-block {
                    type boolean;
                    must "../ldp-sync-block='false' or ../ldp-sync-enable='false'" {
                      tailf:xpath-root 3;
                    }
                    default "false";
                    description
                      "Enable/disable LDP sync on this interface.";
                  }
                  leaf ldp-sync-enable {
                    type boolean;
                    must "../ldp-sync-enable='false' or ../ldp-sync-block='false'" {
                      tailf:xpath-root 3;
                    }
                    default "false";
                    description
                      "Enable/disable LDP and OSPF synchronization on an interface.";
                  }
                  leaf link-cost {
                    type uint32 {
                      range "1..65535";
                    }
                    description
                      "Link cost to be incremented when link quality is low. The default of Loopback is 0,others is 1.";
                  }
                  leaf suppress-reachability {
                    type suppr-reach;
                    default "not-configured";
                    description
                      "Suppress its own prefixes and ignore the suppressed prefixes.";
                  }
                  leaf mpls-ldp-auto-flag {
                    type if-auto-cfg-state;
                    default "none";
                    description
                      "Block MPLS LDP auto configuration on the interface.";
                  }
                  leaf dcn-opq-blk-enable {
                    type boolean;
                    default "false";
                    description
                      "Enable/disable filter type-10 dcn opaque LSAs.";
                  }
                  leaf peer-hold-max-timer {
                    type uint32 {
                      range "100..1000000";
                    }
                    units "ms";
                    description
                      "Config peer hold max cost interval.";
                  }
                  leaf fallback-cost {
                    when "/ifm:ifm/ifm:interfaces/ifm:interface[ifm:name=current()/../name]/ifm:type='Eth-Trunk'" {
                      tailf:xpath-root 3;
                    }
                    type uint32 {
                      range "1..65535";
                    }
                    description
                      "Fallback cost.";
                  }
                  leaf fallback-bw {
                    when '../fallback-cost' {
                      tailf:xpath-root 3;
                    }
                    type uint32 {
                      range "1..4294967295";
                    }
                    units "Mbit/s";
                    mandatory true;
                    description
                      "Fallback bandwidth threshold.";
                  }
                  leaf source-sub-ip-address {
                    type inet:ipv4-address-no-zone;
                    description
                      "Source address indicating a subordinate IP address.";
                  }
                  container frr {
                    description
                      "Configure FRR.";
                    leaf frr-disable {
                      type boolean;
                      default "false";
                      description
                        "Enable/disable not use this interface for FRR calculation.";
                    }
                    leaf rlfa-disable {
                      type boolean;
                      default "false";
                      description
                        "Enable/disable remote LFA of the Interface.";
                    }
                    container ti-lfa {
                      description
                        "Configure topology independent loop free alternate (TILFA) computation using segment routing.";
                      leaf disable {
                        type boolean;
                        default "false";
                        description
                          "Enable/disable topology independent LFA on the interface except Loopback.";
                      }
                    }
                  }
                  container timer {
                    description
                      "Configure timer.";
                    leaf hello-interval {
                      type int32 {
                        range "1..65535";
                      }
                      ext:dynamic-default {
                        ext:default-value "10" {
                          when "../../network-type = 'p2p' or ../../network-type = 'broadcast'" {
                            tailf:xpath-root 3;
                          }
                          description
                            "The default value is 10 when network-type is p2p or broadcast.";
                        }
                        ext:default-value "30" {
                          when "../../network-type = 'p2mp' or ../../network-type = 'nbma'" {
                            tailf:xpath-root 3;
                          }
                          description
                            "The default value is 30 when network-type is p2mp or nbma.";
                        }
                      }
                      description
                        "Interval for sending hello packets on an interface.";
                    }
                    leaf hello-conser {
                      type boolean;
                      default "false";
                      description
                        "Enable/disable the compensation mechanism of controling the deadtimer to enable.";
                    }
                    leaf dead-interval {
                      type int32 {
                        range "1..235926000";
                      }
                      must '../hello-interval<../dead-interval' {
                        tailf:xpath-root 3;
                      }
                      ext:dynamic-default {
                        ext:default-value "4*(../hello-interval)" {
                          description
                            "The default value of dead interval is 4 times that of hello interval.";
                        }
                      }
                      description
                        "Dead interval of an OSPF neighbor.";
                    }
                    leaf wait-interval {
                      type uint32 {
                        range "1..235926000";
                      }
                      ext:dynamic-default {
                        ext:default-value "../dead-interval" {
                          description
                            "The default value of wait interval is equal to dead interval.";
                        }
                      }
                      description
                        "Wait time.";
                    }
                    leaf poll-interval {
                      type int32 {
                        range "1..3600";
                      }
                      default "120";
                      description
                        "Poll interval for sending hello packets. On the NBMA network, after the neighbor is invalid, the router sends hello packets periodically according to the interval set through the ospf timer poll command. The poll interval should be at least four times of the interval for sending hello packets.";
                    }
                    leaf retransmit-interval {
                      type int32 {
                        range "1..3600";
                      }
                      default "5";
                      description
                        "Interval for retransmitting LSAs on an interface.";
                    }
                  }
                  container ldp-sync {
                    description
                      "Configure timer ldp sync.";
                    leaf hold-down-timer {
                      type uint16 {
                        range "0..65535";
                      }
                      units "s";
                      default "10";
                      description
                        "Hold down interval.";
                    }
                    choice hold-cost-max {
                      description
                        "Set timer ldp sync.";
                      case timer {
                        description
                          "Set max cost interval.";
                        leaf timer {
                          type uint16 {
                            range "0..65535";
                          }
                          units "s";
                          description
                            "Max cost interval range.";
                        }
                      }
                      case infinite {
                        description
                          "Always advertise the maximum cost.";
                        leaf infinite {
                          type empty;
                          description
                            "Always advertise the maximum cost.";
                        }
                      }
                    }
                  }
                  container bfd {
                    description
                      "Configure BFD.";
                    leaf enable {
                      type boolean;
                      must "../enable='false' or ../block='false'" {
                        tailf:xpath-root 3;
                      }
                      default "false";
                      description
                        "Enable/disable BFD.";
                    }
                    leaf block {
                      type boolean;
                      must "../block='false' or ../enable='false'" {
                        tailf:xpath-root 3;
                      }
                      default "false";
                      description
                        "Enable/disable to prevent the dynamic establishment of a BFD session on an interface.";
                    }
                    leaf detect-multiplier {
                      type uint32 {
                        range "3..50";
                      }
                      default "3";
                      description
                        "Local detection multiplier.";
                    }
                    leaf min-tx {
                      type uint32 {
                        range "3..20000";
                      }
                      units "ms";
                      description
                        "Minimum interval for sending BFD packets to the peer end. The ranges and the default value is determined by the PAF.";
                    }
                    leaf min-rx {
                      type uint32 {
                        range "3..20000";
                      }
                      units "ms";
                      description
                        "Minimum interval for receiving BFD packets from the peer end. The ranges and the default value is determined by the PAF.";
                    }
                    leaf frr-binding {
                      type boolean;
                      default "false";
                      description
                        "Enable/disable bind FRR with BFD.";
                    }
                    choice incr-cost {
                      description
                        "Interface BFD sync cost.";
                      case incr-cost-block {
                        description
                          "Interface BFD sync cost block.";
                        leaf incr-cost-block {
                          type empty;
                          description
                            "Interface BFD sync cost block.";
                        }
                      }
                      case incr-cost-value {
                        description
                          "Interface BFD sync cost.";
                        leaf incr-cost-value {
                          type uint32 {
                            range "1..65535";
                          }
                          description
                            "Interface BFD sync cost.";
                        }
                      }
                    }
                    leaf per-link-flag {
                      type boolean;
                      must "../one-arm-echo-flag=../per-link-flag and (../per-link-flag='false' or ../enable='true')" {
                        tailf:xpath-root 3;
                      }
                      default "false";
                      description
                        "Enable/disable BFD session per link, support only VLANif interface.";
                    }
                    leaf one-arm-echo-flag {
                      type boolean;
                      must "../one-arm-echo-flag=../per-link-flag and (../one-arm-echo-flag='false' or /ifm:ifm/ifm:interfaces/ifm:interface[ifm:name=current()/../../name]/ifm:type='Vlanif')" {
                        tailf:xpath-root 3;
                      }
                      default "false";
                      description
                        "Enable/disable echo detection mode, support only VLANif interface.";
                    }
                  }
                  container authentication {
                    description
                      "Configure authentication. The encryption algorithm MD5 has a low security, which may bring security risks. Using more secure authentication is recommended.";
                    leaf mode {
                      type intf-authen-mode;
                      default "none";
                      description
                        "Set Authentication type.";
                    }
                    leaf auth-text-simple {
                      when "../mode='simple'" {
                        tailf:xpath-root 3;
                      }
                      type pub-type:password;
                      description
                        "Simple authentication key. The password is a string ranging from 1 to 8 characters for a unencrypted password and 24 to 128 characters for a encrypted password.";
                    }
                    leaf key-id {
                      when "../mode='hmac-md5' or ../mode='hmac-sha256' or ../mode='md5'" {
                        tailf:xpath-root 3;
                      }
                      type uint32 {
                        range "1..255";
                      }
                      must '../key-id and ../auth-text-md5' {
                        tailf:xpath-root 3;
                      }
                      description
                        "Authentication identifier.";
                    }
                    leaf auth-text-md5 {
                      when "../mode='hmac-md5' or ../mode='hmac-sha256' or ../mode='md5'" {
                        tailf:xpath-root 3;
                      }
                      type pub-type:password-extend;
                      must '../key-id and ../auth-text-md5' {
                        tailf:xpath-root 3;
                      }
                      description
                        "Encrypted authentication password.";
                    }
                    leaf key-chain-name {
                      when "../mode='keychain'" {
                        tailf:xpath-root 3;
                      }
                      type string {
                        length "1..47";
                        pattern '[^A-Z]+';
                      }
                      ext:case-sensitivity "lower-only";
                      mandatory true;
                      description
                        "Keychain name.";
                    }
                  }
                  container filter-lsa-out {
                    description
                      "Configure filter lsa out.";
                    choice type {
                      description
                        "Set filter lsa out type.";
                      case total {
                        description
                          "Filter total types of LSAs.";
                        leaf all-flag {
                          type empty;
                          description
                            "Filter all types of LSAs.";
                        }
                      }
                      case other {
                        description
                          "Filter other types of LSAs.";
                        leaf sum-flag {
                          type empty;
                          description
                            "Filter type3 summary LSAs.";
                        }
                        choice sum-filter {
                          description
                            "Type of a filtering rule.";
                          case acl {
                            description
                              "Basic ACL name or ACL number.";
                            leaf sum-name {
                              when '../sum-flag' {
                                tailf:xpath-root 3;
                              }
                              type leafref {
                                path "/ncs:devices/ncs:device/ncs:config/acl:acl/acl:groups/acl:group/acl:identity" {
                                  tailf:xpath-root 3;
                                }
                              }
                              must "/acl:acl/acl:groups/acl:group[acl:identity=current()]/acl:type='basic'" {
                                tailf:xpath-root 3;
                              }
                              description
                                "Basic ACL name or ACL number.";
                            }
                          }
                        }
                        leaf ase-flag {
                          type empty;
                          description
                            "Filter type5 ASE LSAs.";
                        }
                        choice ase-filter {
                          description
                            "Type of a filtering rule.";
                          case acl {
                            description
                              "Basic ACL name or ACL number.";
                            leaf ase-name {
                              when '../ase-flag' {
                                tailf:xpath-root 3;
                              }
                              type leafref {
                                path "/ncs:devices/ncs:device/ncs:config/acl:acl/acl:groups/acl:group/acl:identity" {
                                  tailf:xpath-root 3;
                                }
                              }
                              must "/acl:acl/acl:groups/acl:group[acl:identity=current()]/acl:type='basic'" {
                                tailf:xpath-root 3;
                              }
                              description
                                "Basic ACL name or ACL number.";
                            }
                          }
                        }
                        leaf nssa-flag {
                          type empty;
                          description
                            "Filter type7 NSSA LSAs.";
                        }
                        choice nssa-filter {
                          description
                            "Type of a filtering rule.";
                          case acl {
                            description
                              "Basic ACL name or ACL number.";
                            leaf nssa-name {
                              when '../nssa-flag' {
                                tailf:xpath-root 3;
                              }
                              type leafref {
                                path "/ncs:devices/ncs:device/ncs:config/acl:acl/acl:groups/acl:group/acl:identity" {
                                  tailf:xpath-root 3;
                                }
                              }
                              must "/acl:acl/acl:groups/acl:group[acl:identity=current()]/acl:type='basic'" {
                                tailf:xpath-root 3;
                              }
                              description
                                "Basic ACL name or ACL number.";
                            }
                          }
                        }
                      }
                    }
                  }
                  container suppress-flapping {
                    description
                      "Configure flapping suppression.";
                    container peer {
                      must 'resume-interval>detect-interval' {
                        tailf:xpath-root 3;
                      }
                      description
                        "Configure flapping suppression peer. Not support Loopback.";
                      leaf enable {
                        type boolean;
                        default "true";
                        description
                          "Enable/disable interface peer flapping suppress.";
                      }
                      leaf detect-interval {
                        type uint32 {
                          range "1..300";
                        }
                        default "60";
                        description
                          "Detecting interval.";
                      }
                      leaf threshold {
                        type uint32 {
                          range "1..1000";
                        }
                        default "10";
                        description
                          "Threshold.";
                      }
                      leaf resume-interval {
                        type uint32 {
                          range "2..1000";
                        }
                        default "120";
                        description
                          "Resume interval.";
                      }
                      leaf hold-down-interval {
                        type uint32 {
                          range "1..86400";
                        }
                        description
                          "Hold down interval.";
                      }
                      leaf hold-max-cost {
                        type boolean;
                        default "true";
                        description
                          "Enable/disable hold max cost.";
                      }
                    }
                  }
                  container flush-source-trace {
                    description
                      "Configure OSPF flush source trace function.";
                    leaf block {
                      type boolean;
                      default "false";
                      description
                        "Enable/disable OSPF flush source trace.";
                    }
                  }
                  container mpls-te-peers {
                    description
                      "List of OSPF passive peer.";
                    list mpls-te-peer {
                      key "id router-id intf-ip";
                      description
                        "Configure OSPF passive peer.";
                      leaf id {
                        type uint32 {
                          range "1..255";
                        }
                        description
                          "Neighbor ID.";
                      }
                      leaf router-id {
                        type inet:ipv4-address-no-zone;
                        description
                          "Configure OSPF passive peer router ID.";
                      }
                      leaf intf-ip {
                        type inet:ipv4-address-no-zone;
                        description
                          "Configure interface address of passive peer.";
                      }
                      container procs {
                        description
                          "List of OSPF passive peers area.";
                        list proc {
                          key "pid aid";
                          max-elements 1;
                          description
                            "Configure OSPF passive peers area.";
                          leaf pid {
                            type uint32 {
                              range "1..4294967295";
                            }
                            description
                              "Process ID.";
                          }
                          leaf aid {
                            type inet:ipv4-address-no-zone;
                            description
                              "Area ID.";
                          }
                          leaf cost {
                            type uint32 {
                              range "1..65535";
                            }
                            default "1";
                            description
                              "Configuration cost value.";
                          }
                        }
                      }
                    }
                  }
                  container multi-areas {
                    description
                      "List of the information about the multi-area interface enabled with OSPF.";
                    list multi-area {
                      key "area-id";
                      description
                        "Configure the interface enabled with OSPF.";
                      leaf area-id {
                        type leafref {
                          path "/ncs:devices/ncs:device/ncs:config/ni:network-instance/ni:instances/ni:instance/ospfv2:ospfv2/ospfv2:sites/ospfv2:site/ospfv2:areas/ospfv2:area/ospfv2:area-id" {
                            tailf:xpath-root 3;
                          }
                        }
                        must '../area-id!=../../../../../area-id' {
                          tailf:xpath-root 3;
                        }
                        description
                          "Multi area id.";
                      }
                      leaf transmit-delay {
                        type int32 {
                          range "1..500";
                        }
                        units "s";
                        default "1";
                        description
                          "Delay for transmitting LSAs on an interface.";
                      }
                      leaf mtu-enable {
                        type boolean;
                        default "false";
                        description
                          "Enable/disable MTU.Configure the interface to fill in the MTU field (actual MTU of the interface) when the interface sends DD packets.
                           After a virtual connection is established through the virtual template or tunnel, different vendors may use different MTUs as default settings. To ensure consistency, the MTU is set to 0 by default when the interface sends DD packets. Thus, the ospf mtu-enable command usually does not need to be configured. OSPF does not support the preceding configuration on a null interface.";
                      }
                      leaf cost {
                        type uint32 {
                          range "1..65535";
                        }
                        description
                          "To set the cost of an interface. The default value is 1. But the default of Loopback is 0.";
                      }
                      leaf smart-discover {
                        type boolean;
                        default "false";
                        description
                          "Enable/disable smart discover on an interface. When the neighbor status of a router or a DR or BDR on the multi-address network of the broadcast or NBMA type changes, the router can send Hello packets to the neighbor actively rather than wait for the expiration of the Hello timer.";
                      }
                      leaf ldp-sync-block {
                        type boolean;
                        must "../ldp-sync-block='false' or ../ldp-sync-enable='false'" {
                          tailf:xpath-root 3;
                        }
                        default "false";
                        description
                          "Enable/disable ldp sync on this interface.";
                      }
                      leaf ldp-sync-enable {
                        type boolean;
                        must "../ldp-sync-enable='false' or ../ldp-sync-block='false'" {
                          tailf:xpath-root 3;
                        }
                        default "false";
                        description
                          "Enable/disable LDP and OSPF synchronization on an interface.";
                      }
                      leaf fallback-cost {
                        when "/ifm:ifm/ifm:interfaces/ifm:interface[ifm:name=current()/../../../name]/ifm:type='Eth-Trunk'" {
                          tailf:xpath-root 3;
                        }
                        type uint16 {
                          range "1..65535";
                        }
                        description
                          "Fallback cost.";
                      }
                      leaf fallback-bw {
                        when '../fallback-cost' {
                          tailf:xpath-root 3;
                        }
                        type uint32 {
                          range "1..4294967295";
                        }
                        units "Mbit/s";
                        mandatory true;
                        description
                          "Fallback bandwidth threshold.";
                      }
                      container frr {
                        description
                          "Configure frr.";
                        leaf frr-disable {
                          type boolean;
                          default "false";
                          description
                            "Enable/disable use this interface for FRR calculation.";
                        }
                        leaf rlfa-disable {
                          type boolean;
                          default "false";
                          description
                            "Enable/disable remote LFA of the Interface.";
                        }
                        leaf ti-lfa-disable {
                          type boolean;
                          default "false";
                          description
                            "Enable/disable Topology Independent LFA on the interface except Loopback.";
                        }
                      }
                      container timer {
                        description
                          "Configure timer.";
                        leaf hello-interval {
                          type int32 {
                            range "1..65535";
                          }
                          units "s";
                          ext:dynamic-default {
                            ext:default-value "10" {
                              when "../../../../network-type = 'p2p' or ../../../../network-type = 'broadcast'" {
                                tailf:xpath-root 3;
                              }
                              description
                                "The default value is 10 when network-type is p2p or broadcast.";
                            }
                            ext:default-value "30" {
                              when "../../../../network-type = 'p2mp' or ../../../../network-type = 'nbma'" {
                                tailf:xpath-root 3;
                              }
                              description
                                "The default value is 30 when network-type is p2mp or nbma.";
                            }
                          }
                          description
                            "Interval for sending Hello packets on an interface. The default value of p2p and broadcast is 10.The default of p2mp and NBMA is 30.";
                        }
                        leaf dead-interval {
                          type int32 {
                            range "1..235926000";
                          }
                          units "s";
                          must '../hello-interval<../dead-interval' {
                            tailf:xpath-root 3;
                          }
                          ext:dynamic-default {
                            ext:default-value "4*(../hello-interval)" {
                              description
                                "The default value of dead interval is 4 times that of hello interval.";
                            }
                          }
                          description
                            "Dead interval of an OSPF neighbor. The default value of p2p and broadcast is 40.The default of p2mp and NBMA is 120.";
                        }
                        leaf retransmit-interval {
                          type int32 {
                            range "1..3600";
                          }
                          default "5";
                          description
                            "Interval for Retransmitting LSAs on an Interface.";
                        }
                      }
                      container ldp-sync {
                        description
                          "Configure timer ldp sync.";
                        leaf hold-down-timer {
                          type uint16 {
                            range "0..65535";
                          }
                          units "s";
                          default "10";
                          description
                            "Hold down interval range.";
                        }
                        choice hold-cost-max {
                          description
                            "Set timer ldp-sync.";
                          case timer {
                            description
                              "Set max cost interval.";
                            leaf timer {
                              type uint16 {
                                range "0..65535";
                              }
                              units "s";
                              description
                                "Max cost interval range.";
                            }
                          }
                          case infinite {
                            description
                              "Always advertise the maximum cost.";
                            leaf infinite {
                              type empty;
                              description
                                "Always advertise the maximum cost.";
                            }
                          }
                        }
                      }
                      container bfd {
                        description
                          "Configure BFD.";
                        leaf block {
                          type boolean;
                          default "false";
                          description
                            "Enable/disable prevent the dynamic establishment of a BFD session on an interface.";
                        }
                      }
                      container authentication {
                        must '(key-id and auth-text-md5) or (not(key-id) and not(auth-text-md5))' {
                          tailf:xpath-root 3;
                        }
                        description
                          "Configure authentication. The encryption algorithm MD5 has a low security, which may bring security risks. Using more secure authentication is recommended.";
                        leaf mode {
                          type intf-authen-mode;
                          default "none";
                          description
                            "Set Authentication type.";
                        }
                        leaf auth-text-simple {
                          when "../mode='simple'" {
                            tailf:xpath-root 3;
                          }
                          type pub-type:password;
                          description
                            "Simple authentication key. The password is a string ranging from 1 to 8 characters for a unencrypted password and 24 to 128 characters for a encrypted password.";
                        }
                        leaf key-id {
                          when "../mode='hmac-md5' or ../mode='hmac-sha256' or ../mode='md5'" {
                            tailf:xpath-root 3;
                          }
                          type uint32 {
                            range "1..255";
                          }
                          description
                            "Authentication identifier.";
                        }
                        leaf auth-text-md5 {
                          when "../mode='hmac-md5' or ../mode='hmac-sha256' or ../mode='md5'" {
                            tailf:xpath-root 3;
                          }
                          type pub-type:password-extend;
                          description
                            "MD5/HMAC-MD5/HMAC-SHA256 Authentication Password.";
                        }
                        leaf key-chain-name {
                          when "../mode='keychain'" {
                            tailf:xpath-root 3;
                          }
                          type string {
                            length "1..47";
                            pattern '[^A-Z]+';
                          }
                          ext:case-sensitivity "lower-only";
                          mandatory true;
                          description
                            "Keychain Name.";
                        }
                      }
                      container filter-lsa-out {
                        presence "Enable multi area filter lsa out.";
                        description
                          "Configure filter-lsa-out.";
                        choice type {
                          mandatory true;
                          description
                            "Set filter-lsa-out type.";
                          case total {
                            description
                              "Filter total types of LSAs.";
                            leaf all-flag {
                              type empty;
                              description
                                "Filter all types of LSAs.";
                            }
                          }
                          case other {
                            description
                              "Filter other types of LSAs.";
                            leaf sum-flag {
                              type empty;
                              description
                                "Filter type-3 Summary LSAs.";
                            }
                            choice sum-filter {
                              description
                                "Type of a filtering rule.";
                              case acl {
                                description
                                  "ACL-Name or ACL-Number.";
                                leaf sum-name {
                                  when '../sum-flag' {
                                    tailf:xpath-root 3;
                                  }
                                  type leafref {
                                    path "/ncs:devices/ncs:device/ncs:config/acl:acl/acl:groups/acl:group/acl:identity" {
                                      tailf:xpath-root 3;
                                    }
                                  }
                                  description
                                    "ACL-Name or ACL-Number.";
                                }
                              }
                            }
                            leaf ase-flag {
                              type empty;
                              description
                                "Filter type-5 ASE LSAs.";
                            }
                            choice ase-filter {
                              description
                                "Type of a filtering rule.";
                              case acl {
                                description
                                  "ACL-Name or ACL-Number.";
                                leaf ase-name {
                                  when '../ase-flag' {
                                    tailf:xpath-root 3;
                                  }
                                  type leafref {
                                    path "/ncs:devices/ncs:device/ncs:config/acl:acl/acl:groups/acl:group/acl:identity" {
                                      tailf:xpath-root 3;
                                    }
                                  }
                                  description
                                    "ACL-Name or ACL-Number.";
                                }
                              }
                            }
                            leaf nssa-flag {
                              type empty;
                              description
                                "Filter type-7 NSSA LSAs.";
                            }
                            choice nssa-filter {
                              description
                                "Type of a filtering rule.";
                              case acl {
                                description
                                  "ACL-Name or ACL-Number.";
                                leaf nssa-name {
                                  when '../nssa-flag' {
                                    tailf:xpath-root 3;
                                  }
                                  type leafref {
                                    path "/ncs:devices/ncs:device/ncs:config/acl:acl/acl:groups/acl:group/acl:identity" {
                                      tailf:xpath-root 3;
                                    }
                                  }
                                  description
                                    "ACL-Name or ACL-Number.";
                                }
                              }
                            }
                          }
                        }
                      }
                      container suppress-flapping {
                        description
                          "Configure flapping suppression.";
                        container peer {
                          must 'resume-interval>detect-interval' {
                            tailf:xpath-root 3;
                          }
                          description
                            "Configure flapping suppression peer. Not support Loopback.";
                          leaf enable {
                            type boolean;
                            default "true";
                            description
                              "Enable/disable interface peer flapping suppress.";
                          }
                          leaf detect-interval {
                            type uint32 {
                              range "1..300";
                            }
                            default "60";
                            description
                              "Detecting-interval.";
                          }
                          leaf threshold {
                            type uint32 {
                              range "1..1000";
                            }
                            default "10";
                            description
                              "Threshold.";
                          }
                          leaf resume-interval {
                            type uint32 {
                              range "2..1000";
                            }
                            default "120";
                            description
                              "Resume-interval.";
                          }
                          leaf hold-down-interval {
                            type uint32 {
                              range "1..86400";
                            }
                            description
                              "Hold-down-interval.";
                          }
                          leaf hold-max-cost {
                            type boolean;
                            default "true";
                            description
                              "Enable/disable hold max cost.";
                          }
                        }
                      }
                    }
                  }
                  // NCS drop config false container 'disp-data'
                  // NCS drop config false container 'nbr-statistics'
                  // NCS drop config false container 'error-data'
                }
              }
              // NCS drop config false container 'disp-data'
            }
          }
          // NCS drop config false container 'disp-data'
          // NCS drop config false container 'migp-routings'
          // NCS drop config false container 'abr-asbr-statistics'
          // NCS drop config false container 'nexthop-paras'
          // NCS drop config false container 'lsdb-statistics'
          // NCS drop config false container 'lsdb-briefs'
          // NCS drop config false container 'last-down-nbrs'
          // NCS drop config false container 'disp-graceful-restart'
          // NCS drop config false container 'error-process-data'
          // NCS drop config false container 'as-lsdb-brief'
          // NCS drop config false container neighbors
          // NCS drop config false container routings
          // NCS drop config false container 'vlink-nbr-statistics'
        }
      }
    }
  }
}
