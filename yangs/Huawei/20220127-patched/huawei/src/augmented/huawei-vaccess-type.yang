submodule huawei-vaccess-type {
  // Generated by yanger -t ncs
  tailf:mount-id "huawei-nc-1.0:huawei-nc-1.0";

  belongs-to huawei-vaccess {
    prefix vaccess;
  }

  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Virtual Access Type Information.";

  revision 2020-03-24 {
    description
      "Fixed some descriptions.";
    reference "Huawei private.";
  }
  revision 2019-06-05 {
    description
      "Initial revision.";
    reference "Huawei private.";
  }

  typedef ncs_template_vaccess-va-role {
    type string;
    description
      "The role of virtual access node.";
  }

  typedef ncs_rpc_notif_vaccess-va-role {
    type enumeration {
      enum "default" {
        value 0;
        description
          "The default value of virtual access node type.";
      }
      enum "master" {
        value 1;
        description
          "Virtual access node type is master.";
      }
      enum "ap" {
        value 2;
        description
          "Virtual access node type is ap.";
      }
    }
    description
      "The role of virtual access node.";
  }

  typedef live_ncs_vaccess-va-role {
    type enumeration {
      enum "default" {
        value 0;
        description
          "The default value of virtual access node type.";
      }
      enum "master" {
        value 1;
        description
          "Virtual access node type is master.";
      }
      enum "ap" {
        value 2;
        description
          "Virtual access node type is ap.";
      }
    }
    description
      "The role of virtual access node.";
  }

  typedef vaccess-va-role {
    type enumeration {
      enum "default" {
        value 0;
        description
          "The default value of virtual access node type.";
      }
      enum "master" {
        value 1;
        description
          "Virtual access node type is master.";
      }
      enum "ap" {
        value 2;
        description
          "Virtual access node type is ap.";
      }
    }
    description
      "The role of virtual access node.";
  }
}
