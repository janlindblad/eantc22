submodule huawei-dhcpv6-relay {
  // Generated by yanger -t ncs
  tailf:mount-id "huawei-nc-1.0:huawei-nc-1.0";

  yang-version 1;
  belongs-to huawei-dhcpv6 {
    prefix dhcpv6;
  }

  import ietf-inet-types {
    prefix inet;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "This module contains a collection of YANG definitions for managing DHCPv6 relay.";

  revision 2020-03-09 {
    description
      "Modify description.";
    reference "Huawei private.";
  }
  revision 2019-12-16 {
    description
      "Initial revision.";
    reference "Huawei private.";
  }

  grouping ncs_template_dhcpv6-relay-type {
    description
      "DHCPv6 relay.";
    container pd-route {
      description
        "Configure DHCPv6 PD route.";
      leaf export {
        type string;
        // NCS drop default statement
        description
          "Enable/disable DHCPv6 export PD route.";
      }
      leaf save-file-name {
        type string;
        description
          "Name of the file for saving PD routes. For example, the name can be in the format of cfcard:/dhcp/xxx.pd or home:/dhcp/xxx.pd, where xxx can be any characters.";
      }
    }
    container server-groups {
      description
        "List of DHCPv6 relay server groups.";
      list server-group {
        // NCS patched for predictable order
        ordered-by user;
        key "name";
        // NCS drop max-elements statement
        description
          "Configure a DHCPv6 relay server group.";
        leaf name {
          type string;
          description
            "DHCPv6 relay server group name.";
        }
        container server-addresses {
          description
            "List of DHCPv6 relay destination servers in a server group.";
          list server-address {
            // NCS patched for predictable order
            ordered-by user;
            key "server";
            // NCS drop max-elements statement
            description
              "Configure a DHCPv6 relay destination server in a server group.";
            leaf server {
              type string;
              description
                "DHCPv6 relay destination server address in a server group.";
            }
          }
        }
      }
    }
  }

  grouping ncs_rpc_notif_dhcpv6-relay-type {
    description
      "DHCPv6 relay.";
    container pd-route {
      description
        "Configure DHCPv6 PD route.";
      leaf export {
        type boolean;
        default "false";
        description
          "Enable/disable DHCPv6 export PD route.";
      }
      leaf save-file-name {
        type string {
          length "12..69";
          pattern '\S+:/dhcp/\S+\.pd';
        }
        description
          "Name of the file for saving PD routes. For example, the name can be in the format of cfcard:/dhcp/xxx.pd or home:/dhcp/xxx.pd, where xxx can be any characters.";
      }
    }
    container server-groups {
      description
        "List of DHCPv6 relay server groups.";
      list server-group {
        key "name";
        max-elements 10;
        description
          "Configure a DHCPv6 relay server group.";
        leaf name {
          type string {
            length "1..32";
          }
          description
            "DHCPv6 relay server group name.";
        }
        container server-addresses {
          description
            "List of DHCPv6 relay destination servers in a server group.";
          list server-address {
            key "server";
            max-elements 20;
            description
              "Configure a DHCPv6 relay destination server in a server group.";
            leaf server {
              type inet:ipv6-address-no-zone;
              description
                "DHCPv6 relay destination server address in a server group.";
            }
          }
        }
      }
    }
  }

  grouping live_ncs_dhcpv6-relay-type {
    description
      "DHCPv6 relay.";
    container pd-route {
      description
        "Configure DHCPv6 PD route.";
      leaf export {
        type boolean;
        // NCS drop default statement
        description
          "Enable/disable DHCPv6 export PD route.";
      }
      leaf save-file-name {
        type string {
          length "12..69";
          pattern '\S+:/dhcp/\S+\.pd';
        }
        description
          "Name of the file for saving PD routes. For example, the name can be in the format of cfcard:/dhcp/xxx.pd or home:/dhcp/xxx.pd, where xxx can be any characters.";
      }
    }
    container server-groups {
      description
        "List of DHCPv6 relay server groups.";
      list server-group {
        key "name";
        // NCS drop max-elements statement
        description
          "Configure a DHCPv6 relay server group.";
        leaf name {
          type string {
            length "1..32";
          }
          description
            "DHCPv6 relay server group name.";
        }
        container server-addresses {
          description
            "List of DHCPv6 relay destination servers in a server group.";
          list server-address {
            key "server";
            // NCS drop max-elements statement
            description
              "Configure a DHCPv6 relay destination server in a server group.";
            leaf server {
              type inet:ipv6-address-no-zone;
              description
                "DHCPv6 relay destination server address in a server group.";
            }
          }
        }
      }
    }
  }

  grouping dhcpv6-relay-type {
    description
      "DHCPv6 relay.";
    container pd-route {
      description
        "Configure DHCPv6 PD route.";
      leaf export {
        type boolean;
        default "false";
        description
          "Enable/disable DHCPv6 export PD route.";
      }
      leaf save-file-name {
        type string {
          length "12..69";
          pattern '\S+:/dhcp/\S+\.pd';
        }
        description
          "Name of the file for saving PD routes. For example, the name can be in the format of cfcard:/dhcp/xxx.pd or home:/dhcp/xxx.pd, where xxx can be any characters.";
      }
    }
    container server-groups {
      description
        "List of DHCPv6 relay server groups.";
      list server-group {
        key "name";
        max-elements 10;
        description
          "Configure a DHCPv6 relay server group.";
        leaf name {
          type string {
            length "1..32";
          }
          description
            "DHCPv6 relay server group name.";
        }
        container server-addresses {
          description
            "List of DHCPv6 relay destination servers in a server group.";
          list server-address {
            key "server";
            max-elements 20;
            description
              "Configure a DHCPv6 relay destination server in a server group.";
            leaf server {
              type inet:ipv6-address-no-zone;
              description
                "DHCPv6 relay destination server address in a server group.";
            }
          }
        }
      }
    }
  }
}
