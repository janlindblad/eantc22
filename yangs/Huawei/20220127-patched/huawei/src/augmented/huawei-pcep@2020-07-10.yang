module huawei-pcep {
  // Generated by yanger -t ncs
  tailf:mount-id "huawei-nc-1.0:huawei-nc-1.0";
  tailf:ncs-device-type "netconf";

  namespace "urn:huawei:yang:huawei-pcep";
  prefix pcep;

  import huawei-extension {
    prefix ext;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Path Computation Element Communication (PCEP).";

  revision 2020-07-10 {
    description
      "Initial revision.";
    reference "Huawei private.";
  }
  ext:task-name "pce";

  augment "/ncs:devices/ncs:device/ncs:config" {
    container pcep {
      tailf:ncs-device-type "netconf";
      tailf:display-when "not(../../ncs:module) or ../../ncs:module[ncs:name='huawei-pcep']";
      description
        "PCEP configuration.";
      container session-car {
        description
          "Configure session CAR.";
        container ipv4 {
          must 'cir<=pir' {
            tailf:xpath-root 3;
          }
          must 'cbs<=pbs' {
            tailf:xpath-root 3;
          }
          description
            "Configure PCEP IPv4 session CAR.";
          leaf enable {
            type boolean;
            default "true";
            description
              "Enable/disable PCEP IPv4 session CAR.";
          }
          leaf cir {
            type uint32 {
              range "1..1000000";
            }
            units "kbit/s";
            default "9";
            description
              "Session CAR CIR value.";
          }
          leaf cbs {
            type uint32 {
              range "1..9000000";
            }
            units "Byte";
            default "1758";
            description
              "Session CAR CBS value.";
          }
          leaf pir {
            type uint32 {
              range "1..1000000";
            }
            units "kbit/s";
            default "2400";
            description
              "Session CAR PIR value.";
          }
          leaf pbs {
            type uint32 {
              range "1..9000000";
            }
            units "Byte";
            default "450000";
            description
              "Session CAR PBS value.";
          }
        }
      }
    }
  }
  augment "/ncs:devices/ncs:device/ncs:live-status" {
    container pcep {
      tailf:ncs-device-type "netconf";
      tailf:display-when "not(../../ncs:module) or ../../ncs:module[ncs:name='huawei-pcep'] or (../../ncs:live-status-protocol[not(ncs:capability)]) or (../../ncs:live-status-protocol/ncs:capability/ncs:module[.='huawei-pcep'])";
      description
        "PCEP configuration.";
      container session-car {
        description
          "Configure session CAR.";
        container ipv4 {
          // NCS drop must statement
          // NCS drop must statement
          description
            "Configure PCEP IPv4 session CAR.";
          leaf enable {
            type boolean;
            // NCS drop default statement
            description
              "Enable/disable PCEP IPv4 session CAR.";
          }
          leaf cir {
            type uint32 {
              range "1..1000000";
            }
            units "kbit/s";
            // NCS drop default statement
            description
              "Session CAR CIR value.";
          }
          leaf cbs {
            type uint32 {
              range "1..9000000";
            }
            units "Byte";
            // NCS drop default statement
            description
              "Session CAR CBS value.";
          }
          leaf pir {
            type uint32 {
              range "1..1000000";
            }
            units "kbit/s";
            // NCS drop default statement
            description
              "Session CAR PIR value.";
          }
          leaf pbs {
            type uint32 {
              range "1..9000000";
            }
            units "Byte";
            // NCS drop default statement
            description
              "Session CAR PBS value.";
          }
        }
      }
    }
  }
  augment "/ncs:devices/ncs:template/ncs:ned-id/ncs:config" {
    container pcep {
      description
        "PCEP configuration.";
      container session-car {
        description
          "Configure session CAR.";
        container ipv4 {
          // NCS drop must statement
          // NCS drop must statement
          description
            "Configure PCEP IPv4 session CAR.";
          leaf enable {
            type string;
            // NCS drop default statement
            description
              "Enable/disable PCEP IPv4 session CAR.";
          }
          leaf cir {
            type string;
            units "kbit/s";
            // NCS drop default statement
            description
              "Session CAR CIR value.";
          }
          leaf cbs {
            type string;
            units "Byte";
            // NCS drop default statement
            description
              "Session CAR CBS value.";
          }
          leaf pir {
            type string;
            units "kbit/s";
            // NCS drop default statement
            description
              "Session CAR PIR value.";
          }
          leaf pbs {
            type string;
            units "Byte";
            // NCS drop default statement
            description
              "Session CAR PBS value.";
          }
        }
      }
    }
  }
}
