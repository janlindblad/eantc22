module huawei-ethernet-ext {
  // Generated by yanger -t ncs
  tailf:mount-id "huawei-nc-1.0:huawei-nc-1.0";
  tailf:ncs-device-type "netconf";

  namespace "urn:huawei:yang:huawei-ethernet-ext";
  prefix ethernet-ext;

  import huawei-ifm {
    prefix ifm;
  }
  import huawei-ethernet {
    prefix ethernet;
  }
  import huawei-extension {
    prefix ext;
  }
  import huawei-l2vpn {
    prefix l2vpn;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Ethernet Interface.";

  revision 2020-01-22 {
    description
      "The modifications in the schema file are synchronized to the YANG file.";
    reference "Huawei private.";
  }
  revision 2019-04-23 {
    description
      "Initial revision.";
    reference "Huawei private.";
  }
  ext:task-name "forwarding";

  augment "/ncs:devices/ncs:template/ncs:ned-id/ncs:config/ifm:ifm/ifm:interfaces/ifm:interface/ethernet:ethernet/ethernet:l3-sub-interface/ethernet:flow-type/ethernet:dot1q-termination/ethernet:dot1q-termination" {
    description
      "L3 dot1q-termination sub interface attribute.";
    container termination-mode-enable {
      description
        "Configure the dot1q-termination sub interface as single-mode after binding a vsi service in qualify mode.";
      leaf single-mode-enable {
        type string;
        // NCS drop must statement
        // NCS drop default statement
        description
          "Enable/disable single-mode configuration.";
      }
    }
  }
  augment "/ncs:devices/ncs:device/ncs:live-status/ifm:ifm/ifm:interfaces/ifm:interface/ethernet:ethernet/ethernet:l3-sub-interface/ethernet:flow-type/ethernet:dot1q-termination/ethernet:dot1q-termination" {
    description
      "L3 dot1q-termination sub interface attribute.";
    container termination-mode-enable {
      tailf:ncs-device-type "netconf";
      tailf:display-when "not(../../../../../../../../../../ncs:module) or ../../../../../../../../../../ncs:module[ncs:name='huawei-ethernet-ext'] or (../../../../../../../../../../ncs:live-status-protocol[not(ncs:capability)]) or (../../../../../../../../../../ncs:live-status-protocol/ncs:capability/ncs:module[.='huawei-ethernet-ext'])";
      description
        "Configure the dot1q-termination sub interface as single-mode after binding a vsi service in qualify mode.";
      leaf single-mode-enable {
        type boolean;
        // NCS drop must statement
        // NCS drop default statement
        description
          "Enable/disable single-mode configuration.";
      }
    }
  }
  augment "/ncs:devices/ncs:device/ncs:config/ifm:ifm/ifm:interfaces/ifm:interface/ethernet:ethernet/ethernet:l3-sub-interface/ethernet:flow-type/ethernet:dot1q-termination/ethernet:dot1q-termination" {
    description
      "L3 dot1q-termination sub interface attribute.";
    container termination-mode-enable {
      tailf:ncs-device-type "netconf";
      tailf:display-when "not(../../../../../../../../../../ncs:module) or ../../../../../../../../../../ncs:module[ncs:name='huawei-ethernet-ext']";
      description
        "Configure the dot1q-termination sub interface as single-mode after binding a vsi service in qualify mode.";
      leaf single-mode-enable {
        type boolean;
        must "../single-mode-enable='false' or (/l2vpn:l2vpn/l2vpn:instances/l2vpn:instance/l2vpn:vpls[l2vpn:mac-learn-style='qualify']/l2vpn:acs/l2vpn:ac[l2vpn:interface-name=current()/../../../../../ifm:name])" {
          tailf:xpath-root 3;
        }
        default "false";
        description
          "Enable/disable single-mode configuration.";
      }
    }
  }
  augment "/ncs:devices/ncs:template/ncs:ned-id/ncs:config/ifm:ifm/ifm:interfaces/ifm:interface/ethernet:ethernet/ethernet:l3-sub-interface/ethernet:flow-type/ethernet:qinq-stacking/ethernet:qinq-stacking" {
    description
      "L3 qinq-stacking sub interface attribute.";
    container stacking-mode-enable {
      description
        "Configure the qinq-stacking sub interface as single-mode when binding VSI service.";
      leaf single-mode-enable {
        type string;
        // NCS drop must statement
        // NCS drop default statement
        description
          "Enable/disable single-mode configuration.";
      }
    }
  }
  augment "/ncs:devices/ncs:device/ncs:live-status/ifm:ifm/ifm:interfaces/ifm:interface/ethernet:ethernet/ethernet:l3-sub-interface/ethernet:flow-type/ethernet:qinq-stacking/ethernet:qinq-stacking" {
    description
      "L3 qinq-stacking sub interface attribute.";
    container stacking-mode-enable {
      tailf:ncs-device-type "netconf";
      tailf:display-when "not(../../../../../../../../../../ncs:module) or ../../../../../../../../../../ncs:module[ncs:name='huawei-ethernet-ext'] or (../../../../../../../../../../ncs:live-status-protocol[not(ncs:capability)]) or (../../../../../../../../../../ncs:live-status-protocol/ncs:capability/ncs:module[.='huawei-ethernet-ext'])";
      description
        "Configure the qinq-stacking sub interface as single-mode when binding VSI service.";
      leaf single-mode-enable {
        type boolean;
        // NCS drop must statement
        // NCS drop default statement
        description
          "Enable/disable single-mode configuration.";
      }
    }
  }
  augment "/ncs:devices/ncs:device/ncs:config/ifm:ifm/ifm:interfaces/ifm:interface/ethernet:ethernet/ethernet:l3-sub-interface/ethernet:flow-type/ethernet:qinq-stacking/ethernet:qinq-stacking" {
    description
      "L3 qinq-stacking sub interface attribute.";
    container stacking-mode-enable {
      tailf:ncs-device-type "netconf";
      tailf:display-when "not(../../../../../../../../../../ncs:module) or ../../../../../../../../../../ncs:module[ncs:name='huawei-ethernet-ext']";
      description
        "Configure the qinq-stacking sub interface as single-mode when binding VSI service.";
      leaf single-mode-enable {
        type boolean;
        must "../single-mode-enable='false' or ../../ethernet:stacking-vid" {
          tailf:xpath-root 3;
        }
        default "false";
        description
          "Enable/disable single-mode configuration.";
      }
    }
  }
}
