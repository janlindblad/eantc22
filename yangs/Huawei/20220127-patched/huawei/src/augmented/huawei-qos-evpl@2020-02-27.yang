module huawei-qos-evpl {
  // Generated by yanger -t ncs
  tailf:mount-id "huawei-nc-1.0:huawei-nc-1.0";
  tailf:ncs-device-type "netconf";

  namespace "urn:huawei:yang:huawei-qos-evpl";
  prefix qos-evpl;

  import huawei-extension {
    prefix ext;
  }
  import huawei-evpl {
    prefix evpl;
  }
  import huawei-qos {
    prefix qos;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Quality of service for EVPL management.";

  revision 2020-02-27 {
    description
      "Add new nodes.";
    reference "Huawei private.";
  }
  revision 2020-01-20 {
    description
      "Add new nodes.";
    reference "Huawei private.";
  }
  revision 2019-12-02 {
    description
      "Initial revision.";
    reference "Huawei private.";
  }
  ext:task-name "qos";

  augment "/ncs:devices/ncs:template/ncs:ned-id/ncs:config/evpl:evpl/evpl:instances/evpl:instance" {
    description
      "Adds QoS configuration to the EVPL.";
    container vxlan-mode-phb {
      // NCS drop when statement
      description
        "Configure QoS PHB VXLAN mode.";
      leaf diffserv-domain-name {
        type string;
        description
          "Name of a diffserv-domain.";
      }
    }
  }
  augment "/ncs:devices/ncs:device/ncs:live-status/evpl:evpl/evpl:instances/evpl:instance" {
    description
      "Adds QoS configuration to the EVPL.";
    container vxlan-mode-phb {
      tailf:ncs-device-type "netconf";
      tailf:display-when "not(../../../../../ncs:module) or ../../../../../ncs:module[ncs:name='huawei-qos-evpl'] or (../../../../../ncs:live-status-protocol[not(ncs:capability)]) or (../../../../../ncs:live-status-protocol/ncs:capability/ncs:module[.='huawei-qos-evpl'])";
      // NCS drop when statement
      description
        "Configure QoS PHB VXLAN mode.";
      leaf diffserv-domain-name {
        type leafref {
          path "/ncs:devices/ncs:device/ncs:live-status/qos:qos/qos:classifier-template/qos:diffserv-domains/qos:diffserv-domain/qos:name" {
            tailf:xpath-root 3;
          }
        }
        description
          "Name of a diffserv-domain.";
      }
    }
  }
  augment "/ncs:devices/ncs:device/ncs:config/evpl:evpl/evpl:instances/evpl:instance" {
    description
      "Adds QoS configuration to the EVPL.";
    container vxlan-mode-phb {
      tailf:ncs-device-type "netconf";
      tailf:display-when "not(../../../../../ncs:module) or ../../../../../ncs:module[ncs:name='huawei-qos-evpl']";
      when "../evpl:mode='vxlan-mode'" {
        tailf:xpath-root 3;
      }
      description
        "Configure QoS PHB VXLAN mode.";
      leaf diffserv-domain-name {
        type leafref {
          path "/ncs:devices/ncs:device/ncs:config/qos:qos/qos:classifier-template/qos:diffserv-domains/qos:diffserv-domain/qos:name" {
            tailf:xpath-root 3;
          }
        }
        description
          "Name of a diffserv-domain.";
      }
    }
  }
}
