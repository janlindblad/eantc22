module huawei-vxlan-path-detect {
  // Generated by yanger -t ncs
  tailf:mount-id "huawei-nc-1.0:huawei-nc-1.0";
  tailf:ncs-device-type "netconf";

  yang-version 1;
  namespace "urn:huawei:yang:huawei-vxlan-path-detect";
  prefix vxlan-path-detect;

  import ietf-inet-types {
    prefix inet;
  }
  import huawei-pub-type {
    prefix pub-type;
  }
  import huawei-extension {
    prefix ext;
  }
  import huawei-ifm {
    prefix ifm;
  }
  import huawei-network-instance {
    prefix ni;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Vxlan oam management, which includes dscp path detection, IP ping, MAC ping, IPv6 ping.";

  revision 2020-06-20 {
    description
      "Add RPC.";
    reference "Huawei private.";
  }
  revision 2020-01-21 {
    description
      "Initial revision.";
    reference "Huawei private.";
  }
  ext:task-name "forwarding";

  typedef ncs_template_protocol-type {
    type string;
    description
      "Protocol type.";
  }

  typedef ncs_rpc_notif_protocol-type {
    type enumeration {
      enum "icmp" {
        value 1;
        description
          "Protocol type is ICMP.";
      }
      enum "tcp" {
        value 6;
        description
          "Protocol type is TCP.";
      }
      enum "udp" {
        value 17;
        description
          "Protocol type is UDP.";
      }
      enum "sctp" {
        value 132;
        description
          "Protocol type is SCTP.";
      }
    }
    description
      "Protocol type.";
  }

  typedef live_ncs_protocol-type {
    type enumeration {
      enum "icmp" {
        value 1;
        description
          "Protocol type is ICMP.";
      }
      enum "tcp" {
        value 6;
        description
          "Protocol type is TCP.";
      }
      enum "udp" {
        value 17;
        description
          "Protocol type is UDP.";
      }
      enum "sctp" {
        value 132;
        description
          "Protocol type is SCTP.";
      }
    }
    description
      "Protocol type.";
  }

  typedef protocol-type {
    type enumeration {
      enum "icmp" {
        value 1;
        description
          "Protocol type is ICMP.";
      }
      enum "tcp" {
        value 6;
        description
          "Protocol type is TCP.";
      }
      enum "udp" {
        value 17;
        description
          "Protocol type is UDP.";
      }
      enum "sctp" {
        value 132;
        description
          "Protocol type is SCTP.";
      }
    }
    description
      "Protocol type.";
  }

  augment "/ncs:devices/ncs:device/ncs:rpc" {
    container rpc-path-detection-send-pkt {
      tailf:ncs-device-type "netconf";
      tailf:display-when "not(../../ncs:module) or ../../ncs:module[ncs:name='huawei-vxlan-path-detect']";
      tailf:action path-detection-send-pkt {
        tailf:actionpoint ncsproxy {
          tailf:internal;
        }
        description
          "Sending one packet when path detection.";
        input {
          leaf source-mac {
            type pub-type:ncs_rpc_notif_mac-address;
            mandatory true;
            description
              "Source MAC.";
          }
          leaf destination-mac {
            type pub-type:ncs_rpc_notif_mac-address;
            mandatory true;
            description
              "Destination MAC.";
          }
          leaf pe-vlan {
            type uint16 {
              range "1..4094";
            }
            description
              "Pe-VLAN.";
          }
          leaf priority {
            when '../pe-vlan' {
              tailf:xpath-root 3;
            }
            type uint8 {
              range "0..7";
            }
            description
              "IEEE 802.1P encapsulation priority.";
          }
          leaf ce-vlan {
            when '../pe-vlan' {
              tailf:xpath-root 3;
            }
            type uint16 {
              range "1..4094";
            }
            description
              "Ce-VLAN.";
          }
          leaf source-ip {
            type inet:ip-address-no-zone;
            mandatory true;
            description
              "Source IP.";
          }
          leaf destination-ip {
            type inet:ip-address-no-zone;
            mandatory true;
            description
              "Destination IP.";
          }
          leaf protocol {
            type ncs_rpc_notif_protocol-type;
            mandatory true;
            description
              "Protocol type.";
          }
          leaf source-port {
            when "../protocol='tcp' or ../protocol='udp' or ../protocol='sctp'" {
              tailf:xpath-root 3;
            }
            type uint16 {
              range "1..65535";
            }
            mandatory true;
            description
              "Source port.";
          }
          leaf destination-port {
            when "../protocol='tcp' or ../protocol='udp' or ../protocol='sctp'" {
              tailf:xpath-root 3;
            }
            type uint16 {
              range "1..65535";
            }
            mandatory true;
            description
              "Destination port.";
          }
          leaf gtp-teid {
            when "../protocol='udp' and (../source-port=2152 or ../destination-port=2152)" {
              tailf:xpath-root 3;
            }
            type uint32;
            description
              "GTP TEID.";
          }
          leaf dscp {
            type inet:dscp;
            mandatory true;
            description
              "DSCP value.";
          }
          leaf vpn-instance-name {
            type string;
            description
              "VPN instance name.";
          }
          leaf interface-name {
            type string;
            mandatory true;
            description
              "Interface name.";
          }
          leaf test-id {
            type uint32;
            mandatory true;
            description
              "Test ID.";
          }
        }
      }
    }
  }
  augment "/ncs:devices/ncs:device-group/ncs:ned-id/ncs:rpc" {
    container rpc-path-detection-send-pkt {
      tailf:ncs-device-type "netconf";
      tailf:display-when "/ncs:devices/ncs:device[ncs:name=current()/../../../ncs:member]/ncs:module[ncs:name='huawei-vxlan-path-detect']";
      tailf:action path-detection-send-pkt {
        tailf:actionpoint ncsproxy {
          tailf:internal;
        }
        description
          "Sending one packet when path detection.";
        input {
          leaf source-mac {
            type pub-type:ncs_rpc_notif_mac-address;
            mandatory true;
            description
              "Source MAC.";
          }
          leaf destination-mac {
            type pub-type:ncs_rpc_notif_mac-address;
            mandatory true;
            description
              "Destination MAC.";
          }
          leaf pe-vlan {
            type uint16 {
              range "1..4094";
            }
            description
              "Pe-VLAN.";
          }
          leaf priority {
            when '../pe-vlan' {
              tailf:xpath-root 4;
            }
            type uint8 {
              range "0..7";
            }
            description
              "IEEE 802.1P encapsulation priority.";
          }
          leaf ce-vlan {
            when '../pe-vlan' {
              tailf:xpath-root 4;
            }
            type uint16 {
              range "1..4094";
            }
            description
              "Ce-VLAN.";
          }
          leaf source-ip {
            type inet:ip-address-no-zone;
            mandatory true;
            description
              "Source IP.";
          }
          leaf destination-ip {
            type inet:ip-address-no-zone;
            mandatory true;
            description
              "Destination IP.";
          }
          leaf protocol {
            type ncs_rpc_notif_protocol-type;
            mandatory true;
            description
              "Protocol type.";
          }
          leaf source-port {
            when "../protocol='tcp' or ../protocol='udp' or ../protocol='sctp'" {
              tailf:xpath-root 4;
            }
            type uint16 {
              range "1..65535";
            }
            mandatory true;
            description
              "Source port.";
          }
          leaf destination-port {
            when "../protocol='tcp' or ../protocol='udp' or ../protocol='sctp'" {
              tailf:xpath-root 4;
            }
            type uint16 {
              range "1..65535";
            }
            mandatory true;
            description
              "Destination port.";
          }
          leaf gtp-teid {
            when "../protocol='udp' and (../source-port=2152 or ../destination-port=2152)" {
              tailf:xpath-root 4;
            }
            type uint32;
            description
              "GTP TEID.";
          }
          leaf dscp {
            type inet:dscp;
            mandatory true;
            description
              "DSCP value.";
          }
          leaf vpn-instance-name {
            type string;
            description
              "VPN instance name.";
          }
          leaf interface-name {
            type string;
            mandatory true;
            description
              "Interface name.";
          }
          leaf test-id {
            type uint32;
            mandatory true;
            description
              "Test ID.";
          }
        }
      }
    }
  }
  augment "/ncs:devices/ncs:device/ncs:config" {
    container vxlan-path-detect {
      tailf:ncs-device-type "netconf";
      tailf:display-when "not(../../ncs:module) or ../../ncs:module[ncs:name='huawei-vxlan-path-detect']";
      description
        "Vxlan path detect.";
      container ipv4-dscp-path-detect {
        presence "Enable IPv4 DSCP detect.";
        description
          "Configure IPv4 DSCP path detect.";
        leaf dscp-value {
          type inet:dscp;
          mandatory true;
          description
            "DSCP value.";
        }
      }
      container ipv6-dscp-path-detect {
        presence "Enable IPv6 DSCP detect.";
        description
          "Configure IPv6 DSCP path detect.";
        leaf dscp-value {
          type inet:dscp;
          mandatory true;
          description
            "DSCP value.";
        }
      }
      container ip-ping-detects {
        description
          "List of IP ping detect.";
        list ip-ping-detect {
          key "src-ip dst-ip";
          description
            "Configure IP ping detect.";
          leaf src-ip {
            type inet:ipv4-address-no-zone;
            description
              "Source IPv4 address.";
          }
          leaf dst-ip {
            type inet:ipv4-address-no-zone;
            description
              "Destination IPv4 address.";
          }
        }
      }
      container mac-ping-detects {
        description
          "List of MAC ping detect.";
        list mac-ping-detect {
          key "src-ip dst-ip";
          description
            "Configure MAC ping detect.";
          leaf src-ip {
            type inet:ipv4-address-no-zone;
            description
              "Source IPv4 address.";
          }
          leaf dst-ip {
            type inet:ipv4-address-no-zone;
            description
              "Destination IPv4 address.";
          }
          leaf src-mac {
            type pub-type:mac-address;
            description
              "Source MAC address.";
          }
          leaf dst-mac {
            type pub-type:mac-address;
            description
              "Destination MAC address.";
          }
        }
      }
      container ipv6-ping-detects {
        description
          "List of IPv6 ping detect.";
        list ipv6-ping-detect {
          key "src-ipv6 dst-ipv6";
          description
            "Configure IPv6 ping detect.";
          leaf src-ipv6 {
            type inet:ipv6-address-no-zone;
            description
              "Source IPv6 address.";
          }
          leaf dst-ipv6 {
            type inet:ipv6-address-no-zone;
            description
              "Destination IPv6 address.";
          }
        }
      }
    }
  }
  augment "/ncs:devices/ncs:device/ncs:live-status" {
    container vxlan-path-detect {
      tailf:ncs-device-type "netconf";
      tailf:display-when "not(../../ncs:module) or ../../ncs:module[ncs:name='huawei-vxlan-path-detect'] or (../../ncs:live-status-protocol[not(ncs:capability)]) or (../../ncs:live-status-protocol/ncs:capability/ncs:module[.='huawei-vxlan-path-detect'])";
      description
        "Vxlan path detect.";
      container ipv4-dscp-path-detect {
        presence "Enable IPv4 DSCP detect.";
        description
          "Configure IPv4 DSCP path detect.";
        leaf dscp-value {
          type inet:dscp;
          // NCS drop mandatory statement
          description
            "DSCP value.";
        }
      }
      container ipv6-dscp-path-detect {
        presence "Enable IPv6 DSCP detect.";
        description
          "Configure IPv6 DSCP path detect.";
        leaf dscp-value {
          type inet:dscp;
          // NCS drop mandatory statement
          description
            "DSCP value.";
        }
      }
      container ip-ping-detects {
        description
          "List of IP ping detect.";
        list ip-ping-detect {
          key "src-ip dst-ip";
          description
            "Configure IP ping detect.";
          leaf src-ip {
            type inet:ipv4-address-no-zone;
            description
              "Source IPv4 address.";
          }
          leaf dst-ip {
            type inet:ipv4-address-no-zone;
            description
              "Destination IPv4 address.";
          }
        }
      }
      container mac-ping-detects {
        description
          "List of MAC ping detect.";
        list mac-ping-detect {
          key "src-ip dst-ip";
          description
            "Configure MAC ping detect.";
          leaf src-ip {
            type inet:ipv4-address-no-zone;
            description
              "Source IPv4 address.";
          }
          leaf dst-ip {
            type inet:ipv4-address-no-zone;
            description
              "Destination IPv4 address.";
          }
          leaf src-mac {
            type pub-type:live_ncs_mac-address;
            description
              "Source MAC address.";
          }
          leaf dst-mac {
            type pub-type:live_ncs_mac-address;
            description
              "Destination MAC address.";
          }
        }
      }
      container ipv6-ping-detects {
        description
          "List of IPv6 ping detect.";
        list ipv6-ping-detect {
          key "src-ipv6 dst-ipv6";
          description
            "Configure IPv6 ping detect.";
          leaf src-ipv6 {
            type inet:ipv6-address-no-zone;
            description
              "Source IPv6 address.";
          }
          leaf dst-ipv6 {
            type inet:ipv6-address-no-zone;
            description
              "Destination IPv6 address.";
          }
        }
      }
    }
  }
  augment "/ncs:devices/ncs:template/ncs:ned-id/ncs:config" {
    container vxlan-path-detect {
      description
        "Vxlan path detect.";
      container ipv4-dscp-path-detect {
        presence "Enable IPv4 DSCP detect.";
        description
          "Configure IPv4 DSCP path detect.";
        leaf dscp-value {
          type string;
          // NCS drop mandatory statement
          description
            "DSCP value.";
        }
      }
      container ipv6-dscp-path-detect {
        presence "Enable IPv6 DSCP detect.";
        description
          "Configure IPv6 DSCP path detect.";
        leaf dscp-value {
          type string;
          // NCS drop mandatory statement
          description
            "DSCP value.";
        }
      }
      container ip-ping-detects {
        description
          "List of IP ping detect.";
        list ip-ping-detect {
          // NCS patched for predictable order
          ordered-by user;
          key "src-ip dst-ip";
          description
            "Configure IP ping detect.";
          leaf src-ip {
            type string;
            description
              "Source IPv4 address.";
          }
          leaf dst-ip {
            type string;
            description
              "Destination IPv4 address.";
          }
        }
      }
      container mac-ping-detects {
        description
          "List of MAC ping detect.";
        list mac-ping-detect {
          // NCS patched for predictable order
          ordered-by user;
          key "src-ip dst-ip";
          description
            "Configure MAC ping detect.";
          leaf src-ip {
            type string;
            description
              "Source IPv4 address.";
          }
          leaf dst-ip {
            type string;
            description
              "Destination IPv4 address.";
          }
          leaf src-mac {
            type pub-type:ncs_template_mac-address;
            description
              "Source MAC address.";
          }
          leaf dst-mac {
            type pub-type:ncs_template_mac-address;
            description
              "Destination MAC address.";
          }
        }
      }
      container ipv6-ping-detects {
        description
          "List of IPv6 ping detect.";
        list ipv6-ping-detect {
          // NCS patched for predictable order
          ordered-by user;
          key "src-ipv6 dst-ipv6";
          description
            "Configure IPv6 ping detect.";
          leaf src-ipv6 {
            type string;
            description
              "Source IPv6 address.";
          }
          leaf dst-ipv6 {
            type string;
            description
              "Destination IPv6 address.";
          }
        }
      }
    }
  }
}
