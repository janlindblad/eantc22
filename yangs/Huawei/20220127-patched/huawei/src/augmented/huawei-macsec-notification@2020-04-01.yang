module huawei-macsec-notification {
  // Generated by yanger -t ncs
  tailf:mount-id "huawei-nc-1.0:huawei-nc-1.0";
  tailf:ncs-device-type "netconf";

  yang-version 1;
  namespace "urn:huawei:yang:huawei-macsec-notification";
  prefix macsec-notification;

  import huawei-extension {
    prefix ext;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Notification of macsec-notification.";

  revision 2020-04-01 {
    description
      "Add new nodes.";
    reference "Huawei private.";
  }
  revision 2020-02-20 {
    description
      "Initial revision.";
    reference "Huawei private.";
  }
  ext:task-name "macsec";

  typedef ncs_template_role-type {
    type string;
    description
      "Role type.";
  }

  typedef ncs_rpc_notif_role-type {
    type enumeration {
      enum "client" {
        value 1;
        description
          "Client.";
      }
      enum "server" {
        value 2;
        description
          "Server.";
      }
    }
    description
      "Role type.";
  }

  typedef live_ncs_role-type {
    type enumeration {
      enum "client" {
        value 1;
        description
          "Client.";
      }
      enum "server" {
        value 2;
        description
          "Server.";
      }
    }
    description
      "Role type.";
  }

  typedef role-type {
    type enumeration {
      enum "client" {
        value 1;
        description
          "Client.";
      }
      enum "server" {
        value 2;
        description
          "Server.";
      }
    }
    description
      "Role type.";
  }

  augment "/ncs:devices/ncs:device/ncs:notifications/ncs:received-notifications/ncs:notification/ncs:data" {
    container macsec-receive-response-timeout-resume {
      presence "";
      config false;
      description
        "The MKA protocol status is restored or the MACSEC configuration is deleted.";
      leaf if-index {
        type uint32;
        description
          "Interface index.";
      }
      leaf role {
        type ncs_rpc_notif_role-type;
        description
          "Role.";
      }
      leaf local-port {
        type string {
          length "1..64";
        }
        description
          "Local port.";
      }
    }
  }
  augment "/ncs:devices/ncs:device/ncs:notifications/ncs:received-notifications/ncs:notification/ncs:data" {
    container macsec-receive-response-timeout {
      presence "";
      config false;
      description
        "The MKA protocol status of the local interface becomes Down because the response message cannot be received during the timeout period.";
      leaf if-index {
        type uint32;
        description
          "Interface index.";
      }
      leaf role {
        type ncs_rpc_notif_role-type;
        description
          "Role.";
      }
      leaf local-port {
        type string {
          length "1..64";
        }
        description
          "Local port.";
      }
    }
  }
  augment "/ncs:devices/ncs:device/ncs:notifications/ncs:received-notifications/ncs:notification/ncs:data" {
    container macsec-ckn-switch-fail {
      presence "";
      config false;
      description
        "If the CKN switchover fails or the switchover is not complete three minutes later, an alarm is generated.";
      leaf if-index {
        type uint32;
        description
          "Interface index.";
      }
      leaf role {
        type ncs_rpc_notif_role-type;
        description
          "Role.";
      }
      leaf local-port {
        type string {
          length "1..64";
        }
        description
          "Local port.";
      }
      leaf old-ckn {
        type string {
          length "1..65";
        }
        description
          "Old ckn.";
      }
      leaf new-ckn {
        type string {
          length "1..65";
        }
        description
          "New ckn.";
      }
      leaf switch-reason {
        type string {
          length "1..128";
        }
        description
          "Switch reason.";
      }
      leaf fail-reason {
        type string {
          length "1..128";
        }
        description
          "Fail reason.";
      }
    }
  }
  augment "/ncs:devices/ncs:device/ncs:netconf-notifications/ncs:received-notifications/ncs:notification/ncs:data" {
    container macsec-receive-response-timeout-resume {
      presence "";
      config false;
      description
        "The MKA protocol status is restored or the MACSEC configuration is deleted.";
      leaf if-index {
        type uint32;
        description
          "Interface index.";
      }
      leaf role {
        type ncs_rpc_notif_role-type;
        description
          "Role.";
      }
      leaf local-port {
        type string {
          length "1..64";
        }
        description
          "Local port.";
      }
    }
  }
  augment "/ncs:devices/ncs:device/ncs:netconf-notifications/ncs:received-notifications/ncs:notification/ncs:data" {
    container macsec-receive-response-timeout {
      presence "";
      config false;
      description
        "The MKA protocol status of the local interface becomes Down because the response message cannot be received during the timeout period.";
      leaf if-index {
        type uint32;
        description
          "Interface index.";
      }
      leaf role {
        type ncs_rpc_notif_role-type;
        description
          "Role.";
      }
      leaf local-port {
        type string {
          length "1..64";
        }
        description
          "Local port.";
      }
    }
  }
  augment "/ncs:devices/ncs:device/ncs:netconf-notifications/ncs:received-notifications/ncs:notification/ncs:data" {
    container macsec-ckn-switch-fail {
      presence "";
      config false;
      description
        "If the CKN switchover fails or the switchover is not complete three minutes later, an alarm is generated.";
      leaf if-index {
        type uint32;
        description
          "Interface index.";
      }
      leaf role {
        type ncs_rpc_notif_role-type;
        description
          "Role.";
      }
      leaf local-port {
        type string {
          length "1..64";
        }
        description
          "Local port.";
      }
      leaf old-ckn {
        type string {
          length "1..65";
        }
        description
          "Old ckn.";
      }
      leaf new-ckn {
        type string {
          length "1..65";
        }
        description
          "New ckn.";
      }
      leaf switch-reason {
        type string {
          length "1..128";
        }
        description
          "Switch reason.";
      }
      leaf fail-reason {
        type string {
          length "1..128";
        }
        description
          "Fail reason.";
      }
    }
  }
}
