module huawei-software {
  // Generated by yanger -t ncs
  tailf:mount-id "huawei-nc-1.0:huawei-nc-1.0";
  tailf:ncs-device-type "netconf";

  namespace "urn:huawei:yang:huawei-software";
  prefix software;

  import huawei-extension {
    prefix ext;
  }
  import ietf-yang-types {
    prefix yang;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Specify software package upgrade management.";

  revision 2020-06-30 {
    description
      "Revert modification of software node's config attribute.";
    reference "Huawei private.";
  }
  revision 2020-06-29 {
    description
      "Modify node description.";
    reference "Huawei private.";
  }
  revision 2020-05-27 {
    description
      "Add rpc refresh-startup-secure-version-configuration.";
    reference "Huawei private.";
  }
  revision 2020-03-02 {
    description
      "Add install-feature-software, uninstall-feature-software, upgrade-feature-software.";
    reference "Huawei private.";
  }
  revision 2019-12-02 {
    description
      "Initial revision.";
    reference "Huawei private.";
  }
  ext:task-name "upgrade";

  typedef ncs_template_startup-mode {
    type string;
    description
      "Startup mode.";
  }

  typedef ncs_template_package-type {
    type string;
    description
      "Specify the type of a software package on the device.";
  }

  typedef ncs_template_checkpoint-create-type {
    type string;
    description
      "Specify the type of a software package on the device.";
  }

  typedef ncs_rpc_notif_startup-mode {
    type enumeration {
      enum "primary" {
        value 1;
        description
          "Upgrade the software package on the master MPU.";
      }
      enum "slave" {
        value 2;
        description
          "Upgrade the software package on the slave MPU.";
      }
      enum "all" {
        value 3;
        description
          "Upgrade the software package on all MPUs.";
      }
    }
    description
      "Startup mode.";
  }

  typedef ncs_rpc_notif_package-type {
    type enumeration {
      enum "system" {
        value 1;
        description
          "The type of a software package on the device is a system software package.";
      }
      enum "feature" {
        value 2;
        description
          "The type of a software package on the device is a feature software package.";
      }
    }
    description
      "Specify the type of a software package on the device.";
  }

  typedef ncs_rpc_notif_checkpoint-create-type {
    type enumeration {
      enum "manual" {
        value 1;
        description
          "The type of a checkpoint created mode.";
      }
      enum "auto" {
        value 2;
        description
          "The type of a checkpoint created mode.";
      }
    }
    description
      "Specify the type of a software package on the device.";
  }

  typedef live_ncs_startup-mode {
    type enumeration {
      enum "primary" {
        value 1;
        description
          "Upgrade the software package on the master MPU.";
      }
      enum "slave" {
        value 2;
        description
          "Upgrade the software package on the slave MPU.";
      }
      enum "all" {
        value 3;
        description
          "Upgrade the software package on all MPUs.";
      }
    }
    description
      "Startup mode.";
  }

  typedef live_ncs_package-type {
    type enumeration {
      enum "system" {
        value 1;
        description
          "The type of a software package on the device is a system software package.";
      }
      enum "feature" {
        value 2;
        description
          "The type of a software package on the device is a feature software package.";
      }
    }
    description
      "Specify the type of a software package on the device.";
  }

  typedef live_ncs_checkpoint-create-type {
    type enumeration {
      enum "manual" {
        value 1;
        description
          "The type of a checkpoint created mode.";
      }
      enum "auto" {
        value 2;
        description
          "The type of a checkpoint created mode.";
      }
    }
    description
      "Specify the type of a software package on the device.";
  }

  typedef startup-mode {
    type enumeration {
      enum "primary" {
        value 1;
        description
          "Upgrade the software package on the master MPU.";
      }
      enum "slave" {
        value 2;
        description
          "Upgrade the software package on the slave MPU.";
      }
      enum "all" {
        value 3;
        description
          "Upgrade the software package on all MPUs.";
      }
    }
    description
      "Startup mode.";
  }

  typedef package-type {
    type enumeration {
      enum "system" {
        value 1;
        description
          "The type of a software package on the device is a system software package.";
      }
      enum "feature" {
        value 2;
        description
          "The type of a software package on the device is a feature software package.";
      }
    }
    description
      "Specify the type of a software package on the device.";
  }

  typedef checkpoint-create-type {
    type enumeration {
      enum "manual" {
        value 1;
        description
          "The type of a checkpoint created mode.";
      }
      enum "auto" {
        value 2;
        description
          "The type of a checkpoint created mode.";
      }
    }
    description
      "Specify the type of a software package on the device.";
  }

  augment "/ncs:devices/ncs:device/ncs:rpc" {
    container rpc-refresh-startup-secure-version-configuration {
      tailf:ncs-device-type "netconf";
      tailf:display-when "not(../../ncs:module) or ../../ncs:module[ncs:name='huawei-software']";
      tailf:action refresh-startup-secure-version-configuration {
        tailf:actionpoint ncsproxy {
          tailf:internal;
        }
        description
          "Update the eFUSE and version revocation list. If the slot parameter is not specified, information on all boards is updated.";
        input {
          leaf slot {
            type string {
              length "1..49";
            }
            description
              "Specify the slot name.";
          }
        }
      }
    }
  }
  augment "/ncs:devices/ncs:device-group/ncs:ned-id/ncs:rpc" {
    container rpc-refresh-startup-secure-version-configuration {
      tailf:ncs-device-type "netconf";
      tailf:display-when "/ncs:devices/ncs:device[ncs:name=current()/../../../ncs:member]/ncs:module[ncs:name='huawei-software']";
      tailf:action refresh-startup-secure-version-configuration {
        tailf:actionpoint ncsproxy {
          tailf:internal;
        }
        description
          "Update the eFUSE and version revocation list. If the slot parameter is not specified, information on all boards is updated.";
        input {
          leaf slot {
            type string {
              length "1..49";
            }
            description
              "Specify the slot name.";
          }
        }
      }
    }
  }
  augment "/ncs:devices/ncs:device/ncs:rpc" {
    container rpc-restore-startup-checkpoint {
      tailf:ncs-device-type "netconf";
      tailf:display-when "not(../../ncs:module) or ../../ncs:module[ncs:name='huawei-software']";
      tailf:action restore-startup-checkpoint {
        tailf:actionpoint ncsproxy {
          tailf:internal;
        }
        ext:node-ref "/software/checkpoint-infos/checkpoint-info";
        description
          "Restore a specified checkpoint.";
        input {
          leaf name {
            type string;
            mandatory true;
            description
              "Specify the name of a checkpoint.";
          }
        }
      }
    }
  }
  augment "/ncs:devices/ncs:device-group/ncs:ned-id/ncs:rpc" {
    container rpc-restore-startup-checkpoint {
      tailf:ncs-device-type "netconf";
      tailf:display-when "/ncs:devices/ncs:device[ncs:name=current()/../../../ncs:member]/ncs:module[ncs:name='huawei-software']";
      tailf:action restore-startup-checkpoint {
        tailf:actionpoint ncsproxy {
          tailf:internal;
        }
        ext:node-ref "/software/checkpoint-infos/checkpoint-info";
        description
          "Restore a specified checkpoint.";
        input {
          leaf name {
            type string;
            mandatory true;
            description
              "Specify the name of a checkpoint.";
          }
        }
      }
    }
  }
  augment "/ncs:devices/ncs:device/ncs:rpc" {
    container rpc-check-startup-checkpoint {
      tailf:ncs-device-type "netconf";
      tailf:display-when "not(../../ncs:module) or ../../ncs:module[ncs:name='huawei-software']";
      tailf:action check-startup-checkpoint {
        tailf:actionpoint ncsproxy {
          tailf:internal;
        }
        ext:node-ref "/software/checkpoint-infos/checkpoint-info";
        description
          "Check a specified startup checkpoint.";
        input {
          leaf name {
            type string;
            mandatory true;
            description
              "Specify the name of a checkpoint.";
          }
        }
      }
    }
  }
  augment "/ncs:devices/ncs:device-group/ncs:ned-id/ncs:rpc" {
    container rpc-check-startup-checkpoint {
      tailf:ncs-device-type "netconf";
      tailf:display-when "/ncs:devices/ncs:device[ncs:name=current()/../../../ncs:member]/ncs:module[ncs:name='huawei-software']";
      tailf:action check-startup-checkpoint {
        tailf:actionpoint ncsproxy {
          tailf:internal;
        }
        ext:node-ref "/software/checkpoint-infos/checkpoint-info";
        description
          "Check a specified startup checkpoint.";
        input {
          leaf name {
            type string;
            mandatory true;
            description
              "Specify the name of a checkpoint.";
          }
        }
      }
    }
  }
  augment "/ncs:devices/ncs:device/ncs:rpc" {
    container rpc-delete-startup-checkpoint {
      tailf:ncs-device-type "netconf";
      tailf:display-when "not(../../ncs:module) or ../../ncs:module[ncs:name='huawei-software']";
      tailf:action delete-startup-checkpoint {
        tailf:actionpoint ncsproxy {
          tailf:internal;
        }
        ext:node-ref "/software/checkpoint-infos/checkpoint-info";
        description
          "Delete a specified startup checkpoint.";
        input {
          leaf name {
            type string;
            mandatory true;
            description
              "Specify the name of a checkpoint.";
          }
        }
      }
    }
  }
  augment "/ncs:devices/ncs:device-group/ncs:ned-id/ncs:rpc" {
    container rpc-delete-startup-checkpoint {
      tailf:ncs-device-type "netconf";
      tailf:display-when "/ncs:devices/ncs:device[ncs:name=current()/../../../ncs:member]/ncs:module[ncs:name='huawei-software']";
      tailf:action delete-startup-checkpoint {
        tailf:actionpoint ncsproxy {
          tailf:internal;
        }
        ext:node-ref "/software/checkpoint-infos/checkpoint-info";
        description
          "Delete a specified startup checkpoint.";
        input {
          leaf name {
            type string;
            mandatory true;
            description
              "Specify the name of a checkpoint.";
          }
        }
      }
    }
  }
  augment "/ncs:devices/ncs:device/ncs:rpc" {
    container rpc-create-startup-checkpoint {
      tailf:ncs-device-type "netconf";
      tailf:display-when "not(../../ncs:module) or ../../ncs:module[ncs:name='huawei-software']";
      tailf:action create-startup-checkpoint {
        tailf:actionpoint ncsproxy {
          tailf:internal;
        }
        ext:node-ref "/software/checkpoint-infos/checkpoint-info";
        description
          "Create a specified startup checkpoint.";
        input {
          leaf name {
            type string;
            mandatory true;
            description
              "Specify the name of a checkpoint.";
          }
        }
      }
    }
  }
  augment "/ncs:devices/ncs:device-group/ncs:ned-id/ncs:rpc" {
    container rpc-create-startup-checkpoint {
      tailf:ncs-device-type "netconf";
      tailf:display-when "/ncs:devices/ncs:device[ncs:name=current()/../../../ncs:member]/ncs:module[ncs:name='huawei-software']";
      tailf:action create-startup-checkpoint {
        tailf:actionpoint ncsproxy {
          tailf:internal;
        }
        ext:node-ref "/software/checkpoint-infos/checkpoint-info";
        description
          "Create a specified startup checkpoint.";
        input {
          leaf name {
            type string;
            mandatory true;
            description
              "Specify the name of a checkpoint.";
          }
        }
      }
    }
  }
  augment "/ncs:devices/ncs:device/ncs:rpc" {
    container rpc-startup-feature-software {
      tailf:ncs-device-type "netconf";
      tailf:display-when "not(../../ncs:module) or ../../ncs:module[ncs:name='huawei-software']";
      tailf:action startup-feature-software {
        tailf:actionpoint ncsproxy {
          tailf:internal;
        }
        description
          "Startup feature software.";
        input {
          leaf feature-package-name {
            type string {
              length "4..127";
            }
            mandatory true;
            description
              "Specify the name of a feature software package.";
          }
        }
      }
    }
  }
  augment "/ncs:devices/ncs:device-group/ncs:ned-id/ncs:rpc" {
    container rpc-startup-feature-software {
      tailf:ncs-device-type "netconf";
      tailf:display-when "/ncs:devices/ncs:device[ncs:name=current()/../../../ncs:member]/ncs:module[ncs:name='huawei-software']";
      tailf:action startup-feature-software {
        tailf:actionpoint ncsproxy {
          tailf:internal;
        }
        description
          "Startup feature software.";
        input {
          leaf feature-package-name {
            type string {
              length "4..127";
            }
            mandatory true;
            description
              "Specify the name of a feature software package.";
          }
        }
      }
    }
  }
  augment "/ncs:devices/ncs:device/ncs:rpc" {
    container rpc-upgrade-feature-software {
      tailf:ncs-device-type "netconf";
      tailf:display-when "not(../../ncs:module) or ../../ncs:module[ncs:name='huawei-software']";
      tailf:action upgrade-feature-software {
        tailf:actionpoint ncsproxy {
          tailf:internal;
        }
        description
          "Upgrade feature software on line.";
        input {
          leaf name {
            type string {
              length "4..127";
            }
            mandatory true;
            description
              "Specify the name of a feature software package.";
          }
        }
      }
    }
  }
  augment "/ncs:devices/ncs:device-group/ncs:ned-id/ncs:rpc" {
    container rpc-upgrade-feature-software {
      tailf:ncs-device-type "netconf";
      tailf:display-when "/ncs:devices/ncs:device[ncs:name=current()/../../../ncs:member]/ncs:module[ncs:name='huawei-software']";
      tailf:action upgrade-feature-software {
        tailf:actionpoint ncsproxy {
          tailf:internal;
        }
        description
          "Upgrade feature software on line.";
        input {
          leaf name {
            type string {
              length "4..127";
            }
            mandatory true;
            description
              "Specify the name of a feature software package.";
          }
        }
      }
    }
  }
  augment "/ncs:devices/ncs:device/ncs:rpc" {
    container rpc-uninstall-feature-software {
      tailf:ncs-device-type "netconf";
      tailf:display-when "not(../../ncs:module) or ../../ncs:module[ncs:name='huawei-software']";
      tailf:action uninstall-feature-software {
        tailf:actionpoint ncsproxy {
          tailf:internal;
        }
        description
          "Uninstall feature software.";
        input {
          leaf name {
            type string {
              length "4..127";
            }
            mandatory true;
            description
              "Specify the name of a feature software package.";
          }
        }
      }
    }
  }
  augment "/ncs:devices/ncs:device-group/ncs:ned-id/ncs:rpc" {
    container rpc-uninstall-feature-software {
      tailf:ncs-device-type "netconf";
      tailf:display-when "/ncs:devices/ncs:device[ncs:name=current()/../../../ncs:member]/ncs:module[ncs:name='huawei-software']";
      tailf:action uninstall-feature-software {
        tailf:actionpoint ncsproxy {
          tailf:internal;
        }
        description
          "Uninstall feature software.";
        input {
          leaf name {
            type string {
              length "4..127";
            }
            mandatory true;
            description
              "Specify the name of a feature software package.";
          }
        }
      }
    }
  }
  augment "/ncs:devices/ncs:device/ncs:rpc" {
    container rpc-install-feature-software {
      tailf:ncs-device-type "netconf";
      tailf:display-when "not(../../ncs:module) or ../../ncs:module[ncs:name='huawei-software']";
      tailf:action install-feature-software {
        tailf:actionpoint ncsproxy {
          tailf:internal;
        }
        description
          "Install feature software.";
        input {
          leaf name {
            type string {
              length "4..127";
            }
            mandatory true;
            description
              "Specify the name of a feature software package.";
          }
        }
      }
    }
  }
  augment "/ncs:devices/ncs:device-group/ncs:ned-id/ncs:rpc" {
    container rpc-install-feature-software {
      tailf:ncs-device-type "netconf";
      tailf:display-when "/ncs:devices/ncs:device[ncs:name=current()/../../../ncs:member]/ncs:module[ncs:name='huawei-software']";
      tailf:action install-feature-software {
        tailf:actionpoint ncsproxy {
          tailf:internal;
        }
        description
          "Install feature software.";
        input {
          leaf name {
            type string {
              length "4..127";
            }
            mandatory true;
            description
              "Specify the name of a feature software package.";
          }
        }
      }
    }
  }
  augment "/ncs:devices/ncs:device/ncs:rpc" {
    container rpc-undo-upgrade-rollback {
      tailf:ncs-device-type "netconf";
      tailf:display-when "not(../../ncs:module) or ../../ncs:module[ncs:name='huawei-software']";
      tailf:action undo-upgrade-rollback {
        tailf:actionpoint ncsproxy {
          tailf:internal;
        }
        ext:node-ref "/software/upgrade-rollback-timer";
        description
          "Delete the rollback time when upgrade software package.";
      }
    }
  }
  augment "/ncs:devices/ncs:device-group/ncs:ned-id/ncs:rpc" {
    container rpc-undo-upgrade-rollback {
      tailf:ncs-device-type "netconf";
      tailf:display-when "/ncs:devices/ncs:device[ncs:name=current()/../../../ncs:member]/ncs:module[ncs:name='huawei-software']";
      tailf:action undo-upgrade-rollback {
        tailf:actionpoint ncsproxy {
          tailf:internal;
        }
        ext:node-ref "/software/upgrade-rollback-timer";
        description
          "Delete the rollback time when upgrade software package.";
      }
    }
  }
  augment "/ncs:devices/ncs:device/ncs:rpc" {
    container rpc-enable-upgrade-rollback {
      tailf:ncs-device-type "netconf";
      tailf:display-when "not(../../ncs:module) or ../../ncs:module[ncs:name='huawei-software']";
      tailf:action enable-upgrade-rollback {
        tailf:actionpoint ncsproxy {
          tailf:internal;
        }
        description
          "Specify the rollback time when upgrade software package.";
        input {
          leaf rollback-time {
            type uint32 {
              range "10..360";
            }
            units "min";
            mandatory true;
            description
              "Specify the rollback time.";
          }
        }
      }
    }
  }
  augment "/ncs:devices/ncs:device-group/ncs:ned-id/ncs:rpc" {
    container rpc-enable-upgrade-rollback {
      tailf:ncs-device-type "netconf";
      tailf:display-when "/ncs:devices/ncs:device[ncs:name=current()/../../../ncs:member]/ncs:module[ncs:name='huawei-software']";
      tailf:action enable-upgrade-rollback {
        tailf:actionpoint ncsproxy {
          tailf:internal;
        }
        description
          "Specify the rollback time when upgrade software package.";
        input {
          leaf rollback-time {
            type uint32 {
              range "10..360";
            }
            units "min";
            mandatory true;
            description
              "Specify the rollback time.";
          }
        }
      }
    }
  }
  augment "/ncs:devices/ncs:device/ncs:rpc" {
    container rpc-startup-by-slot-id {
      tailf:ncs-device-type "netconf";
      tailf:display-when "not(../../ncs:module) or ../../ncs:module[ncs:name='huawei-software']";
      tailf:action startup-by-slot-id {
        tailf:actionpoint ncsproxy {
          tailf:internal;
        }
        description
          "Specify the slot ID-based upgrade for software packages.";
        ext:node-ref "/software/packages/package";
        input {
          leaf name {
            type string {
              length "4..127";
            }
            mandatory true;
            description
              "Specify the name of a software package that needs to be upgraded.";
          }
          leaf slot-id {
            type string {
              length "1..31";
            }
            description
              "Specify the slot ID of a board on which a software package needs to be upgraded.";
          }
        }
      }
    }
  }
  augment "/ncs:devices/ncs:device-group/ncs:ned-id/ncs:rpc" {
    container rpc-startup-by-slot-id {
      tailf:ncs-device-type "netconf";
      tailf:display-when "/ncs:devices/ncs:device[ncs:name=current()/../../../ncs:member]/ncs:module[ncs:name='huawei-software']";
      tailf:action startup-by-slot-id {
        tailf:actionpoint ncsproxy {
          tailf:internal;
        }
        description
          "Specify the slot ID-based upgrade for software packages.";
        ext:node-ref "/software/packages/package";
        input {
          leaf name {
            type string {
              length "4..127";
            }
            mandatory true;
            description
              "Specify the name of a software package that needs to be upgraded.";
          }
          leaf slot-id {
            type string {
              length "1..31";
            }
            description
              "Specify the slot ID of a board on which a software package needs to be upgraded.";
          }
        }
      }
    }
  }
  augment "/ncs:devices/ncs:device/ncs:rpc" {
    container rpc-startup-by-mode {
      tailf:ncs-device-type "netconf";
      tailf:display-when "not(../../ncs:module) or ../../ncs:module[ncs:name='huawei-software']";
      tailf:action startup-by-mode {
        tailf:actionpoint ncsproxy {
          tailf:internal;
        }
        description
          "Specify the mode-based upgrade for software packages.";
        ext:node-ref "/software/packages/package";
        input {
          leaf name {
            type string {
              length "4..127";
            }
            mandatory true;
            description
              "Specify the name of a software package that needs to be upgraded.";
          }
          leaf mode {
            type ncs_rpc_notif_startup-mode;
            description
              "Specify a software package upgrade mode.";
          }
        }
      }
    }
  }
  augment "/ncs:devices/ncs:device-group/ncs:ned-id/ncs:rpc" {
    container rpc-startup-by-mode {
      tailf:ncs-device-type "netconf";
      tailf:display-when "/ncs:devices/ncs:device[ncs:name=current()/../../../ncs:member]/ncs:module[ncs:name='huawei-software']";
      tailf:action startup-by-mode {
        tailf:actionpoint ncsproxy {
          tailf:internal;
        }
        description
          "Specify the mode-based upgrade for software packages.";
        ext:node-ref "/software/packages/package";
        input {
          leaf name {
            type string {
              length "4..127";
            }
            mandatory true;
            description
              "Specify the name of a software package that needs to be upgraded.";
          }
          leaf mode {
            type ncs_rpc_notif_startup-mode;
            description
              "Specify a software package upgrade mode.";
          }
        }
      }
    }
  }
  augment "/ncs:devices/ncs:device/ncs:config" {
    container software {
      tailf:ncs-device-type "netconf";
      tailf:display-when "not(../../ncs:module) or ../../ncs:module[ncs:name='huawei-software']";
      description
        "Specify software package upgrade management.";
      container global {
        description
          "Configure of auto save checkpoint switch.";
        container auto-save {
          description
            "Configure of enable auto save checkpoint.";
          leaf enable {
            type boolean;
            default "true";
            description
              "Enable/disable auto save checkpoint when upgrade software package.";
          }
        }
      }
      // NCS drop config false container versions
      // NCS drop config false container 'startup-packages'
      // NCS drop config false container packages
      // NCS drop config false container 'upgrade-rollback-timer'
      // NCS drop config false container 'checkpoint-infos'
    }
  }
  augment "/ncs:devices/ncs:device/ncs:live-status" {
    container software {
      tailf:ncs-device-type "netconf";
      tailf:display-when "not(../../ncs:module) or ../../ncs:module[ncs:name='huawei-software'] or (../../ncs:live-status-protocol[not(ncs:capability)]) or (../../ncs:live-status-protocol/ncs:capability/ncs:module[.='huawei-software'])";
      description
        "Specify software package upgrade management.";
      container global {
        description
          "Configure of auto save checkpoint switch.";
        container auto-save {
          description
            "Configure of enable auto save checkpoint.";
          leaf enable {
            type boolean;
            // NCS drop default statement
            description
              "Enable/disable auto save checkpoint when upgrade software package.";
          }
        }
      }
      container versions {
        status deprecated;
        description
          "List of operational state of software package versions. The node versions is deprecated. You are advised to use the node /system/system-info.";
        list version {
          key "base";
          status deprecated;
          description
            "Operational state of a software package version. The node version is deprecated. You are advised to use the node /system/system-info.";
          leaf base {
            type string {
              length "1..63";
            }
            status deprecated;
            description
              "Current software package version. The node base is deprecated. You are advised to use the node /system/system-info/product-version.";
          }
          leaf patch {
            type string {
              length "1..63";
            }
            status deprecated;
            description
              "Current patch package version. The node patch is deprecated. You are advised to use the node /system/system-info/patch-version.";
          }
        }
      }
      container startup-packages {
        description
          "List of operational state of startup software packages.";
        list startup-package {
          key "slot-id";
          description
            "Operational state of startup software package.";
          leaf slot-id {
            type string {
              length "1..31";
            }
            description
              "Slot ID.";
          }
          leaf current-package {
            type string {
              length "4..255";
            }
            description
              "The name of a software package used at the current startup.";
          }
          leaf next-package {
            type string {
              length "4..255";
            }
            description
              "The name of a software package used at the next startup.";
          }
        }
      }
      container packages {
        description
          "List of operational state of software packages on the device.";
        list package {
          key "name";
          description
            "Operational state of a software package on the device.";
          leaf name {
            type string {
              length "4..255";
            }
            description
              "The name of a software package on the device. There may exist user-created software packages with names longer than 127 on the device, however, such packages cannot be used for the next startup.";
          }
          leaf package-type {
            type live_ncs_package-type;
            description
              "The type of a software package on the device.";
          }
        }
      }
      container upgrade-rollback-timer {
        description
          "Operational data of upgrade rollback timer.";
        leaf timer-enable {
          type boolean;
          description
            "When the rollback timer is closed, the time leaf will not be shown.";
        }
        leaf time {
          // NCS drop when statement
          type uint32 {
            range "10..360";
          }
          units "min";
          description
            "Rollback time.";
        }
      }
      container checkpoint-infos {
        description
          "List of checkpoint base information.";
        list checkpoint-info {
          key "name";
          description
            "Statistics of a checkpoint info.";
          leaf name {
            type string {
              length "5..32";
            }
            description
              "Checkpoint name.";
          }
          leaf create-time {
            type yang:date-and-time;
            description
              "Checkpoint create time.";
          }
          leaf create-mode {
            type live_ncs_checkpoint-create-type;
            description
              "Checkpoint create mode.";
          }
          leaf base-package {
            type string {
              length "0..255";
            }
            description
              "Checkpoint software package.";
          }
          leaf feature-package {
            type string {
              length "0..2047";
            }
            description
              "Checkpoint feature packages.";
          }
          leaf patch-package {
            type string {
              length "0..2047";
            }
            description
              "Checkpoint patch packages.";
          }
          leaf module-package {
            type string {
              length "0..2047";
            }
            description
              "Checkpoint mod patchs.";
          }
        }
      }
    }
  }
  augment "/ncs:devices/ncs:template/ncs:ned-id/ncs:config" {
    container software {
      description
        "Specify software package upgrade management.";
      container global {
        description
          "Configure of auto save checkpoint switch.";
        container auto-save {
          description
            "Configure of enable auto save checkpoint.";
          leaf enable {
            type string;
            // NCS drop default statement
            description
              "Enable/disable auto save checkpoint when upgrade software package.";
          }
        }
      }
      // NCS drop config false container versions
      // NCS drop config false container 'startup-packages'
      // NCS drop config false container packages
      // NCS drop config false container 'upgrade-rollback-timer'
      // NCS drop config false container 'checkpoint-infos'
    }
  }
}
