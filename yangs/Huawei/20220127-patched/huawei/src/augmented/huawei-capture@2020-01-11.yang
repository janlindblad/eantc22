module huawei-capture {
  // Generated by yanger -t ncs
  tailf:mount-id "huawei-nc-1.0:huawei-nc-1.0";
  tailf:ncs-device-type "netconf";

  yang-version 1;
  namespace "urn:huawei:yang:huawei-capture";
  prefix capture;

  import huawei-extension {
    prefix ext;
  }
  import huawei-ifm {
    prefix ifm;
  }
  import huawei-vlan {
    prefix vlan;
  }
  import huawei-acl {
    prefix acl;
  }
  import ietf-yang-types {
    prefix yang;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Network capture.";

  revision 2020-01-11 {
    description
      "Initial revision.";
    reference "Huawei private.";
  }
  ext:task-name "capture";

  typedef ncs_template_tag-format {
    type string;
    description
      "Tag format of VXLAN overlay packets.";
  }

  typedef ncs_template_result {
    type string;
    description
      "Packet obtain result.";
  }

  typedef ncs_template_capture-index {
    type string;
    description
      "Index of the packet obtain instance.";
  }

  typedef ncs_template_direction {
    type string;
    description
      "Packet obtain direction.";
  }

  typedef ncs_template_packet-header-status {
    type string;
    description
      "Packet obtain status.";
  }

  typedef ncs_template_packet-header-link-type {
    type string;
    description
      "Packet header link type.";
  }

  typedef ncs_rpc_notif_tag-format {
    type enumeration {
      enum "none" {
        value 0;
        description
          "VXLAN overlay packets without VLAN tag.";
      }
      enum "single" {
        value 1;
        description
          "VXLAN overlay packets with single VLAN tag.";
      }
    }
    description
      "Tag format of VXLAN overlay packets.";
  }

  typedef ncs_rpc_notif_result {
    type enumeration {
      enum "success" {
        value 0;
        description
          "The packet obtain result is successful.";
      }
      enum "fail" {
        value 1;
        description
          "The packet obtain result is fail.";
      }
    }
    description
      "Packet obtain result.";
  }

  typedef ncs_rpc_notif_capture-index {
    type uint32 {
      range "1..8";
    }
    description
      "Index of the packet obtain instance.";
  }

  typedef ncs_rpc_notif_direction {
    type enumeration {
      enum "inbound" {
        value 1;
        description
          "Inbound.";
      }
      enum "outbound" {
        value 2;
        description
          "Outbound.";
      }
      enum "both" {
        value 3;
        description
          "Both.";
      }
    }
    description
      "Packet obtain direction.";
  }

  typedef ncs_rpc_notif_packet-header-status {
    type enumeration {
      enum "stopped" {
        value 0;
        description
          "Stop.";
      }
      enum "running" {
        value 1;
        description
          "Running.";
      }
    }
    description
      "Packet obtain status.";
  }

  typedef ncs_rpc_notif_packet-header-link-type {
    type enumeration {
      enum "none" {
        value 0;
        description
          "Interface of linktype.";
      }
      enum "ethernet" {
        value 1;
        description
          "Ethernet of link type.";
      }
      enum "ppp" {
        value 2;
        description
          "PPP protocol of link type.";
      }
      enum "hdlc" {
        value 3;
        description
          "HDLC protocol of link type.";
      }
      enum "atm" {
        value 4;
        description
          "ATM of link type.";
      }
    }
    description
      "Packet header link type.";
  }

  typedef live_ncs_tag-format {
    type enumeration {
      enum "none" {
        value 0;
        description
          "VXLAN overlay packets without VLAN tag.";
      }
      enum "single" {
        value 1;
        description
          "VXLAN overlay packets with single VLAN tag.";
      }
    }
    description
      "Tag format of VXLAN overlay packets.";
  }

  typedef live_ncs_result {
    type enumeration {
      enum "success" {
        value 0;
        description
          "The packet obtain result is successful.";
      }
      enum "fail" {
        value 1;
        description
          "The packet obtain result is fail.";
      }
    }
    description
      "Packet obtain result.";
  }

  typedef live_ncs_capture-index {
    type uint32 {
      range "1..8";
    }
    description
      "Index of the packet obtain instance.";
  }

  typedef live_ncs_direction {
    type enumeration {
      enum "inbound" {
        value 1;
        description
          "Inbound.";
      }
      enum "outbound" {
        value 2;
        description
          "Outbound.";
      }
      enum "both" {
        value 3;
        description
          "Both.";
      }
    }
    description
      "Packet obtain direction.";
  }

  typedef live_ncs_packet-header-status {
    type enumeration {
      enum "stopped" {
        value 0;
        description
          "Stop.";
      }
      enum "running" {
        value 1;
        description
          "Running.";
      }
    }
    description
      "Packet obtain status.";
  }

  typedef live_ncs_packet-header-link-type {
    type enumeration {
      enum "none" {
        value 0;
        description
          "Interface of linktype.";
      }
      enum "ethernet" {
        value 1;
        description
          "Ethernet of link type.";
      }
      enum "ppp" {
        value 2;
        description
          "PPP protocol of link type.";
      }
      enum "hdlc" {
        value 3;
        description
          "HDLC protocol of link type.";
      }
      enum "atm" {
        value 4;
        description
          "ATM of link type.";
      }
    }
    description
      "Packet header link type.";
  }

  typedef tag-format {
    type enumeration {
      enum "none" {
        value 0;
        description
          "VXLAN overlay packets without VLAN tag.";
      }
      enum "single" {
        value 1;
        description
          "VXLAN overlay packets with single VLAN tag.";
      }
    }
    description
      "Tag format of VXLAN overlay packets.";
  }

  typedef result {
    type enumeration {
      enum "success" {
        value 0;
        description
          "The packet obtain result is successful.";
      }
      enum "fail" {
        value 1;
        description
          "The packet obtain result is fail.";
      }
    }
    description
      "Packet obtain result.";
  }

  typedef capture-index {
    type uint32 {
      range "1..8";
    }
    description
      "Index of the packet obtain instance.";
  }

  typedef direction {
    type enumeration {
      enum "inbound" {
        value 1;
        description
          "Inbound.";
      }
      enum "outbound" {
        value 2;
        description
          "Outbound.";
      }
      enum "both" {
        value 3;
        description
          "Both.";
      }
    }
    description
      "Packet obtain direction.";
  }

  typedef packet-header-status {
    type enumeration {
      enum "stopped" {
        value 0;
        description
          "Stop.";
      }
      enum "running" {
        value 1;
        description
          "Running.";
      }
    }
    description
      "Packet obtain status.";
  }

  typedef packet-header-link-type {
    type enumeration {
      enum "none" {
        value 0;
        description
          "Interface of linktype.";
      }
      enum "ethernet" {
        value 1;
        description
          "Ethernet of link type.";
      }
      enum "ppp" {
        value 2;
        description
          "PPP protocol of link type.";
      }
      enum "hdlc" {
        value 3;
        description
          "HDLC protocol of link type.";
      }
      enum "atm" {
        value 4;
        description
          "ATM of link type.";
      }
    }
    description
      "Packet header link type.";
  }

  augment "/ncs:devices/ncs:device/ncs:rpc" {
    container rpc-free-packet-header-obtain {
      tailf:ncs-device-type "netconf";
      tailf:display-when "not(../../ncs:module) or ../../ncs:module[ncs:name='huawei-capture']";
      tailf:action free-packet-header-obtain {
        tailf:actionpoint ncsproxy {
          tailf:internal;
        }
        description
          "To free instance.";
        input {
          leaf instance-id {
            type uint8;
            description
              "Instance ID.";
          }
        }
      }
    }
  }
  augment "/ncs:devices/ncs:device-group/ncs:ned-id/ncs:rpc" {
    container rpc-free-packet-header-obtain {
      tailf:ncs-device-type "netconf";
      tailf:display-when "/ncs:devices/ncs:device[ncs:name=current()/../../../ncs:member]/ncs:module[ncs:name='huawei-capture']";
      tailf:action free-packet-header-obtain {
        tailf:actionpoint ncsproxy {
          tailf:internal;
        }
        description
          "To free instance.";
        input {
          leaf instance-id {
            type uint8;
            description
              "Instance ID.";
          }
        }
      }
    }
  }
  augment "/ncs:devices/ncs:device/ncs:rpc" {
    container rpc-stop-capture {
      tailf:ncs-device-type "netconf";
      tailf:display-when "not(../../ncs:module) or ../../ncs:module[ncs:name='huawei-capture']";
      tailf:action stop-capture {
        tailf:actionpoint ncsproxy {
          tailf:internal;
        }
        description
          "To stop capure.";
        input {
          choice mode {
            mandatory true;
            description
              "Stop mode.";
            case all {
              description
                "All the packet obtain instance.";
              leaf all {
                type empty;
                description
                  "All the packet obtain instance.";
              }
            }
            case index {
              description
                "The packet obtain instance with a specified index.";
              leaf capture-index {
                type ncs_rpc_notif_capture-index;
                description
                  "Index of the packet obtain instance.";
              }
            }
            case interface {
              description
                "The packet obtain instance with a specified interface.";
              leaf-list interface-name {
                type string;
                min-elements 1;
                max-elements 8;
                description
                  "Interface name for packet obtain.";
              }
              leaf direction {
                type ncs_rpc_notif_direction;
                description
                  "Packet obtain direction.";
              }
            }
          }
        }
      }
    }
  }
  augment "/ncs:devices/ncs:device-group/ncs:ned-id/ncs:rpc" {
    container rpc-stop-capture {
      tailf:ncs-device-type "netconf";
      tailf:display-when "/ncs:devices/ncs:device[ncs:name=current()/../../../ncs:member]/ncs:module[ncs:name='huawei-capture']";
      tailf:action stop-capture {
        tailf:actionpoint ncsproxy {
          tailf:internal;
        }
        description
          "To stop capure.";
        input {
          choice mode {
            mandatory true;
            description
              "Stop mode.";
            case all {
              description
                "All the packet obtain instance.";
              leaf all {
                type empty;
                description
                  "All the packet obtain instance.";
              }
            }
            case index {
              description
                "The packet obtain instance with a specified index.";
              leaf capture-index {
                type ncs_rpc_notif_capture-index;
                description
                  "Index of the packet obtain instance.";
              }
            }
            case interface {
              description
                "The packet obtain instance with a specified interface.";
              leaf-list interface-name {
                type string;
                min-elements 1;
                max-elements 8;
                description
                  "Interface name for packet obtain.";
              }
              leaf direction {
                type ncs_rpc_notif_direction;
                description
                  "Packet obtain direction.";
              }
            }
          }
        }
      }
    }
  }
  augment "/ncs:devices/ncs:device/ncs:rpc" {
    container rpc-capture-packet {
      tailf:ncs-device-type "netconf";
      tailf:display-when "not(../../ncs:module) or ../../ncs:module[ncs:name='huawei-capture']";
      tailf:action capture-packet {
        tailf:actionpoint ncsproxy {
          tailf:internal;
        }
        description
          "To start capture.";
        input {
          leaf local-host {
            type boolean;
            default "false";
            description
              "Obtain packets sent to the CPU.";
          }
          choice tunnel {
            description
              "Configure the tunnel type for packet obtain.";
            case normal {
              description
                "Normal packet.";
              leaf vlan-id {
                type vlan:ncs_rpc_notif_vlan-id;
                description
                  "Outer VLAN ID.";
              }
              leaf cvlan-id {
                type vlan:ncs_rpc_notif_vlan-id;
                description
                  "Inner VLAN ID.";
              }
            }
            case vxlan {
              description
                "Vxlan packet.";
              leaf vxlan {
                type empty;
                mandatory true;
                description
                  "Indicates that only VXLAN packets are captured.";
              }
              leaf vni-id {
                type uint32 {
                  range "1..16777215";
                }
                description
                  "VXLAN network identifier value.";
              }
              leaf tag-format {
                type ncs_rpc_notif_tag-format;
                description
                  "Tag format for vxlan packet.";
              }
            }
          }
          choice acl {
            description
              "Configure the acl for packet obtain.";
            case acl {
              description
                "IPv4 acl.";
              leaf acl-name {
                type string;
                description
                  "Acl number or name.";
              }
            }
            case acl6 {
              description
                "IPv6 acl.";
              leaf acl6-name {
                type string;
                description
                  "Acl number or name.";
              }
            }
          }
          leaf-list interface-name {
            type string;
            description
              "Interface name for packet obtain.";
          }
          leaf packet-number {
            type uint32 {
              range "1..5000";
            }
            default "100";
            description
              "Maximum number of packets to be captured.";
          }
          leaf packet-length {
            type uint16 {
              range "20..64";
            }
            units "Byte";
            default "64";
            description
              "Maximum packet length to be captured.";
          }
          leaf timeout {
            type uint32 {
              range "1..86400";
            }
            units "s";
            default "60";
            description
              "Timeout interval.";
          }
          leaf file-name {
            type string {
              length "5..64";
            }
            default "capture.cap";
            description
              "Name of the file for saving captured packets.";
          }
          leaf clear-payload {
            type boolean;
            default "false";
            description
              "Sets the data content of captured packets to 0. Only the data content of TCP and UDP packets can be set to 0.";
          }
          leaf direction {
            type ncs_rpc_notif_direction;
            description
              "Packet obtain direction.";
          }
          choice vlan-mode {
            description
              "VLAN for packet obtain.";
            case vlan {
              description
                "VLAN for packet obtain.";
              leaf vlan-begin {
                type vlan:ncs_rpc_notif_vlan-id;
                mandatory true;
                description
                  "Begin VLAN ID for packet obtain.";
              }
              leaf vlan-end {
                type vlan:ncs_rpc_notif_vlan-id;
                mandatory true;
                description
                  "End VLAN ID for packet obtain.";
              }
            }
            case pe-and-ce {
              description
                "Pe and Ce VLAN for packet obtain.";
              leaf pe-vlan {
                type vlan:ncs_rpc_notif_vlan-id;
                mandatory true;
                description
                  "Pe VLAN ID for packet obtain.";
              }
              leaf ce-vlan-begin {
                type vlan:ncs_rpc_notif_vlan-id;
                mandatory true;
                description
                  "Begin inner VLAN ID for packet obtain.";
              }
              leaf ce-vlan-end {
                type vlan:ncs_rpc_notif_vlan-id;
                mandatory true;
                description
                  "End inner VLAN ID for packet obtain.";
              }
            }
          }
          leaf file-size {
            type uint8;
            units "MB";
            default "2";
            description
              "File size.";
          }
          leaf buffer-only {
            type boolean;
            default "false";
            description
              "Type buffer only.";
          }
          leaf overwrite {
            type boolean;
            default "false";
            description
              "Overwrite the buffer.";
          }
        }
        output {
          leaf capture-index {
            type ncs_rpc_notif_capture-index;
            description
              "Index of the packet obtain instance.";
          }
        }
      }
    }
  }
  augment "/ncs:devices/ncs:device-group/ncs:ned-id/ncs:rpc" {
    container rpc-capture-packet {
      tailf:ncs-device-type "netconf";
      tailf:display-when "/ncs:devices/ncs:device[ncs:name=current()/../../../ncs:member]/ncs:module[ncs:name='huawei-capture']";
      tailf:action capture-packet {
        tailf:actionpoint ncsproxy {
          tailf:internal;
        }
        description
          "To start capture.";
        input {
          leaf local-host {
            type boolean;
            default "false";
            description
              "Obtain packets sent to the CPU.";
          }
          choice tunnel {
            description
              "Configure the tunnel type for packet obtain.";
            case normal {
              description
                "Normal packet.";
              leaf vlan-id {
                type vlan:ncs_rpc_notif_vlan-id;
                description
                  "Outer VLAN ID.";
              }
              leaf cvlan-id {
                type vlan:ncs_rpc_notif_vlan-id;
                description
                  "Inner VLAN ID.";
              }
            }
            case vxlan {
              description
                "Vxlan packet.";
              leaf vxlan {
                type empty;
                mandatory true;
                description
                  "Indicates that only VXLAN packets are captured.";
              }
              leaf vni-id {
                type uint32 {
                  range "1..16777215";
                }
                description
                  "VXLAN network identifier value.";
              }
              leaf tag-format {
                type ncs_rpc_notif_tag-format;
                description
                  "Tag format for vxlan packet.";
              }
            }
          }
          choice acl {
            description
              "Configure the acl for packet obtain.";
            case acl {
              description
                "IPv4 acl.";
              leaf acl-name {
                type string;
                description
                  "Acl number or name.";
              }
            }
            case acl6 {
              description
                "IPv6 acl.";
              leaf acl6-name {
                type string;
                description
                  "Acl number or name.";
              }
            }
          }
          leaf-list interface-name {
            type string;
            description
              "Interface name for packet obtain.";
          }
          leaf packet-number {
            type uint32 {
              range "1..5000";
            }
            default "100";
            description
              "Maximum number of packets to be captured.";
          }
          leaf packet-length {
            type uint16 {
              range "20..64";
            }
            units "Byte";
            default "64";
            description
              "Maximum packet length to be captured.";
          }
          leaf timeout {
            type uint32 {
              range "1..86400";
            }
            units "s";
            default "60";
            description
              "Timeout interval.";
          }
          leaf file-name {
            type string {
              length "5..64";
            }
            default "capture.cap";
            description
              "Name of the file for saving captured packets.";
          }
          leaf clear-payload {
            type boolean;
            default "false";
            description
              "Sets the data content of captured packets to 0. Only the data content of TCP and UDP packets can be set to 0.";
          }
          leaf direction {
            type ncs_rpc_notif_direction;
            description
              "Packet obtain direction.";
          }
          choice vlan-mode {
            description
              "VLAN for packet obtain.";
            case vlan {
              description
                "VLAN for packet obtain.";
              leaf vlan-begin {
                type vlan:ncs_rpc_notif_vlan-id;
                mandatory true;
                description
                  "Begin VLAN ID for packet obtain.";
              }
              leaf vlan-end {
                type vlan:ncs_rpc_notif_vlan-id;
                mandatory true;
                description
                  "End VLAN ID for packet obtain.";
              }
            }
            case pe-and-ce {
              description
                "Pe and Ce VLAN for packet obtain.";
              leaf pe-vlan {
                type vlan:ncs_rpc_notif_vlan-id;
                mandatory true;
                description
                  "Pe VLAN ID for packet obtain.";
              }
              leaf ce-vlan-begin {
                type vlan:ncs_rpc_notif_vlan-id;
                mandatory true;
                description
                  "Begin inner VLAN ID for packet obtain.";
              }
              leaf ce-vlan-end {
                type vlan:ncs_rpc_notif_vlan-id;
                mandatory true;
                description
                  "End inner VLAN ID for packet obtain.";
              }
            }
          }
          leaf file-size {
            type uint8;
            units "MB";
            default "2";
            description
              "File size.";
          }
          leaf buffer-only {
            type boolean;
            default "false";
            description
              "Type buffer only.";
          }
          leaf overwrite {
            type boolean;
            default "false";
            description
              "Overwrite the buffer.";
          }
        }
        output {
          container "device" {
            leaf "name" {
              type string;
            }
            leaf "info" {
              type string;
            }
            container "result" {
              leaf capture-index {
                type ncs_rpc_notif_capture-index;
                description
                  "Index of the packet obtain instance.";
              }
            }
          }
        }
      }
    }
  }
  augment "/ncs:devices/ncs:device/ncs:notifications/ncs:received-notifications/ncs:notification/ncs:data" {
    container capture-end-notification {
      presence "";
      config false;
      description
        "This notification is used to report the event of the end of captureing and get the captureing file from the device to controller.";
      leaf capture-index {
        type ncs_rpc_notif_capture-index;
        // NCS drop mandatory statement
        description
          "Index of the packet obtain instance.";
      }
      leaf esn {
        type string {
          length "1..256";
        }
        // NCS drop mandatory statement
        description
          "The device name.";
      }
      leaf file-name {
        type string {
          length "1..60";
        }
        // NCS drop mandatory statement
        description
          "Name of the file for saving captured packets.";
      }
      leaf type {
        type string {
          length "1..256";
        }
        description
          "File type.";
      }
      leaf result {
        type ncs_rpc_notif_result;
        default "success";
        description
          "Packet obtain result.";
      }
      leaf error-code {
        type uint32;
        description
          "Error code of the packet obtain result.";
      }
      leaf error-detail {
        type string {
          length "1..256";
        }
        description
          "Error details of the packet obtain result.";
      }
    }
  }
  augment "/ncs:devices/ncs:device/ncs:netconf-notifications/ncs:received-notifications/ncs:notification/ncs:data" {
    container capture-end-notification {
      presence "";
      config false;
      description
        "This notification is used to report the event of the end of captureing and get the captureing file from the device to controller.";
      leaf capture-index {
        type ncs_rpc_notif_capture-index;
        // NCS drop mandatory statement
        description
          "Index of the packet obtain instance.";
      }
      leaf esn {
        type string {
          length "1..256";
        }
        // NCS drop mandatory statement
        description
          "The device name.";
      }
      leaf file-name {
        type string {
          length "1..60";
        }
        // NCS drop mandatory statement
        description
          "Name of the file for saving captured packets.";
      }
      leaf type {
        type string {
          length "1..256";
        }
        description
          "File type.";
      }
      leaf result {
        type ncs_rpc_notif_result;
        default "success";
        description
          "Packet obtain result.";
      }
      leaf error-code {
        type uint32;
        description
          "Error code of the packet obtain result.";
      }
      leaf error-detail {
        type string {
          length "1..256";
        }
        description
          "Error details of the packet obtain result.";
      }
    }
  }
  augment "/ncs:devices/ncs:device/ncs:config" {
    container capture {
      tailf:ncs-device-type "netconf";
      tailf:display-when "not(../../ncs:module) or ../../ncs:module[ncs:name='huawei-capture']";
      description
        "Forwarding packet headers information.";
      // NCS drop config false container 'capture-instances'
    }
  }
  augment "/ncs:devices/ncs:device/ncs:live-status" {
    container capture {
      tailf:ncs-device-type "netconf";
      tailf:display-when "not(../../ncs:module) or ../../ncs:module[ncs:name='huawei-capture'] or (../../ncs:live-status-protocol[not(ncs:capability)]) or (../../ncs:live-status-protocol/ncs:capability/ncs:module[.='huawei-capture'])";
      description
        "Forwarding packet headers information.";
      container capture-instances {
        description
          "List of obtain packet headers instance.";
        list capture-instance {
          key "instance-id";
          description
            "Operational data of obtain packet headers instance.";
          leaf instance-id {
            type uint8 {
              range "1..8";
            }
            description
              "Instance ID.";
          }
          leaf inbound-instance {
            type uint32;
            description
              "Inbound instance.";
          }
          leaf outbound-instance {
            type uint32;
            description
              "Outbound instance.";
          }
          leaf total-instance {
            type uint32;
            description
              "Total instance statistic.";
          }
          leaf status {
            type live_ncs_packet-header-status;
            description
              "Obtain packet headers status.";
          }
          leaf timeout {
            type uint32 {
              range "1..86400";
            }
            units "s";
            description
              "Timeout.";
          }
          leaf record-packet-number {
            type uint32 {
              range "1..6000";
            }
            description
              "Record packet number.";
          }
          leaf total-memory-size {
            type uint32;
            units "MB";
            description
              "Record packet size.";
          }
          leaf obtain-packet-number {
            type uint32;
            description
              "Obtain packet number.";
          }
          leaf obtain-packet-size {
            type uint32;
            units "Byte";
            description
              "Obtain packet size.";
          }
          leaf saved-packet-number {
            type uint32;
            description
              "Saved packet number.";
          }
          leaf saved-packet-size {
            type uint32;
            units "Byte";
            description
              "Saved packet size.";
          }
          leaf delete-packet-number {
            type uint32;
            description
              "Delete packet number.";
          }
          leaf delete-packet-size {
            type uint32;
            units "Byte";
            description
              "Delete packet size.";
          }
          leaf first-packet-time {
            type yang:date-and-time;
            description
              "First packet time.";
          }
          leaf last-packet-time {
            type yang:date-and-time;
            description
              "Last packet time.";
          }
          leaf acl {
            type string {
              length "1..63";
            }
            description
              "Acl number or name.";
          }
          leaf memory-packet-number {
            type uint32;
            description
              "Memory packet number.";
          }
          leaf remain-time {
            type uint32 {
              range "1..86400";
            }
            units "s";
            description
              "Remain time.";
          }
          leaf remain-time-delete {
            type uint32 {
              range "1..86400";
            }
            units "s";
            description
              "Remain time.";
          }
          leaf packet-device-name {
            type string {
              length "5..64";
            }
            description
              "Packet device name.";
          }
          leaf file-name {
            type string {
              length "5..64";
            }
            description
              "File name.";
          }
          leaf file-length {
            type uint8;
            units "MB";
            // NCS drop default statement
            description
              "File length.";
          }
          leaf link-type {
            type live_ncs_packet-header-link-type;
            description
              "Link type.";
          }
          leaf interface-name {
            type leafref {
              path "/ncs:devices/ncs:device/ncs:live-status/ifm:ifm/ifm:interfaces/ifm:interface/ifm:name" {
                tailf:xpath-root 3;
              }
            }
            description
              "Interface name.";
          }
          leaf direction {
            type live_ncs_direction;
            description
              "Direction.";
          }
        }
      }
    }
  }
  augment "/ncs:devices/ncs:template/ncs:ned-id/ncs:config" {
    container capture {
      description
        "Forwarding packet headers information.";
      // NCS drop config false container 'capture-instances'
    }
  }
}
