module huawei-diagnostic-tools {
  // Generated by yanger -t ncs
  tailf:mount-id "huawei-nc-1.0:huawei-nc-1.0";
  tailf:ncs-device-type "netconf";

  yang-version 1;
  namespace "urn:huawei:yang:huawei-diagnostic-tools";
  prefix diagnostic-tools;

  import huawei-extension {
    prefix ext;
  }
  include huawei-diagnostic-tools-ipv4;
  include huawei-diagnostic-tools-ipv6;
  include huawei-diagnostic-tools-lsp;
  include huawei-diagnostic-tools-type;
  include huawei-diagnostic-tools-srv6;
  include huawei-diagnostic-tools-evpn;
  include huawei-diagnostic-tools-common;
  include huawei-diagnostic-tools-tcp;
  include huawei-diagnostic-tools-gmac;
  include huawei-diagnostic-tools-bier;
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Diagnosis tool.";

  revision 2020-09-10 {
    description
      "Add fast reply inbound node.";
    reference "Huawei private.";
  }
  revision 2020-08-24 {
    description
      "Modify BIER description.";
    reference "Huawei private.";
  }
  revision 2020-07-04 {
    description
      "Add BIER IPv6 Ping.";
    reference "Huawei private.";
  }
  revision 2020-01-14 {
    description
      "Modify of evpn.";
    reference "Huawei private.";
  }
  revision 2019-11-05 {
    description
      "Initial revision.";
    reference "Huawei private.";
  }
  ext:task-name "sla";
}
