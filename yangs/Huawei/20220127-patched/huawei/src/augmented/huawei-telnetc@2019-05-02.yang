module huawei-telnetc {
  // Generated by yanger -t ncs
  tailf:mount-id "huawei-nc-1.0:huawei-nc-1.0";
  tailf:ncs-device-type "netconf";

  namespace "urn:huawei:yang:huawei-telnetc";
  prefix telnetc;

  import huawei-pub-type {
    prefix pub-type;
  }
  import ietf-inet-types {
    prefix inet;
  }
  import huawei-extension {
    prefix ext;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Telnet client component.";

  revision 2019-05-02 {
    description
      "Initial revision.";
    reference "Huawei private.";
  }
  ext:task-name "telnet-client";

  augment "/ncs:devices/ncs:device/ncs:config" {
    container telnetc {
      tailf:ncs-device-type "netconf";
      tailf:display-when "not(../../ncs:module) or ../../ncs:module[ncs:name='huawei-telnetc']";
      description
        "Telnet client component.";
      container client {
        description
          "Configure Telnet client information.";
        leaf src-interface {
          type pub-type:if-name;
          description
            "Specify the source interface name. The specified source interface must exist and an IP address must be configured on the interface.";
        }
        leaf src-ipv4-addr {
          when 'not(../src-interface)' {
            tailf:xpath-root 3;
          }
          type inet:ipv4-address-no-zone;
          description
            "Source IPv4 address.";
        }
        leaf packet-dscp {
          type uint32 {
            range "0..63";
          }
          default "48";
          description
            "Config DSCP value.";
        }
        leaf src-ipv6-addr {
          type inet:ipv6-address-no-zone;
          description
            "Telnet source IPv6 address.";
        }
        leaf ipv6-vpn-instance-name {
          when '../src-ipv6-addr' {
            tailf:xpath-root 3;
          }
          type string {
            length "1..31";
          }
          description
            "The specified VPN instance must exist and IPv6-family must be enabled in the VPN instance.";
        }
      }
    }
  }
  augment "/ncs:devices/ncs:device/ncs:live-status" {
    container telnetc {
      tailf:ncs-device-type "netconf";
      tailf:display-when "not(../../ncs:module) or ../../ncs:module[ncs:name='huawei-telnetc'] or (../../ncs:live-status-protocol[not(ncs:capability)]) or (../../ncs:live-status-protocol/ncs:capability/ncs:module[.='huawei-telnetc'])";
      description
        "Telnet client component.";
      container client {
        description
          "Configure Telnet client information.";
        leaf src-interface {
          type pub-type:live_ncs_if-name;
          description
            "Specify the source interface name. The specified source interface must exist and an IP address must be configured on the interface.";
        }
        leaf src-ipv4-addr {
          // NCS drop when statement
          type inet:ipv4-address-no-zone;
          description
            "Source IPv4 address.";
        }
        leaf packet-dscp {
          type uint32 {
            range "0..63";
          }
          // NCS drop default statement
          description
            "Config DSCP value.";
        }
        leaf src-ipv6-addr {
          type inet:ipv6-address-no-zone;
          description
            "Telnet source IPv6 address.";
        }
        leaf ipv6-vpn-instance-name {
          // NCS drop when statement
          type string {
            length "1..31";
          }
          description
            "The specified VPN instance must exist and IPv6-family must be enabled in the VPN instance.";
        }
      }
    }
  }
  augment "/ncs:devices/ncs:template/ncs:ned-id/ncs:config" {
    container telnetc {
      description
        "Telnet client component.";
      container client {
        description
          "Configure Telnet client information.";
        leaf src-interface {
          type pub-type:ncs_template_if-name;
          description
            "Specify the source interface name. The specified source interface must exist and an IP address must be configured on the interface.";
        }
        leaf src-ipv4-addr {
          // NCS drop when statement
          type string;
          description
            "Source IPv4 address.";
        }
        leaf packet-dscp {
          type string;
          // NCS drop default statement
          description
            "Config DSCP value.";
        }
        leaf src-ipv6-addr {
          type string;
          description
            "Telnet source IPv6 address.";
        }
        leaf ipv6-vpn-instance-name {
          // NCS drop when statement
          type string;
          description
            "The specified VPN instance must exist and IPv6-family must be enabled in the VPN instance.";
        }
      }
    }
  }
}
