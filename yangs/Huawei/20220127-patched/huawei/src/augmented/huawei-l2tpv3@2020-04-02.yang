module huawei-l2tpv3 {
  // Generated by yanger -t ncs
  tailf:mount-id "huawei-nc-1.0:huawei-nc-1.0";
  tailf:ncs-device-type "netconf";

  namespace "urn:huawei:yang:huawei-l2tpv3";
  prefix l2tpv3;

  import huawei-ifm {
    prefix ifm;
  }
  import huawei-pub-type {
    prefix pub-type;
  }
  import ietf-inet-types {
    prefix inet;
  }
  import huawei-ip {
    prefix ip;
  }
  import huawei-extension {
    prefix ext;
  }
  import huawei-ethernet {
    prefix ethernet;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "L2TPv3.";

  revision 2020-04-02 {
    description
      "Modify the module of remote-cookie, local-cookie and local-secondary-cookie.";
    reference "Huawei private.";
  }
  revision 2020-03-13 {
    description
      "Modify description.";
    reference "Huawei private.";
  }
  revision 2019-11-06 {
    description
      "Initial revision.";
    reference "Huawei private.";
  }
  ext:task-name "l2tpv3";

  typedef ncs_template_cookie-length {
    type string;
    description
      "Cookie length.";
  }

  typedef ncs_template_instance-type {
    type string;
    description
      "Instance type.";
  }

  typedef ncs_template_pw-role-type {
    type string;
    description
      "PW role type.";
  }

  typedef ncs_template_state {
    type string;
    description
      "L2TPv3 state.";
  }

  typedef ncs_rpc_notif_cookie-length {
    type enumeration {
      enum "4-bytes" {
        value 4;
        description
          "4 bytes.";
      }
      enum "8-bytes" {
        value 8;
        description
          "8 bytes.";
      }
    }
    description
      "Cookie length.";
  }

  typedef ncs_rpc_notif_instance-type {
    type enumeration {
      enum "local-connect" {
        value 1;
        description
          "Local connect type.";
      }
      enum "normal" {
        value 2;
        description
          "Normal type.";
      }
    }
    description
      "Instance type.";
  }

  typedef ncs_rpc_notif_pw-role-type {
    type enumeration {
      enum "primary" {
        value 1;
        description
          "Primary tunnel.";
      }
      enum "injected" {
        value 2;
        description
          "Injected tunnel.";
      }
    }
    description
      "PW role type.";
  }

  typedef ncs_rpc_notif_state {
    type enumeration {
      enum "up" {
        value 1;
        description
          "Up state.";
      }
      enum "down" {
        value 2;
        description
          "Down state.";
      }
    }
    description
      "L2TPv3 state.";
  }

  typedef live_ncs_cookie-length {
    type enumeration {
      enum "4-bytes" {
        value 4;
        description
          "4 bytes.";
      }
      enum "8-bytes" {
        value 8;
        description
          "8 bytes.";
      }
    }
    description
      "Cookie length.";
  }

  typedef live_ncs_instance-type {
    type enumeration {
      enum "local-connect" {
        value 1;
        description
          "Local connect type.";
      }
      enum "normal" {
        value 2;
        description
          "Normal type.";
      }
    }
    description
      "Instance type.";
  }

  typedef live_ncs_pw-role-type {
    type enumeration {
      enum "primary" {
        value 1;
        description
          "Primary tunnel.";
      }
      enum "injected" {
        value 2;
        description
          "Injected tunnel.";
      }
    }
    description
      "PW role type.";
  }

  typedef live_ncs_state {
    type enumeration {
      enum "up" {
        value 1;
        description
          "Up state.";
      }
      enum "down" {
        value 2;
        description
          "Down state.";
      }
    }
    description
      "L2TPv3 state.";
  }

  typedef cookie-length {
    type enumeration {
      enum "4-bytes" {
        value 4;
        description
          "4 bytes.";
      }
      enum "8-bytes" {
        value 8;
        description
          "8 bytes.";
      }
    }
    description
      "Cookie length.";
  }

  typedef instance-type {
    type enumeration {
      enum "local-connect" {
        value 1;
        description
          "Local connect type.";
      }
      enum "normal" {
        value 2;
        description
          "Normal type.";
      }
    }
    description
      "Instance type.";
  }

  typedef pw-role-type {
    type enumeration {
      enum "primary" {
        value 1;
        description
          "Primary tunnel.";
      }
      enum "injected" {
        value 2;
        description
          "Injected tunnel.";
      }
    }
    description
      "PW role type.";
  }

  typedef state {
    type enumeration {
      enum "up" {
        value 1;
        description
          "Up state.";
      }
      enum "down" {
        value 2;
        description
          "Down state.";
      }
    }
    description
      "L2TPv3 state.";
  }

  augment "/ncs:devices/ncs:device/ncs:config" {
    container l2tpv3 {
      tailf:ncs-device-type "netconf";
      tailf:display-when "not(../../ncs:module) or ../../ncs:module[ncs:name='huawei-l2tpv3']";
      presence "Enable L2TPv3.";
      description
        "L2TPv3 configurations.";
      container pws {
        description
          "List of L2TPv3 tunnels.";
        list pw {
          key "name";
          unique "ip-type/ipv4/source-ip ip-type/ipv4/destination-ip local-session-id";
          unique "ip-type/ipv6/source-ipv6 ip-type/ipv6/destination-ipv6";
          description
            "Configure L2TPv3 tunnel.";
          leaf name {
            type string {
              length "1..19";
              pattern '[a-zA-Z]([^\s]*)';
            }
            description
              "Name of a tunnel.";
          }
          leaf source-interface {
            type leafref {
              path "/ncs:devices/ncs:device/ncs:config/ifm:ifm/ifm:interfaces/ifm:interface/ifm:name" {
                tailf:xpath-root 3;
              }
            }
            must '(../source-interface and (../source-ip or ../source-ipv6)) or (not (../source-interface) and not (../source-ip or ../source-ipv6))' {
              tailf:xpath-root 3;
            }
            description
              "Source interface name. The interface must be a physical interface or loopback interface.";
          }
          choice ip-type {
            description
              "Source and destination configuration.";
            case ipv4 {
              description
                "IPv4 type.";
              leaf source-ip {
                when '../source-interface' {
                  tailf:xpath-root 3;
                }
                type leafref {
                  path "/ncs:devices/ncs:device/ncs:config/ifm:ifm/ifm:interfaces/ifm:interface[ifm:name=current()/../source-interface]/ip:ipv4/ip:addresses/ip:address/ip:ip" {
                    tailf:xpath-root 3;
                  }
                }
                mandatory true;
                description
                  "Source IP address of tunnel.";
              }
              leaf destination-ip {
                type inet:ipv4-address-no-zone;
                description
                  "Destination IP address of tunnel.";
              }
            }
            case ipv6 {
              description
                "IPv6 type.";
              leaf source-ipv6 {
                when '../source-interface' {
                  tailf:xpath-root 3;
                }
                type inet:ipv6-address-no-zone;
                mandatory true;
                description
                  "Source IPv6 address of tunnel. If the source inferface is a physical interface, the source IPv6 address references the IPv6 address of the physical interface. If the source inferface is a loopback interface, the source IPv6 address must be on the same network segment as the IPv6 address of the loopback interface.";
              }
              leaf destination-ipv6 {
                type inet:ipv6-address-no-zone;
                description
                  "Destination IPv6 address of tunnel.";
              }
            }
          }
          leaf local-session-id {
            type uint32 {
              range "1..4294967295";
            }
            default "4294967295";
            description
              "Local session ID.";
          }
          leaf remote-session-id {
            type uint32 {
              range "1..4294967295";
            }
            default "4294967295";
            description
              "Remote session ID.";
          }
          choice local-cookie {
            description
              "The local cookie.";
            case cipher {
              description
                "Local ciphertext cookie.";
              leaf local-cookie-cipher {
                type pub-type:password {
                  length "1..108";
                }
                description
                  "The value of the local ciphertext cookie. The ciphertext cookie is a string ranging from 1 to 8 characters for a unencrypted password and 48 or 108 characters for a encrypted password.";
              }
            }
            case plain {
              description
                "Local plaintext cookie.";
              leaf local-cookie-length {
                type cookie-length;
                description
                  "The length of the local cookie.";
              }
              leaf local-cookie-low {
                when '../local-cookie-length' {
                  tailf:xpath-root 3;
                }
                type pub-type:hex-binary {
                  pattern '(0x)[0-9a-f]+';
                }
                mandatory true;
                description
                  "The value of the lower 4 bytes of the local cookie.";
              }
              leaf local-cookie-high {
                when "../local-cookie-length='8-bytes'" {
                  tailf:xpath-root 3;
                }
                type pub-type:hex-binary {
                  pattern '(0x)[0-9a-f]+';
                }
                mandatory true;
                description
                  "The value of the upper 4 bytes of the local cookie.";
              }
            }
          }
          choice local-secondary-cookie {
            description
              "The local secondary cookie.";
            case cipher {
              description
                "Local secondary ciphertext cookie.";
              leaf local-secondary-cookie-cipher {
                when '../local-cookie-cipher or ../local-cookie-length' {
                  tailf:xpath-root 3;
                }
                type pub-type:password {
                  length "1..108";
                }
                description
                  "The value of the local secondary ciphertext cookie. The ciphertext cookie is a string ranging from 1 to 8 characters for a unencrypted password and 48 or 108 characters for a encrypted password.";
              }
            }
            case plain {
              description
                "Local secondary plaintext cookie.";
              leaf local-secondary-cookie-length {
                when '../local-cookie-cipher or ../local-cookie-length' {
                  tailf:xpath-root 3;
                }
                type cookie-length;
                description
                  "The length of the local secondary cookie.";
              }
              leaf local-secondary-cookie-low {
                when '../local-secondary-cookie-length' {
                  tailf:xpath-root 3;
                }
                type pub-type:hex-binary {
                  pattern '(0x)[0-9a-f]+';
                }
                mandatory true;
                description
                  "The value of the lower 4 bytes of the local secondary cookie.";
              }
              leaf local-secondary-cookie-high {
                when "../local-secondary-cookie-length='8-bytes'" {
                  tailf:xpath-root 3;
                }
                type pub-type:hex-binary {
                  pattern '(0x)[0-9a-f]+';
                }
                mandatory true;
                description
                  "The value of the upper 4 bytes of the local secondary cookie.";
              }
            }
          }
          choice remote-cookie {
            description
              "The remote cookie.";
            case cipher {
              description
                "Remote ciphertext cookie.";
              leaf remote-cookie-cipher {
                type pub-type:password {
                  length "1..108";
                }
                description
                  "The value of the remote ciphertext cookie. The ciphertext cookie is a string ranging from 1 to 8 characters for a unencrypted password and 48 or 108 characters for a encrypted password.";
              }
            }
            case plain {
              description
                "Remote plaintext cookie.";
              leaf remote-cookie-length {
                type cookie-length;
                description
                  "The length of the remote cookie.";
              }
              leaf remote-cookie-low {
                when '../remote-cookie-length' {
                  tailf:xpath-root 3;
                }
                type pub-type:hex-binary {
                  pattern '(0x)[0-9a-f]+';
                }
                mandatory true;
                description
                  "The value of the lower 4 bytes of the remote cookie.";
              }
              leaf remote-cookie-high {
                when "../remote-cookie-length='8-bytes'" {
                  tailf:xpath-root 3;
                }
                type pub-type:hex-binary {
                  pattern '(0x)[0-9a-f]+';
                }
                mandatory true;
                description
                  "The value of the upper 4 bytes of the remote cookie.";
              }
            }
          }
        }
      }
      container instances {
        description
          "List of L2TPv3 instances.";
        list instance {
          key "name type";
          unique "interface-name";
          unique "out-interface-name";
          description
            "Configure L2TPv3 instance.";
          leaf name {
            type string {
              length "1..31";
              pattern '[a-zA-Z]([^\s]*)';
            }
            description
              "Instance name.";
          }
          leaf type {
            type instance-type;
            description
              "Instance type.";
          }
          leaf interface-name {
            type leafref {
              path "/ncs:devices/ncs:device/ncs:config/ifm:ifm/ifm:interfaces/ifm:interface/ifm:name" {
                tailf:xpath-root 3;
              }
            }
            must "(/ifm:ifm/ifm:interfaces/ifm:interface[ifm:name=current()]/ethernet:ethernet/ethernet:l2-sub-interface/ethernet:default or (/ifm:ifm/ifm:interfaces/ifm:interface[ifm:name=current()]/ethernet:ethernet/ethernet:l2-sub-interface/ethernet:dot1q/ethernet:vlans/ethernet:vlan-list and /ifm:ifm/ifm:interfaces/ifm:interface[ifm:name=current()]/ethernet:ethernet/ethernet:l2-sub-interface/ethernet:flow-action/ethernet:action-type='pop-outer') or (/ifm:ifm/ifm:interfaces/ifm:interface[ifm:name=current()]/ethernet:ethernet/ethernet:l2-sub-interface/ethernet:qinqs/ethernet:qinq-vids/ethernet:qinq-vid/ethernet:ce-vlan-list and /ifm:ifm/ifm:interfaces/ifm:interface[ifm:name=current()]/ethernet:ethernet/ethernet:l2-sub-interface/ethernet:flow-action/ethernet:action-type='pop-double')) or (../l2tpv3:type = 'normal' and /ifm:ifm/ifm:interfaces/ifm:interface[ifm:name = current()]/ifm:class = 'sub-interface' and /ifm:ifm/ifm:interfaces/ifm:interface[ifm:name = current()]/ifm:l2-mode-enable = 'false')" {
              tailf:xpath-root 3;
            }
            mandatory true;
            description
              "Name of a sub-interface.";
          }
          leaf out-interface-name {
            when "../type='local-connect'" {
              tailf:xpath-root 3;
            }
            type leafref {
              path "/ncs:devices/ncs:device/ncs:config/ifm:ifm/ifm:interfaces/ifm:interface/ifm:name" {
                tailf:xpath-root 3;
              }
            }
            must "/ifm:ifm/ifm:interfaces/ifm:interface[ifm:name=current()]/ethernet:ethernet/ethernet:l2-sub-interface/ethernet:default or (/ifm:ifm/ifm:interfaces/ifm:interface[ifm:name=current()]/ethernet:ethernet/ethernet:l2-sub-interface/ethernet:dot1q/ethernet:vlans/ethernet:vlan-list and /ifm:ifm/ifm:interfaces/ifm:interface[ifm:name=current()]/ethernet:ethernet/ethernet:l2-sub-interface/ethernet:flow-action/ethernet:action-type='pop-outer') or (/ifm:ifm/ifm:interfaces/ifm:interface[ifm:name=current()]/ethernet:ethernet/ethernet:l2-sub-interface/ethernet:qinqs/ethernet:qinq-vids/ethernet:qinq-vid/ethernet:ce-vlan-list and /ifm:ifm/ifm:interfaces/ifm:interface[ifm:name=current()]/ethernet:ethernet/ethernet:l2-sub-interface/ethernet:flow-action/ethernet:action-type='pop-double')" {
              tailf:xpath-root 3;
            }
            mandatory true;
            description
              "Name of a sub-interface.";
          }
          container pws {
            when "../type='normal'" {
              tailf:xpath-root 3;
            }
            description
              "List of L2TPv3 tunnel informations.";
            list pw {
              must '(../../../../pws/pw/source-interface and (../../../../pws/pw/destination-ip or ../../../../pws/pw/destination-ipv6))' {
                tailf:xpath-root 3;
              }
              key "name";
              unique "role";
              max-elements 2;
              description
                "Configure L2TPv3 tunnel information.";
              leaf name {
                type leafref {
                  path "../../../../../pws/pw/name";
                }
                must "(/ifm:ifm/ifm:interfaces/ifm:interface[ifm:name = current()/../../../l2tpv3:interface-name]/ethernet:ethernet/ethernet:l2-sub-interface/ethernet:default or (/ifm:ifm/ifm:interfaces/ifm:interface[ifm:name = current()/../../../l2tpv3:interface-name]/ethernet:ethernet/ethernet:l2-sub-interface/ethernet:dot1q/ethernet:vlans/ethernet:vlan-list and /ifm:ifm/ifm:interfaces/ifm:interface[ifm:name = current()/../../../l2tpv3:interface-name]/ethernet:ethernet/ethernet:l2-sub-interface/ethernet:flow-action/ethernet:action-type='pop-outer') or (/ifm:ifm/ifm:interfaces/ifm:interface[ifm:name = current()/../../../l2tpv3:interface-name]/ethernet:ethernet/ethernet:l2-sub-interface/ethernet:qinqs/ethernet:qinq-vids/ethernet:qinq-vid/ethernet:ce-vlan-list and /ifm:ifm/ifm:interfaces/ifm:interface[ifm:name = current()/../../../l2tpv3:interface-name]/ethernet:ethernet/ethernet:l2-sub-interface/ethernet:flow-action/ethernet:action-type='pop-double')) or (/ifm:ifm/ifm:interfaces/ifm:interface[ifm:name = current()/../../../l2tpv3:interface-name]/ethernet:ethernet/ethernet:l3-sub-interface/ethernet:qinq-termination/ethernet:symmetry-mode/ethernet:symmetry-type = 'asymmetry' and count(/ifm:ifm/ifm:interfaces/ifm:interface[ifm:name = current()/../../../l2tpv3:interface-name]/ethernet:ethernet/ethernet:l3-sub-interface/ethernet:qinq-termination/ethernet:qinq-vids/ethernet:qinq-vid) = 1) or (/ifm:ifm/ifm:interfaces/ifm:interface[ifm:name = current()/../../../l2tpv3:interface-name]/ethernet:ethernet/ethernet:l3-sub-interface/ethernet:vlan-type-dot1q/ethernet:vlan-type-vid)" {
                  tailf:xpath-root 3;
                }
                description
                  "Name of a tunnel.";
              }
              leaf role {
                ext:operation-exclude "update";
                type pw-role-type;
                mandatory true;
                description
                  "Whether the tunnel is a primary or injected tunnel.";
              }
            }
          }
        }
      }
    }
  }
  augment "/ncs:devices/ncs:device/ncs:live-status" {
    container l2tpv3 {
      tailf:ncs-device-type "netconf";
      tailf:display-when "not(../../ncs:module) or ../../ncs:module[ncs:name='huawei-l2tpv3'] or (../../ncs:live-status-protocol[not(ncs:capability)]) or (../../ncs:live-status-protocol/ncs:capability/ncs:module[.='huawei-l2tpv3'])";
      presence "Enable L2TPv3.";
      description
        "L2TPv3 configurations.";
      container pws {
        description
          "List of L2TPv3 tunnels.";
        list pw {
          key "name";
          unique "ip-type/ipv4/source-ip ip-type/ipv4/destination-ip local-session-id";
          unique "ip-type/ipv6/source-ipv6 ip-type/ipv6/destination-ipv6";
          description
            "Configure L2TPv3 tunnel.";
          leaf name {
            type string {
              length "1..19";
              pattern '[a-zA-Z]([^\s]*)';
            }
            description
              "Name of a tunnel.";
          }
          leaf source-interface {
            type leafref {
              path "/ncs:devices/ncs:device/ncs:live-status/ifm:ifm/ifm:interfaces/ifm:interface/ifm:name" {
                tailf:xpath-root 3;
              }
            }
            // NCS drop must statement
            description
              "Source interface name. The interface must be a physical interface or loopback interface.";
          }
          choice ip-type {
            description
              "Source and destination configuration.";
            case ipv4 {
              description
                "IPv4 type.";
              leaf source-ip {
                // NCS drop when statement
                type leafref {
                  path "/ncs:devices/ncs:device/ncs:live-status/ifm:ifm/ifm:interfaces/ifm:interface[ifm:name=current()/../source-interface]/ip:ipv4/ip:addresses/ip:address/ip:ip" {
                    tailf:xpath-root 3;
                  }
                }
                // NCS drop mandatory statement
                description
                  "Source IP address of tunnel.";
              }
              leaf destination-ip {
                type inet:ipv4-address-no-zone;
                description
                  "Destination IP address of tunnel.";
              }
            }
            case ipv6 {
              description
                "IPv6 type.";
              leaf source-ipv6 {
                // NCS drop when statement
                type inet:ipv6-address-no-zone;
                // NCS drop mandatory statement
                description
                  "Source IPv6 address of tunnel. If the source inferface is a physical interface, the source IPv6 address references the IPv6 address of the physical interface. If the source inferface is a loopback interface, the source IPv6 address must be on the same network segment as the IPv6 address of the loopback interface.";
              }
              leaf destination-ipv6 {
                type inet:ipv6-address-no-zone;
                description
                  "Destination IPv6 address of tunnel.";
              }
            }
          }
          leaf local-session-id {
            type uint32 {
              range "1..4294967295";
            }
            // NCS drop default statement
            description
              "Local session ID.";
          }
          leaf remote-session-id {
            type uint32 {
              range "1..4294967295";
            }
            // NCS drop default statement
            description
              "Remote session ID.";
          }
          choice local-cookie {
            description
              "The local cookie.";
            case cipher {
              description
                "Local ciphertext cookie.";
              leaf local-cookie-cipher {
                type pub-type:live_ncs_password;
                description
                  "The value of the local ciphertext cookie. The ciphertext cookie is a string ranging from 1 to 8 characters for a unencrypted password and 48 or 108 characters for a encrypted password.";
              }
            }
            case plain {
              description
                "Local plaintext cookie.";
              leaf local-cookie-length {
                type live_ncs_cookie-length;
                description
                  "The length of the local cookie.";
              }
              leaf local-cookie-low {
                // NCS drop when statement
                type pub-type:live_ncs_hex-binary;
                // NCS drop mandatory statement
                description
                  "The value of the lower 4 bytes of the local cookie.";
              }
              leaf local-cookie-high {
                // NCS drop when statement
                type pub-type:live_ncs_hex-binary;
                // NCS drop mandatory statement
                description
                  "The value of the upper 4 bytes of the local cookie.";
              }
            }
          }
          choice local-secondary-cookie {
            description
              "The local secondary cookie.";
            case cipher {
              description
                "Local secondary ciphertext cookie.";
              leaf local-secondary-cookie-cipher {
                // NCS drop when statement
                type pub-type:live_ncs_password;
                description
                  "The value of the local secondary ciphertext cookie. The ciphertext cookie is a string ranging from 1 to 8 characters for a unencrypted password and 48 or 108 characters for a encrypted password.";
              }
            }
            case plain {
              description
                "Local secondary plaintext cookie.";
              leaf local-secondary-cookie-length {
                // NCS drop when statement
                type live_ncs_cookie-length;
                description
                  "The length of the local secondary cookie.";
              }
              leaf local-secondary-cookie-low {
                // NCS drop when statement
                type pub-type:live_ncs_hex-binary;
                // NCS drop mandatory statement
                description
                  "The value of the lower 4 bytes of the local secondary cookie.";
              }
              leaf local-secondary-cookie-high {
                // NCS drop when statement
                type pub-type:live_ncs_hex-binary;
                // NCS drop mandatory statement
                description
                  "The value of the upper 4 bytes of the local secondary cookie.";
              }
            }
          }
          choice remote-cookie {
            description
              "The remote cookie.";
            case cipher {
              description
                "Remote ciphertext cookie.";
              leaf remote-cookie-cipher {
                type pub-type:live_ncs_password;
                description
                  "The value of the remote ciphertext cookie. The ciphertext cookie is a string ranging from 1 to 8 characters for a unencrypted password and 48 or 108 characters for a encrypted password.";
              }
            }
            case plain {
              description
                "Remote plaintext cookie.";
              leaf remote-cookie-length {
                type live_ncs_cookie-length;
                description
                  "The length of the remote cookie.";
              }
              leaf remote-cookie-low {
                // NCS drop when statement
                type pub-type:live_ncs_hex-binary;
                // NCS drop mandatory statement
                description
                  "The value of the lower 4 bytes of the remote cookie.";
              }
              leaf remote-cookie-high {
                // NCS drop when statement
                type pub-type:live_ncs_hex-binary;
                // NCS drop mandatory statement
                description
                  "The value of the upper 4 bytes of the remote cookie.";
              }
            }
          }
        }
      }
      container instances {
        description
          "List of L2TPv3 instances.";
        list instance {
          key "name type";
          unique "interface-name";
          unique "out-interface-name";
          description
            "Configure L2TPv3 instance.";
          leaf name {
            type string {
              length "1..31";
              pattern '[a-zA-Z]([^\s]*)';
            }
            description
              "Instance name.";
          }
          leaf type {
            type live_ncs_instance-type;
            description
              "Instance type.";
          }
          leaf interface-name {
            type leafref {
              path "/ncs:devices/ncs:device/ncs:live-status/ifm:ifm/ifm:interfaces/ifm:interface/ifm:name" {
                tailf:xpath-root 3;
              }
            }
            // NCS drop must statement
            // NCS drop mandatory statement
            description
              "Name of a sub-interface.";
          }
          leaf out-interface-name {
            // NCS drop when statement
            type leafref {
              path "/ncs:devices/ncs:device/ncs:live-status/ifm:ifm/ifm:interfaces/ifm:interface/ifm:name" {
                tailf:xpath-root 3;
              }
            }
            // NCS drop must statement
            // NCS drop mandatory statement
            description
              "Name of a sub-interface.";
          }
          container pws {
            // NCS drop when statement
            description
              "List of L2TPv3 tunnel informations.";
            list pw {
              // NCS drop must statement
              key "name";
              unique "role";
              // NCS drop max-elements statement
              description
                "Configure L2TPv3 tunnel information.";
              leaf name {
                type leafref {
                  path "../../../../../pws/pw/name";
                }
                // NCS drop must statement
                description
                  "Name of a tunnel.";
              }
              leaf role {
                ext:operation-exclude "update";
                type live_ncs_pw-role-type;
                // NCS drop mandatory statement
                description
                  "Whether the tunnel is a primary or injected tunnel.";
              }
            }
          }
        }
      }
    }
  }
  augment "/ncs:devices/ncs:template/ncs:ned-id/ncs:config" {
    container l2tpv3 {
      presence "Enable L2TPv3.";
      description
        "L2TPv3 configurations.";
      container pws {
        description
          "List of L2TPv3 tunnels.";
        list pw {
          // NCS patched for predictable order
          ordered-by user;
          key "name";
          unique "ip-type/ipv4/source-ip ip-type/ipv4/destination-ip local-session-id";
          unique "ip-type/ipv6/source-ipv6 ip-type/ipv6/destination-ipv6";
          description
            "Configure L2TPv3 tunnel.";
          leaf name {
            type string;
            description
              "Name of a tunnel.";
          }
          leaf source-interface {
            type string;
            // NCS drop must statement
            description
              "Source interface name. The interface must be a physical interface or loopback interface.";
          }
          choice ip-type {
            description
              "Source and destination configuration.";
            case ipv4 {
              description
                "IPv4 type.";
              leaf source-ip {
                // NCS drop when statement
                type string;
                // NCS drop mandatory statement
                description
                  "Source IP address of tunnel.";
              }
              leaf destination-ip {
                type string;
                description
                  "Destination IP address of tunnel.";
              }
            }
            case ipv6 {
              description
                "IPv6 type.";
              leaf source-ipv6 {
                // NCS drop when statement
                type string;
                // NCS drop mandatory statement
                description
                  "Source IPv6 address of tunnel. If the source inferface is a physical interface, the source IPv6 address references the IPv6 address of the physical interface. If the source inferface is a loopback interface, the source IPv6 address must be on the same network segment as the IPv6 address of the loopback interface.";
              }
              leaf destination-ipv6 {
                type string;
                description
                  "Destination IPv6 address of tunnel.";
              }
            }
          }
          leaf local-session-id {
            type string;
            // NCS drop default statement
            description
              "Local session ID.";
          }
          leaf remote-session-id {
            type string;
            // NCS drop default statement
            description
              "Remote session ID.";
          }
          choice local-cookie {
            description
              "The local cookie.";
            case cipher {
              description
                "Local ciphertext cookie.";
              leaf local-cookie-cipher {
                type pub-type:ncs_template_password;
                description
                  "The value of the local ciphertext cookie. The ciphertext cookie is a string ranging from 1 to 8 characters for a unencrypted password and 48 or 108 characters for a encrypted password.";
              }
            }
            case plain {
              description
                "Local plaintext cookie.";
              leaf local-cookie-length {
                type ncs_template_cookie-length;
                description
                  "The length of the local cookie.";
              }
              leaf local-cookie-low {
                // NCS drop when statement
                type pub-type:ncs_template_hex-binary;
                // NCS drop mandatory statement
                description
                  "The value of the lower 4 bytes of the local cookie.";
              }
              leaf local-cookie-high {
                // NCS drop when statement
                type pub-type:ncs_template_hex-binary;
                // NCS drop mandatory statement
                description
                  "The value of the upper 4 bytes of the local cookie.";
              }
            }
          }
          choice local-secondary-cookie {
            description
              "The local secondary cookie.";
            case cipher {
              description
                "Local secondary ciphertext cookie.";
              leaf local-secondary-cookie-cipher {
                // NCS drop when statement
                type pub-type:ncs_template_password;
                description
                  "The value of the local secondary ciphertext cookie. The ciphertext cookie is a string ranging from 1 to 8 characters for a unencrypted password and 48 or 108 characters for a encrypted password.";
              }
            }
            case plain {
              description
                "Local secondary plaintext cookie.";
              leaf local-secondary-cookie-length {
                // NCS drop when statement
                type ncs_template_cookie-length;
                description
                  "The length of the local secondary cookie.";
              }
              leaf local-secondary-cookie-low {
                // NCS drop when statement
                type pub-type:ncs_template_hex-binary;
                // NCS drop mandatory statement
                description
                  "The value of the lower 4 bytes of the local secondary cookie.";
              }
              leaf local-secondary-cookie-high {
                // NCS drop when statement
                type pub-type:ncs_template_hex-binary;
                // NCS drop mandatory statement
                description
                  "The value of the upper 4 bytes of the local secondary cookie.";
              }
            }
          }
          choice remote-cookie {
            description
              "The remote cookie.";
            case cipher {
              description
                "Remote ciphertext cookie.";
              leaf remote-cookie-cipher {
                type pub-type:ncs_template_password;
                description
                  "The value of the remote ciphertext cookie. The ciphertext cookie is a string ranging from 1 to 8 characters for a unencrypted password and 48 or 108 characters for a encrypted password.";
              }
            }
            case plain {
              description
                "Remote plaintext cookie.";
              leaf remote-cookie-length {
                type ncs_template_cookie-length;
                description
                  "The length of the remote cookie.";
              }
              leaf remote-cookie-low {
                // NCS drop when statement
                type pub-type:ncs_template_hex-binary;
                // NCS drop mandatory statement
                description
                  "The value of the lower 4 bytes of the remote cookie.";
              }
              leaf remote-cookie-high {
                // NCS drop when statement
                type pub-type:ncs_template_hex-binary;
                // NCS drop mandatory statement
                description
                  "The value of the upper 4 bytes of the remote cookie.";
              }
            }
          }
        }
      }
      container instances {
        description
          "List of L2TPv3 instances.";
        list instance {
          // NCS patched for predictable order
          ordered-by user;
          key "name type";
          unique "interface-name";
          unique "out-interface-name";
          description
            "Configure L2TPv3 instance.";
          leaf name {
            type string;
            description
              "Instance name.";
          }
          leaf type {
            type ncs_template_instance-type;
            description
              "Instance type.";
          }
          leaf interface-name {
            type string;
            // NCS drop must statement
            // NCS drop mandatory statement
            description
              "Name of a sub-interface.";
          }
          leaf out-interface-name {
            // NCS drop when statement
            type string;
            // NCS drop must statement
            // NCS drop mandatory statement
            description
              "Name of a sub-interface.";
          }
          container pws {
            // NCS drop when statement
            description
              "List of L2TPv3 tunnel informations.";
            list pw {
              // NCS patched for predictable order
              ordered-by user;
              // NCS drop must statement
              key "name";
              unique "role";
              // NCS drop max-elements statement
              description
                "Configure L2TPv3 tunnel information.";
              leaf name {
                type string;
                // NCS drop must statement
                description
                  "Name of a tunnel.";
              }
              leaf role {
                ext:operation-exclude "update";
                type ncs_template_pw-role-type;
                // NCS drop mandatory statement
                description
                  "Whether the tunnel is a primary or injected tunnel.";
              }
            }
          }
        }
      }
    }
  }
}
