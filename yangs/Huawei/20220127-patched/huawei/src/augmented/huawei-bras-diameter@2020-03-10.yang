module huawei-bras-diameter {
  // Generated by yanger -t ncs
  tailf:mount-id "huawei-nc-1.0:huawei-nc-1.0";
  tailf:ncs-device-type "netconf";

  namespace "urn:huawei:yang:huawei-bras-diameter";
  prefix bras-diameter;

  import huawei-extension {
    prefix ext;
  }
  ext:task-name "diameter";

  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Diameter.";

  revision 2020-03-10 {
    description
      "Modify description.";
    reference "Huawei private.";
  }
  revision 2019-03-23 {
    description
      "Init revision.";
    reference "Huawei private.";
  }

  augment "/ncs:devices/ncs:device/ncs:config" {
    container bras-diameter {
      tailf:ncs-device-type "netconf";
      tailf:display-when "not(../../ncs:module) or ../../ncs:module[ncs:name='huawei-bras-diameter']";
      description
        "Diameter.";
      container diameter {
        presence "Enables the Diameter protocol.";
        description
          "Configure the Diameter protocol.";
      }
    }
  }
  augment "/ncs:devices/ncs:device/ncs:live-status" {
    container bras-diameter {
      tailf:ncs-device-type "netconf";
      tailf:display-when "not(../../ncs:module) or ../../ncs:module[ncs:name='huawei-bras-diameter'] or (../../ncs:live-status-protocol[not(ncs:capability)]) or (../../ncs:live-status-protocol/ncs:capability/ncs:module[.='huawei-bras-diameter'])";
      description
        "Diameter.";
      container diameter {
        presence "Enables the Diameter protocol.";
        description
          "Configure the Diameter protocol.";
      }
    }
  }
  augment "/ncs:devices/ncs:template/ncs:ned-id/ncs:config" {
    container bras-diameter {
      description
        "Diameter.";
      container diameter {
        presence "Enables the Diameter protocol.";
        description
          "Configure the Diameter protocol.";
      }
    }
  }
}
