module huawei-ifit-common {
  // Generated by yanger -t ncs
  tailf:mount-id "huawei-nc-1.0:huawei-nc-1.0";
  tailf:ncs-device-type "netconf";

  yang-version 1;
  namespace "urn:huawei:yang:huawei-ifit-common";
  prefix ifit-common;

  import huawei-ifit {
    prefix ifit;
  }
  import huawei-extension {
    prefix ext;
  }
  import ietf-inet-types {
    prefix inet;
  }
  import huawei-ifm {
    prefix ifm;
  }
  import huawei-network-instance {
    prefix ni;
  }
  import huawei-l3vpn {
    prefix l3vpn;
  }
  import huawei-evpl {
    prefix evpl;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "This module contains a collection of YANG definitions IFIT feature.";

  revision 2020-04-08 {
    description
      "Initial revision.";
    reference "Huawei private.";
  }
  ext:task-name "ifit";

  typedef ncs_template_flow-type {
    type string;
    description
      "Flow type.";
  }

  typedef ncs_template_measure-mode {
    type string;
    description
      "Measure mode.";
  }

  typedef ncs_template_addr-type {
    type string;
    description
      "Address type.";
  }

  typedef ncs_template_flow-direction {
    type string;
    description
      "Flow direction.";
  }

  typedef ncs_template_addr-family-type {
    type string;
    description
      "Address family.";
  }

  typedef ncs_rpc_notif_flow-type {
    type enumeration {
      enum "unidirection" {
        value 2;
        description
          "An unidirection IFIT flow.";
      }
      enum "bidirection" {
        value 1;
        description
          "A bidirection IFIT flow.";
      }
    }
    description
      "Flow type.";
  }

  typedef ncs_rpc_notif_measure-mode {
    type enumeration {
      enum "e2e" {
        value 1;
        description
          "E2E measure mode.";
      }
      enum "trace" {
        value 2;
        description
          "Trace measure mode.";
      }
    }
    description
      "Measure mode.";
  }

  typedef ncs_rpc_notif_addr-type {
    type enumeration {
      enum "ipv4" {
        value 0;
        description
          "IPv4 address.";
      }
      enum "ipv6" {
        value 1;
        description
          "IPv6 address.";
      }
    }
    description
      "Address type.";
  }

  typedef ncs_rpc_notif_flow-direction {
    type enumeration {
      enum "ingress" {
        value 1;
        description
          "Ingress of an IFIT flow.";
      }
      enum "transit-input" {
        value 2;
        description
          "Transit input of an IFIT flow.";
      }
      enum "transit-output" {
        value 3;
        description
          "Transit output of an IFIT flow.";
      }
      enum "egress" {
        value 4;
        description
          "Egress of an IFIT flow.";
      }
    }
    description
      "Flow direction.";
  }

  typedef ncs_rpc_notif_addr-family-type {
    type enumeration {
      enum "ipv4-unicast" {
        value 1;
        description
          "IPv4 unicast.";
      }
      enum "ipv6-unicast" {
        value 2;
        description
          "IPv6 unicast.";
      }
    }
    description
      "Address family.";
  }

  typedef live_ncs_flow-type {
    type enumeration {
      enum "unidirection" {
        value 2;
        description
          "An unidirection IFIT flow.";
      }
      enum "bidirection" {
        value 1;
        description
          "A bidirection IFIT flow.";
      }
    }
    description
      "Flow type.";
  }

  typedef live_ncs_measure-mode {
    type enumeration {
      enum "e2e" {
        value 1;
        description
          "E2E measure mode.";
      }
      enum "trace" {
        value 2;
        description
          "Trace measure mode.";
      }
    }
    description
      "Measure mode.";
  }

  typedef live_ncs_addr-type {
    type enumeration {
      enum "ipv4" {
        value 0;
        description
          "IPv4 address.";
      }
      enum "ipv6" {
        value 1;
        description
          "IPv6 address.";
      }
    }
    description
      "Address type.";
  }

  typedef live_ncs_flow-direction {
    type enumeration {
      enum "ingress" {
        value 1;
        description
          "Ingress of an IFIT flow.";
      }
      enum "transit-input" {
        value 2;
        description
          "Transit input of an IFIT flow.";
      }
      enum "transit-output" {
        value 3;
        description
          "Transit output of an IFIT flow.";
      }
      enum "egress" {
        value 4;
        description
          "Egress of an IFIT flow.";
      }
    }
    description
      "Flow direction.";
  }

  typedef live_ncs_addr-family-type {
    type enumeration {
      enum "ipv4-unicast" {
        value 1;
        description
          "IPv4 unicast.";
      }
      enum "ipv6-unicast" {
        value 2;
        description
          "IPv6 unicast.";
      }
    }
    description
      "Address family.";
  }

  typedef flow-type {
    type enumeration {
      enum "unidirection" {
        value 2;
        description
          "An unidirection IFIT flow.";
      }
      enum "bidirection" {
        value 1;
        description
          "A bidirection IFIT flow.";
      }
    }
    description
      "Flow type.";
  }

  typedef measure-mode {
    type enumeration {
      enum "e2e" {
        value 1;
        description
          "E2E measure mode.";
      }
      enum "trace" {
        value 2;
        description
          "Trace measure mode.";
      }
    }
    description
      "Measure mode.";
  }

  typedef addr-type {
    type enumeration {
      enum "ipv4" {
        value 0;
        description
          "IPv4 address.";
      }
      enum "ipv6" {
        value 1;
        description
          "IPv6 address.";
      }
    }
    description
      "Address type.";
  }

  typedef flow-direction {
    type enumeration {
      enum "ingress" {
        value 1;
        description
          "Ingress of an IFIT flow.";
      }
      enum "transit-input" {
        value 2;
        description
          "Transit input of an IFIT flow.";
      }
      enum "transit-output" {
        value 3;
        description
          "Transit output of an IFIT flow.";
      }
      enum "egress" {
        value 4;
        description
          "Egress of an IFIT flow.";
      }
    }
    description
      "Flow direction.";
  }

  typedef addr-family-type {
    type enumeration {
      enum "ipv4-unicast" {
        value 1;
        description
          "IPv4 unicast.";
      }
      enum "ipv6-unicast" {
        value 2;
        description
          "IPv6 unicast.";
      }
    }
    description
      "Address family.";
  }

  augment "/ncs:devices/ncs:device/ncs:rpc" {
    container rpc-reset-dynamic-flow {
      tailf:ncs-device-type "netconf";
      tailf:display-when "not(../../ncs:module) or ../../ncs:module[ncs:name='huawei-ifit-common']";
      tailf:action reset-dynamic-flow {
        tailf:actionpoint ncsproxy {
          tailf:internal;
        }
        description
          "Clear specified dynamic flow.";
        ext:node-ref "/ifit:ifit/ifit-common:ifit-common/ifit-common:dynamic-flows/ifit-common:dynamic-flow";
        input {
          leaf address-type {
            type ifit-common:ncs_rpc_notif_addr-type;
            mandatory true;
            description
              "Address type of IFIT flow.";
          }
          leaf source-ip {
            type inet:ip-address-no-zone;
            description
              "Source IP address of an IFIT flow.";
          }
          leaf destination-ip {
            type inet:ip-address-no-zone;
            description
              "Destination IP address of an IFIT flow.";
          }
          leaf source-mask {
            when '../source-ip' {
              tailf:xpath-root 3;
            }
            type uint8 {
              range "1..128";
            }
            description
              "Source IP address mask of an IFIT flow.";
          }
          leaf destination-mask {
            when '../destination-ip' {
              tailf:xpath-root 3;
            }
            type uint8 {
              range "1..128";
            }
            description
              "Destination IP address mask of an IFIT flow.";
          }
          leaf protocol {
            type uint8 {
              range "0..254";
              ext:value-meaning {
                ext:item "6" {
                  ext:meaning "tcp";
                }
                ext:item "17" {
                  ext:meaning "udp";
                }
                ext:item "132" {
                  ext:meaning "sctp";
                }
              }
            }
            description
              "Protocol of an IFIT flow.";
          }
          leaf source-port {
            type uint16 {
              range "1..65535";
            }
            description
              "Source port of an IFIT flow.";
          }
          leaf destination-port {
            type uint16 {
              range "1..65535";
            }
            description
              "Destination port of an IFIT flow.";
          }
          leaf ni-name {
            type string;
            description
              "Name of the VPN to which an IFIT flow belongs.";
          }
          leaf if-name {
            type string;
            mandatory true;
            description
              "Interface name to which an IFIT flow binds.";
          }
          leaf dscp {
            type uint16 {
              range "0..63";
            }
            description
              "DSCP of an IFIT flow.";
          }
        }
      }
    }
  }
  augment "/ncs:devices/ncs:device-group/ncs:ned-id/ncs:rpc" {
    container rpc-reset-dynamic-flow {
      tailf:ncs-device-type "netconf";
      tailf:display-when "/ncs:devices/ncs:device[ncs:name=current()/../../../ncs:member]/ncs:module[ncs:name='huawei-ifit-common']";
      tailf:action reset-dynamic-flow {
        tailf:actionpoint ncsproxy {
          tailf:internal;
        }
        description
          "Clear specified dynamic flow.";
        ext:node-ref "/ifit:ifit/ifit-common:ifit-common/ifit-common:dynamic-flows/ifit-common:dynamic-flow";
        input {
          leaf address-type {
            type ifit-common:ncs_rpc_notif_addr-type;
            mandatory true;
            description
              "Address type of IFIT flow.";
          }
          leaf source-ip {
            type inet:ip-address-no-zone;
            description
              "Source IP address of an IFIT flow.";
          }
          leaf destination-ip {
            type inet:ip-address-no-zone;
            description
              "Destination IP address of an IFIT flow.";
          }
          leaf source-mask {
            when '../source-ip' {
              tailf:xpath-root 4;
            }
            type uint8 {
              range "1..128";
            }
            description
              "Source IP address mask of an IFIT flow.";
          }
          leaf destination-mask {
            when '../destination-ip' {
              tailf:xpath-root 4;
            }
            type uint8 {
              range "1..128";
            }
            description
              "Destination IP address mask of an IFIT flow.";
          }
          leaf protocol {
            type uint8 {
              range "0..254";
              ext:value-meaning {
                ext:item "6" {
                  ext:meaning "tcp";
                }
                ext:item "17" {
                  ext:meaning "udp";
                }
                ext:item "132" {
                  ext:meaning "sctp";
                }
              }
            }
            description
              "Protocol of an IFIT flow.";
          }
          leaf source-port {
            type uint16 {
              range "1..65535";
            }
            description
              "Source port of an IFIT flow.";
          }
          leaf destination-port {
            type uint16 {
              range "1..65535";
            }
            description
              "Destination port of an IFIT flow.";
          }
          leaf ni-name {
            type string;
            description
              "Name of the VPN to which an IFIT flow belongs.";
          }
          leaf if-name {
            type string;
            mandatory true;
            description
              "Interface name to which an IFIT flow binds.";
          }
          leaf dscp {
            type uint16 {
              range "0..63";
            }
            description
              "DSCP of an IFIT flow.";
          }
        }
      }
    }
  }
  augment "/ncs:devices/ncs:device/ncs:rpc" {
    container rpc-set-dynamic-flow {
      tailf:ncs-device-type "netconf";
      tailf:display-when "not(../../ncs:module) or ../../ncs:module[ncs:name='huawei-ifit-common']";
      tailf:action set-dynamic-flow {
        tailf:actionpoint ncsproxy {
          tailf:internal;
        }
        description
          "Set IFIT Flow parameter.";
        ext:node-ref "/ifit:ifit/ifit-common:ifit-common/ifit-common:dynamic-flows/ifit-common:dynamic-flow";
        input {
          leaf source-ip {
            type inet:ip-address-no-zone;
            description
              "Source IP address of an IFIT flow.";
          }
          leaf destination-ip {
            type inet:ip-address-no-zone;
            description
              "Destination IP address of an IFIT flow.";
          }
          leaf source-mask {
            when '../source-ip' {
              tailf:xpath-root 3;
            }
            type uint8;
            description
              "Source IP address mask of an IFIT flow.";
          }
          leaf destination-mask {
            when '../destination-ip' {
              tailf:xpath-root 3;
            }
            type uint8;
            description
              "Destination IP address mask of an IFIT flow.";
          }
          leaf address-type {
            type ifit-common:ncs_rpc_notif_addr-type;
            mandatory true;
            description
              "Address type of IFIT flow.";
          }
          leaf if-name {
            type string;
            mandatory true;
            description
              "Interface name to which an IFIT flow binds.";
          }
          leaf ni-name {
            type string;
            description
              "Name of the VPN to which an IFIT flow belongs.";
          }
          leaf dscp {
            type uint16 {
              range "0..63";
            }
            description
              "DSCP of an IFIT flow.";
          }
          leaf interval {
            type uint16 {
              range "10|30|60|300";
            }
            units "s";
            default "30";
            description
              "Interval of an IFIT flow.";
          }
          leaf measure-mode {
            type ifit-common:ncs_rpc_notif_measure-mode;
            default "e2e";
            description
              "Measure mode of an IFIT flow.";
          }
          leaf loss-measure-enable {
            type boolean;
            default "true";
            description
              "Enable/disable loss measure function of an IFIT flow.";
          }
          leaf delay-measure-enable {
            type boolean;
            default "true";
            description
              "Enable/disable delay measure function of an IFIT flow.";
          }
          leaf disorder-measure-enable {
            type boolean;
            default "false";
            description
              "Enable/disable disorder measure function of an IFIT flow.";
          }
          leaf protocol {
            type uint8 {
              range "0..254";
              ext:value-meaning {
                ext:item "6" {
                  ext:meaning "tcp";
                }
                ext:item "17" {
                  ext:meaning "udp";
                }
                ext:item "132" {
                  ext:meaning "sctp";
                }
              }
            }
            description
              "Protocol of an IFIT flow.";
          }
          leaf source-port {
            type uint16 {
              range "1..65535";
            }
            description
              "Source port of an IFIT flow.";
          }
          leaf destination-port {
            type uint16 {
              range "1..65535";
            }
            description
              "Destination port of an IFIT flow.";
          }
        }
      }
    }
  }
  augment "/ncs:devices/ncs:device-group/ncs:ned-id/ncs:rpc" {
    container rpc-set-dynamic-flow {
      tailf:ncs-device-type "netconf";
      tailf:display-when "/ncs:devices/ncs:device[ncs:name=current()/../../../ncs:member]/ncs:module[ncs:name='huawei-ifit-common']";
      tailf:action set-dynamic-flow {
        tailf:actionpoint ncsproxy {
          tailf:internal;
        }
        description
          "Set IFIT Flow parameter.";
        ext:node-ref "/ifit:ifit/ifit-common:ifit-common/ifit-common:dynamic-flows/ifit-common:dynamic-flow";
        input {
          leaf source-ip {
            type inet:ip-address-no-zone;
            description
              "Source IP address of an IFIT flow.";
          }
          leaf destination-ip {
            type inet:ip-address-no-zone;
            description
              "Destination IP address of an IFIT flow.";
          }
          leaf source-mask {
            when '../source-ip' {
              tailf:xpath-root 4;
            }
            type uint8;
            description
              "Source IP address mask of an IFIT flow.";
          }
          leaf destination-mask {
            when '../destination-ip' {
              tailf:xpath-root 4;
            }
            type uint8;
            description
              "Destination IP address mask of an IFIT flow.";
          }
          leaf address-type {
            type ifit-common:ncs_rpc_notif_addr-type;
            mandatory true;
            description
              "Address type of IFIT flow.";
          }
          leaf if-name {
            type string;
            mandatory true;
            description
              "Interface name to which an IFIT flow binds.";
          }
          leaf ni-name {
            type string;
            description
              "Name of the VPN to which an IFIT flow belongs.";
          }
          leaf dscp {
            type uint16 {
              range "0..63";
            }
            description
              "DSCP of an IFIT flow.";
          }
          leaf interval {
            type uint16 {
              range "10|30|60|300";
            }
            units "s";
            default "30";
            description
              "Interval of an IFIT flow.";
          }
          leaf measure-mode {
            type ifit-common:ncs_rpc_notif_measure-mode;
            default "e2e";
            description
              "Measure mode of an IFIT flow.";
          }
          leaf loss-measure-enable {
            type boolean;
            default "true";
            description
              "Enable/disable loss measure function of an IFIT flow.";
          }
          leaf delay-measure-enable {
            type boolean;
            default "true";
            description
              "Enable/disable delay measure function of an IFIT flow.";
          }
          leaf disorder-measure-enable {
            type boolean;
            default "false";
            description
              "Enable/disable disorder measure function of an IFIT flow.";
          }
          leaf protocol {
            type uint8 {
              range "0..254";
              ext:value-meaning {
                ext:item "6" {
                  ext:meaning "tcp";
                }
                ext:item "17" {
                  ext:meaning "udp";
                }
                ext:item "132" {
                  ext:meaning "sctp";
                }
              }
            }
            description
              "Protocol of an IFIT flow.";
          }
          leaf source-port {
            type uint16 {
              range "1..65535";
            }
            description
              "Source port of an IFIT flow.";
          }
          leaf destination-port {
            type uint16 {
              range "1..65535";
            }
            description
              "Destination port of an IFIT flow.";
          }
        }
      }
    }
  }
  augment "/ncs:devices/ncs:device/ncs:rpc" {
    container rpc-reset-dynamic-flowid {
      tailf:ncs-device-type "netconf";
      tailf:display-when "not(../../ncs:module) or ../../ncs:module[ncs:name='huawei-ifit-common']";
      tailf:action reset-dynamic-flowid {
        tailf:actionpoint ncsproxy {
          tailf:internal;
        }
        description
          "Clear specified dynamic IFIT ID.";
        ext:node-ref "/ifit:ifit/ifit-common:ifit-common/ifit-common:dynamic-flow-hops/ifit-common:dynamic-flow-hop";
        input {
          leaf flow-id {
            type uint64;
            mandatory true;
            description
              "Clear specified dynamic IFIT ID.";
          }
        }
      }
    }
  }
  augment "/ncs:devices/ncs:device-group/ncs:ned-id/ncs:rpc" {
    container rpc-reset-dynamic-flowid {
      tailf:ncs-device-type "netconf";
      tailf:display-when "/ncs:devices/ncs:device[ncs:name=current()/../../../ncs:member]/ncs:module[ncs:name='huawei-ifit-common']";
      tailf:action reset-dynamic-flowid {
        tailf:actionpoint ncsproxy {
          tailf:internal;
        }
        description
          "Clear specified dynamic IFIT ID.";
        ext:node-ref "/ifit:ifit/ifit-common:ifit-common/ifit-common:dynamic-flow-hops/ifit-common:dynamic-flow-hop";
        input {
          leaf flow-id {
            type uint64;
            mandatory true;
            description
              "Clear specified dynamic IFIT ID.";
          }
        }
      }
    }
  }
  augment "/ncs:devices/ncs:device/ncs:rpc" {
    container rpc-reset-dynamic-flow-all {
      tailf:ncs-device-type "netconf";
      tailf:display-when "not(../../ncs:module) or ../../ncs:module[ncs:name='huawei-ifit-common']";
      tailf:action reset-dynamic-flow-all {
        tailf:actionpoint ncsproxy {
          tailf:internal;
        }
        description
          "Clear all dynamic IFIT flow.";
        ext:node-ref "/ifit:ifit/ifit-common:ifit-common/ifit-common:dynamic-flow-hops";
        input {
          leaf all-flow {
            type boolean;
            mandatory true;
            description
              "Clear all dynamic IFIT flow.";
          }
        }
      }
    }
  }
  augment "/ncs:devices/ncs:device-group/ncs:ned-id/ncs:rpc" {
    container rpc-reset-dynamic-flow-all {
      tailf:ncs-device-type "netconf";
      tailf:display-when "/ncs:devices/ncs:device[ncs:name=current()/../../../ncs:member]/ncs:module[ncs:name='huawei-ifit-common']";
      tailf:action reset-dynamic-flow-all {
        tailf:actionpoint ncsproxy {
          tailf:internal;
        }
        description
          "Clear all dynamic IFIT flow.";
        ext:node-ref "/ifit:ifit/ifit-common:ifit-common/ifit-common:dynamic-flow-hops";
        input {
          leaf all-flow {
            type boolean;
            mandatory true;
            description
              "Clear all dynamic IFIT flow.";
          }
        }
      }
    }
  }
  augment "/ncs:devices/ncs:template/ncs:ned-id/ncs:config/ifit:ifit" {
    description
      "IFIT augment.";
    container ifit-common {
      description
        "Configure IFIT function.";
      container global {
        description
          "Configure global parameter of IFIT.";
        leaf node-id {
          ext:operation-exclude "update" {
            // NCS drop when statement
            description
              "The 'node-id' cannot be updated, when static-instance exists.";
          }
          type string;
          description
            "Node ID of IFIT.";
        }
        leaf dynamic-flow-aging-multiplier {
          type string;
          description
            "Multiplier of an dynamic IFIT flow age interval. If the instance interval calculation result is less than 10 minutes, the 10 minutes shall prevail.";
        }
      }
      container next-hops {
        description
          "List of IFIT function for the next hop addresses.";
        list next-hop {
          // NCS patched for predictable order
          ordered-by user;
          key "address";
          description
            "Configure IFIT function for the next hop address.";
          leaf address {
            type string;
            description
              "Next hop address.";
          }
        }
      }
      container peer-locators {
        description
          "List of IFIT function for the next locator addresses.";
        list peer-locator {
          // NCS patched for predictable order
          ordered-by user;
          key "prefix";
          status obsolete;
          description
            "Configure IFIT function for the next locator address.";
          leaf prefix {
            type string;
            status obsolete;
            description
              "Next locator address.";
          }
          leaf prefix-mask-length {
            ext:operation-exclude "update";
            type string;
            // NCS drop mandatory statement
            status obsolete;
            description
              "Mask length of a next locator address.";
          }
        }
      }
      container static-instances {
        description
          "List of static instances of IFIT.";
        list static-instance {
          // NCS patched for predictable order
          ordered-by user;
          // NCS drop must statement
          key "name";
          unique "flow/flow-filter/filter-condition1/flow-address-type/ipv4-condition/source-ip flow/flow-filter/filter-condition1/flow-address-type/ipv4-condition/destination-ip flow/flow-filter/filter-condition1/flow-address-type/ipv4-condition/source-mask flow/flow-filter/filter-condition1/flow-address-type/ipv4-condition/destination-mask flow/flow-filter/filter-condition1/protocol flow/flow-filter/filter-condition1/source-port flow/flow-filter/filter-condition1/destination-port flow/flow-filter/filter-condition1/gtp-enable flow/flow-filter/filter-condition1/gtp-teid flow/flow-filter/filter-condition1/ni-name flow/flow-filter/filter-condition1/dscp";
          unique "flow/flow-filter/filter-condition1/flow-address-type/ipv6-condition/source-ipv6 flow/flow-filter/filter-condition1/flow-address-type/ipv6-condition/destination-ipv6 flow/flow-filter/filter-condition1/flow-address-type/ipv6-condition/source-ipv6-mask flow/flow-filter/filter-condition1/flow-address-type/ipv6-condition/destination-ipv6-mask flow/flow-filter/filter-condition1/protocol flow/flow-filter/filter-condition1/source-port flow/flow-filter/filter-condition1/destination-port flow/flow-filter/filter-condition1/gtp-enable flow/flow-filter/filter-condition1/gtp-teid flow/flow-filter/filter-condition1/ni-name flow/flow-filter/filter-condition1/dscp";
          unique "flow/flow-filter/filter-condition2/vpn-filter/ni-condition/address-type flow/flow-filter/filter-condition2/vpn-filter/ni-condition/peer-ni-name flow/flow-filter/filter-condition2/peer-filter/ip-condition/peer-ip";
          unique "flow/flow-filter/filter-condition2/vpn-filter/evpl-condition/peer-evpl-id flow/flow-filter/filter-condition2/peer-filter/ip-condition/peer-ip";
          description
            "Configure static instance of IFIT.";
          leaf name {
            type string;
            // NCS drop must statement
            description
              "Instance name of IFIT.";
          }
          leaf interval {
            type string;
            units "s";
            // NCS drop default statement
            description
              "Interval of an IFIT flow.";
          }
          leaf measure-mode {
            type ifit-common:ncs_template_measure-mode;
            // NCS drop default statement
            description
              "Measure mode of an IFIT flow.";
          }
          leaf loss-measure-enable {
            type string;
            // NCS drop default statement
            description
              "Enable/disable loss measure function of an IFIT flow.";
          }
          leaf delay-measure-enable {
            type string;
            // NCS drop default statement
            description
              "Enable/disable delay measure function of an IFIT flow.";
          }
          leaf disorder-measure-enable {
            type string;
            // NCS drop default statement
            description
              "Enable/disable disorder measure function of an IFIT flow.";
          }
          leaf gtpu-sn-measure-enable {
            type string;
            // NCS drop default statement
            description
              "Enable/disable gtpu sequence number measure function of an IFIT flow.";
          }
          container flow {
            // NCS drop must statement
            // NCS drop must statement
            presence "Enable flow";
            description
              "Configure IFIT flow.";
            leaf flow-type {
              ext:operation-exclude "update";
              type ifit-common:ncs_template_flow-type;
              // NCS drop mandatory statement
              description
                "Flow type of an IFIT flow.";
            }
            choice flow-filter {
              // NCS drop mandatory statement
              description
                "Configure the filter of a flow.";
              case filter-condition1 {
                description
                  "Filter condition 1.";
                choice flow-address-type {
                  // NCS drop mandatory statement
                  description
                    "Configure the address of a flow.";
                  case ipv4-condition {
                    description
                      "IPv4 condition.";
                    leaf source-ip {
                      ext:operation-exclude "update|delete";
                      ext:support-filter "true";
                      type string;
                      description
                        "Source IPv4 address of an IFIT flow.";
                    }
                    leaf destination-ip {
                      ext:operation-exclude "update";
                      ext:support-filter "true";
                      type string;
                      // NCS drop must statement
                      // NCS drop mandatory statement
                      description
                        "Destination IPv4 address of an IFIT flow.";
                    }
                    leaf source-mask {
                      // NCS drop when statement
                      ext:operation-exclude "update|delete";
                      type string;
                      // NCS drop default statement
                      description
                        "Source IPv4 address mask of an IFIT flow.";
                    }
                    leaf destination-mask {
                      ext:operation-exclude "update|delete";
                      type string;
                      // NCS drop default statement
                      description
                        "Destination IPv4 address mask of an IFIT flow.";
                    }
                  }
                  case ipv6-condition {
                    description
                      "IPv6 condition.";
                    leaf source-ipv6 {
                      ext:operation-exclude "update";
                      ext:support-filter "true";
                      type string;
                      // NCS drop mandatory statement
                      description
                        "Source IPv6 address of an IFIT flow.";
                    }
                    leaf destination-ipv6 {
                      ext:operation-exclude "update";
                      ext:support-filter "true";
                      type string;
                      // NCS drop must statement
                      // NCS drop mandatory statement
                      description
                        "Destination IPv6 address of an IFIT flow.";
                    }
                    leaf source-ipv6-mask {
                      ext:operation-exclude "update|delete";
                      type string;
                      // NCS drop default statement
                      description
                        "Source IPv6 address mask of an IFIT flow.";
                    }
                    leaf destination-ipv6-mask {
                      ext:operation-exclude "update|delete";
                      type string;
                      // NCS drop default statement
                      description
                        "Destination IPv6 address mask of an IFIT flow.";
                    }
                  }
                }
                leaf protocol {
                  ext:operation-exclude "update|delete";
                  type string;
                  description
                    "Protocol of an IFIT flow.";
                }
                leaf source-port {
                  ext:operation-exclude "update|delete";
                  type string;
                  // NCS drop must statement
                  description
                    "Source port of an IFIT flow.";
                }
                leaf destination-port {
                  ext:operation-exclude "update|delete";
                  type string;
                  // NCS drop must statement
                  description
                    "Destination port of an IFIT flow.";
                }
                leaf gtp-enable {
                  // NCS drop when statement
                  ext:operation-exclude "update|delete";
                  type string;
                  // NCS drop default statement
                  description
                    "Enable/disable GTP protocol measure for an IFIT flow.";
                }
                leaf gtp-teid {
                  // NCS drop when statement
                  ext:operation-exclude "update|delete";
                  type string;
                  description
                    "GTP TEID of an IFIT flow.";
                }
                leaf ni-name {
                  ext:operation-exclude "update|delete";
                  type string;
                  // NCS drop must statement
                  description
                    "Name of the VPN to which an IFIT flow belongs.";
                }
                leaf dscp {
                  ext:operation-exclude "update|delete";
                  type string;
                  description
                    "DSCP of an IFIT flow.";
                }
              }
              case filter-condition2 {
                // NCS drop when statement
                description
                  "Filter condition 2.";
                choice vpn-filter {
                  // NCS drop mandatory statement
                  description
                    "Configure the VPN filter of a flow.";
                  case ni-condition {
                    description
                      "Peer netconf instance condition.";
                    leaf address-type {
                      ext:operation-exclude "update";
                      type ncs_template_addr-family-type;
                      // NCS drop mandatory statement
                      description
                        "Address type of an IFIT flow peer.";
                    }
                    leaf peer-ni-name {
                      ext:operation-exclude "update";
                      type string;
                      // NCS drop must statement
                      // NCS drop mandatory statement
                      description
                        "Name of the VPN to which an IFIT flow peer belongs.";
                    }
                  }
                  case evpl-condition {
                    description
                      "Peer EVPL condition.";
                    leaf peer-evpl-id {
                      ext:operation-exclude "update";
                      type string;
                      // NCS drop must statement
                      // NCS drop mandatory statement
                      description
                        "ID of the EVPL instance to which an IFIT flow peer belongs.";
                    }
                  }
                }
                choice peer-filter {
                  // NCS drop mandatory statement
                  description
                    "Configure the peer filter of a flow.";
                  case ip-condition {
                    description
                      "Peer filter ip condition.";
                    leaf peer-ip {
                      ext:operation-exclude "update";
                      type string;
                      // NCS drop mandatory statement
                      description
                        "Peer IP address of an IFIT flow.";
                    }
                  }
                  case locator-condition {
                    description
                      "Peer filter locatior condition.";
                    leaf peer-locator-prefix {
                      ext:operation-exclude "update";
                      type string;
                      // NCS drop mandatory statement
                      description
                        "Peer locator address.";
                    }
                    leaf peer-locator-prefix-mask-len {
                      ext:operation-exclude "update";
                      type string;
                      // NCS drop mandatory statement
                      description
                        "Mask length of a peer locator address.";
                    }
                  }
                }
              }
            }
            container bind-ifs {
              description
                "List of flow specified interfaces of IFIT.";
              list bind-if {
                // NCS patched for predictable order
                ordered-by user;
                key "if-name";
                description
                  "Configure flow specified interface of IFIT.";
                leaf if-name {
                  type string;
                  description
                    "Interface name to which an IFIT flow binds.";
                }
                // NCS drop config false leaf 'flow-id'
              }
            }
          }
        }
      }
      // NCS drop config false container 'dynamic-flow-hops'
      // NCS drop config false container 'dynamic-flows'
    }
  }
  augment "/ncs:devices/ncs:device/ncs:live-status/ifit:ifit" {
    description
      "IFIT augment.";
    container ifit-common {
      tailf:ncs-device-type "netconf";
      tailf:display-when "not(../../../ncs:module) or ../../../ncs:module[ncs:name='huawei-ifit-common'] or (../../../ncs:live-status-protocol[not(ncs:capability)]) or (../../../ncs:live-status-protocol/ncs:capability/ncs:module[.='huawei-ifit-common'])";
      description
        "Configure IFIT function.";
      container global {
        description
          "Configure global parameter of IFIT.";
        leaf node-id {
          ext:operation-exclude "update" {
            // NCS drop when statement
            description
              "The 'node-id' cannot be updated, when static-instance exists.";
          }
          type uint32 {
            range "1..1048575";
          }
          description
            "Node ID of IFIT.";
        }
        leaf dynamic-flow-aging-multiplier {
          type uint16 {
            range "2..100";
          }
          description
            "Multiplier of an dynamic IFIT flow age interval. If the instance interval calculation result is less than 10 minutes, the 10 minutes shall prevail.";
        }
      }
      container next-hops {
        description
          "List of IFIT function for the next hop addresses.";
        list next-hop {
          key "address";
          description
            "Configure IFIT function for the next hop address.";
          leaf address {
            type inet:ip-address-no-zone;
            description
              "Next hop address.";
          }
        }
      }
      container peer-locators {
        description
          "List of IFIT function for the next locator addresses.";
        list peer-locator {
          key "prefix";
          status obsolete;
          description
            "Configure IFIT function for the next locator address.";
          leaf prefix {
            type inet:ipv6-address-no-zone;
            status obsolete;
            description
              "Next locator address.";
          }
          leaf prefix-mask-length {
            ext:operation-exclude "update";
            type uint32 {
              range "32..120";
            }
            // NCS drop mandatory statement
            status obsolete;
            description
              "Mask length of a next locator address.";
          }
        }
      }
      container static-instances {
        description
          "List of static instances of IFIT.";
        list static-instance {
          // NCS drop must statement
          key "name";
          unique "flow/flow-filter/filter-condition1/flow-address-type/ipv4-condition/source-ip flow/flow-filter/filter-condition1/flow-address-type/ipv4-condition/destination-ip flow/flow-filter/filter-condition1/flow-address-type/ipv4-condition/source-mask flow/flow-filter/filter-condition1/flow-address-type/ipv4-condition/destination-mask flow/flow-filter/filter-condition1/protocol flow/flow-filter/filter-condition1/source-port flow/flow-filter/filter-condition1/destination-port flow/flow-filter/filter-condition1/gtp-enable flow/flow-filter/filter-condition1/gtp-teid flow/flow-filter/filter-condition1/ni-name flow/flow-filter/filter-condition1/dscp";
          unique "flow/flow-filter/filter-condition1/flow-address-type/ipv6-condition/source-ipv6 flow/flow-filter/filter-condition1/flow-address-type/ipv6-condition/destination-ipv6 flow/flow-filter/filter-condition1/flow-address-type/ipv6-condition/source-ipv6-mask flow/flow-filter/filter-condition1/flow-address-type/ipv6-condition/destination-ipv6-mask flow/flow-filter/filter-condition1/protocol flow/flow-filter/filter-condition1/source-port flow/flow-filter/filter-condition1/destination-port flow/flow-filter/filter-condition1/gtp-enable flow/flow-filter/filter-condition1/gtp-teid flow/flow-filter/filter-condition1/ni-name flow/flow-filter/filter-condition1/dscp";
          unique "flow/flow-filter/filter-condition2/vpn-filter/ni-condition/address-type flow/flow-filter/filter-condition2/vpn-filter/ni-condition/peer-ni-name flow/flow-filter/filter-condition2/peer-filter/ip-condition/peer-ip";
          unique "flow/flow-filter/filter-condition2/vpn-filter/evpl-condition/peer-evpl-id flow/flow-filter/filter-condition2/peer-filter/ip-condition/peer-ip";
          description
            "Configure static instance of IFIT.";
          leaf name {
            type string {
              length "1..31";
            }
            // NCS drop must statement
            description
              "Instance name of IFIT.";
          }
          leaf interval {
            type uint16 {
              range "10|30|60|300";
            }
            units "s";
            // NCS drop default statement
            description
              "Interval of an IFIT flow.";
          }
          leaf measure-mode {
            type ifit-common:live_ncs_measure-mode;
            // NCS drop default statement
            description
              "Measure mode of an IFIT flow.";
          }
          leaf loss-measure-enable {
            type boolean;
            // NCS drop default statement
            description
              "Enable/disable loss measure function of an IFIT flow.";
          }
          leaf delay-measure-enable {
            type boolean;
            // NCS drop default statement
            description
              "Enable/disable delay measure function of an IFIT flow.";
          }
          leaf disorder-measure-enable {
            type boolean;
            // NCS drop default statement
            description
              "Enable/disable disorder measure function of an IFIT flow.";
          }
          leaf gtpu-sn-measure-enable {
            type boolean;
            // NCS drop default statement
            description
              "Enable/disable gtpu sequence number measure function of an IFIT flow.";
          }
          container flow {
            // NCS drop must statement
            // NCS drop must statement
            presence "Enable flow";
            description
              "Configure IFIT flow.";
            leaf flow-type {
              ext:operation-exclude "update";
              type ifit-common:live_ncs_flow-type;
              // NCS drop mandatory statement
              description
                "Flow type of an IFIT flow.";
            }
            choice flow-filter {
              // NCS drop mandatory statement
              description
                "Configure the filter of a flow.";
              case filter-condition1 {
                description
                  "Filter condition 1.";
                choice flow-address-type {
                  // NCS drop mandatory statement
                  description
                    "Configure the address of a flow.";
                  case ipv4-condition {
                    description
                      "IPv4 condition.";
                    leaf source-ip {
                      ext:operation-exclude "update|delete";
                      ext:support-filter "true";
                      type inet:ipv4-address-no-zone;
                      description
                        "Source IPv4 address of an IFIT flow.";
                    }
                    leaf destination-ip {
                      ext:operation-exclude "update";
                      ext:support-filter "true";
                      type inet:ipv4-address-no-zone;
                      // NCS drop must statement
                      // NCS drop mandatory statement
                      description
                        "Destination IPv4 address of an IFIT flow.";
                    }
                    leaf source-mask {
                      // NCS drop when statement
                      ext:operation-exclude "update|delete";
                      type uint8 {
                        range "1..32";
                      }
                      // NCS drop default statement
                      description
                        "Source IPv4 address mask of an IFIT flow.";
                    }
                    leaf destination-mask {
                      ext:operation-exclude "update|delete";
                      type uint8 {
                        range "1..32";
                      }
                      // NCS drop default statement
                      description
                        "Destination IPv4 address mask of an IFIT flow.";
                    }
                  }
                  case ipv6-condition {
                    description
                      "IPv6 condition.";
                    leaf source-ipv6 {
                      ext:operation-exclude "update";
                      ext:support-filter "true";
                      type inet:ipv6-address-no-zone;
                      // NCS drop mandatory statement
                      description
                        "Source IPv6 address of an IFIT flow.";
                    }
                    leaf destination-ipv6 {
                      ext:operation-exclude "update";
                      ext:support-filter "true";
                      type inet:ipv6-address-no-zone;
                      // NCS drop must statement
                      // NCS drop mandatory statement
                      description
                        "Destination IPv6 address of an IFIT flow.";
                    }
                    leaf source-ipv6-mask {
                      ext:operation-exclude "update|delete";
                      type uint8 {
                        range "32..128";
                      }
                      // NCS drop default statement
                      description
                        "Source IPv6 address mask of an IFIT flow.";
                    }
                    leaf destination-ipv6-mask {
                      ext:operation-exclude "update|delete";
                      type uint8 {
                        range "32..128";
                      }
                      // NCS drop default statement
                      description
                        "Destination IPv6 address mask of an IFIT flow.";
                    }
                  }
                }
                leaf protocol {
                  ext:operation-exclude "update|delete";
                  type uint8 {
                    range "0..254";
                    ext:value-meaning {
                      ext:item "6" {
                        ext:meaning "tcp";
                      }
                      ext:item "17" {
                        ext:meaning "udp";
                      }
                      ext:item "132" {
                        ext:meaning "sctp";
                      }
                    }
                  }
                  description
                    "Protocol of an IFIT flow.";
                }
                leaf source-port {
                  ext:operation-exclude "update|delete";
                  type uint16 {
                    range "1..65535";
                  }
                  // NCS drop must statement
                  description
                    "Source port of an IFIT flow.";
                }
                leaf destination-port {
                  ext:operation-exclude "update|delete";
                  type uint16 {
                    range "1..65535";
                  }
                  // NCS drop must statement
                  description
                    "Destination port of an IFIT flow.";
                }
                leaf gtp-enable {
                  // NCS drop when statement
                  ext:operation-exclude "update|delete";
                  type boolean;
                  // NCS drop default statement
                  description
                    "Enable/disable GTP protocol measure for an IFIT flow.";
                }
                leaf gtp-teid {
                  // NCS drop when statement
                  ext:operation-exclude "update|delete";
                  type uint32 {
                    range "1..4294967295";
                  }
                  description
                    "GTP TEID of an IFIT flow.";
                }
                leaf ni-name {
                  ext:operation-exclude "update|delete";
                  type leafref {
                    path "/ncs:devices/ncs:device/ncs:live-status/ni:network-instance/ni:instances/ni:instance/ni:name" {
                      tailf:xpath-root 3;
                    }
                  }
                  // NCS drop must statement
                  description
                    "Name of the VPN to which an IFIT flow belongs.";
                }
                leaf dscp {
                  ext:operation-exclude "update|delete";
                  type uint16 {
                    range "0..63";
                  }
                  description
                    "DSCP of an IFIT flow.";
                }
              }
              case filter-condition2 {
                // NCS drop when statement
                description
                  "Filter condition 2.";
                choice vpn-filter {
                  // NCS drop mandatory statement
                  description
                    "Configure the VPN filter of a flow.";
                  case ni-condition {
                    description
                      "Peer netconf instance condition.";
                    leaf address-type {
                      ext:operation-exclude "update";
                      type live_ncs_addr-family-type;
                      // NCS drop mandatory statement
                      description
                        "Address type of an IFIT flow peer.";
                    }
                    leaf peer-ni-name {
                      ext:operation-exclude "update";
                      type leafref {
                        path "/ncs:devices/ncs:device/ncs:live-status/ni:network-instance/ni:instances/ni:instance/ni:name" {
                          tailf:xpath-root 3;
                        }
                      }
                      // NCS drop must statement
                      // NCS drop mandatory statement
                      description
                        "Name of the VPN to which an IFIT flow peer belongs.";
                    }
                  }
                  case evpl-condition {
                    description
                      "Peer EVPL condition.";
                    leaf peer-evpl-id {
                      ext:operation-exclude "update";
                      type leafref {
                        path "/ncs:devices/ncs:device/ncs:live-status/evpl:evpl/evpl:instances/evpl:instance/evpl:id" {
                          tailf:xpath-root 3;
                        }
                      }
                      // NCS drop must statement
                      // NCS drop mandatory statement
                      description
                        "ID of the EVPL instance to which an IFIT flow peer belongs.";
                    }
                  }
                }
                choice peer-filter {
                  // NCS drop mandatory statement
                  description
                    "Configure the peer filter of a flow.";
                  case ip-condition {
                    description
                      "Peer filter ip condition.";
                    leaf peer-ip {
                      ext:operation-exclude "update";
                      type inet:ipv4-address-no-zone;
                      // NCS drop mandatory statement
                      description
                        "Peer IP address of an IFIT flow.";
                    }
                  }
                  case locator-condition {
                    description
                      "Peer filter locatior condition.";
                    leaf peer-locator-prefix {
                      ext:operation-exclude "update";
                      type inet:ipv6-address-no-zone;
                      // NCS drop mandatory statement
                      description
                        "Peer locator address.";
                    }
                    leaf peer-locator-prefix-mask-len {
                      ext:operation-exclude "update";
                      type uint32 {
                        range "32..120";
                      }
                      // NCS drop mandatory statement
                      description
                        "Mask length of a peer locator address.";
                    }
                  }
                }
              }
            }
            container bind-ifs {
              description
                "List of flow specified interfaces of IFIT.";
              list bind-if {
                key "if-name";
                description
                  "Configure flow specified interface of IFIT.";
                leaf if-name {
                  type leafref {
                    path "/ncs:devices/ncs:device/ncs:live-status/ifm:ifm/ifm:interfaces/ifm:interface/ifm:name" {
                      tailf:xpath-root 3;
                    }
                  }
                  description
                    "Interface name to which an IFIT flow binds.";
                }
                leaf flow-id {
                  type uint64;
                  description
                    "Flow ID of an IFIT flow.";
                }
              }
            }
          }
        }
      }
      container dynamic-flow-hops {
        description
          "List of dynamic flow hops of IFIT.";
        list dynamic-flow-hop {
          key "flow-id";
          description
            "Operational data of dynamic flow hop of IFIT.";
          leaf flow-id {
            type uint64;
            description
              "Flow ID of an IFIT flow.";
          }
          leaf flow-type {
            type ifit-common:live_ncs_flow-type;
            description
              "Flow type of an IFIT flow.";
          }
          leaf if-name {
            type leafref {
              path "/ncs:devices/ncs:device/ncs:live-status/ifm:ifm/ifm:interfaces/ifm:interface/ifm:name" {
                tailf:xpath-root 3;
              }
            }
            description
              "Interface name to which an IFIT flow passes.";
          }
          leaf interval {
            type uint16 {
              range "10|30|60|300";
            }
            units "s";
            description
              "Interval of an IFIT flow.";
          }
          leaf direction {
            type ifit-common:live_ncs_flow-direction;
            description
              "Direction of an IFIT flow.";
          }
          leaf loss-measure-enable {
            type boolean;
            description
              "Enable/disable loss measure function of an IFIT flow.";
          }
          leaf delay-measure-enable {
            type boolean;
            description
              "Enable/disable delay measure function of an IFIT flow.";
          }
          leaf disorder-measure-enable {
            type boolean;
            description
              "Enable/disable disorder measure function of an IFIT flow.";
          }
        }
      }
      container dynamic-flows {
        description
          "List of dynamic flows of IFIT.";
        list dynamic-flow {
          key "flow-id";
          description
            "Operational data of dynamic flow of IFIT.";
          leaf flow-id {
            type uint64;
            description
              "Flow ID of an IFIT flow.";
          }
          leaf flow-type {
            type ifit-common:live_ncs_flow-type;
            description
              "Flow type of an IFIT flow.";
          }
          leaf address-type {
            type live_ncs_addr-type;
            description
              "Address type of an IFIT flow.";
          }
          leaf source-ip {
            ext:support-filter "true";
            type inet:ip-address-no-zone;
            description
              "Source IP address of an IFIT flow.";
          }
          leaf destination-ip {
            ext:support-filter "true";
            type inet:ip-address-no-zone;
            description
              "Destination IP address of an IFIT flow.";
          }
          leaf source-mask {
            type uint8 {
              range "1..128";
            }
            description
              "Source IP address mask of an IFIT flow.";
          }
          leaf destination-mask {
            type uint8 {
              range "1..128";
            }
            description
              "Destination IP address mask of an IFIT flow.";
          }
          leaf protocol {
            type uint8 {
              range "0..254";
              ext:value-meaning {
                ext:item "6" {
                  ext:meaning "tcp";
                }
                ext:item "17" {
                  ext:meaning "udp";
                }
                ext:item "132" {
                  ext:meaning "sctp";
                }
              }
            }
            description
              "Protocol of an IFIT flow.";
          }
          leaf source-port {
            type uint16 {
              range "1..65535";
            }
            description
              "Source port of an IFIT flow.";
          }
          leaf destination-port {
            type uint16 {
              range "1..65535";
            }
            description
              "Destination port of an IFIT flow.";
          }
          leaf ni-name {
            type leafref {
              path "/ncs:devices/ncs:device/ncs:live-status/ni:network-instance/ni:instances/ni:instance/ni:name" {
                tailf:xpath-root 3;
              }
            }
            description
              "Name of the VPN to which an IFIT flow belongs.";
          }
          leaf if-name {
            type leafref {
              path "/ncs:devices/ncs:device/ncs:live-status/ifm:ifm/ifm:interfaces/ifm:interface/ifm:name" {
                tailf:xpath-root 3;
              }
            }
            description
              "Interface name to which an IFIT flow passes.";
          }
          leaf interval {
            type uint16 {
              range "10|30|60|300";
            }
            units "s";
            description
              "Interval of an IFIT flow.";
          }
          leaf measure-mode {
            type ifit-common:live_ncs_measure-mode;
            description
              "Measure mode of an IFIT flow.";
          }
          leaf delay-measure-enable {
            type boolean;
            description
              "Enable/disable delay measure function of an IFIT flow.";
          }
          leaf loss-measure-enable {
            type boolean;
            description
              "Enable/disable loss measure function of an IFIT flow.";
          }
          leaf disorder-measure-enable {
            type boolean;
            description
              "Enable/disable disorder measure function of an IFIT flow.";
          }
          leaf dscp {
            type uint16 {
              range "0..63";
            }
            description
              "DSCP of an IFIT flow.";
          }
        }
      }
    }
  }
  augment "/ncs:devices/ncs:device/ncs:config/ifit:ifit" {
    description
      "IFIT augment.";
    container ifit-common {
      tailf:ncs-device-type "netconf";
      tailf:display-when "not(../../../ncs:module) or ../../../ncs:module[ncs:name='huawei-ifit-common']";
      description
        "Configure IFIT function.";
      container global {
        description
          "Configure global parameter of IFIT.";
        leaf node-id {
          ext:operation-exclude "update" {
            when '../../static-instances/static-instance' {
              tailf:xpath-root 3;
            }
            description
              "The 'node-id' cannot be updated, when static-instance exists.";
          }
          type uint32 {
            range "1..1048575";
          }
          description
            "Node ID of IFIT.";
        }
        leaf dynamic-flow-aging-multiplier {
          type uint16 {
            range "2..100";
          }
          description
            "Multiplier of an dynamic IFIT flow age interval. If the instance interval calculation result is less than 10 minutes, the 10 minutes shall prevail.";
        }
      }
      container next-hops {
        description
          "List of IFIT function for the next hop addresses.";
        list next-hop {
          key "address";
          description
            "Configure IFIT function for the next hop address.";
          leaf address {
            type inet:ip-address-no-zone;
            description
              "Next hop address.";
          }
        }
      }
      container peer-locators {
        description
          "List of IFIT function for the next locator addresses.";
        list peer-locator {
          key "prefix";
          status obsolete;
          description
            "Configure IFIT function for the next locator address.";
          leaf prefix {
            type inet:ipv6-address-no-zone;
            status obsolete;
            description
              "Next locator address.";
          }
          leaf prefix-mask-length {
            ext:operation-exclude "update";
            type uint32 {
              range "32..120";
            }
            mandatory true;
            status obsolete;
            description
              "Mask length of a next locator address.";
          }
        }
      }
      container static-instances {
        description
          "List of static instances of IFIT.";
        list static-instance {
          must "gtpu-sn-measure-enable='false' or disorder-measure-enable = 'false'" {
            tailf:xpath-root 3;
          }
          key "name";
          unique "flow/flow-filter/filter-condition1/flow-address-type/ipv4-condition/source-ip flow/flow-filter/filter-condition1/flow-address-type/ipv4-condition/destination-ip flow/flow-filter/filter-condition1/flow-address-type/ipv4-condition/source-mask flow/flow-filter/filter-condition1/flow-address-type/ipv4-condition/destination-mask flow/flow-filter/filter-condition1/protocol flow/flow-filter/filter-condition1/source-port flow/flow-filter/filter-condition1/destination-port flow/flow-filter/filter-condition1/gtp-enable flow/flow-filter/filter-condition1/gtp-teid flow/flow-filter/filter-condition1/ni-name flow/flow-filter/filter-condition1/dscp";
          unique "flow/flow-filter/filter-condition1/flow-address-type/ipv6-condition/source-ipv6 flow/flow-filter/filter-condition1/flow-address-type/ipv6-condition/destination-ipv6 flow/flow-filter/filter-condition1/flow-address-type/ipv6-condition/source-ipv6-mask flow/flow-filter/filter-condition1/flow-address-type/ipv6-condition/destination-ipv6-mask flow/flow-filter/filter-condition1/protocol flow/flow-filter/filter-condition1/source-port flow/flow-filter/filter-condition1/destination-port flow/flow-filter/filter-condition1/gtp-enable flow/flow-filter/filter-condition1/gtp-teid flow/flow-filter/filter-condition1/ni-name flow/flow-filter/filter-condition1/dscp";
          unique "flow/flow-filter/filter-condition2/vpn-filter/ni-condition/address-type flow/flow-filter/filter-condition2/vpn-filter/ni-condition/peer-ni-name flow/flow-filter/filter-condition2/peer-filter/ip-condition/peer-ip";
          unique "flow/flow-filter/filter-condition2/vpn-filter/evpl-condition/peer-evpl-id flow/flow-filter/filter-condition2/peer-filter/ip-condition/peer-ip";
          description
            "Configure static instance of IFIT.";
          leaf name {
            type string {
              length "1..31";
            }
            must '(../../../global/node-id)' {
              tailf:xpath-root 3;
            }
            description
              "Instance name of IFIT.";
          }
          leaf interval {
            type uint16 {
              range "10|30|60|300";
            }
            units "s";
            default "30";
            description
              "Interval of an IFIT flow.";
          }
          leaf measure-mode {
            type ifit-common:measure-mode;
            default "e2e";
            description
              "Measure mode of an IFIT flow.";
          }
          leaf loss-measure-enable {
            type boolean;
            default "true";
            description
              "Enable/disable loss measure function of an IFIT flow.";
          }
          leaf delay-measure-enable {
            type boolean;
            default "true";
            description
              "Enable/disable delay measure function of an IFIT flow.";
          }
          leaf disorder-measure-enable {
            type boolean;
            default "false";
            description
              "Enable/disable disorder measure function of an IFIT flow.";
          }
          leaf gtpu-sn-measure-enable {
            type boolean;
            default "false";
            description
              "Enable/disable gtpu sequence number measure function of an IFIT flow.";
          }
          container flow {
            must "flow-type='bidirection' or (source-ip or source-ipv6 or address-type or peer-evpl-id)" {
              tailf:xpath-root 3;
            }
            must "not (gtp-enable='true') or (not (protocol) or (protocol='17' and ((source-port=2152 and destination-port>=2152) or (destination-port=2152 and source-port>=2152))))" {
              tailf:xpath-root 3;
            }
            presence "Enable flow";
            description
              "Configure IFIT flow.";
            leaf flow-type {
              ext:operation-exclude "update";
              type ifit-common:flow-type;
              mandatory true;
              description
                "Flow type of an IFIT flow.";
            }
            choice flow-filter {
              mandatory true;
              description
                "Configure the filter of a flow.";
              case filter-condition1 {
                description
                  "Filter condition 1.";
                choice flow-address-type {
                  mandatory true;
                  description
                    "Configure the address of a flow.";
                  case ipv4-condition {
                    description
                      "IPv4 condition.";
                    leaf source-ip {
                      ext:operation-exclude "update|delete";
                      ext:support-filter "true";
                      type inet:ipv4-address-no-zone;
                      description
                        "Source IPv4 address of an IFIT flow.";
                    }
                    leaf destination-ip {
                      ext:operation-exclude "update";
                      ext:support-filter "true";
                      type inet:ipv4-address-no-zone;
                      must '../destination-ip != ../source-ip' {
                        tailf:xpath-root 3;
                      }
                      mandatory true;
                      description
                        "Destination IPv4 address of an IFIT flow.";
                    }
                    leaf source-mask {
                      when '../source-ip' {
                        tailf:xpath-root 3;
                      }
                      ext:operation-exclude "update|delete";
                      type uint8 {
                        range "1..32";
                      }
                      default "32";
                      description
                        "Source IPv4 address mask of an IFIT flow.";
                    }
                    leaf destination-mask {
                      ext:operation-exclude "update|delete";
                      type uint8 {
                        range "1..32";
                      }
                      default "32";
                      description
                        "Destination IPv4 address mask of an IFIT flow.";
                    }
                  }
                  case ipv6-condition {
                    description
                      "IPv6 condition.";
                    leaf source-ipv6 {
                      ext:operation-exclude "update";
                      ext:support-filter "true";
                      type inet:ipv6-address-no-zone;
                      mandatory true;
                      description
                        "Source IPv6 address of an IFIT flow.";
                    }
                    leaf destination-ipv6 {
                      ext:operation-exclude "update";
                      ext:support-filter "true";
                      type inet:ipv6-address-no-zone;
                      must '../destination-ipv6 != ../source-ipv6' {
                        tailf:xpath-root 3;
                      }
                      mandatory true;
                      description
                        "Destination IPv6 address of an IFIT flow.";
                    }
                    leaf source-ipv6-mask {
                      ext:operation-exclude "update|delete";
                      type uint8 {
                        range "32..128";
                      }
                      default "128";
                      description
                        "Source IPv6 address mask of an IFIT flow.";
                    }
                    leaf destination-ipv6-mask {
                      ext:operation-exclude "update|delete";
                      type uint8 {
                        range "32..128";
                      }
                      default "128";
                      description
                        "Destination IPv6 address mask of an IFIT flow.";
                    }
                  }
                }
                leaf protocol {
                  ext:operation-exclude "update|delete";
                  type uint8 {
                    range "0..254";
                    ext:value-meaning {
                      ext:item "6" {
                        ext:meaning "tcp";
                      }
                      ext:item "17" {
                        ext:meaning "udp";
                      }
                      ext:item "132" {
                        ext:meaning "sctp";
                      }
                    }
                  }
                  description
                    "Protocol of an IFIT flow.";
                }
                leaf source-port {
                  ext:operation-exclude "update|delete";
                  type uint16 {
                    range "1..65535";
                  }
                  must '../protocol=6 or ../protocol=17 or ../protocol=132' {
                    tailf:xpath-root 3;
                  }
                  description
                    "Source port of an IFIT flow.";
                }
                leaf destination-port {
                  ext:operation-exclude "update|delete";
                  type uint16 {
                    range "1..65535";
                  }
                  must '../protocol =6 or ../protocol=17 or ../protocol=132' {
                    tailf:xpath-root 3;
                  }
                  description
                    "Destination port of an IFIT flow.";
                }
                leaf gtp-enable {
                  when "../flow-type='unidirection'" {
                    tailf:xpath-root 3;
                  }
                  ext:operation-exclude "update|delete";
                  type boolean;
                  default "false";
                  description
                    "Enable/disable GTP protocol measure for an IFIT flow.";
                }
                leaf gtp-teid {
                  when "../flow-type='unidirection' and ../gtp-enable = 'true'" {
                    tailf:xpath-root 3;
                  }
                  ext:operation-exclude "update|delete";
                  type uint32 {
                    range "1..4294967295";
                  }
                  description
                    "GTP TEID of an IFIT flow.";
                }
                leaf ni-name {
                  ext:operation-exclude "update|delete";
                  type leafref {
                    path "/ncs:devices/ncs:device/ncs:config/ni:network-instance/ni:instances/ni:instance/ni:name" {
                      tailf:xpath-root 3;
                    }
                  }
                  must "../ni-name!='_public_' and (((../destination-ip) and /ni:network-instance/ni:instances/ni:instance[ni:name=current()]/l3vpn:afs/l3vpn:af[l3vpn:type='ipv4-unicast']) or ((../destination-ipv6) and /ni:network-instance/ni:instances/ni:instance[ni:name=current()]/l3vpn:afs/l3vpn:af[l3vpn:type='ipv6-unicast']))" {
                    tailf:xpath-root 3;
                  }
                  description
                    "Name of the VPN to which an IFIT flow belongs.";
                }
                leaf dscp {
                  ext:operation-exclude "update|delete";
                  type uint16 {
                    range "0..63";
                  }
                  description
                    "DSCP of an IFIT flow.";
                }
              }
              case filter-condition2 {
                when "flow-type='unidirection' and ../gtpu-sn-measure-enable='false'" {
                  tailf:xpath-root 3;
                }
                description
                  "Filter condition 2.";
                choice vpn-filter {
                  mandatory true;
                  description
                    "Configure the VPN filter of a flow.";
                  case ni-condition {
                    description
                      "Peer netconf instance condition.";
                    leaf address-type {
                      ext:operation-exclude "update";
                      type addr-family-type;
                      mandatory true;
                      description
                        "Address type of an IFIT flow peer.";
                    }
                    leaf peer-ni-name {
                      ext:operation-exclude "update";
                      type leafref {
                        path "/ncs:devices/ncs:device/ncs:config/ni:network-instance/ni:instances/ni:instance/ni:name" {
                          tailf:xpath-root 3;
                        }
                      }
                      must " ../peer-ni-name!='_public_' and /ni:network-instance/ni:instances/ni:instance[ni:name = current()]/l3vpn:afs/l3vpn:af[l3vpn:type=current()/../address-type]" {
                        tailf:xpath-root 3;
                      }
                      mandatory true;
                      description
                        "Name of the VPN to which an IFIT flow peer belongs.";
                    }
                  }
                  case evpl-condition {
                    description
                      "Peer EVPL condition.";
                    leaf peer-evpl-id {
                      ext:operation-exclude "update";
                      type leafref {
                        path "/ncs:devices/ncs:device/ncs:config/evpl:evpl/evpl:instances/evpl:instance/evpl:id" {
                          tailf:xpath-root 3;
                        }
                      }
                      must "((../peer-ip and /evpl:evpl/evpl:instances/evpl:instance[evpl:id=current()][evpl:mode='mpls-mode']) or (../peer-locator-prefix and /evpl:evpl/evpl:instances/evpl:instance[evpl:id=current()][evpl:mode='srv6-mode']))" {
                        tailf:xpath-root 3;
                      }
                      mandatory true;
                      description
                        "ID of the EVPL instance to which an IFIT flow peer belongs.";
                    }
                  }
                }
                choice peer-filter {
                  mandatory true;
                  description
                    "Configure the peer filter of a flow.";
                  case ip-condition {
                    description
                      "Peer filter ip condition.";
                    leaf peer-ip {
                      ext:operation-exclude "update";
                      type inet:ipv4-address-no-zone;
                      mandatory true;
                      description
                        "Peer IP address of an IFIT flow.";
                    }
                  }
                  case locator-condition {
                    description
                      "Peer filter locatior condition.";
                    leaf peer-locator-prefix {
                      ext:operation-exclude "update";
                      type inet:ipv6-address-no-zone;
                      mandatory true;
                      description
                        "Peer locator address.";
                    }
                    leaf peer-locator-prefix-mask-len {
                      ext:operation-exclude "update";
                      type uint32 {
                        range "32..120";
                      }
                      mandatory true;
                      description
                        "Mask length of a peer locator address.";
                    }
                  }
                }
              }
            }
            container bind-ifs {
              description
                "List of flow specified interfaces of IFIT.";
              list bind-if {
                key "if-name";
                description
                  "Configure flow specified interface of IFIT.";
                leaf if-name {
                  type leafref {
                    path "/ncs:devices/ncs:device/ncs:config/ifm:ifm/ifm:interfaces/ifm:interface/ifm:name" {
                      tailf:xpath-root 3;
                    }
                  }
                  description
                    "Interface name to which an IFIT flow binds.";
                }
                // NCS drop config false leaf 'flow-id'
              }
            }
          }
        }
      }
      // NCS drop config false container 'dynamic-flow-hops'
      // NCS drop config false container 'dynamic-flows'
    }
  }
}
