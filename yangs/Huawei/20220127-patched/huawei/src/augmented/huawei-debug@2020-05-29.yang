module huawei-debug {
  // Generated by yanger -t ncs
  tailf:mount-id "huawei-nc-1.0:huawei-nc-1.0";
  tailf:ncs-device-type "netconf";

  namespace "urn:huawei:yang:huawei-debug";
  prefix debug;

  import huawei-extension {
    prefix ext;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Global configuration.";

  revision 2020-05-29 {
    description
      "Init revision.";
    reference "Huawei private.";
  }
  ext:task-name "diagnose";

  augment "/ncs:devices/ncs:device/ncs:config" {
    container debug {
      tailf:ncs-device-type "netconf";
      tailf:display-when "not(../../ncs:module) or ../../ncs:module[ncs:name='huawei-debug']";
      description
        "Debug information.";
      container cpu-infos {
        description
          "List of CPU information of boards.";
        list cpu-info {
          must 'unoverload-threshold <= (overload-threshold - 3)' {
            tailf:xpath-root 3;
          }
          key "position";
          ext:generated-by "system";
          ext:operation-exclude "create";
          description
            "Configure CPU information of a board.";
          leaf position {
            type string {
              length "1..32";
            }
            description
              "Board position.";
          }
          leaf overload-threshold {
            type uint32 {
              range "4..100";
            }
            units "%";
            default "90";
            description
              "Overload threshold.";
          }
          leaf unoverload-threshold {
            type uint32 {
              range "1..97";
            }
            units "%";
            default "75";
            description
              "Overload alarm clear threshold.";
          }
          leaf interval {
            type uint32 {
              range "1..60";
            }
            units "min";
            default "8";
            description
              "Overload alarm cycle.";
          }
          // NCS drop config false leaf index
          // NCS drop config false leaf 'system-cpu-usage'
          // NCS drop config false leaf 'monitor-number'
          // NCS drop config false leaf 'monitor-cycle'
          // NCS drop config false leaf 'overload-state-change-time'
          // NCS drop config false leaf 'current-overload-state'
        }
      }
      container memory-infos {
        description
          "List of memory information of boards.";
        list memory-info {
          must 'unoverload-threshold <= (overload-threshold - 3)' {
            tailf:xpath-root 3;
          }
          must 'overload-threshold <= memreli-exception-threshold' {
            tailf:xpath-root 3;
          }
          must 'memreli-notice-threshold <= (memreli-overload-threshold - 5)' {
            tailf:xpath-root 3;
          }
          must 'memreli-overload-threshold <= (memreli-exception-threshold - 5)' {
            tailf:xpath-root 3;
          }
          key "position";
          ext:generated-by "system";
          ext:operation-exclude "create";
          description
            "Configure memory information about a board.";
          leaf position {
            type string {
              length "1..32";
            }
            description
              "Board position.";
          }
          leaf overload-threshold {
            ext:dynamic-default;
            type uint32 {
              range "75..100";
            }
            units "%";
            description
              "Overload threshold.";
          }
          leaf unoverload-threshold {
            ext:dynamic-default;
            type uint32 {
              range "1..97";
            }
            units "%";
            description
              "Overload alarm clear threshold.";
          }
          leaf memreli-notice-threshold {
            ext:dynamic-default;
            type uint32 {
              range "5..90";
            }
            units "%";
            description
              "Board memory reliability notice threshold.";
          }
          leaf memreli-overload-threshold {
            ext:dynamic-default;
            type uint32 {
              range "10..95";
            }
            units "%";
            description
              "Board memory reliability overload threshold.";
          }
          leaf memreli-exception-threshold {
            ext:dynamic-default;
            type uint32 {
              range "75..100";
            }
            units "%";
            description
              "Board memory reliability exception threshold.";
          }
          // NCS drop config false leaf index
          // NCS drop config false leaf 'os-memory-total'
          // NCS drop config false leaf 'os-memory-use'
          // NCS drop config false leaf 'os-memory-free'
          // NCS drop config false leaf 'os-memory-usage'
          // NCS drop config false leaf 'do-memory-total'
          // NCS drop config false leaf 'do-memory-use'
          // NCS drop config false leaf 'do-memory-free'
          // NCS drop config false leaf 'do-memory-usage'
          // NCS drop config false leaf 'simple-memory-total'
          // NCS drop config false leaf 'simple-memory-use'
          // NCS drop config false leaf 'simple-memory-free'
          // NCS drop config false leaf 'simple-memory-usage'
          // NCS drop config false leaf 'overload-state-change-time'
          // NCS drop config false leaf 'current-overload-state'
        }
      }
      container resouce-reliability {
        description
          "Configure resouce reliability info.";
        container memory-reliability {
          description
            "Configure memory reliability info.";
          leaf enable {
            type boolean;
            default "false";
            description
              "Enable/disable memory reliability.";
          }
        }
        container memory-reliability-switchover-threshold {
          description
            "Configure memory threshold for board switchover.";
          leaf threshold {
            ext:dynamic-default;
            type uint32 {
              range "50..100";
            }
            units "%";
            description
              "Memory threshold for board switchover.";
          }
        }
        container flow-control-message-reliability {
          description
            "Configure flow-control-message reliability info.";
          leaf enable {
            type boolean;
            default "true";
            description
              "Enable/disable flow-control-message reliability.";
          }
        }
      }
      // NCS drop config false container 'service-cpu-infos'
      // NCS drop config false container 'board-resouce-states'
    }
  }
  augment "/ncs:devices/ncs:device/ncs:live-status" {
    container debug {
      tailf:ncs-device-type "netconf";
      tailf:display-when "not(../../ncs:module) or ../../ncs:module[ncs:name='huawei-debug'] or (../../ncs:live-status-protocol[not(ncs:capability)]) or (../../ncs:live-status-protocol/ncs:capability/ncs:module[.='huawei-debug'])";
      description
        "Debug information.";
      container cpu-infos {
        description
          "List of CPU information of boards.";
        list cpu-info {
          // NCS drop must statement
          key "position";
          ext:generated-by "system";
          ext:operation-exclude "create";
          description
            "Configure CPU information of a board.";
          leaf position {
            type string {
              length "1..32";
            }
            description
              "Board position.";
          }
          leaf overload-threshold {
            type uint32 {
              range "4..100";
            }
            units "%";
            // NCS drop default statement
            description
              "Overload threshold.";
          }
          leaf unoverload-threshold {
            type uint32 {
              range "1..97";
            }
            units "%";
            // NCS drop default statement
            description
              "Overload alarm clear threshold.";
          }
          leaf interval {
            type uint32 {
              range "1..60";
            }
            units "min";
            // NCS drop default statement
            description
              "Overload alarm cycle.";
          }
          leaf index {
            type uint32;
            description
              "Board index.";
          }
          leaf system-cpu-usage {
            type uint32 {
              range "0..100";
            }
            units "%";
            description
              "CPU usage.";
          }
          leaf monitor-number {
            type uint32 {
              range "6..360";
            }
            description
              "Monitor number in one alarm cycle.";
          }
          leaf monitor-cycle {
            type uint32;
            units "s";
            description
              "Monitor cycle.";
          }
          leaf overload-state-change-time {
            type string {
              length "1..32";
            }
            description
              "Last overload state changetime.";
          }
          leaf current-overload-state {
            type string {
              length "1..31";
            }
            description
              "Current overload state.";
          }
        }
      }
      container memory-infos {
        description
          "List of memory information of boards.";
        list memory-info {
          // NCS drop must statement
          // NCS drop must statement
          // NCS drop must statement
          // NCS drop must statement
          key "position";
          ext:generated-by "system";
          ext:operation-exclude "create";
          description
            "Configure memory information about a board.";
          leaf position {
            type string {
              length "1..32";
            }
            description
              "Board position.";
          }
          leaf overload-threshold {
            ext:dynamic-default;
            type uint32 {
              range "75..100";
            }
            units "%";
            description
              "Overload threshold.";
          }
          leaf unoverload-threshold {
            ext:dynamic-default;
            type uint32 {
              range "1..97";
            }
            units "%";
            description
              "Overload alarm clear threshold.";
          }
          leaf memreli-notice-threshold {
            ext:dynamic-default;
            type uint32 {
              range "5..90";
            }
            units "%";
            description
              "Board memory reliability notice threshold.";
          }
          leaf memreli-overload-threshold {
            ext:dynamic-default;
            type uint32 {
              range "10..95";
            }
            units "%";
            description
              "Board memory reliability overload threshold.";
          }
          leaf memreli-exception-threshold {
            ext:dynamic-default;
            type uint32 {
              range "75..100";
            }
            units "%";
            description
              "Board memory reliability exception threshold.";
          }
          leaf index {
            type uint32;
            description
              "Board index.";
          }
          leaf os-memory-total {
            type uint32;
            units "kB";
            description
              "Total OS memory.";
          }
          leaf os-memory-use {
            type uint32;
            units "kB";
            description
              "Used OS memory.";
          }
          leaf os-memory-free {
            type uint32;
            units "kB";
            description
              "Available OS memory.";
          }
          leaf os-memory-usage {
            type uint32 {
              range "0..100";
            }
            units "%";
            description
              "OS memory usage.";
          }
          leaf do-memory-total {
            type uint32;
            units "kB";
            description
              "Total VRP memory.";
          }
          leaf do-memory-use {
            type uint32;
            units "kB";
            description
              "Used VRP memory.";
          }
          leaf do-memory-free {
            type uint32;
            units "kB";
            description
              "Available VRP memory.";
          }
          leaf do-memory-usage {
            type uint32 {
              range "0..100";
            }
            units "%";
            description
              "VRP memory usage.";
          }
          leaf simple-memory-total {
            type uint32;
            units "kB";
            description
              "Total simple memory.";
          }
          leaf simple-memory-use {
            type uint32;
            units "kB";
            description
              "Used simple memory.";
          }
          leaf simple-memory-free {
            type uint32;
            units "kB";
            description
              "Available simple memory.";
          }
          leaf simple-memory-usage {
            type uint32 {
              range "0..100";
            }
            units "%";
            description
              "Simple memory usage.";
          }
          leaf overload-state-change-time {
            type string {
              length "1..31";
            }
            description
              "Last overload state changetime.";
          }
          leaf current-overload-state {
            type string {
              length "1..32";
            }
            description
              "Current overload state.";
          }
        }
      }
      container resouce-reliability {
        description
          "Configure resouce reliability info.";
        container memory-reliability {
          description
            "Configure memory reliability info.";
          leaf enable {
            type boolean;
            // NCS drop default statement
            description
              "Enable/disable memory reliability.";
          }
        }
        container memory-reliability-switchover-threshold {
          description
            "Configure memory threshold for board switchover.";
          leaf threshold {
            ext:dynamic-default;
            type uint32 {
              range "50..100";
            }
            units "%";
            description
              "Memory threshold for board switchover.";
          }
        }
        container flow-control-message-reliability {
          description
            "Configure flow-control-message reliability info.";
          leaf enable {
            type boolean;
            // NCS drop default statement
            description
              "Enable/disable flow-control-message reliability.";
          }
        }
      }
      container service-cpu-infos {
        description
          "List of service cpu-usage information of boards.";
        list service-cpu-info {
          key "position service-name";
          description
            "Service cpu-usage statistics for a board.";
          leaf position {
            type string {
              length "1..32";
            }
            description
              "Board position.";
          }
          leaf service-name {
            type string {
              length "0..50";
            }
            description
              "Service name.";
          }
          leaf service-cpu-usage {
            type uint32 {
              range "0..100";
            }
            units "%";
            description
              "CPU usage of service.";
          }
        }
      }
      container board-resouce-states {
        description
          "List of board monitoring information.";
        list board-resouce-state {
          key "position";
          description
            "Board monitoring statistics.";
          leaf position {
            type string {
              length "1..32";
            }
            description
              "Board position.";
          }
          leaf entity-index {
            type uint32;
            description
              "Board index.";
          }
          leaf board-name {
            type string {
              length "0..128";
            }
            description
              "Board name.";
          }
          leaf cpu-usage {
            type uint32;
            units "%";
            description
              "CPU usage.";
          }
          leaf memory-total-size {
            type uint32;
            units "kB";
            description
              "Total memory size.";
          }
          leaf memory-used-size {
            type uint32;
            units "kB";
            description
              "Used memory size.";
          }
          leaf memory-usage {
            type uint32;
            units "%";
            description
              "Memory usage.";
          }
        }
      }
    }
  }
  augment "/ncs:devices/ncs:template/ncs:ned-id/ncs:config" {
    container debug {
      description
        "Debug information.";
      container cpu-infos {
        description
          "List of CPU information of boards.";
        list cpu-info {
          // NCS patched for predictable order
          ordered-by user;
          // NCS drop must statement
          key "position";
          ext:generated-by "system";
          ext:operation-exclude "create";
          description
            "Configure CPU information of a board.";
          leaf position {
            type string;
            description
              "Board position.";
          }
          leaf overload-threshold {
            type string;
            units "%";
            // NCS drop default statement
            description
              "Overload threshold.";
          }
          leaf unoverload-threshold {
            type string;
            units "%";
            // NCS drop default statement
            description
              "Overload alarm clear threshold.";
          }
          leaf interval {
            type string;
            units "min";
            // NCS drop default statement
            description
              "Overload alarm cycle.";
          }
          // NCS drop config false leaf index
          // NCS drop config false leaf 'system-cpu-usage'
          // NCS drop config false leaf 'monitor-number'
          // NCS drop config false leaf 'monitor-cycle'
          // NCS drop config false leaf 'overload-state-change-time'
          // NCS drop config false leaf 'current-overload-state'
        }
      }
      container memory-infos {
        description
          "List of memory information of boards.";
        list memory-info {
          // NCS patched for predictable order
          ordered-by user;
          // NCS drop must statement
          // NCS drop must statement
          // NCS drop must statement
          // NCS drop must statement
          key "position";
          ext:generated-by "system";
          ext:operation-exclude "create";
          description
            "Configure memory information about a board.";
          leaf position {
            type string;
            description
              "Board position.";
          }
          leaf overload-threshold {
            ext:dynamic-default;
            type string;
            units "%";
            description
              "Overload threshold.";
          }
          leaf unoverload-threshold {
            ext:dynamic-default;
            type string;
            units "%";
            description
              "Overload alarm clear threshold.";
          }
          leaf memreli-notice-threshold {
            ext:dynamic-default;
            type string;
            units "%";
            description
              "Board memory reliability notice threshold.";
          }
          leaf memreli-overload-threshold {
            ext:dynamic-default;
            type string;
            units "%";
            description
              "Board memory reliability overload threshold.";
          }
          leaf memreli-exception-threshold {
            ext:dynamic-default;
            type string;
            units "%";
            description
              "Board memory reliability exception threshold.";
          }
          // NCS drop config false leaf index
          // NCS drop config false leaf 'os-memory-total'
          // NCS drop config false leaf 'os-memory-use'
          // NCS drop config false leaf 'os-memory-free'
          // NCS drop config false leaf 'os-memory-usage'
          // NCS drop config false leaf 'do-memory-total'
          // NCS drop config false leaf 'do-memory-use'
          // NCS drop config false leaf 'do-memory-free'
          // NCS drop config false leaf 'do-memory-usage'
          // NCS drop config false leaf 'simple-memory-total'
          // NCS drop config false leaf 'simple-memory-use'
          // NCS drop config false leaf 'simple-memory-free'
          // NCS drop config false leaf 'simple-memory-usage'
          // NCS drop config false leaf 'overload-state-change-time'
          // NCS drop config false leaf 'current-overload-state'
        }
      }
      container resouce-reliability {
        description
          "Configure resouce reliability info.";
        container memory-reliability {
          description
            "Configure memory reliability info.";
          leaf enable {
            type string;
            // NCS drop default statement
            description
              "Enable/disable memory reliability.";
          }
        }
        container memory-reliability-switchover-threshold {
          description
            "Configure memory threshold for board switchover.";
          leaf threshold {
            ext:dynamic-default;
            type string;
            units "%";
            description
              "Memory threshold for board switchover.";
          }
        }
        container flow-control-message-reliability {
          description
            "Configure flow-control-message reliability info.";
          leaf enable {
            type string;
            // NCS drop default statement
            description
              "Enable/disable flow-control-message reliability.";
          }
        }
      }
      // NCS drop config false container 'service-cpu-infos'
      // NCS drop config false container 'board-resouce-states'
    }
  }
}
