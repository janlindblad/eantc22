module huawei-aaa {
  // Generated by yanger -t ncs
  tailf:mount-id "huawei-nc-1.0:huawei-nc-1.0";
  tailf:ncs-device-type "netconf";

  namespace "urn:huawei:yang:huawei-aaa";
  prefix aaa;

  import huawei-hwtacacs {
    prefix hwtacacs;
  }
  import huawei-extension {
    prefix ext;
  }
  include huawei-aaa-type;
  include huawei-aaa-lam;
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Security management, which includes the management on authentication, authorization, accounting, domains, and users.";

  revision 2020-07-01 {
    description
      "Add node constraint information.";
    reference "Huawei private.";
  }
  revision 2020-06-17 {
    description
      "Add management-user-qrys node.";
    reference "Huawei private.";
  }
  revision 2020-03-02 {
    description
      "Init revision.";
    reference "Huawei private.";
  }
  ext:task-name "aaa";

  augment "/ncs:devices/ncs:device/ncs:config" {
    container aaa {
      tailf:ncs-device-type "netconf";
      tailf:display-when "not(../../ncs:module) or ../../ncs:module[ncs:name='huawei-aaa']";
      description
        "Security management, which includes the management on authentication, authorization, accounting, domains, and users.";
      // NCS drop config false container tasks
      container task-groups {
        description
          "List of task groups.";
        list task-group {
          key "name";
          max-elements 256;
          description
            "Configure a collection of certain tasks. The default task groups are set in the system before the NE delivery and cannot be deleted.";
          leaf name {
            type string {
              length "1..32";
              pattern '[^A-Z/\*":?<>|]+';
            }
            ext:case-sensitivity "lower-only";
            description
              "Name of a task group.";
          }
          container task-group-include-maps {
            description
              "List of the task groups included in a main task group.";
            list task-group-include-map {
              key "include-task-group-name";
              max-elements 1;
              description
                "Configure task group included in a main task group.";
              leaf include-task-group-name {
                type leafref {
                  path "../../../name";
                }
                must '(../../../name!=../include-task-group-name)' {
                  tailf:xpath-root 3;
                }
                description
                  "Name of included task group, it is not case sensitive.";
              }
            }
          }
          container task-group-task-maps {
            description
              "List of the tasks included in a task group.";
            list task-group-task-map {
              key "task-name";
              description
                "Configure task in a task group. The default task group cannot be modified.";
              leaf task-name {
                type string {
                  length "1..32";
                  pattern '[^A-Z]+';
                }
                ext:case-sensitivity "lower-only";
                must "(../write='enable' or ../execute='enable' or ../debug='enable' or ../read='enable')" {
                  tailf:xpath-root 3;
                }
                description
                  "Name of a task. It must be an existing task.";
              }
              leaf read {
                type aaa-enable-type;
                must "not(../write='disable' and ../execute='disable' and ../debug='disable') or (../write='disable' and ../execute='disable' and ../debug='disable' and ../read!=../write)" {
                  tailf:xpath-root 3;
                }
                default "disable";
                description
                  "To determine whether a task has the read right.";
              }
              leaf write {
                type aaa-enable-type;
                default "disable";
                description
                  "To determine whether a task has the write right.";
              }
              leaf execute {
                type aaa-enable-type;
                default "disable";
                description
                  "To determine whether a task has the operation right.";
              }
              leaf debug {
                type aaa-enable-type;
                default "disable";
                description
                  "To determine whether a task has the debug right.";
              }
            }
          }
        }
      }
      container user-groups {
        description
          "List of user groups.";
        list user-group {
          key "name";
          max-elements 64;
          description
            "Configure a collection of certain users. Certain default user groups are set before an NE is delivered and cannot be deleted.";
          leaf name {
            type string {
              length "1..32";
              pattern '[^A-Z/\*":?<>|]+';
            }
            ext:case-sensitivity "lower-only";
            description
              "Name of a user group.";
          }
          container user-group-task-group-maps {
            description
              "List of the task groups included in a user group.";
            list user-group-task-group-map {
              key "task-group-name";
              description
                "Configure task group in a user group.";
              leaf task-group-name {
                type leafref {
                  path "../../../../../task-groups/task-group/name";
                }
                description
                  "Name of a task group, it is not case sensitive.";
              }
            }
          }
          container user-group-include-maps {
            description
              "List of the user groups included in a main user group.";
            list user-group-include-map {
              key "include-user-group-name";
              max-elements 1;
              description
                "Configure user group included in a main user group.";
              leaf include-user-group-name {
                type leafref {
                  path "../../../name";
                }
                must '(../../../name!=../include-user-group-name)' {
                  tailf:xpath-root 3;
                }
                description
                  "Name of a task group, it is not case sensitive.";
              }
            }
          }
        }
      }
      container authentication-schemes {
        description
          "List of authentication scheme.";
        list authentication-scheme {
          key "authen-scheme-name";
          max-elements 32;
          description
            "Configure authentication scheme. The default authentication scheme cannot be deleted.";
          leaf authen-scheme-name {
            type string {
              length "1..32";
              pattern '[^A-Z/\*":?<>|]+';
            }
            ext:case-sensitivity "lower-only";
            description
              "Name of an authentication scheme.";
          }
          choice authen-mode-type {
            description
              "Sorting method of authentication mode.";
            case ordered-strictly {
              description
                "Ordered strictly case.";
              leaf first-authen-mode {
                type aaa-authen-mode;
                must "(../first-authen-mode!='invalid' )" {
                  tailf:xpath-root 3;
                }
                default "local";
                description
                  "Preferred authentication mode. The second, third, or fourth authentication mode is used only when the first authentication mode does not respond. The first authentication mode cannot be set to unavailable.";
              }
              leaf second-authen-mode {
                type aaa-authen-mode;
                must "(../second-authen-mode!='radius-proxy' and (((../first-authen-mode='none' or ../first-authen-mode='radius-proxy') and (../second-authen-mode='invalid')) or ((../first-authen-mode!='none' and ../first-authen-mode!='radius-proxy') and ../first-authen-mode!=../second-authen-mode)))" {
                  tailf:xpath-root 3;
                }
                default "invalid";
                description
                  "Authentication mode with the preference lower than the first authentication mode. The second authentication mode is used when the first authentication mode does not respond. If the setting of the second authentication mode is unavailable, the third and fourth authentication modes fail to be set.";
              }
              leaf third-authen-mode {
                type aaa-authen-mode;
                must "(../third-authen-mode!='radius-proxy' and ((../second-authen-mode ='none' or ../second-authen-mode='invalid') and (../third-authen-mode='invalid') ) or ((../second-authen-mode !='none' and ../second-authen-mode!='invalid'  and ../first-authen-mode!='radius-proxy') and ../third-authen-mode!=../second-authen-mode and ../third-authen-mode!=../first-authen-mode ))" {
                  tailf:xpath-root 3;
                }
                default "invalid";
                description
                  "Authentication mode with the preference lower than the first and second authentication modes. The third authentication mode is used when the first and second authentication modes do not respond. If the setting of the third authentication mode is unavailable, the fourth authentication mode fails to be set.";
              }
              leaf fourth-authen-mode {
                type aaa-authen-mode;
                must "(../fourth-authen-mode='none' and ../first-authen-mode!='invalid' and ../first-authen-mode!='none' and ../first-authen-mode!='radius-proxy' and ../second-authen-mode!='invalid' and ../second-authen-mode!='none' and ../third-authen-mode!='invalid' and ../third-authen-mode!='none' ) or ../fourth-authen-mode='invalid' " {
                  tailf:xpath-root 3;
                }
                default "invalid";
                description
                  "Authentication mode with the least preference. The fourth authentication mode is used when the first, second, and third authentication modes do not respond. If the setting of the fourth authentication mode is unavailable or the fourth authentication mode does not respond, the authentication fails.";
              }
            }
          }
        }
      }
      container authorization-schemes {
        description
          "List of authorization scheme.";
        list authorization-scheme {
          key "author-scheme-name";
          max-elements 32;
          description
            "Configure authorization scheme. The default authorization scheme cannot be deleted.";
          leaf author-scheme-name {
            type string {
              length "1..32";
              pattern '[^A-Z/\*":?<>|]+';
            }
            ext:case-sensitivity "lower-only";
            description
              "Name of an authorization scheme. The name uniquely identifies the authorization scheme and can be used in the domain.";
          }
          choice author-mode-type {
            description
              "Sorting method of authorization mode.";
            case ordered-strictly {
              description
                "Ordered strictly case.";
              leaf first-author-mode {
                type aaa-author-mode;
                must "../first-author-mode='local' or ../first-author-mode='hwtacacs' or ../first-author-mode='if-authenticated' or ../first-author-mode='none'" {
                  tailf:xpath-root 3;
                }
                default "local";
                description
                  "Preferred authorization mode. The second, third, or fourth authorization mode can be used only when the first authorization mode does not respond. The first authorization mode must be available.";
              }
              leaf second-author-mode {
                type aaa-author-mode;
                must "(../first-author-mode='none' and (../second-author-mode='invalid') ) or (../first-author-mode!='invalid' and ../first-author-mode!='none' and ../second-author-mode!=../first-author-mode)" {
                  tailf:xpath-root 3;
                }
                default "invalid";
                description
                  "Authorization mode with the preference next to the first authorization mode. It is used when the first authorization mode does not respond. If the setting of the second authorization mode is unavailable, the third and fourth authorization modes fail to be set.";
              }
              leaf third-author-mode {
                type aaa-author-mode;
                must "((../second-author-mode='none' or ../second-author-mode='invalid') and ../third-author-mode='invalid' ) or (../second-author-mode !='none' and ../second-author-mode!='invalid'  and ../first-author-mode!='none' and ../third-author-mode!=../second-author-mode and ../third-author-mode!=../first-author-mode ) or (../first-author-mode='none' and (../third-author-mode='invalid') )" {
                  tailf:xpath-root 3;
                }
                default "invalid";
                description
                  "Authorization mode with the preference next to the first and second authorization modes. It is used when the first and second authorization modes do not respond. If the setting of the third authorization mode is unavailable, the fourth authorization mode fails to be set.";
              }
              leaf fourth-author-mode {
                type aaa-author-mode;
                must "(../fourth-author-mode='none' and ../first-author-mode!='invalid' and ../first-author-mode!='none' and ../second-author-mode!='invalid' and ../second-author-mode!='none' and ../third-author-mode!='invalid' and ../third-author-mode!='none' ) or ../fourth-author-mode='invalid' " {
                  tailf:xpath-root 3;
                }
                default "invalid";
                description
                  "Authorization mode with the least preference. It is used when the first, second, and third authorization modes do not respond. If the setting of the fourth authorization mode is unavailable or the fourth authorization mode does not respond, the authorization fails.";
              }
            }
          }
          leaf no-lvl-first-cmd-author {
            type aaa-author-cmd-mode;
            must "../no-lvl-first-cmd-author='local' or ../no-lvl-first-cmd-author='hwtacacs'" {
              tailf:xpath-root 3;
            }
            default "local";
            description
              "Configures the first authorization mode for users of user group.";
          }
          leaf no-lvl-second-cmd-author {
            type aaa-author-cmd-mode;
            must "(../no-lvl-first-cmd-author='local' and (../no-lvl-second-cmd-author='invalid' or ../no-lvl-second-cmd-author='hwtacacs') ) or ((not(../no-lvl-first-cmd-author='local') and (../no-lvl-second-cmd-author='invalid' or ../no-lvl-second-cmd-author='local') ))" {
              tailf:xpath-root 3;
            }
            default "invalid";
            description
              "Configures the second authorization mode for users of user group.";
          }
          leaf no-response-policy {
            type author-no-res-policy-type;
            default "online";
            description
              "Configures a policy for a scenario where no responses are obtained during command line-based authorization.";
          }
          leaf no-response-times {
            when "../no-response-policy='offline'" {
              tailf:xpath-root 3;
            }
            type uint32 {
              range "1..10";
            }
            default "5";
            description
              "Configures the number of times of failed authorization.";
          }
          container authorization-cmds {
            description
              "List of authorization cmd.";
            list authorization-cmd {
              key "level";
              description
                "Configure authorization cmd.";
              leaf level {
                type uint32 {
                  range "0..15";
                }
                description
                  "The level of authorization cmd.";
              }
              choice cmd-author-mode-type {
                description
                  "Sorting method of cmd authorization mode.";
                case ordered-strictly {
                  description
                    "Ordered strictly case.";
                  leaf first-cmd-author {
                    type aaa-author-cmd-mode;
                    must "../first-cmd-author='local' or ../first-cmd-author='hwtacacs'" {
                      tailf:xpath-root 3;
                    }
                    default "local";
                    description
                      "First cmd authorization mode.";
                  }
                  leaf second-cmd-author {
                    type aaa-author-cmd-mode;
                    must "(../first-cmd-author='local' and (../second-cmd-author='invalid' or ../second-cmd-author='hwtacacs') ) or ((not(../first-cmd-author='local') and (../second-cmd-author='invalid' or ../second-cmd-author='local') ))" {
                      tailf:xpath-root 3;
                    }
                    default "invalid";
                    description
                      "Second cmd authorization mode.";
                  }
                }
              }
            }
          }
        }
      }
      container accounting-schemes {
        description
          "List of accounting scheme.";
        list accounting-scheme {
          key "acct-scheme-name";
          max-elements 256;
          description
            "Configure accounting scheme. The default accounting scheme cannot be deleted.";
          leaf acct-scheme-name {
            type string {
              length "1..32";
              pattern '[^A-Z/\*":?<>|]+';
            }
            ext:case-sensitivity "lower-only";
            description
              "Accounting scheme name.";
          }
          leaf accounting-mode {
            type aaa-acct-mode;
            must "../accounting-mode='radius' or ../accounting-mode='hwtacacs' or ../accounting-mode='none'" {
              tailf:xpath-root 3;
            }
            default "none";
            description
              "Accounting Mode.";
          }
        }
      }
      container domains {
        description
          "List of domain.";
        list domain {
          key "name";
          max-elements 1024;
          description
            "Configure in a domain, users apply the same authentication/authorization scheme or server. The default domain cannot be deleted.";
          leaf name {
            type string {
              length "1..64";
              pattern "([^A-Z*?\"']{3,})|[^A-Z*?\"'-]|([^A-Z*?\"'-][^A-Z*?\"'])|([^A-Z*?\"'][^A-Z*?\"'-])";
            }
            ext:case-sensitivity "lower-only";
            description
              "Name of a domain.";
          }
          leaf admin-level {
            type uint32 {
              range "0..15";
            }
            description
              "The admin level of domain. If the command level adjustment function is disabled, the value of adminLevel ranges from 0 to 3. If the command level adjustment function is enabled, the value of adminLevel ranges from 0 to 15.";
          }
          leaf authen-scheme-name {
            type leafref {
              path "../../../authentication-schemes/authentication-scheme/authen-scheme-name";
            }
            ext:dynamic-default {
              ext:default-value "default0" {
                when "../name = 'default0'" {
                  tailf:xpath-root 3;
                }
              }
              ext:default-value "default1" {
                when "../name = 'default1'" {
                  tailf:xpath-root 3;
                }
              }
              ext:default-value "default" {
                when "../name = 'default_admin'" {
                  tailf:xpath-root 3;
                }
              }
              ext:default-value "default1";
            }
            description
              "Name of the authentication scheme used by the domain, it is not case sensitive. The default value varies according to domains. The default value is restored when the node is deleted.";
          }
          leaf author-scheme-name {
            type leafref {
              path "../../../authorization-schemes/authorization-scheme/author-scheme-name";
            }
            description
              "Name of the authorization scheme used by the domain, it is not case sensitive. The default value varies according to domains. The default value is restored when the node is deleted.";
          }
          leaf acct-scheme-name {
            type leafref {
              path "../../../accounting-schemes/accounting-scheme/acct-scheme-name";
            }
            ext:dynamic-default {
              ext:default-value "default0" {
                when "../name = 'default0'" {
                  tailf:xpath-root 3;
                }
              }
              ext:default-value "default1" {
                when "../name = 'default1'" {
                  tailf:xpath-root 3;
                }
              }
              ext:default-value "default0" {
                when "../name = 'default_admin'" {
                  tailf:xpath-root 3;
                }
              }
              ext:default-value "default1";
            }
            description
              "Name of the accounting scheme used by the domain, it is not case sensitive. The default value varies according to domains. The default value is restored when the node is deleted.";
          }
          leaf access-limit {
            type int32 {
              range "0..2147483647";
            }
            description
              "Domain max access number. The default value is defined in the PAF file and is restored when the node is deleted.";
          }
          leaf radius-server-template {
            type string {
              length "1..32";
            }
            description
              "Name of the RADIUS server used by the domain, it is not case sensitive.";
          }
          leaf hwtacacs-server-template {
            type leafref {
              path "/ncs:devices/ncs:device/ncs:config/hwtacacs:hwtacacs/hwtacacs:templates/hwtacacs:template/hwtacacs:name" {
                tailf:xpath-root 3;
              }
            }
            description
              "Name of the HWTACACS server used by the domain, it is not case sensitive.";
          }
          leaf state {
            type aaa-state-type;
            default "active";
            description
              "Activated state of the domain.";
          }
          leaf time-range-enable {
            type boolean;
            default "false";
            description
              "Enable/disable the time range function used by a domain.";
          }
          leaf service-terminal {
            type boolean;
            default "true";
            description
              "Enable/disable users to log in Terminal mode.";
          }
          leaf service-telnet {
            type boolean;
            default "true";
            description
              "Enable/disable users to log in Telnet mode.";
          }
          leaf service-ftp {
            type boolean;
            default "true";
            description
              "Enable/disable users to log in FTP mode.";
          }
          leaf service-ppp {
            type boolean;
            default "true";
            description
              "Enable/disable users to log in PPP mode.";
          }
          leaf service-ssh {
            type boolean;
            default "true";
            description
              "Enable/disable users to log in SSH mode.";
          }
          leaf service-qx {
            type boolean;
            default "true";
            description
              "Enable/disable users to log in QX mode.";
          }
          leaf service-snmp {
            type boolean;
            default "true";
            description
              "Enable/disable users to log in SNMP mode.";
          }
          leaf service-mml {
            type boolean;
            default "true";
            description
              "Enable/disable users to log in MML mode.";
          }
          leaf service-http {
            type boolean;
            default "true";
            description
              "Enable/disable users to log in HTTP mode.";
          }
          // NCS drop config false leaf 'online-num'
        }
      }
      container login-alarm-threshold {
        description
          "Configure alarm when manager login failed frequently.";
        leaf report-times {
          type uint16 {
            range "0..100";
          }
          units "min";
          must '../resume-times<=../report-times' {
            tailf:xpath-root 3;
          }
          default "30";
          description
            "Login Alarm report times.";
        }
        leaf resume-times {
          type uint16 {
            range "0..100";
          }
          must '../resume-times<=../report-times' {
            tailf:xpath-root 3;
          }
          default "20";
          description
            "Login Alarm resume times.";
        }
        leaf period {
          type uint16 {
            range "1..120";
          }
          units "min";
          default "5";
          description
            "Login Alarm period.";
        }
      }
      // NCS drop config false container 'alive-user-qrys'
      container global-policy {
        description
          "Configure global policy.";
        leaf domain-location {
          type aaa-domain-location-type;
          default "after-delimiter";
          description
            "Domain Location.";
        }
        leaf domain-parse-direction {
          type aaa-parse-direction-type;
          default "left-to-right";
          description
            "Domain Parse Direction.";
        }
        leaf default-admin-domain {
          type leafref {
            path "../../domains/domain/name";
          }
          default "default_admin";
          description
            "Admin user default domain.";
        }
        leaf default-access-domain {
          type leafref {
            path "../../domains/domain/name";
          }
          default "default1";
          description
            "Access user default domain.";
        }
        leaf parse-priority {
          type aaa-parse-priority-type;
          default "domain-first";
          description
            "Specifies priorities for parsing domain names.";
        }
        leaf realm-location {
          type aaa-realm-location-type;
          default "before-delimiter";
          description
            "Specifies a position for a realm domain name.";
        }
        leaf real-name-delimiter {
          type string {
            length "1";
            pattern "[/:<>\\|@%']";
          }
          description
            "Specifies a realm name delimiter used to parse the user account. The value is a single character. It can be one of the following symbols: back-slant, /, :, <, >, |, @, %, '.";
        }
        leaf real-name-parse-direction {
          type aaa-parse-direction-type;
          default "left-to-right";
          description
            "Specifies a parsing direction for the realm name.";
        }
        leaf roam-character {
          type string {
            length "1";
            pattern '[/:*<>\|]';
          }
          default ":";
          description
            "Specifies an identifier for a roaming user. The value is a single character. It can be one of the following symbols: back-slant, /, :, *, <, >, |.";
        }
      }
      container recording {
        description
          "Configure recording function.";
        container function {
          description
            "Configure recording function.";
          leaf cmd-record-scheme {
            type leafref {
              path "../../schemes/scheme/name";
            }
            description
              "The recording scheme used by cmd recording.";
          }
          leaf system-record-scheme {
            type leafref {
              path "../../schemes/scheme/name";
            }
            description
              "Configures a solution to record system events. Currently, only events triggered by the reboot command are recorded.";
          }
          leaf outbound-record-scheme {
            type leafref {
              path "../../schemes/scheme/name";
            }
            description
              "Records remote login operations for the device that functions as the client.";
          }
        }
        container schemes {
          description
            "List of recording scheme.";
          list scheme {
            key "name";
            description
              "Configure recording scheme.";
            leaf name {
              type string {
                length "1..32";
                pattern '[^A-Z/\*":?<>|]+';
              }
              ext:case-sensitivity "lower-only";
              description
                "Recording scheme name.";
            }
            leaf tacacs-group {
              type leafref {
                path "/ncs:devices/ncs:device/ncs:config/hwtacacs:hwtacacs/hwtacacs:templates/hwtacacs:template/hwtacacs:name" {
                  tailf:xpath-root 3;
                }
              }
              description
                "The binded HWTACACS server.";
            }
          }
        }
      }
      container online-offline-rec-switch {
        description
          "Configure whether to enable login failure and logout recording for management users.";
        leaf login-fail-rec-switch {
          type aaa-enable-type;
          default "enable";
          description
            "Enables recording of login failures.";
        }
        leaf logout-rec-switch {
          type aaa-enable-type;
          default "enable";
          description
            "Enables recording of normal and abnormal logouts.";
        }
        leaf abnormal-logout-rec-switch {
          type aaa-enable-type;
          default "enable";
          description
            "Enables recording of abnormal logouts.";
        }
        leaf normal-logout-rec-switch {
          type aaa-enable-type;
          default "enable";
          description
            "Enables recording of normal logouts.";
        }
      }
      container abnormal-offline-hidens {
        description
          "List of the function that replaces the abnormal offline reason with 'the user requests to go offline'.";
        list abnormal-offline-hiden {
          key "hidden-id";
          description
            "Configure the function that replaces the abnormal offline reason with 'the user requests to go offline'.";
          leaf hidden-id {
            type uint32 {
              range "2..18";
            }
            description
              "Specifies an ID for an abnormal logout reason.";
          }
        }
      }
      container lam {
        description
          "Configure the local account and related policy management functions.";
        uses aaa:aaa-lam-type;
      }
      container local-server {
        description
          "Configure a local AAA server. You can perform access security configurations for local users.";
        uses aaa:aaa-local-server-type;
      }
    }
  }
  augment "/ncs:devices/ncs:device/ncs:live-status" {
    container aaa {
      tailf:ncs-device-type "netconf";
      tailf:display-when "not(../../ncs:module) or ../../ncs:module[ncs:name='huawei-aaa'] or (../../ncs:live-status-protocol[not(ncs:capability)]) or (../../ncs:live-status-protocol/ncs:capability/ncs:module[.='huawei-aaa'])";
      description
        "Security management, which includes the management on authentication, authorization, accounting, domains, and users.";
      container tasks {
        description
          "List of tasks.";
        list task {
          key "name";
          description
            "Statistics of minimum unit for dividing rights on an NE. Tasks can be determined when an NE is delivered. Tasks cannot be customized.";
          leaf name {
            type string {
              length "1..32";
            }
            description
              "Name of a task, it is not case sensitive.";
          }
        }
      }
      container task-groups {
        description
          "List of task groups.";
        list task-group {
          key "name";
          // NCS drop max-elements statement
          description
            "Configure a collection of certain tasks. The default task groups are set in the system before the NE delivery and cannot be deleted.";
          leaf name {
            type string {
              length "1..32";
              pattern '[^A-Z/\*":?<>|]+';
            }
            ext:case-sensitivity "lower-only";
            description
              "Name of a task group.";
          }
          container task-group-include-maps {
            description
              "List of the task groups included in a main task group.";
            list task-group-include-map {
              key "include-task-group-name";
              // NCS drop max-elements statement
              description
                "Configure task group included in a main task group.";
              leaf include-task-group-name {
                type leafref {
                  path "../../../name";
                }
                // NCS drop must statement
                description
                  "Name of included task group, it is not case sensitive.";
              }
            }
          }
          container task-group-task-maps {
            description
              "List of the tasks included in a task group.";
            list task-group-task-map {
              key "task-name";
              description
                "Configure task in a task group. The default task group cannot be modified.";
              leaf task-name {
                type string {
                  length "1..32";
                  pattern '[^A-Z]+';
                }
                ext:case-sensitivity "lower-only";
                // NCS drop must statement
                description
                  "Name of a task. It must be an existing task.";
              }
              leaf read {
                type live_ncs_aaa-enable-type;
                // NCS drop must statement
                // NCS drop default statement
                description
                  "To determine whether a task has the read right.";
              }
              leaf write {
                type live_ncs_aaa-enable-type;
                // NCS drop default statement
                description
                  "To determine whether a task has the write right.";
              }
              leaf execute {
                type live_ncs_aaa-enable-type;
                // NCS drop default statement
                description
                  "To determine whether a task has the operation right.";
              }
              leaf debug {
                type live_ncs_aaa-enable-type;
                // NCS drop default statement
                description
                  "To determine whether a task has the debug right.";
              }
            }
          }
        }
      }
      container user-groups {
        description
          "List of user groups.";
        list user-group {
          key "name";
          // NCS drop max-elements statement
          description
            "Configure a collection of certain users. Certain default user groups are set before an NE is delivered and cannot be deleted.";
          leaf name {
            type string {
              length "1..32";
              pattern '[^A-Z/\*":?<>|]+';
            }
            ext:case-sensitivity "lower-only";
            description
              "Name of a user group.";
          }
          container user-group-task-group-maps {
            description
              "List of the task groups included in a user group.";
            list user-group-task-group-map {
              key "task-group-name";
              description
                "Configure task group in a user group.";
              leaf task-group-name {
                type leafref {
                  path "../../../../../task-groups/task-group/name";
                }
                description
                  "Name of a task group, it is not case sensitive.";
              }
            }
          }
          container user-group-include-maps {
            description
              "List of the user groups included in a main user group.";
            list user-group-include-map {
              key "include-user-group-name";
              // NCS drop max-elements statement
              description
                "Configure user group included in a main user group.";
              leaf include-user-group-name {
                type leafref {
                  path "../../../name";
                }
                // NCS drop must statement
                description
                  "Name of a task group, it is not case sensitive.";
              }
            }
          }
        }
      }
      container authentication-schemes {
        description
          "List of authentication scheme.";
        list authentication-scheme {
          key "authen-scheme-name";
          // NCS drop max-elements statement
          description
            "Configure authentication scheme. The default authentication scheme cannot be deleted.";
          leaf authen-scheme-name {
            type string {
              length "1..32";
              pattern '[^A-Z/\*":?<>|]+';
            }
            ext:case-sensitivity "lower-only";
            description
              "Name of an authentication scheme.";
          }
          choice authen-mode-type {
            description
              "Sorting method of authentication mode.";
            case ordered-strictly {
              description
                "Ordered strictly case.";
              leaf first-authen-mode {
                type live_ncs_aaa-authen-mode;
                // NCS drop must statement
                // NCS drop default statement
                description
                  "Preferred authentication mode. The second, third, or fourth authentication mode is used only when the first authentication mode does not respond. The first authentication mode cannot be set to unavailable.";
              }
              leaf second-authen-mode {
                type live_ncs_aaa-authen-mode;
                // NCS drop must statement
                // NCS drop default statement
                description
                  "Authentication mode with the preference lower than the first authentication mode. The second authentication mode is used when the first authentication mode does not respond. If the setting of the second authentication mode is unavailable, the third and fourth authentication modes fail to be set.";
              }
              leaf third-authen-mode {
                type live_ncs_aaa-authen-mode;
                // NCS drop must statement
                // NCS drop default statement
                description
                  "Authentication mode with the preference lower than the first and second authentication modes. The third authentication mode is used when the first and second authentication modes do not respond. If the setting of the third authentication mode is unavailable, the fourth authentication mode fails to be set.";
              }
              leaf fourth-authen-mode {
                type live_ncs_aaa-authen-mode;
                // NCS drop must statement
                // NCS drop default statement
                description
                  "Authentication mode with the least preference. The fourth authentication mode is used when the first, second, and third authentication modes do not respond. If the setting of the fourth authentication mode is unavailable or the fourth authentication mode does not respond, the authentication fails.";
              }
            }
          }
        }
      }
      container authorization-schemes {
        description
          "List of authorization scheme.";
        list authorization-scheme {
          key "author-scheme-name";
          // NCS drop max-elements statement
          description
            "Configure authorization scheme. The default authorization scheme cannot be deleted.";
          leaf author-scheme-name {
            type string {
              length "1..32";
              pattern '[^A-Z/\*":?<>|]+';
            }
            ext:case-sensitivity "lower-only";
            description
              "Name of an authorization scheme. The name uniquely identifies the authorization scheme and can be used in the domain.";
          }
          choice author-mode-type {
            description
              "Sorting method of authorization mode.";
            case ordered-strictly {
              description
                "Ordered strictly case.";
              leaf first-author-mode {
                type live_ncs_aaa-author-mode;
                // NCS drop must statement
                // NCS drop default statement
                description
                  "Preferred authorization mode. The second, third, or fourth authorization mode can be used only when the first authorization mode does not respond. The first authorization mode must be available.";
              }
              leaf second-author-mode {
                type live_ncs_aaa-author-mode;
                // NCS drop must statement
                // NCS drop default statement
                description
                  "Authorization mode with the preference next to the first authorization mode. It is used when the first authorization mode does not respond. If the setting of the second authorization mode is unavailable, the third and fourth authorization modes fail to be set.";
              }
              leaf third-author-mode {
                type live_ncs_aaa-author-mode;
                // NCS drop must statement
                // NCS drop default statement
                description
                  "Authorization mode with the preference next to the first and second authorization modes. It is used when the first and second authorization modes do not respond. If the setting of the third authorization mode is unavailable, the fourth authorization mode fails to be set.";
              }
              leaf fourth-author-mode {
                type live_ncs_aaa-author-mode;
                // NCS drop must statement
                // NCS drop default statement
                description
                  "Authorization mode with the least preference. It is used when the first, second, and third authorization modes do not respond. If the setting of the fourth authorization mode is unavailable or the fourth authorization mode does not respond, the authorization fails.";
              }
            }
          }
          leaf no-lvl-first-cmd-author {
            type live_ncs_aaa-author-cmd-mode;
            // NCS drop must statement
            // NCS drop default statement
            description
              "Configures the first authorization mode for users of user group.";
          }
          leaf no-lvl-second-cmd-author {
            type live_ncs_aaa-author-cmd-mode;
            // NCS drop must statement
            // NCS drop default statement
            description
              "Configures the second authorization mode for users of user group.";
          }
          leaf no-response-policy {
            type live_ncs_author-no-res-policy-type;
            // NCS drop default statement
            description
              "Configures a policy for a scenario where no responses are obtained during command line-based authorization.";
          }
          leaf no-response-times {
            // NCS drop when statement
            type uint32 {
              range "1..10";
            }
            // NCS drop default statement
            description
              "Configures the number of times of failed authorization.";
          }
          container authorization-cmds {
            description
              "List of authorization cmd.";
            list authorization-cmd {
              key "level";
              description
                "Configure authorization cmd.";
              leaf level {
                type uint32 {
                  range "0..15";
                }
                description
                  "The level of authorization cmd.";
              }
              choice cmd-author-mode-type {
                description
                  "Sorting method of cmd authorization mode.";
                case ordered-strictly {
                  description
                    "Ordered strictly case.";
                  leaf first-cmd-author {
                    type live_ncs_aaa-author-cmd-mode;
                    // NCS drop must statement
                    // NCS drop default statement
                    description
                      "First cmd authorization mode.";
                  }
                  leaf second-cmd-author {
                    type live_ncs_aaa-author-cmd-mode;
                    // NCS drop must statement
                    // NCS drop default statement
                    description
                      "Second cmd authorization mode.";
                  }
                }
              }
            }
          }
        }
      }
      container accounting-schemes {
        description
          "List of accounting scheme.";
        list accounting-scheme {
          key "acct-scheme-name";
          // NCS drop max-elements statement
          description
            "Configure accounting scheme. The default accounting scheme cannot be deleted.";
          leaf acct-scheme-name {
            type string {
              length "1..32";
              pattern '[^A-Z/\*":?<>|]+';
            }
            ext:case-sensitivity "lower-only";
            description
              "Accounting scheme name.";
          }
          leaf accounting-mode {
            type live_ncs_aaa-acct-mode;
            // NCS drop must statement
            // NCS drop default statement
            description
              "Accounting Mode.";
          }
        }
      }
      container domains {
        description
          "List of domain.";
        list domain {
          key "name";
          // NCS drop max-elements statement
          description
            "Configure in a domain, users apply the same authentication/authorization scheme or server. The default domain cannot be deleted.";
          leaf name {
            type string {
              length "1..64";
              pattern "([^A-Z*?\"']{3,})|[^A-Z*?\"'-]|([^A-Z*?\"'-][^A-Z*?\"'])|([^A-Z*?\"'][^A-Z*?\"'-])";
            }
            ext:case-sensitivity "lower-only";
            description
              "Name of a domain.";
          }
          leaf admin-level {
            type uint32 {
              range "0..15";
            }
            description
              "The admin level of domain. If the command level adjustment function is disabled, the value of adminLevel ranges from 0 to 3. If the command level adjustment function is enabled, the value of adminLevel ranges from 0 to 15.";
          }
          leaf authen-scheme-name {
            type leafref {
              path "../../../authentication-schemes/authentication-scheme/authen-scheme-name";
            }
            ext:dynamic-default {
              ext:default-value "default0" {
                // NCS drop when statement
              }
              ext:default-value "default1" {
                // NCS drop when statement
              }
              ext:default-value "default" {
                // NCS drop when statement
              }
              ext:default-value "default1";
            }
            description
              "Name of the authentication scheme used by the domain, it is not case sensitive. The default value varies according to domains. The default value is restored when the node is deleted.";
          }
          leaf author-scheme-name {
            type leafref {
              path "../../../authorization-schemes/authorization-scheme/author-scheme-name";
            }
            description
              "Name of the authorization scheme used by the domain, it is not case sensitive. The default value varies according to domains. The default value is restored when the node is deleted.";
          }
          leaf acct-scheme-name {
            type leafref {
              path "../../../accounting-schemes/accounting-scheme/acct-scheme-name";
            }
            ext:dynamic-default {
              ext:default-value "default0" {
                // NCS drop when statement
              }
              ext:default-value "default1" {
                // NCS drop when statement
              }
              ext:default-value "default0" {
                // NCS drop when statement
              }
              ext:default-value "default1";
            }
            description
              "Name of the accounting scheme used by the domain, it is not case sensitive. The default value varies according to domains. The default value is restored when the node is deleted.";
          }
          leaf access-limit {
            type int32 {
              range "0..2147483647";
            }
            description
              "Domain max access number. The default value is defined in the PAF file and is restored when the node is deleted.";
          }
          leaf radius-server-template {
            type string {
              length "1..32";
            }
            description
              "Name of the RADIUS server used by the domain, it is not case sensitive.";
          }
          leaf hwtacacs-server-template {
            type leafref {
              path "/ncs:devices/ncs:device/ncs:live-status/hwtacacs:hwtacacs/hwtacacs:templates/hwtacacs:template/hwtacacs:name" {
                tailf:xpath-root 3;
              }
            }
            description
              "Name of the HWTACACS server used by the domain, it is not case sensitive.";
          }
          leaf state {
            type live_ncs_aaa-state-type;
            // NCS drop default statement
            description
              "Activated state of the domain.";
          }
          leaf time-range-enable {
            type boolean;
            // NCS drop default statement
            description
              "Enable/disable the time range function used by a domain.";
          }
          leaf service-terminal {
            type boolean;
            // NCS drop default statement
            description
              "Enable/disable users to log in Terminal mode.";
          }
          leaf service-telnet {
            type boolean;
            // NCS drop default statement
            description
              "Enable/disable users to log in Telnet mode.";
          }
          leaf service-ftp {
            type boolean;
            // NCS drop default statement
            description
              "Enable/disable users to log in FTP mode.";
          }
          leaf service-ppp {
            type boolean;
            // NCS drop default statement
            description
              "Enable/disable users to log in PPP mode.";
          }
          leaf service-ssh {
            type boolean;
            // NCS drop default statement
            description
              "Enable/disable users to log in SSH mode.";
          }
          leaf service-qx {
            type boolean;
            // NCS drop default statement
            description
              "Enable/disable users to log in QX mode.";
          }
          leaf service-snmp {
            type boolean;
            // NCS drop default statement
            description
              "Enable/disable users to log in SNMP mode.";
          }
          leaf service-mml {
            type boolean;
            // NCS drop default statement
            description
              "Enable/disable users to log in MML mode.";
          }
          leaf service-http {
            type boolean;
            // NCS drop default statement
            description
              "Enable/disable users to log in HTTP mode.";
          }
          leaf online-num {
            type int32 {
              range "0..2147483647";
            }
            description
              "Online number of the domain.";
          }
        }
      }
      container login-alarm-threshold {
        description
          "Configure alarm when manager login failed frequently.";
        leaf report-times {
          type uint16 {
            range "0..100";
          }
          units "min";
          // NCS drop must statement
          // NCS drop default statement
          description
            "Login Alarm report times.";
        }
        leaf resume-times {
          type uint16 {
            range "0..100";
          }
          // NCS drop must statement
          // NCS drop default statement
          description
            "Login Alarm resume times.";
        }
        leaf period {
          type uint16 {
            range "1..120";
          }
          units "min";
          // NCS drop default statement
          description
            "Login Alarm period.";
        }
      }
      container alive-user-qrys {
        description
          "List of alive users.";
        list alive-user-qry {
          key "user-id";
          description
            "Statistics of active users.";
          leaf user-id {
            type uint32;
            description
              "User ID.";
          }
          leaf user-name {
            type string {
              length "1..253";
            }
            description
              "Name of an access user, it is not case sensitive.";
          }
          leaf level {
            type uint32 {
              range "0..15";
            }
            description
              "User level.";
          }
          leaf user-group-name {
            type string {
              length "1..32";
            }
            description
              "Specifies the name of a user group, it is not case sensitive.";
          }
          leaf name {
            type string {
              length "1..64";
            }
            description
              "Name of a domain, it is not case sensitive.";
          }
          leaf access-type {
            type live_ncs_aaa-user-access-type;
            description
              "Access type.";
          }
          leaf authen-type {
            type live_ncs_aaa-authen-access-type;
            description
              "Authentication Type.";
          }
          leaf authen-method {
            type live_ncs_aaa-authen-mode;
            description
              "Alive user current authentication mode.";
          }
          leaf authen-state {
            type live_ncs_aaa-authen-state-type;
            description
              "Authentication state.";
          }
          leaf author-method {
            type live_ncs_aaa-author-mode;
            description
              "Currnet authorization mode.";
          }
          leaf author-state {
            type live_ncs_aaa-author-state-type;
            description
              "Author state.";
          }
          leaf acct-method {
            type live_ncs_aaa-acct-mode;
            description
              "Current accounting Mode.";
          }
          leaf acct-state {
            type live_ncs_aaa-acct-state-type;
            description
              "Accounting state.";
          }
        }
      }
      container global-policy {
        description
          "Configure global policy.";
        leaf domain-location {
          type live_ncs_aaa-domain-location-type;
          // NCS drop default statement
          description
            "Domain Location.";
        }
        leaf domain-parse-direction {
          type live_ncs_aaa-parse-direction-type;
          // NCS drop default statement
          description
            "Domain Parse Direction.";
        }
        leaf default-admin-domain {
          type leafref {
            path "../../domains/domain/name";
          }
          // NCS drop default statement
          description
            "Admin user default domain.";
        }
        leaf default-access-domain {
          type leafref {
            path "../../domains/domain/name";
          }
          // NCS drop default statement
          description
            "Access user default domain.";
        }
        leaf parse-priority {
          type live_ncs_aaa-parse-priority-type;
          // NCS drop default statement
          description
            "Specifies priorities for parsing domain names.";
        }
        leaf realm-location {
          type live_ncs_aaa-realm-location-type;
          // NCS drop default statement
          description
            "Specifies a position for a realm domain name.";
        }
        leaf real-name-delimiter {
          type string {
            length "1";
            pattern "[/:<>\\|@%']";
          }
          description
            "Specifies a realm name delimiter used to parse the user account. The value is a single character. It can be one of the following symbols: back-slant, /, :, <, >, |, @, %, '.";
        }
        leaf real-name-parse-direction {
          type live_ncs_aaa-parse-direction-type;
          // NCS drop default statement
          description
            "Specifies a parsing direction for the realm name.";
        }
        leaf roam-character {
          type string {
            length "1";
            pattern '[/:*<>\|]';
          }
          // NCS drop default statement
          description
            "Specifies an identifier for a roaming user. The value is a single character. It can be one of the following symbols: back-slant, /, :, *, <, >, |.";
        }
      }
      container recording {
        description
          "Configure recording function.";
        container function {
          description
            "Configure recording function.";
          leaf cmd-record-scheme {
            type leafref {
              path "../../schemes/scheme/name";
            }
            description
              "The recording scheme used by cmd recording.";
          }
          leaf system-record-scheme {
            type leafref {
              path "../../schemes/scheme/name";
            }
            description
              "Configures a solution to record system events. Currently, only events triggered by the reboot command are recorded.";
          }
          leaf outbound-record-scheme {
            type leafref {
              path "../../schemes/scheme/name";
            }
            description
              "Records remote login operations for the device that functions as the client.";
          }
        }
        container schemes {
          description
            "List of recording scheme.";
          list scheme {
            key "name";
            description
              "Configure recording scheme.";
            leaf name {
              type string {
                length "1..32";
                pattern '[^A-Z/\*":?<>|]+';
              }
              ext:case-sensitivity "lower-only";
              description
                "Recording scheme name.";
            }
            leaf tacacs-group {
              type leafref {
                path "/ncs:devices/ncs:device/ncs:live-status/hwtacacs:hwtacacs/hwtacacs:templates/hwtacacs:template/hwtacacs:name" {
                  tailf:xpath-root 3;
                }
              }
              description
                "The binded HWTACACS server.";
            }
          }
        }
      }
      container online-offline-rec-switch {
        description
          "Configure whether to enable login failure and logout recording for management users.";
        leaf login-fail-rec-switch {
          type live_ncs_aaa-enable-type;
          // NCS drop default statement
          description
            "Enables recording of login failures.";
        }
        leaf logout-rec-switch {
          type live_ncs_aaa-enable-type;
          // NCS drop default statement
          description
            "Enables recording of normal and abnormal logouts.";
        }
        leaf abnormal-logout-rec-switch {
          type live_ncs_aaa-enable-type;
          // NCS drop default statement
          description
            "Enables recording of abnormal logouts.";
        }
        leaf normal-logout-rec-switch {
          type live_ncs_aaa-enable-type;
          // NCS drop default statement
          description
            "Enables recording of normal logouts.";
        }
      }
      container abnormal-offline-hidens {
        description
          "List of the function that replaces the abnormal offline reason with 'the user requests to go offline'.";
        list abnormal-offline-hiden {
          key "hidden-id";
          description
            "Configure the function that replaces the abnormal offline reason with 'the user requests to go offline'.";
          leaf hidden-id {
            type uint32 {
              range "2..18";
            }
            description
              "Specifies an ID for an abnormal logout reason.";
          }
        }
      }
      container lam {
        description
          "Configure the local account and related policy management functions.";
        uses aaa:live_ncs_aaa-lam-type;
      }
      container local-server {
        description
          "Configure a local AAA server. You can perform access security configurations for local users.";
        uses aaa:live_ncs_aaa-local-server-type;
      }
    }
  }
  augment "/ncs:devices/ncs:template/ncs:ned-id/ncs:config" {
    container aaa {
      description
        "Security management, which includes the management on authentication, authorization, accounting, domains, and users.";
      // NCS drop config false container tasks
      container task-groups {
        description
          "List of task groups.";
        list task-group {
          // NCS patched for predictable order
          ordered-by user;
          key "name";
          // NCS drop max-elements statement
          description
            "Configure a collection of certain tasks. The default task groups are set in the system before the NE delivery and cannot be deleted.";
          leaf name {
            type string;
            ext:case-sensitivity "lower-only";
            description
              "Name of a task group.";
          }
          container task-group-include-maps {
            description
              "List of the task groups included in a main task group.";
            list task-group-include-map {
              // NCS patched for predictable order
              ordered-by user;
              key "include-task-group-name";
              // NCS drop max-elements statement
              description
                "Configure task group included in a main task group.";
              leaf include-task-group-name {
                type string;
                // NCS drop must statement
                description
                  "Name of included task group, it is not case sensitive.";
              }
            }
          }
          container task-group-task-maps {
            description
              "List of the tasks included in a task group.";
            list task-group-task-map {
              // NCS patched for predictable order
              ordered-by user;
              key "task-name";
              description
                "Configure task in a task group. The default task group cannot be modified.";
              leaf task-name {
                type string;
                ext:case-sensitivity "lower-only";
                // NCS drop must statement
                description
                  "Name of a task. It must be an existing task.";
              }
              leaf read {
                type ncs_template_aaa-enable-type;
                // NCS drop must statement
                // NCS drop default statement
                description
                  "To determine whether a task has the read right.";
              }
              leaf write {
                type ncs_template_aaa-enable-type;
                // NCS drop default statement
                description
                  "To determine whether a task has the write right.";
              }
              leaf execute {
                type ncs_template_aaa-enable-type;
                // NCS drop default statement
                description
                  "To determine whether a task has the operation right.";
              }
              leaf debug {
                type ncs_template_aaa-enable-type;
                // NCS drop default statement
                description
                  "To determine whether a task has the debug right.";
              }
            }
          }
        }
      }
      container user-groups {
        description
          "List of user groups.";
        list user-group {
          // NCS patched for predictable order
          ordered-by user;
          key "name";
          // NCS drop max-elements statement
          description
            "Configure a collection of certain users. Certain default user groups are set before an NE is delivered and cannot be deleted.";
          leaf name {
            type string;
            ext:case-sensitivity "lower-only";
            description
              "Name of a user group.";
          }
          container user-group-task-group-maps {
            description
              "List of the task groups included in a user group.";
            list user-group-task-group-map {
              // NCS patched for predictable order
              ordered-by user;
              key "task-group-name";
              description
                "Configure task group in a user group.";
              leaf task-group-name {
                type string;
                description
                  "Name of a task group, it is not case sensitive.";
              }
            }
          }
          container user-group-include-maps {
            description
              "List of the user groups included in a main user group.";
            list user-group-include-map {
              // NCS patched for predictable order
              ordered-by user;
              key "include-user-group-name";
              // NCS drop max-elements statement
              description
                "Configure user group included in a main user group.";
              leaf include-user-group-name {
                type string;
                // NCS drop must statement
                description
                  "Name of a task group, it is not case sensitive.";
              }
            }
          }
        }
      }
      container authentication-schemes {
        description
          "List of authentication scheme.";
        list authentication-scheme {
          // NCS patched for predictable order
          ordered-by user;
          key "authen-scheme-name";
          // NCS drop max-elements statement
          description
            "Configure authentication scheme. The default authentication scheme cannot be deleted.";
          leaf authen-scheme-name {
            type string;
            ext:case-sensitivity "lower-only";
            description
              "Name of an authentication scheme.";
          }
          choice authen-mode-type {
            description
              "Sorting method of authentication mode.";
            case ordered-strictly {
              description
                "Ordered strictly case.";
              leaf first-authen-mode {
                type ncs_template_aaa-authen-mode;
                // NCS drop must statement
                // NCS drop default statement
                description
                  "Preferred authentication mode. The second, third, or fourth authentication mode is used only when the first authentication mode does not respond. The first authentication mode cannot be set to unavailable.";
              }
              leaf second-authen-mode {
                type ncs_template_aaa-authen-mode;
                // NCS drop must statement
                // NCS drop default statement
                description
                  "Authentication mode with the preference lower than the first authentication mode. The second authentication mode is used when the first authentication mode does not respond. If the setting of the second authentication mode is unavailable, the third and fourth authentication modes fail to be set.";
              }
              leaf third-authen-mode {
                type ncs_template_aaa-authen-mode;
                // NCS drop must statement
                // NCS drop default statement
                description
                  "Authentication mode with the preference lower than the first and second authentication modes. The third authentication mode is used when the first and second authentication modes do not respond. If the setting of the third authentication mode is unavailable, the fourth authentication mode fails to be set.";
              }
              leaf fourth-authen-mode {
                type ncs_template_aaa-authen-mode;
                // NCS drop must statement
                // NCS drop default statement
                description
                  "Authentication mode with the least preference. The fourth authentication mode is used when the first, second, and third authentication modes do not respond. If the setting of the fourth authentication mode is unavailable or the fourth authentication mode does not respond, the authentication fails.";
              }
            }
          }
        }
      }
      container authorization-schemes {
        description
          "List of authorization scheme.";
        list authorization-scheme {
          // NCS patched for predictable order
          ordered-by user;
          key "author-scheme-name";
          // NCS drop max-elements statement
          description
            "Configure authorization scheme. The default authorization scheme cannot be deleted.";
          leaf author-scheme-name {
            type string;
            ext:case-sensitivity "lower-only";
            description
              "Name of an authorization scheme. The name uniquely identifies the authorization scheme and can be used in the domain.";
          }
          choice author-mode-type {
            description
              "Sorting method of authorization mode.";
            case ordered-strictly {
              description
                "Ordered strictly case.";
              leaf first-author-mode {
                type ncs_template_aaa-author-mode;
                // NCS drop must statement
                // NCS drop default statement
                description
                  "Preferred authorization mode. The second, third, or fourth authorization mode can be used only when the first authorization mode does not respond. The first authorization mode must be available.";
              }
              leaf second-author-mode {
                type ncs_template_aaa-author-mode;
                // NCS drop must statement
                // NCS drop default statement
                description
                  "Authorization mode with the preference next to the first authorization mode. It is used when the first authorization mode does not respond. If the setting of the second authorization mode is unavailable, the third and fourth authorization modes fail to be set.";
              }
              leaf third-author-mode {
                type ncs_template_aaa-author-mode;
                // NCS drop must statement
                // NCS drop default statement
                description
                  "Authorization mode with the preference next to the first and second authorization modes. It is used when the first and second authorization modes do not respond. If the setting of the third authorization mode is unavailable, the fourth authorization mode fails to be set.";
              }
              leaf fourth-author-mode {
                type ncs_template_aaa-author-mode;
                // NCS drop must statement
                // NCS drop default statement
                description
                  "Authorization mode with the least preference. It is used when the first, second, and third authorization modes do not respond. If the setting of the fourth authorization mode is unavailable or the fourth authorization mode does not respond, the authorization fails.";
              }
            }
          }
          leaf no-lvl-first-cmd-author {
            type ncs_template_aaa-author-cmd-mode;
            // NCS drop must statement
            // NCS drop default statement
            description
              "Configures the first authorization mode for users of user group.";
          }
          leaf no-lvl-second-cmd-author {
            type ncs_template_aaa-author-cmd-mode;
            // NCS drop must statement
            // NCS drop default statement
            description
              "Configures the second authorization mode for users of user group.";
          }
          leaf no-response-policy {
            type ncs_template_author-no-res-policy-type;
            // NCS drop default statement
            description
              "Configures a policy for a scenario where no responses are obtained during command line-based authorization.";
          }
          leaf no-response-times {
            // NCS drop when statement
            type string;
            // NCS drop default statement
            description
              "Configures the number of times of failed authorization.";
          }
          container authorization-cmds {
            description
              "List of authorization cmd.";
            list authorization-cmd {
              // NCS patched for predictable order
              ordered-by user;
              key "level";
              description
                "Configure authorization cmd.";
              leaf level {
                type string;
                description
                  "The level of authorization cmd.";
              }
              choice cmd-author-mode-type {
                description
                  "Sorting method of cmd authorization mode.";
                case ordered-strictly {
                  description
                    "Ordered strictly case.";
                  leaf first-cmd-author {
                    type ncs_template_aaa-author-cmd-mode;
                    // NCS drop must statement
                    // NCS drop default statement
                    description
                      "First cmd authorization mode.";
                  }
                  leaf second-cmd-author {
                    type ncs_template_aaa-author-cmd-mode;
                    // NCS drop must statement
                    // NCS drop default statement
                    description
                      "Second cmd authorization mode.";
                  }
                }
              }
            }
          }
        }
      }
      container accounting-schemes {
        description
          "List of accounting scheme.";
        list accounting-scheme {
          // NCS patched for predictable order
          ordered-by user;
          key "acct-scheme-name";
          // NCS drop max-elements statement
          description
            "Configure accounting scheme. The default accounting scheme cannot be deleted.";
          leaf acct-scheme-name {
            type string;
            ext:case-sensitivity "lower-only";
            description
              "Accounting scheme name.";
          }
          leaf accounting-mode {
            type ncs_template_aaa-acct-mode;
            // NCS drop must statement
            // NCS drop default statement
            description
              "Accounting Mode.";
          }
        }
      }
      container domains {
        description
          "List of domain.";
        list domain {
          // NCS patched for predictable order
          ordered-by user;
          key "name";
          // NCS drop max-elements statement
          description
            "Configure in a domain, users apply the same authentication/authorization scheme or server. The default domain cannot be deleted.";
          leaf name {
            type string;
            ext:case-sensitivity "lower-only";
            description
              "Name of a domain.";
          }
          leaf admin-level {
            type string;
            description
              "The admin level of domain. If the command level adjustment function is disabled, the value of adminLevel ranges from 0 to 3. If the command level adjustment function is enabled, the value of adminLevel ranges from 0 to 15.";
          }
          leaf authen-scheme-name {
            type string;
            ext:dynamic-default {
              ext:default-value "default0" {
                // NCS drop when statement
              }
              ext:default-value "default1" {
                // NCS drop when statement
              }
              ext:default-value "default" {
                // NCS drop when statement
              }
              ext:default-value "default1";
            }
            description
              "Name of the authentication scheme used by the domain, it is not case sensitive. The default value varies according to domains. The default value is restored when the node is deleted.";
          }
          leaf author-scheme-name {
            type string;
            description
              "Name of the authorization scheme used by the domain, it is not case sensitive. The default value varies according to domains. The default value is restored when the node is deleted.";
          }
          leaf acct-scheme-name {
            type string;
            ext:dynamic-default {
              ext:default-value "default0" {
                // NCS drop when statement
              }
              ext:default-value "default1" {
                // NCS drop when statement
              }
              ext:default-value "default0" {
                // NCS drop when statement
              }
              ext:default-value "default1";
            }
            description
              "Name of the accounting scheme used by the domain, it is not case sensitive. The default value varies according to domains. The default value is restored when the node is deleted.";
          }
          leaf access-limit {
            type string;
            description
              "Domain max access number. The default value is defined in the PAF file and is restored when the node is deleted.";
          }
          leaf radius-server-template {
            type string;
            description
              "Name of the RADIUS server used by the domain, it is not case sensitive.";
          }
          leaf hwtacacs-server-template {
            type string;
            description
              "Name of the HWTACACS server used by the domain, it is not case sensitive.";
          }
          leaf state {
            type ncs_template_aaa-state-type;
            // NCS drop default statement
            description
              "Activated state of the domain.";
          }
          leaf time-range-enable {
            type string;
            // NCS drop default statement
            description
              "Enable/disable the time range function used by a domain.";
          }
          leaf service-terminal {
            type string;
            // NCS drop default statement
            description
              "Enable/disable users to log in Terminal mode.";
          }
          leaf service-telnet {
            type string;
            // NCS drop default statement
            description
              "Enable/disable users to log in Telnet mode.";
          }
          leaf service-ftp {
            type string;
            // NCS drop default statement
            description
              "Enable/disable users to log in FTP mode.";
          }
          leaf service-ppp {
            type string;
            // NCS drop default statement
            description
              "Enable/disable users to log in PPP mode.";
          }
          leaf service-ssh {
            type string;
            // NCS drop default statement
            description
              "Enable/disable users to log in SSH mode.";
          }
          leaf service-qx {
            type string;
            // NCS drop default statement
            description
              "Enable/disable users to log in QX mode.";
          }
          leaf service-snmp {
            type string;
            // NCS drop default statement
            description
              "Enable/disable users to log in SNMP mode.";
          }
          leaf service-mml {
            type string;
            // NCS drop default statement
            description
              "Enable/disable users to log in MML mode.";
          }
          leaf service-http {
            type string;
            // NCS drop default statement
            description
              "Enable/disable users to log in HTTP mode.";
          }
          // NCS drop config false leaf 'online-num'
        }
      }
      container login-alarm-threshold {
        description
          "Configure alarm when manager login failed frequently.";
        leaf report-times {
          type string;
          units "min";
          // NCS drop must statement
          // NCS drop default statement
          description
            "Login Alarm report times.";
        }
        leaf resume-times {
          type string;
          // NCS drop must statement
          // NCS drop default statement
          description
            "Login Alarm resume times.";
        }
        leaf period {
          type string;
          units "min";
          // NCS drop default statement
          description
            "Login Alarm period.";
        }
      }
      // NCS drop config false container 'alive-user-qrys'
      container global-policy {
        description
          "Configure global policy.";
        leaf domain-location {
          type ncs_template_aaa-domain-location-type;
          // NCS drop default statement
          description
            "Domain Location.";
        }
        leaf domain-parse-direction {
          type ncs_template_aaa-parse-direction-type;
          // NCS drop default statement
          description
            "Domain Parse Direction.";
        }
        leaf default-admin-domain {
          type string;
          // NCS drop default statement
          description
            "Admin user default domain.";
        }
        leaf default-access-domain {
          type string;
          // NCS drop default statement
          description
            "Access user default domain.";
        }
        leaf parse-priority {
          type ncs_template_aaa-parse-priority-type;
          // NCS drop default statement
          description
            "Specifies priorities for parsing domain names.";
        }
        leaf realm-location {
          type ncs_template_aaa-realm-location-type;
          // NCS drop default statement
          description
            "Specifies a position for a realm domain name.";
        }
        leaf real-name-delimiter {
          type string;
          description
            "Specifies a realm name delimiter used to parse the user account. The value is a single character. It can be one of the following symbols: back-slant, /, :, <, >, |, @, %, '.";
        }
        leaf real-name-parse-direction {
          type ncs_template_aaa-parse-direction-type;
          // NCS drop default statement
          description
            "Specifies a parsing direction for the realm name.";
        }
        leaf roam-character {
          type string;
          // NCS drop default statement
          description
            "Specifies an identifier for a roaming user. The value is a single character. It can be one of the following symbols: back-slant, /, :, *, <, >, |.";
        }
      }
      container recording {
        description
          "Configure recording function.";
        container function {
          description
            "Configure recording function.";
          leaf cmd-record-scheme {
            type string;
            description
              "The recording scheme used by cmd recording.";
          }
          leaf system-record-scheme {
            type string;
            description
              "Configures a solution to record system events. Currently, only events triggered by the reboot command are recorded.";
          }
          leaf outbound-record-scheme {
            type string;
            description
              "Records remote login operations for the device that functions as the client.";
          }
        }
        container schemes {
          description
            "List of recording scheme.";
          list scheme {
            // NCS patched for predictable order
            ordered-by user;
            key "name";
            description
              "Configure recording scheme.";
            leaf name {
              type string;
              ext:case-sensitivity "lower-only";
              description
                "Recording scheme name.";
            }
            leaf tacacs-group {
              type string;
              description
                "The binded HWTACACS server.";
            }
          }
        }
      }
      container online-offline-rec-switch {
        description
          "Configure whether to enable login failure and logout recording for management users.";
        leaf login-fail-rec-switch {
          type ncs_template_aaa-enable-type;
          // NCS drop default statement
          description
            "Enables recording of login failures.";
        }
        leaf logout-rec-switch {
          type ncs_template_aaa-enable-type;
          // NCS drop default statement
          description
            "Enables recording of normal and abnormal logouts.";
        }
        leaf abnormal-logout-rec-switch {
          type ncs_template_aaa-enable-type;
          // NCS drop default statement
          description
            "Enables recording of abnormal logouts.";
        }
        leaf normal-logout-rec-switch {
          type ncs_template_aaa-enable-type;
          // NCS drop default statement
          description
            "Enables recording of normal logouts.";
        }
      }
      container abnormal-offline-hidens {
        description
          "List of the function that replaces the abnormal offline reason with 'the user requests to go offline'.";
        list abnormal-offline-hiden {
          // NCS patched for predictable order
          ordered-by user;
          key "hidden-id";
          description
            "Configure the function that replaces the abnormal offline reason with 'the user requests to go offline'.";
          leaf hidden-id {
            type string;
            description
              "Specifies an ID for an abnormal logout reason.";
          }
        }
      }
      container lam {
        description
          "Configure the local account and related policy management functions.";
        uses aaa:ncs_template_aaa-lam-type;
      }
      container local-server {
        description
          "Configure a local AAA server. You can perform access security configurations for local users.";
        uses aaa:ncs_template_aaa-local-server-type;
      }
    }
  }
}
