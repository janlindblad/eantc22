module huawei-devm-vnf-deviations-NE8000 {
  // Generated by yanger -t ncs
  tailf:mount-id "huawei-nc-1.0:huawei-nc-1.0";
  tailf:ncs-device-type "netconf";

  namespace "urn:huawei:yang:huawei-devm-vnf-deviations-NE8000";
  prefix devm-vnf-devs-NE8000;

  import huawei-devm-vnf {
    prefix devm-vnf;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Global Configuration.";

  revision 2019-08-29 {
    description
      "Initial revision.";
    reference "Huawei private.";
  }

  deviation "/ncs:devices/ncs:template/ncs:ned-id/ncs:config/devm-vnf:devm-vnf" {
    deviate not-supported;
  }
  deviation "/ncs:devices/ncs:device/ncs:live-status/devm-vnf:devm-vnf" {
    deviate not-supported;
  }
  deviation "/ncs:devices/ncs:device/ncs:config/devm-vnf:devm-vnf" {
    deviate not-supported;
  }
}
