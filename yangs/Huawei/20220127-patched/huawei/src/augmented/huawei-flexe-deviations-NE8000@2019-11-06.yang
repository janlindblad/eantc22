module huawei-flexe-deviations-NE8000 {
  // Generated by yanger -t ncs
  tailf:mount-id "huawei-nc-1.0:huawei-nc-1.0";
  tailf:ncs-device-type "netconf";

  namespace "urn:huawei:yang:huawei-flexe-deviations-NE8000";
  prefix flexe-devs-NE8000;

  import huawei-flexe {
    prefix flexe;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "This module defines deviation statements for huawei-flexe module.";

  revision 2019-11-06 {
    description
      "Initial revision.";
    reference "Huawei private.";
  }

  typedef ncs_template_flexe-sub-ts-granula-type-deviations {
    type string;
    description
      "Setting sub-timeslot granularity.";
  }

  typedef ncs_rpc_notif_flexe-sub-ts-granula-type-deviations {
    type enumeration {
      enum "1G" {
        value 1;
        description
          "Sub-timeslot granularity 1G.";
      }
      enum "5G" {
        value 0;
        description
          "Sub-timeslot granularity 5G.";
      }
    }
    description
      "Setting sub-timeslot granularity.";
  }

  typedef live_ncs_flexe-sub-ts-granula-type-deviations {
    type enumeration {
      enum "1G" {
        value 1;
        description
          "Sub-timeslot granularity 1G.";
      }
      enum "5G" {
        value 0;
        description
          "Sub-timeslot granularity 5G.";
      }
    }
    description
      "Setting sub-timeslot granularity.";
  }

  typedef flexe-sub-ts-granula-type-deviations {
    type enumeration {
      enum "1G" {
        value 1;
        description
          "Sub-timeslot granularity 1G.";
      }
      enum "5G" {
        value 0;
        description
          "Sub-timeslot granularity 5G.";
      }
    }
    description
      "Setting sub-timeslot granularity.";
  }

  deviation "/ncs:devices/ncs:template/ncs:ned-id/ncs:config/flexe:flexe/flexe:card-attributes/flexe:card-attribute/flexe:sub-timeslot-granula" {
    deviate replace {
      type flexe-devs-NE8000:ncs_template_flexe-sub-ts-granula-type-deviations;
    }
  }
  deviation "/ncs:devices/ncs:device/ncs:live-status/flexe:flexe/flexe:card-attributes/flexe:card-attribute/flexe:sub-timeslot-granula" {
    deviate replace {
      type flexe-devs-NE8000:live_ncs_flexe-sub-ts-granula-type-deviations;
    }
  }
  deviation "/ncs:devices/ncs:device/ncs:config/flexe:flexe/flexe:card-attributes/flexe:card-attribute/flexe:sub-timeslot-granula" {
    deviate replace {
      type flexe-devs-NE8000:flexe-sub-ts-granula-type-deviations;
    }
  }
}
