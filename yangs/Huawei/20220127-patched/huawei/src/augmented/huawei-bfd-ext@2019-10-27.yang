module huawei-bfd-ext {
  // Generated by yanger -t ncs
  tailf:mount-id "huawei-nc-1.0:huawei-nc-1.0";
  tailf:ncs-device-type "netconf";

  yang-version 1;
  namespace "urn:huawei:yang:huawei-bfd-ext";
  prefix bfd-ext;

  import huawei-bfd {
    prefix bfd;
  }
  import huawei-ifm {
    prefix ifm;
  }
  import huawei-ifm-trunk {
    prefix ifm-trunk;
  }
  import huawei-extension {
    prefix ext;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Extended BFD functions.";

  revision 2019-10-27 {
    description
      "Initial revision.";
    reference "Huawei private.";
  }
  ext:task-name "bfd";

  augment "/ncs:devices/ncs:template/ncs:ned-id/ncs:config/ifm:ifm/ifm:interfaces/ifm:interface" {
    description
      "Configure BFD on the interface.";
    container bfd-ext {
      description
        "Configure extended BFD functions based on interfaces.";
      leaf transparent-tx-flag {
        type empty;
        // NCS drop must statement
        description
          "The flag of default BFD transparent transmission.";
      }
    }
  }
  augment "/ncs:devices/ncs:device/ncs:live-status/ifm:ifm/ifm:interfaces/ifm:interface" {
    description
      "Configure BFD on the interface.";
    container bfd-ext {
      tailf:ncs-device-type "netconf";
      tailf:display-when "not(../../../../../ncs:module) or ../../../../../ncs:module[ncs:name='huawei-bfd-ext'] or (../../../../../ncs:live-status-protocol[not(ncs:capability)]) or (../../../../../ncs:live-status-protocol/ncs:capability/ncs:module[.='huawei-bfd-ext'])";
      description
        "Configure extended BFD functions based on interfaces.";
      leaf transparent-tx-flag {
        type empty;
        // NCS drop must statement
        description
          "The flag of default BFD transparent transmission.";
      }
    }
  }
  augment "/ncs:devices/ncs:device/ncs:config/ifm:ifm/ifm:interfaces/ifm:interface" {
    description
      "Configure BFD on the interface.";
    container bfd-ext {
      tailf:ncs-device-type "netconf";
      tailf:display-when "not(../../../../../ncs:module) or ../../../../../ncs:module[ncs:name='huawei-bfd-ext']";
      description
        "Configure extended BFD functions based on interfaces.";
      leaf transparent-tx-flag {
        type empty;
        must '(not(/bfd:bfd/bfd:sessions/bfd:session[bfd:out-if-name-multicast-ipv4 = current()/../../ifm:name])) and (not(/ifm:ifm/ifm:interfaces/ifm:interface/ifm-trunk:trunk/ifm-trunk:members/ifm-trunk:member[ifm-trunk:name = current()/../../ifm:name]))' {
          tailf:xpath-root 3;
        }
        description
          "The flag of default BFD transparent transmission.";
      }
    }
  }
}
