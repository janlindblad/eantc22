module huawei-system-resources-usage {
  // Generated by yanger -t ncs
  tailf:mount-id "huawei-nc-1.0:huawei-nc-1.0";
  tailf:ncs-device-type "netconf";

  namespace "urn:huawei:yang:huawei-system-resources-usage";
  prefix system-resources-usage;

  import huawei-extension {
    prefix ext;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Display system resources usage.";

  revision 2020-02-28 {
    description
      "Init revision.";
    reference "Huawei private.";
  }
  ext:task-name "forward-system";

  augment "/ncs:devices/ncs:device/ncs:config" {
    // NCS drop config false container 'system-resources-usage'
  }
  augment "/ncs:devices/ncs:device/ncs:live-status" {
    container system-resources-usage {
      tailf:ncs-device-type "netconf";
      tailf:display-when "not(../../ncs:module) or ../../ncs:module[ncs:name='huawei-system-resources-usage'] or (../../ncs:live-status-protocol[not(ncs:capability)]) or (../../ncs:live-status-protocol/ncs:capability/ncs:module[.='huawei-system-resources-usage'])";
      description
        "System resources usage.";
      container resources {
        description
          "List of resource informations.";
        list resource {
          key "slot resource-name";
          description
            "Statistics of resource information.";
          leaf slot {
            type string {
              length "1..16";
            }
            description
              "Slot ID.";
          }
          leaf resource-name {
            type string {
              length "1..64";
            }
            description
              "Resource name.";
          }
          leaf total {
            type uint32;
            description
              "Total resource count.";
          }
          leaf allocated {
            type uint32;
            description
              "Allocated resource count.";
          }
          leaf free {
            type uint32;
            description
              "Free resource count.";
          }
        }
      }
    }
  }
  augment "/ncs:devices/ncs:template/ncs:ned-id/ncs:config" {
    // NCS drop config false container 'system-resources-usage'
  }
}
