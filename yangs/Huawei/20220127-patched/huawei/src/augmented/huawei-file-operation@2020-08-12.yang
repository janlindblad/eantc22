module huawei-file-operation {
  // Generated by yanger -t ncs
  tailf:mount-id "huawei-nc-1.0:huawei-nc-1.0";
  tailf:ncs-device-type "netconf";

  namespace "urn:huawei:yang:huawei-file-operation";
  prefix file-operation;

  import ietf-yang-types {
    prefix yang;
  }
  import huawei-pub-type {
    prefix pub-type;
  }
  import huawei-extension {
    prefix ext;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Indicate file system management.";

  revision 2020-08-12 {
    description
      "Modify data type of the node size from int32 to uint32.";
    reference "Huawei private.";
  }
  revision 2020-04-02 {
    description
      "YANG check.";
    reference "Huawei private.";
  }
  revision 2020-02-13 {
    description
      "Add leaf node of copy-file and delete-file.";
    reference "Huawei private.";
  }
  revision 2019-12-20 {
    description
      "Modify node description.";
    reference "Huawei private.";
  }
  revision 2019-12-09 {
    description
      "Initial revision.";
    reference "Huawei private.";
  }
  ext:task-name "rpm";

  typedef ncs_template_delete-type {
    type string;
    description
      "Specify the action of deleting file.";
  }

  typedef ncs_template_overwrite-type {
    type string;
    description
      "The overwrite strategy when there exists a file with same name as the destination file, should be overwrite or not-overwrite.";
  }

  typedef ncs_template_reset-recycle-type {
    type string;
    description
      "Specify the action type of reseting the recycle bin.";
  }

  typedef ncs_rpc_notif_delete-type {
    type enumeration {
      enum "unreserved" {
        value 0;
        description
          "Delete file permanently. The deleted file cannot be restored.";
      }
    }
    description
      "Specify the action of deleting file.";
  }

  typedef ncs_rpc_notif_overwrite-type {
    type enumeration {
      enum "overwrite" {
        value 0;
        description
          "Overwrite the file with same name as the destination file while compressing or decompressing.";
      }
      enum "not-overwrite" {
        value 1;
        description
          "Not to overwrite the file with same name as the destination file while compressing or decompressing.";
      }
    }
    description
      "The overwrite strategy when there exists a file with same name as the destination file, should be overwrite or not-overwrite.";
  }

  typedef ncs_rpc_notif_reset-recycle-type {
    type enumeration {
      enum "all" {
        value 0;
        description
          "Delete all files in the recycle bin.";
      }
    }
    description
      "Specify the action type of reseting the recycle bin.";
  }

  typedef live_ncs_delete-type {
    type enumeration {
      enum "unreserved" {
        value 0;
        description
          "Delete file permanently. The deleted file cannot be restored.";
      }
    }
    description
      "Specify the action of deleting file.";
  }

  typedef live_ncs_overwrite-type {
    type enumeration {
      enum "overwrite" {
        value 0;
        description
          "Overwrite the file with same name as the destination file while compressing or decompressing.";
      }
      enum "not-overwrite" {
        value 1;
        description
          "Not to overwrite the file with same name as the destination file while compressing or decompressing.";
      }
    }
    description
      "The overwrite strategy when there exists a file with same name as the destination file, should be overwrite or not-overwrite.";
  }

  typedef live_ncs_reset-recycle-type {
    type enumeration {
      enum "all" {
        value 0;
        description
          "Delete all files in the recycle bin.";
      }
    }
    description
      "Specify the action type of reseting the recycle bin.";
  }

  typedef delete-type {
    type enumeration {
      enum "unreserved" {
        value 0;
        description
          "Delete file permanently. The deleted file cannot be restored.";
      }
    }
    description
      "Specify the action of deleting file.";
  }

  typedef overwrite-type {
    type enumeration {
      enum "overwrite" {
        value 0;
        description
          "Overwrite the file with same name as the destination file while compressing or decompressing.";
      }
      enum "not-overwrite" {
        value 1;
        description
          "Not to overwrite the file with same name as the destination file while compressing or decompressing.";
      }
    }
    description
      "The overwrite strategy when there exists a file with same name as the destination file, should be overwrite or not-overwrite.";
  }

  typedef reset-recycle-type {
    type enumeration {
      enum "all" {
        value 0;
        description
          "Delete all files in the recycle bin.";
      }
    }
    description
      "Specify the action type of reseting the recycle bin.";
  }

  augment "/ncs:devices/ncs:device/ncs:rpc" {
    container rpc-remove-dir {
      tailf:ncs-device-type "netconf";
      tailf:display-when "not(../../ncs:module) or ../../ncs:module[ncs:name='huawei-file-operation']";
      tailf:action remove-dir {
        tailf:actionpoint ncsproxy {
          tailf:internal;
        }
        description
          "Remove a folder.";
        ext:node-ref "/file-operation/dirs/dir";
        input {
          leaf dir-name {
            type string;
            mandatory true;
            description
              "Specify a folder that will be removed.";
          }
        }
      }
    }
  }
  augment "/ncs:devices/ncs:device-group/ncs:ned-id/ncs:rpc" {
    container rpc-remove-dir {
      tailf:ncs-device-type "netconf";
      tailf:display-when "/ncs:devices/ncs:device[ncs:name=current()/../../../ncs:member]/ncs:module[ncs:name='huawei-file-operation']";
      tailf:action remove-dir {
        tailf:actionpoint ncsproxy {
          tailf:internal;
        }
        description
          "Remove a folder.";
        ext:node-ref "/file-operation/dirs/dir";
        input {
          leaf dir-name {
            type string;
            mandatory true;
            description
              "Specify a folder that will be removed.";
          }
        }
      }
    }
  }
  augment "/ncs:devices/ncs:device/ncs:rpc" {
    container rpc-make-dir {
      tailf:ncs-device-type "netconf";
      tailf:display-when "not(../../ncs:module) or ../../ncs:module[ncs:name='huawei-file-operation']";
      tailf:action make-dir {
        tailf:actionpoint ncsproxy {
          tailf:internal;
        }
        description
          "Create a folder.";
        ext:node-ref "/file-operation/dirs/dir";
        input {
          leaf dir-name {
            type string {
              length "1..255";
            }
            mandatory true;
            description
              "Specify a folder that will be created.";
          }
        }
      }
    }
  }
  augment "/ncs:devices/ncs:device-group/ncs:ned-id/ncs:rpc" {
    container rpc-make-dir {
      tailf:ncs-device-type "netconf";
      tailf:display-when "/ncs:devices/ncs:device[ncs:name=current()/../../../ncs:member]/ncs:module[ncs:name='huawei-file-operation']";
      tailf:action make-dir {
        tailf:actionpoint ncsproxy {
          tailf:internal;
        }
        description
          "Create a folder.";
        ext:node-ref "/file-operation/dirs/dir";
        input {
          leaf dir-name {
            type string {
              length "1..255";
            }
            mandatory true;
            description
              "Specify a folder that will be created.";
          }
        }
      }
    }
  }
  augment "/ncs:devices/ncs:device/ncs:rpc" {
    container rpc-rename {
      tailf:ncs-device-type "netconf";
      tailf:display-when "not(../../ncs:module) or ../../ncs:module[ncs:name='huawei-file-operation']";
      tailf:action rename {
        tailf:actionpoint ncsproxy {
          tailf:internal;
        }
        description
          "Rename a file or folder.";
        ext:node-ref "/file-operation/dirs/dir";
        input {
          leaf src-name {
            type string;
            mandatory true;
            description
              "Specify a source file or folder name that can be listed in a full directory or a relative directory.";
          }
          leaf des-name {
            type string {
              length "1..255";
            }
            mandatory true;
            description
              "Specify a destination file or folder name that can be listed in a full directory or a relative directory.";
          }
        }
      }
    }
  }
  augment "/ncs:devices/ncs:device-group/ncs:ned-id/ncs:rpc" {
    container rpc-rename {
      tailf:ncs-device-type "netconf";
      tailf:display-when "/ncs:devices/ncs:device[ncs:name=current()/../../../ncs:member]/ncs:module[ncs:name='huawei-file-operation']";
      tailf:action rename {
        tailf:actionpoint ncsproxy {
          tailf:internal;
        }
        description
          "Rename a file or folder.";
        ext:node-ref "/file-operation/dirs/dir";
        input {
          leaf src-name {
            type string;
            mandatory true;
            description
              "Specify a source file or folder name that can be listed in a full directory or a relative directory.";
          }
          leaf des-name {
            type string {
              length "1..255";
            }
            mandatory true;
            description
              "Specify a destination file or folder name that can be listed in a full directory or a relative directory.";
          }
        }
      }
    }
  }
  augment "/ncs:devices/ncs:device/ncs:rpc" {
    container rpc-move-file {
      tailf:ncs-device-type "netconf";
      tailf:display-when "not(../../ncs:module) or ../../ncs:module[ncs:name='huawei-file-operation']";
      tailf:action move-file {
        tailf:actionpoint ncsproxy {
          tailf:internal;
        }
        description
          "Move a file. A folder, however, cannot be moved.";
        ext:node-ref "/file-operation/dirs/dir";
        input {
          leaf src-file-name {
            type string;
            mandatory true;
            description
              "Specify a source file name that can be listed in a full directory or a relative directory.";
          }
          leaf des-file-name {
            type string {
              length "1..255";
            }
            mandatory true;
            description
              "Specify a destination file name that can be listed in a full directory or a relative directory.";
          }
        }
      }
    }
  }
  augment "/ncs:devices/ncs:device-group/ncs:ned-id/ncs:rpc" {
    container rpc-move-file {
      tailf:ncs-device-type "netconf";
      tailf:display-when "/ncs:devices/ncs:device[ncs:name=current()/../../../ncs:member]/ncs:module[ncs:name='huawei-file-operation']";
      tailf:action move-file {
        tailf:actionpoint ncsproxy {
          tailf:internal;
        }
        description
          "Move a file. A folder, however, cannot be moved.";
        ext:node-ref "/file-operation/dirs/dir";
        input {
          leaf src-file-name {
            type string;
            mandatory true;
            description
              "Specify a source file name that can be listed in a full directory or a relative directory.";
          }
          leaf des-file-name {
            type string {
              length "1..255";
            }
            mandatory true;
            description
              "Specify a destination file name that can be listed in a full directory or a relative directory.";
          }
        }
      }
    }
  }
  augment "/ncs:devices/ncs:device/ncs:rpc" {
    container rpc-unzip-file {
      tailf:ncs-device-type "netconf";
      tailf:display-when "not(../../ncs:module) or ../../ncs:module[ncs:name='huawei-file-operation']";
      tailf:action unzip-file {
        tailf:actionpoint ncsproxy {
          tailf:internal;
        }
        description
          "Decompress a file. A folder, however, cannot be decompressed.";
        ext:node-ref "/file-operation/dirs/dir";
        input {
          leaf src-file-name {
            type string;
            mandatory true;
            description
              "Specify a source file name that can be listed in a full directory or a relative directory.";
          }
          leaf des-file-name {
            type string {
              length "1..255";
            }
            mandatory true;
            description
              "Specify a destination file name that can be listed in a full path or a relative path.";
          }
          leaf overwrite-type {
            type ncs_rpc_notif_overwrite-type;
            default "not-overwrite";
            description
              "Specify the overwrite strategy when there exists a file with same name as the destination file, should be overwrite or not-overwrite.";
          }
        }
      }
    }
  }
  augment "/ncs:devices/ncs:device-group/ncs:ned-id/ncs:rpc" {
    container rpc-unzip-file {
      tailf:ncs-device-type "netconf";
      tailf:display-when "/ncs:devices/ncs:device[ncs:name=current()/../../../ncs:member]/ncs:module[ncs:name='huawei-file-operation']";
      tailf:action unzip-file {
        tailf:actionpoint ncsproxy {
          tailf:internal;
        }
        description
          "Decompress a file. A folder, however, cannot be decompressed.";
        ext:node-ref "/file-operation/dirs/dir";
        input {
          leaf src-file-name {
            type string;
            mandatory true;
            description
              "Specify a source file name that can be listed in a full directory or a relative directory.";
          }
          leaf des-file-name {
            type string {
              length "1..255";
            }
            mandatory true;
            description
              "Specify a destination file name that can be listed in a full path or a relative path.";
          }
          leaf overwrite-type {
            type ncs_rpc_notif_overwrite-type;
            default "not-overwrite";
            description
              "Specify the overwrite strategy when there exists a file with same name as the destination file, should be overwrite or not-overwrite.";
          }
        }
      }
    }
  }
  augment "/ncs:devices/ncs:device/ncs:rpc" {
    container rpc-zip-file {
      tailf:ncs-device-type "netconf";
      tailf:display-when "not(../../ncs:module) or ../../ncs:module[ncs:name='huawei-file-operation']";
      tailf:action zip-file {
        tailf:actionpoint ncsproxy {
          tailf:internal;
        }
        description
          "Compress a file. A folder, however, cannot be compressed.";
        ext:node-ref "/file-operation/dirs/dir";
        input {
          leaf src-file-name {
            type string;
            mandatory true;
            description
              "Specify a source file name that can be listed in a full directory or a relative directory.";
          }
          leaf des-file-name {
            type string {
              length "1..255";
            }
            mandatory true;
            description
              "Specify a destination file name that can be listed in a full directory or a relative directory.";
          }
          leaf overwrite-type {
            type ncs_rpc_notif_overwrite-type;
            default "not-overwrite";
            description
              "Specify the overwrite strategy when there exists a file with same name as the destination file, should be overwrite or not-overwrite.";
          }
        }
      }
    }
  }
  augment "/ncs:devices/ncs:device-group/ncs:ned-id/ncs:rpc" {
    container rpc-zip-file {
      tailf:ncs-device-type "netconf";
      tailf:display-when "/ncs:devices/ncs:device[ncs:name=current()/../../../ncs:member]/ncs:module[ncs:name='huawei-file-operation']";
      tailf:action zip-file {
        tailf:actionpoint ncsproxy {
          tailf:internal;
        }
        description
          "Compress a file. A folder, however, cannot be compressed.";
        ext:node-ref "/file-operation/dirs/dir";
        input {
          leaf src-file-name {
            type string;
            mandatory true;
            description
              "Specify a source file name that can be listed in a full directory or a relative directory.";
          }
          leaf des-file-name {
            type string {
              length "1..255";
            }
            mandatory true;
            description
              "Specify a destination file name that can be listed in a full directory or a relative directory.";
          }
          leaf overwrite-type {
            type ncs_rpc_notif_overwrite-type;
            default "not-overwrite";
            description
              "Specify the overwrite strategy when there exists a file with same name as the destination file, should be overwrite or not-overwrite.";
          }
        }
      }
    }
  }
  augment "/ncs:devices/ncs:device/ncs:rpc" {
    container rpc-delete-file {
      tailf:ncs-device-type "netconf";
      tailf:display-when "not(../../ncs:module) or ../../ncs:module[ncs:name='huawei-file-operation']";
      tailf:action delete-file {
        tailf:actionpoint ncsproxy {
          tailf:internal;
        }
        description
          "Delete file permanently. A folder, however, cannot be deleted.";
        ext:node-ref "/file-operation/dirs/dir";
        input {
          leaf file-name {
            type string;
            mandatory true;
            description
              "Specify a file name that can be listed in a full directory or a relative directory.";
          }
          leaf delete-type {
            type ncs_rpc_notif_delete-type;
            mandatory true;
            description
              "Specify the action of deleting file.";
          }
          leaf all {
            type boolean;
            description
              "Delete a file of the main board and slave board permanently. A folder, however, cannot be deleted.";
          }
        }
      }
    }
  }
  augment "/ncs:devices/ncs:device-group/ncs:ned-id/ncs:rpc" {
    container rpc-delete-file {
      tailf:ncs-device-type "netconf";
      tailf:display-when "/ncs:devices/ncs:device[ncs:name=current()/../../../ncs:member]/ncs:module[ncs:name='huawei-file-operation']";
      tailf:action delete-file {
        tailf:actionpoint ncsproxy {
          tailf:internal;
        }
        description
          "Delete file permanently. A folder, however, cannot be deleted.";
        ext:node-ref "/file-operation/dirs/dir";
        input {
          leaf file-name {
            type string;
            mandatory true;
            description
              "Specify a file name that can be listed in a full directory or a relative directory.";
          }
          leaf delete-type {
            type ncs_rpc_notif_delete-type;
            mandatory true;
            description
              "Specify the action of deleting file.";
          }
          leaf all {
            type boolean;
            description
              "Delete a file of the main board and slave board permanently. A folder, however, cannot be deleted.";
          }
        }
      }
    }
  }
  augment "/ncs:devices/ncs:device/ncs:rpc" {
    container rpc-copy-file {
      tailf:ncs-device-type "netconf";
      tailf:display-when "not(../../ncs:module) or ../../ncs:module[ncs:name='huawei-file-operation']";
      tailf:action copy-file {
        tailf:actionpoint ncsproxy {
          tailf:internal;
        }
        description
          "Copy a file. A folder, however, cannot be copied.";
        ext:node-ref "/file-operation/dirs/dir";
        input {
          leaf src-file-name {
            type string;
            mandatory true;
            description
              "Specify a source file name that can be listed in a full directory or a relative directory.";
          }
          leaf des-file-name {
            type string {
              length "1..255";
            }
            mandatory true;
            description
              "Specify a destination file name that can be listed in a full path or a relative path.";
          }
          leaf all {
            type boolean;
            description
              "Copy a file to both of the main board and slave board. A folder, however, cannot be copied.";
          }
        }
      }
    }
  }
  augment "/ncs:devices/ncs:device-group/ncs:ned-id/ncs:rpc" {
    container rpc-copy-file {
      tailf:ncs-device-type "netconf";
      tailf:display-when "/ncs:devices/ncs:device[ncs:name=current()/../../../ncs:member]/ncs:module[ncs:name='huawei-file-operation']";
      tailf:action copy-file {
        tailf:actionpoint ncsproxy {
          tailf:internal;
        }
        description
          "Copy a file. A folder, however, cannot be copied.";
        ext:node-ref "/file-operation/dirs/dir";
        input {
          leaf src-file-name {
            type string;
            mandatory true;
            description
              "Specify a source file name that can be listed in a full directory or a relative directory.";
          }
          leaf des-file-name {
            type string {
              length "1..255";
            }
            mandatory true;
            description
              "Specify a destination file name that can be listed in a full path or a relative path.";
          }
          leaf all {
            type boolean;
            description
              "Copy a file to both of the main board and slave board. A folder, however, cannot be copied.";
          }
        }
      }
    }
  }
  augment "/ncs:devices/ncs:device/ncs:rpc" {
    container rpc-reset-recycle-bin {
      tailf:ncs-device-type "netconf";
      tailf:display-when "not(../../ncs:module) or ../../ncs:module[ncs:name='huawei-file-operation']";
      tailf:action reset-recycle-bin {
        tailf:actionpoint ncsproxy {
          tailf:internal;
        }
        description
          "Delete all files in the recycle bin.";
        input {
          leaf reset-type {
            type ncs_rpc_notif_reset-recycle-type;
            description
              "Delete all files in the recycle bin.";
          }
        }
      }
    }
  }
  augment "/ncs:devices/ncs:device-group/ncs:ned-id/ncs:rpc" {
    container rpc-reset-recycle-bin {
      tailf:ncs-device-type "netconf";
      tailf:display-when "/ncs:devices/ncs:device[ncs:name=current()/../../../ncs:member]/ncs:module[ncs:name='huawei-file-operation']";
      tailf:action reset-recycle-bin {
        tailf:actionpoint ncsproxy {
          tailf:internal;
        }
        description
          "Delete all files in the recycle bin.";
        input {
          leaf reset-type {
            type ncs_rpc_notif_reset-recycle-type;
            description
              "Delete all files in the recycle bin.";
          }
        }
      }
    }
  }
  augment "/ncs:devices/ncs:device/ncs:config" {
    // NCS drop config false container 'file-operation'
  }
  augment "/ncs:devices/ncs:device/ncs:live-status" {
    container file-operation {
      tailf:ncs-device-type "netconf";
      tailf:display-when "not(../../ncs:module) or ../../ncs:module[ncs:name='huawei-file-operation'] or (../../ncs:live-status-protocol[not(ncs:capability)]) or (../../ncs:live-status-protocol/ncs:capability/ncs:module[.='huawei-file-operation'])";
      description
        "Indicate file system management.";
      container dirs {
        description
          "List of operational data of file information.";
        list dir {
          key "file-name dir-name";
          description
            "Operational data of file information.";
          leaf file-name {
            type string {
              length "1..255";
            }
            description
              "Name of a folder or file.";
          }
          leaf dir-name {
            type string {
              length "1..255";
            }
            description
              "Name of a folder or a file.";
          }
          leaf attribute {
            type string {
              length "1..16";
            }
            description
              "Attributes of a folder or file.";
          }
          leaf modify-time {
            type yang:date-and-time;
            description
              "Last modified time of a folder or file.";
          }
          leaf size {
            type uint32;
            units "Byte";
            description
              "Size of a folder or file. Integer type and the size of a folder is expressed as 4096.";
          }
        }
      }
      container disk-usages {
        description
          "List of operational data of disk space information.";
        list disk-usage {
          key "name";
          description
            "Operational data of disk space information.";
          leaf name {
            type string {
              length "1..64";
            }
            description
              "Name of a file system partition.";
          }
          leaf path {
            type string {
              length "1..64";
            }
            description
              "Directory of a file system partition.";
          }
          leaf total-size {
            type string {
              length "1..32";
            }
            units "kB";
            description
              "Total size of a file system partition.";
          }
          leaf free-size {
            type string {
              length "1..32";
            }
            units "kB";
            description
              "Size of the free space in a file system partition.";
          }
          leaf usage {
            type pub-type:live_ncs_percent;
            description
              "Usage of a file system partition.";
          }
        }
      }
    }
  }
  augment "/ncs:devices/ncs:template/ncs:ned-id/ncs:config" {
    // NCS drop config false container 'file-operation'
  }
}
