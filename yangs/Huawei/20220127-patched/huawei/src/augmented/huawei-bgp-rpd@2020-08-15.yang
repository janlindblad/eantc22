module huawei-bgp-rpd {
  // Generated by yanger -t ncs
  tailf:mount-id "huawei-nc-1.0:huawei-nc-1.0";
  tailf:ncs-device-type "netconf";

  yang-version 1;
  namespace "urn:huawei:yang:huawei-bgp-rpd";
  prefix bgp-rpd;

  import huawei-extension {
    prefix ext;
  }
  import huawei-network-instance {
    prefix ni;
  }
  import huawei-bgp {
    prefix bgp;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Inter-AS routing protocol that exchanges Network Layer Reachability Information (NLRI) with other BGP systems.";

  revision 2020-08-15 {
    description
      "Initial revision.";
    reference "Huawei private.";
  }
  ext:task-name "bgp";

  augment "/ncs:devices/ncs:template/ncs:ned-id/ncs:config/ni:network-instance/ni:instances/ni:instance/bgp:bgp/bgp:base-process/bgp:afs/bgp:af" {
    description
      "BGP RPD address family configuration.";
    container rpd {
      // NCS drop when statement
      description
        "Configure RPD address family.";
      container common {
        description
          "Configure BGP RPD common options.";
        leaf router-id-filter {
          type string;
          // NCS drop default statement
          description
            "Enable/disable router ID filter.";
        }
      }
    }
  }
  augment "/ncs:devices/ncs:device/ncs:live-status/ni:network-instance/ni:instances/ni:instance/bgp:bgp/bgp:base-process/bgp:afs/bgp:af" {
    description
      "BGP RPD address family configuration.";
    container rpd {
      tailf:ncs-device-type "netconf";
      tailf:display-when "not(../../../../../../../../../ncs:module) or ../../../../../../../../../ncs:module[ncs:name='huawei-bgp-rpd'] or (../../../../../../../../../ncs:live-status-protocol[not(ncs:capability)]) or (../../../../../../../../../ncs:live-status-protocol/ncs:capability/ncs:module[.='huawei-bgp-rpd'])";
      // NCS drop when statement
      description
        "Configure RPD address family.";
      container common {
        description
          "Configure BGP RPD common options.";
        leaf router-id-filter {
          type boolean;
          // NCS drop default statement
          description
            "Enable/disable router ID filter.";
        }
      }
    }
  }
  augment "/ncs:devices/ncs:device/ncs:config/ni:network-instance/ni:instances/ni:instance/bgp:bgp/bgp:base-process/bgp:afs/bgp:af" {
    description
      "BGP RPD address family configuration.";
    container rpd {
      tailf:ncs-device-type "netconf";
      tailf:display-when "not(../../../../../../../../../ncs:module) or ../../../../../../../../../ncs:module[ncs:name='huawei-bgp-rpd']";
      when "../bgp:type='rpd'" {
        tailf:xpath-root 3;
      }
      description
        "Configure RPD address family.";
      container common {
        description
          "Configure BGP RPD common options.";
        leaf router-id-filter {
          type boolean;
          default "true";
          description
            "Enable/disable router ID filter.";
        }
      }
    }
  }
  augment "/ncs:devices/ncs:template/ncs:ned-id/ncs:config/ni:network-instance/ni:instances/ni:instance/bgp:bgp/bgp:base-process/bgp:peers/bgp:peer/bgp:afs/bgp:af" {
    description
      "BGP RPD address family configuration.";
    container rpd {
      // NCS drop when statement
      description
        "Configure RPD options.";
      leaf graceful-restart-static-timer {
        type string;
        units "s";
        description
          "Specifies the maximum time during which a peer waits for a BGP session reestablishment.";
      }
      uses bgp:ncs_template_path-attr-map-type;
    }
  }
  augment "/ncs:devices/ncs:device/ncs:live-status/ni:network-instance/ni:instances/ni:instance/bgp:bgp/bgp:base-process/bgp:peers/bgp:peer/bgp:afs/bgp:af" {
    description
      "BGP RPD address family configuration.";
    container rpd {
      tailf:ncs-device-type "netconf";
      tailf:display-when "not(../../../../../../../../../../../ncs:module) or ../../../../../../../../../../../ncs:module[ncs:name='huawei-bgp-rpd'] or (../../../../../../../../../../../ncs:live-status-protocol[not(ncs:capability)]) or (../../../../../../../../../../../ncs:live-status-protocol/ncs:capability/ncs:module[.='huawei-bgp-rpd'])";
      // NCS drop when statement
      description
        "Configure RPD options.";
      leaf graceful-restart-static-timer {
        type uint32 {
          range "3600..2147483647";
        }
        units "s";
        description
          "Specifies the maximum time during which a peer waits for a BGP session reestablishment.";
      }
      uses bgp:live_ncs_path-attr-map-type;
    }
  }
  augment "/ncs:devices/ncs:device/ncs:config/ni:network-instance/ni:instances/ni:instance/bgp:bgp/bgp:base-process/bgp:peers/bgp:peer/bgp:afs/bgp:af" {
    description
      "BGP RPD address family configuration.";
    container rpd {
      tailf:ncs-device-type "netconf";
      tailf:display-when "not(../../../../../../../../../../../ncs:module) or ../../../../../../../../../../../ncs:module[ncs:name='huawei-bgp-rpd']";
      when "../bgp:type = 'rpd'" {
        tailf:xpath-root 3;
      }
      description
        "Configure RPD options.";
      leaf graceful-restart-static-timer {
        type uint32 {
          range "3600..2147483647";
        }
        units "s";
        description
          "Specifies the maximum time during which a peer waits for a BGP session reestablishment.";
      }
      uses bgp:path-attr-map-type;
    }
  }
}
