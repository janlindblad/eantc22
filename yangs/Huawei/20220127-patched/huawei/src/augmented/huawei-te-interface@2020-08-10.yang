module huawei-te-interface {
  // Generated by yanger -t ncs
  tailf:mount-id "huawei-nc-1.0:huawei-nc-1.0";
  tailf:ncs-device-type "netconf";

  namespace "urn:huawei:yang:huawei-te-interface";
  prefix te-interface;

  import huawei-extension {
    prefix ext;
  }
  import huawei-network-instance {
    prefix ni;
  }
  import huawei-ifm {
    prefix ifm;
  }
  import huawei-mpls {
    prefix mpls;
  }
  import huawei-mpls-te {
    prefix mpls-te;
  }
  import huawei-te {
    prefix te;
  }
  import huawei-pub-type {
    prefix pub-type;
  }
  include huawei-te-interface-type;
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Specifies the traffic engineering configuration.";

  revision 2020-08-10 {
    description
      "Add when condition for attribute container.";
    reference "Huawei private.";
  }
  revision 2020-04-09 {
    description
      "Modify the type of the affinity attribute.";
    reference "Huawei private.";
  }
  revision 2020-03-10 {
    description
      "Add bandwidth for ietf and some conditions fixed.";
    reference "Huawei private.";
  }
  revision 2020-02-14 {
    description
      "Add static-reserved-bandwidth.";
    reference "Huawei private.";
  }
  revision 2019-07-29 {
    description
      "Init revision.";
    reference "Huawei private.";
  }
  ext:task-name "mpls-te";

  augment "/ncs:devices/ncs:template/ncs:ned-id/ncs:config/ni:network-instance/ni:instances/ni:instance/te:te" {
    description
      "TE Configuration information augment to network instance.";
    container interfaces {
      description
        "List of interfaces.";
      list interface {
        // NCS patched for predictable order
        ordered-by user;
        key "name";
        description
          "Configure interface with the TE capability.";
        leaf name {
          type string;
          // NCS drop must statement
          description
            "Specifies the name of a physical interface. The name is case-insensitive.";
        }
        leaf mpls-te-enable {
          // NCS drop when statement
          type string;
          // NCS drop must statement
          // NCS drop default statement
          description
            "Enable/disable MPLS TE in the interface.";
        }
        leaf p2mp-te-disable {
          // NCS drop when statement
          type string;
          // NCS drop default statement
          description
            "Enable/disable P2MP-TE on the interface.";
        }
        container attribute {
          // NCS drop when statement
          // NCS drop must statement
          description
            "Configure TE parameters.";
          leaf metric {
            type string;
            description
              "Specifies the Value of TE interface metric. The link with smallest metric value is used preferentially as a TE LSP.";
          }
          leaf admin-groups {
            type pub-type:ncs_template_hex-binary;
            // NCS drop default statement
            ext:case-sensitivity "upper2lower";
            description
              "Specifies interface management attributes. They are total 32 bits. Each bit is one attribute that is established on a TE LSP. Standby LSPs are selected based on the limit of the LSP affinity attribute.";
          }
          leaf-list admin-groups-name {
            // NCS patched for predictable order
            ordered-by user;
            type string;
            // NCS drop max-elements statement
            description
              "Configure the interface management attributes. They are total 32 bits. Each bit is one attribute that is established on a TE LSP. Standby LSPs are selected based on the limit of the LSP affinity attribute.";
          }
          leaf-list srlg-group {
            // NCS patched for predictable order
            ordered-by user;
            type string;
            // NCS drop max-elements statement
            description
              "Configure a list of risk-shared link groups of TE interfaces.";
          }
          container bandwidth {
            // NCS drop must statement
            description
              "Configure TE link bandwidth attributes.";
            leaf max-reserved {
              type string;
              units "kbit/s";
              // NCS drop default statement
              description
                "Specifies the maximum reserved bandwidth (kbit/s) of TE interfaces.
                 Special explanation:
                 Constraint: If a static BC0 or dynamic BC0 bandwidth is configured, the value of the static maximum reservable bandwidth node must be higher than or equal to the static or dynamic BC0 bandwidth. The configured bandwidth of the static maximum reservable bandwidth on a TE interface cannot exceed the physical bandwidth of the interface. The value of the static maximum reservable bandwidth is mutually exclusive with the dynamic maximum reservable bandwidth.";
            }
            leaf bc0 {
              type string;
              units "kbit/s";
              // NCS drop must statement
              // NCS drop default statement
              description
                "Bc0 bandwidth value in kbps.
                 Special explanation:
                 Constraint: When a static BC0 bandwidth is configured, the value of the static maximum reservable bandwidth must be higher than or equal to the static BC0 bandwidth. And the value of the static BC0 bandwidth is mutually exclusive with the dynamic BC0 bandwidth and the dynamic maximum reservable bandwidth.";
            }
            leaf bc1 {
              // NCS drop when statement
              type string;
              units "kbit/s";
              // NCS drop must statement
              // NCS drop default statement
              description
                "Bc1 bandwidth value in kbps.
                 Special explanation:
                 Constraint: When a static BC1 bandwidth is configured, the value of the static maximum reservable bandwidth must be higher than or equal to the static BC1 bandwidth. And the value of the static BC1 bandwidth is mutually exclusive with the dynamic BC1 bandwidth and the dynamic maximum reservable bandwidth.";
            }
            leaf bc2 {
              // NCS drop when statement
              type string;
              units "kbit/s";
              // NCS drop must statement
              // NCS drop default statement
              description
                "Bc2 bandwidth value in kbps.
                 Special explanation:
                 Constraint: When a static BC2 bandwidth is configured, the value of the static maximum reservable bandwidth must be higher than or equal to the static BC2 bandwidth. And the value of the static BC2 bandwidth is mutually exclusive with the dynamic BC2 bandwidth and the dynamic maximum reservable bandwidth.";
            }
            leaf bc3 {
              // NCS drop when statement
              type string;
              units "kbit/s";
              // NCS drop must statement
              // NCS drop default statement
              description
                "Bc3 bandwidth value in kbps.
                 Special explanation:
                 Constraint: When a static BC3 bandwidth is configured, the value of the static maximum reservable bandwidth must be higher than or equal to the static BC3 bandwidth. And the value of the static BC3 bandwidth is mutually exclusive with the dynamic BC3 bandwidth and the dynamic maximum reservable bandwidth.";
            }
            leaf bc4 {
              // NCS drop when statement
              type string;
              units "kbit/s";
              // NCS drop must statement
              // NCS drop default statement
              description
                "Bc4 bandwidth value in kbps.
                 Special explanation:
                 Constraint: When a static BC4 bandwidth is configured, the value of the static maximum reservable bandwidth must be higher than or equal to the static BC4 bandwidth. And the value of the static BC4 bandwidth is mutually exclusive with the dynamic BC4 bandwidth and the dynamic maximum reservable bandwidth.";
            }
            leaf bc5 {
              // NCS drop when statement
              type string;
              units "kbit/s";
              // NCS drop must statement
              // NCS drop default statement
              description
                "Bc5 bandwidth value in kbps.
                 Special explanation:
                 Constraint: When a static BC5 bandwidth is configured, the value of the static maximum reservable bandwidth must be higher than or equal to the static BC5 bandwidth. And the value of the static BC5 bandwidth is mutually exclusive with the dynamic BC5 bandwidth and the dynamic maximum reservable bandwidth.";
            }
            leaf bc6 {
              // NCS drop when statement
              type string;
              units "kbit/s";
              // NCS drop must statement
              // NCS drop default statement
              description
                "Bc6 bandwidth value in kbps.
                 Special explanation:
                 Constraint: When a static BC6 bandwidth is configured, the value of the static maximum reservable bandwidth must be higher than or equal to the static BC6 bandwidth. And the value of the static BC6 bandwidth is mutually exclusive with the dynamic BC6 bandwidth and the dynamic maximum reservable bandwidth.";
            }
            leaf bc7 {
              // NCS drop when statement
              type string;
              units "kbit/s";
              // NCS drop must statement
              // NCS drop default statement
              description
                "Bc7 bandwidth value in kbps.
                 Special explanation:
                 Constraint: When a static BC7 bandwidth is configured, the value of the static maximum reservable bandwidth must be higher than or equal to the static BC7 bandwidth. And the value of the static BC7 bandwidth is mutually exclusive with the dynamic BC7 bandwidth and the dynamic maximum reservable bandwidth.";
            }
            leaf dynamic-max-reserved-percent {
              type string;
              // NCS drop must statement
              description
                "Specifies the dynamic maximum reserved bandwidth percent of TE interfaces.
                 Special explanation:
                 Constraint: If a dynamic BC0 bandwidth node is configured, the value of dynamic maximum reservable bandwidth cannot be deleted and is mutually exclusive with the static maximum reservable bandwidth.";
            }
            leaf dynamic-bc0-percent {
              type string;
              units "%";
              // NCS drop must statement
              description
                "Specifies the dynamic Bc0 bandwidth percent.
                 Special explanation:
                 Constraint: When a dynamic BC0 bandwidth node is configured, either of the dynamic and static maximum reservable bandwidth must be configured. If a static maximum reservable bandwidth is configured, the value of the dynamic BC0 bandwidth must be lower than or equal to the static maximum reservable bandwidth. And the value of dynamic BC0 bandwidth is mutually exclusive with the static BC0 bandwidth.";
            }
            leaf change-threshold-down {
              type string;
              units "%";
              // NCS drop default statement
              description
                "Specifies the flooding threshold of bandwidth consumption percentage. Establishing TE LSPs consumes the bandwidth of the TE interface, and the available bandwidth of the interface is therefore reduced. If the percentage of the reduced bandwidth is larger than the configured flooding threshold, the bandwidth of the TE interface will be flooded to the network.";
            }
            leaf change-threshold-up {
              type string;
              units "%";
              // NCS drop default statement
              description
                "Specifies the flooding threshold of the percentage of released bandwidth compared with the available interface bandwidth. When a TE LSP of an interface is removed, the bandwidth of the TE LSP is released. The available bandwidth of the interface is therefore increased. If the percentage of the increased bandwidth is larger than the configured flooding threshold, the bandwidth of the TE interface will be flooded over the network.";
            }
          }
          // NCS drop config false container status
        }
        container mpls-te-attribute {
          // NCS drop when statement
          description
            "Configure MPLS TE link parameters.";
          leaf auto-frr-mode {
            type ncs_template_rsvp-fast-reroute-mode;
            // NCS drop default statement
            description
              "Auto FRR protection modes: global inheritance, link protection, node protection and self-adapting. By default, global AutoFRR is global inheritance. Link protection: A bypass tunnel can be used to protect only the links where the outbound interface of the primary LSP resides. Node protection: A bypass tunnel can be used to protect the downstream node of the links where the outbound interface of the primary LSP resides. Self-adapting: A bypass tunnel can be dynamically selected node protection or link protection according to the network conditions.";
          }
          container auto-frr-attributes {
            description
              "Configure MPLS TE link frr parameters.";
            leaf bandwidth {
              type string;
              units "kbit/s";
              description
                "TE link auto bypass tunnel bandwidth (kbits/s) requested by an active tunnel. The value cannot exceed the bandwidth of the active tunnel.";
            }
            leaf setup-priority {
              type string;
              // NCS drop must statement
              // NCS drop default statement
              description
                "TE link auto bypass tunnel setup priority.";
            }
            leaf hold-priority {
              type string;
              // NCS drop default statement
              description
                "TE link auto bypass tunnel hold priority.";
            }
            leaf hop-limit {
              type string;
              description
                "TE link auto bypass tunnel hop limit.";
            }
            leaf include-any {
              type pub-type:ncs_template_hex-binary;
              description
                "TE link auto bypass tunnel administrative group attribute (include any).";
            }
            leaf exclude-any {
              type pub-type:ncs_template_hex-binary;
              description
                "TE link auto bypass tunnel administrative group attribute (exclude).";
            }
            // NCS drop config false leaf 'include-all'
            leaf-list include-any-affinity-name {
              // NCS patched for predictable order
              ordered-by user;
              type string;
              // NCS drop must statement
              // NCS drop max-elements statement
              description
                "Configure a list of affinity names that can be refer to a tunnel to include any.";
            }
            leaf-list exclude-any-affinity-name {
              // NCS patched for predictable order
              ordered-by user;
              type string;
              // NCS drop must statement
              // NCS drop max-elements statement
              description
                "Configure tunnel path affinity attribute: exclude.";
            }
            leaf-list include-all-affinity-name {
              // NCS patched for predictable order
              ordered-by user;
              type string;
              // NCS drop must statement
              // NCS drop max-elements statement
              description
                "Configure a list of affinity names that can be refer to a tunnel to include all.";
            }
          }
        }
      }
    }
  }
  augment "/ncs:devices/ncs:device/ncs:live-status/ni:network-instance/ni:instances/ni:instance/te:te" {
    description
      "TE Configuration information augment to network instance.";
    container interfaces {
      tailf:ncs-device-type "netconf";
      tailf:display-when "not(../../../../../../ncs:module) or ../../../../../../ncs:module[ncs:name='huawei-te-interface'] or (../../../../../../ncs:live-status-protocol[not(ncs:capability)]) or (../../../../../../ncs:live-status-protocol/ncs:capability/ncs:module[.='huawei-te-interface'])";
      description
        "List of interfaces.";
      list interface {
        key "name";
        description
          "Configure interface with the TE capability.";
        leaf name {
          type leafref {
            path "/ncs:devices/ncs:device/ncs:live-status/ifm:ifm/ifm:interfaces/ifm:interface/ifm:name" {
              tailf:xpath-root 3;
            }
          }
          // NCS drop must statement
          description
            "Specifies the name of a physical interface. The name is case-insensitive.";
        }
        leaf mpls-te-enable {
          // NCS drop when statement
          type boolean;
          // NCS drop must statement
          // NCS drop default statement
          description
            "Enable/disable MPLS TE in the interface.";
        }
        leaf p2mp-te-disable {
          // NCS drop when statement
          type boolean;
          // NCS drop default statement
          description
            "Enable/disable P2MP-TE on the interface.";
        }
        container attribute {
          // NCS drop when statement
          // NCS drop must statement
          description
            "Configure TE parameters.";
          leaf metric {
            type uint32 {
              range "1..16777215";
            }
            description
              "Specifies the Value of TE interface metric. The link with smallest metric value is used preferentially as a TE LSP.";
          }
          leaf admin-groups {
            type pub-type:live_ncs_hex-binary;
            // NCS drop default statement
            ext:case-sensitivity "upper2lower";
            description
              "Specifies interface management attributes. They are total 32 bits. Each bit is one attribute that is established on a TE LSP. Standby LSPs are selected based on the limit of the LSP affinity attribute.";
          }
          leaf-list admin-groups-name {
            type leafref {
              path "/ncs:devices/ncs:device/ncs:live-status/te:te/te:affinity-define/te:affinity-mappings/te:affinity-mapping/te:attribute-name" {
                tailf:xpath-root 3;
              }
            }
            // NCS drop max-elements statement
            description
              "Configure the interface management attributes. They are total 32 bits. Each bit is one attribute that is established on a TE LSP. Standby LSPs are selected based on the limit of the LSP affinity attribute.";
          }
          leaf-list srlg-group {
            type uint32 {
              range "0..4294967295";
            }
            // NCS drop max-elements statement
            description
              "Configure a list of risk-shared link groups of TE interfaces.";
          }
          container bandwidth {
            // NCS drop must statement
            description
              "Configure TE link bandwidth attributes.";
            leaf max-reserved {
              type uint32 {
                range "0..4294967295";
                ext:value-meaning {
                  ext:item "0" {
                    ext:meaning "Physical interface bandwidth.";
                  }
                }
              }
              units "kbit/s";
              // NCS drop default statement
              description
                "Specifies the maximum reserved bandwidth (kbit/s) of TE interfaces.
                 Special explanation:
                 Constraint: If a static BC0 or dynamic BC0 bandwidth is configured, the value of the static maximum reservable bandwidth node must be higher than or equal to the static or dynamic BC0 bandwidth. The configured bandwidth of the static maximum reservable bandwidth on a TE interface cannot exceed the physical bandwidth of the interface. The value of the static maximum reservable bandwidth is mutually exclusive with the dynamic maximum reservable bandwidth.";
            }
            leaf bc0 {
              type uint32 {
                range "0..4294967295";
                ext:value-meaning {
                  ext:item "0" {
                    ext:meaning "Physical interface bandwidth.";
                  }
                }
              }
              units "kbit/s";
              // NCS drop must statement
              // NCS drop default statement
              description
                "Bc0 bandwidth value in kbps.
                 Special explanation:
                 Constraint: When a static BC0 bandwidth is configured, the value of the static maximum reservable bandwidth must be higher than or equal to the static BC0 bandwidth. And the value of the static BC0 bandwidth is mutually exclusive with the dynamic BC0 bandwidth and the dynamic maximum reservable bandwidth.";
            }
            leaf bc1 {
              // NCS drop when statement
              type uint32 {
                range "0..4294967295";
                ext:value-meaning {
                  ext:item "0" {
                    ext:meaning "Physical interface bandwidth.";
                  }
                }
              }
              units "kbit/s";
              // NCS drop must statement
              // NCS drop default statement
              description
                "Bc1 bandwidth value in kbps.
                 Special explanation:
                 Constraint: When a static BC1 bandwidth is configured, the value of the static maximum reservable bandwidth must be higher than or equal to the static BC1 bandwidth. And the value of the static BC1 bandwidth is mutually exclusive with the dynamic BC1 bandwidth and the dynamic maximum reservable bandwidth.";
            }
            leaf bc2 {
              // NCS drop when statement
              type uint32 {
                range "0..4294967295";
                ext:value-meaning {
                  ext:item "0" {
                    ext:meaning "Physical interface bandwidth.";
                  }
                }
              }
              units "kbit/s";
              // NCS drop must statement
              // NCS drop default statement
              description
                "Bc2 bandwidth value in kbps.
                 Special explanation:
                 Constraint: When a static BC2 bandwidth is configured, the value of the static maximum reservable bandwidth must be higher than or equal to the static BC2 bandwidth. And the value of the static BC2 bandwidth is mutually exclusive with the dynamic BC2 bandwidth and the dynamic maximum reservable bandwidth.";
            }
            leaf bc3 {
              // NCS drop when statement
              type uint32 {
                range "0..4294967295";
                ext:value-meaning {
                  ext:item "0" {
                    ext:meaning "Physical interface bandwidth.";
                  }
                }
              }
              units "kbit/s";
              // NCS drop must statement
              // NCS drop default statement
              description
                "Bc3 bandwidth value in kbps.
                 Special explanation:
                 Constraint: When a static BC3 bandwidth is configured, the value of the static maximum reservable bandwidth must be higher than or equal to the static BC3 bandwidth. And the value of the static BC3 bandwidth is mutually exclusive with the dynamic BC3 bandwidth and the dynamic maximum reservable bandwidth.";
            }
            leaf bc4 {
              // NCS drop when statement
              type uint32 {
                range "0..4294967295";
                ext:value-meaning {
                  ext:item "0" {
                    ext:meaning "Physical interface bandwidth.";
                  }
                }
              }
              units "kbit/s";
              // NCS drop must statement
              // NCS drop default statement
              description
                "Bc4 bandwidth value in kbps.
                 Special explanation:
                 Constraint: When a static BC4 bandwidth is configured, the value of the static maximum reservable bandwidth must be higher than or equal to the static BC4 bandwidth. And the value of the static BC4 bandwidth is mutually exclusive with the dynamic BC4 bandwidth and the dynamic maximum reservable bandwidth.";
            }
            leaf bc5 {
              // NCS drop when statement
              type uint32 {
                range "0..4294967295";
                ext:value-meaning {
                  ext:item "0" {
                    ext:meaning "Physical interface bandwidth.";
                  }
                }
              }
              units "kbit/s";
              // NCS drop must statement
              // NCS drop default statement
              description
                "Bc5 bandwidth value in kbps.
                 Special explanation:
                 Constraint: When a static BC5 bandwidth is configured, the value of the static maximum reservable bandwidth must be higher than or equal to the static BC5 bandwidth. And the value of the static BC5 bandwidth is mutually exclusive with the dynamic BC5 bandwidth and the dynamic maximum reservable bandwidth.";
            }
            leaf bc6 {
              // NCS drop when statement
              type uint32 {
                range "0..4294967295";
                ext:value-meaning {
                  ext:item "0" {
                    ext:meaning "Physical interface bandwidth.";
                  }
                }
              }
              units "kbit/s";
              // NCS drop must statement
              // NCS drop default statement
              description
                "Bc6 bandwidth value in kbps.
                 Special explanation:
                 Constraint: When a static BC6 bandwidth is configured, the value of the static maximum reservable bandwidth must be higher than or equal to the static BC6 bandwidth. And the value of the static BC6 bandwidth is mutually exclusive with the dynamic BC6 bandwidth and the dynamic maximum reservable bandwidth.";
            }
            leaf bc7 {
              // NCS drop when statement
              type uint32 {
                range "0..4294967295";
                ext:value-meaning {
                  ext:item "0" {
                    ext:meaning "Physical interface bandwidth.";
                  }
                }
              }
              units "kbit/s";
              // NCS drop must statement
              // NCS drop default statement
              description
                "Bc7 bandwidth value in kbps.
                 Special explanation:
                 Constraint: When a static BC7 bandwidth is configured, the value of the static maximum reservable bandwidth must be higher than or equal to the static BC7 bandwidth. And the value of the static BC7 bandwidth is mutually exclusive with the dynamic BC7 bandwidth and the dynamic maximum reservable bandwidth.";
            }
            leaf dynamic-max-reserved-percent {
              type uint16 {
                range "1..1000";
              }
              // NCS drop must statement
              description
                "Specifies the dynamic maximum reserved bandwidth percent of TE interfaces.
                 Special explanation:
                 Constraint: If a dynamic BC0 bandwidth node is configured, the value of dynamic maximum reservable bandwidth cannot be deleted and is mutually exclusive with the static maximum reservable bandwidth.";
            }
            leaf dynamic-bc0-percent {
              type uint8 {
                range "1..100";
              }
              units "%";
              // NCS drop must statement
              description
                "Specifies the dynamic Bc0 bandwidth percent.
                 Special explanation:
                 Constraint: When a dynamic BC0 bandwidth node is configured, either of the dynamic and static maximum reservable bandwidth must be configured. If a static maximum reservable bandwidth is configured, the value of the dynamic BC0 bandwidth must be lower than or equal to the static maximum reservable bandwidth. And the value of dynamic BC0 bandwidth is mutually exclusive with the static BC0 bandwidth.";
            }
            leaf change-threshold-down {
              type int32 {
                range "0..100";
              }
              units "%";
              // NCS drop default statement
              description
                "Specifies the flooding threshold of bandwidth consumption percentage. Establishing TE LSPs consumes the bandwidth of the TE interface, and the available bandwidth of the interface is therefore reduced. If the percentage of the reduced bandwidth is larger than the configured flooding threshold, the bandwidth of the TE interface will be flooded to the network.";
            }
            leaf change-threshold-up {
              type int32 {
                range "0..100";
              }
              units "%";
              // NCS drop default statement
              description
                "Specifies the flooding threshold of the percentage of released bandwidth compared with the available interface bandwidth. When a TE LSP of an interface is removed, the bandwidth of the TE LSP is released. The available bandwidth of the interface is therefore increased. If the percentage of the increased bandwidth is larger than the configured flooding threshold, the bandwidth of the TE interface will be flooded over the network.";
            }
          }
          container status {
            description
              "Operational state of TE interface information.";
            leaf used-bandwidth {
              type uint32 {
                range "0..40000000";
              }
              units "kbit/s";
              description
                "Allocated bandwidth on an interface.";
            }
            leaf line-protocol-state {
              type live_ncs_line-protocol-status;
              description
                "TE Interface line protocol current state.";
            }
            leaf static-reserved-bandwidth {
              type uint32 {
                range "0..40000000";
              }
              units "kbit/s";
              description
                "Static reserved bandwidth on an interface.";
            }
          }
        }
        container mpls-te-attribute {
          // NCS drop when statement
          description
            "Configure MPLS TE link parameters.";
          leaf auto-frr-mode {
            type live_ncs_rsvp-fast-reroute-mode;
            // NCS drop default statement
            description
              "Auto FRR protection modes: global inheritance, link protection, node protection and self-adapting. By default, global AutoFRR is global inheritance. Link protection: A bypass tunnel can be used to protect only the links where the outbound interface of the primary LSP resides. Node protection: A bypass tunnel can be used to protect the downstream node of the links where the outbound interface of the primary LSP resides. Self-adapting: A bypass tunnel can be dynamically selected node protection or link protection according to the network conditions.";
          }
          container auto-frr-attributes {
            description
              "Configure MPLS TE link frr parameters.";
            leaf bandwidth {
              type uint32 {
                range "0..4000000000";
              }
              units "kbit/s";
              description
                "TE link auto bypass tunnel bandwidth (kbits/s) requested by an active tunnel. The value cannot exceed the bandwidth of the active tunnel.";
            }
            leaf setup-priority {
              type uint32 {
                range "0..7";
              }
              // NCS drop must statement
              // NCS drop default statement
              description
                "TE link auto bypass tunnel setup priority.";
            }
            leaf hold-priority {
              type uint32 {
                range "0..7";
              }
              // NCS drop default statement
              description
                "TE link auto bypass tunnel hold priority.";
            }
            leaf hop-limit {
              type uint32 {
                range "1..32";
              }
              description
                "TE link auto bypass tunnel hop limit.";
            }
            leaf include-any {
              type pub-type:live_ncs_hex-binary;
              description
                "TE link auto bypass tunnel administrative group attribute (include any).";
            }
            leaf exclude-any {
              type pub-type:live_ncs_hex-binary;
              description
                "TE link auto bypass tunnel administrative group attribute (exclude).";
            }
            leaf include-all {
              type pub-type:live_ncs_hex-binary;
              description
                "TE link auto bypass tunnel administrative group attribute (include all).";
            }
            leaf-list include-any-affinity-name {
              type leafref {
                path "/ncs:devices/ncs:device/ncs:live-status/te:te/te:affinity-define/te:affinity-mappings/te:affinity-mapping/te:attribute-name" {
                  tailf:xpath-root 3;
                }
              }
              // NCS drop must statement
              // NCS drop max-elements statement
              description
                "Configure a list of affinity names that can be refer to a tunnel to include any.";
            }
            leaf-list exclude-any-affinity-name {
              type leafref {
                path "/ncs:devices/ncs:device/ncs:live-status/te:te/te:affinity-define/te:affinity-mappings/te:affinity-mapping/te:attribute-name" {
                  tailf:xpath-root 3;
                }
              }
              // NCS drop must statement
              // NCS drop max-elements statement
              description
                "Configure tunnel path affinity attribute: exclude.";
            }
            leaf-list include-all-affinity-name {
              type leafref {
                path "/ncs:devices/ncs:device/ncs:live-status/te:te/te:affinity-define/te:affinity-mappings/te:affinity-mapping/te:attribute-name" {
                  tailf:xpath-root 3;
                }
              }
              // NCS drop must statement
              // NCS drop max-elements statement
              description
                "Configure a list of affinity names that can be refer to a tunnel to include all.";
            }
          }
        }
      }
    }
  }
  augment "/ncs:devices/ncs:device/ncs:config/ni:network-instance/ni:instances/ni:instance/te:te" {
    description
      "TE Configuration information augment to network instance.";
    container interfaces {
      tailf:ncs-device-type "netconf";
      tailf:display-when "not(../../../../../../ncs:module) or ../../../../../../ncs:module[ncs:name='huawei-te-interface']";
      description
        "List of interfaces.";
      list interface {
        key "name";
        description
          "Configure interface with the TE capability.";
        leaf name {
          type leafref {
            path "/ncs:devices/ncs:device/ncs:config/ifm:ifm/ifm:interfaces/ifm:interface/ifm:name" {
              tailf:xpath-root 3;
            }
          }
          must '../../../../ni:name=/ifm:ifm/ifm:interfaces/ifm:interface[ifm:name=current()]/ifm:vrf-name' {
            tailf:xpath-root 3;
          }
          description
            "Specifies the name of a physical interface. The name is case-insensitive.";
        }
        leaf mpls-te-enable {
          when "/mpls:mpls/mpls-te:te/mpls-te:enable='true'" {
            tailf:xpath-root 3;
          }
          type boolean;
          must '/ni:network-instance/ni:instances/ni:instance/mpls:mpls/mpls:common/mpls:mpls-interfaces/mpls:mpls-interface[mpls:name=current()/../name]' {
            tailf:xpath-root 3;
          }
          default "false";
          description
            "Enable/disable MPLS TE in the interface.";
        }
        leaf p2mp-te-disable {
          when "../mpls-te-enable='true'" {
            tailf:xpath-root 3;
          }
          type boolean;
          default "false";
          description
            "Enable/disable P2MP-TE on the interface.";
        }
        container attribute {
          when "../mpls-te-enable='true' or /te:te/te:global/te:te-attribute-enable='true'" {
            tailf:xpath-root 3;
          }
          must "not(admin-groups-name) or admin-groups='0x0'" {
            tailf:xpath-root 3;
          }
          description
            "Configure TE parameters.";
          leaf metric {
            type uint32 {
              range "1..16777215";
            }
            description
              "Specifies the Value of TE interface metric. The link with smallest metric value is used preferentially as a TE LSP.";
          }
          leaf admin-groups {
            type pub-type:hex-binary;
            default "0x0";
            ext:case-sensitivity "upper2lower";
            description
              "Specifies interface management attributes. They are total 32 bits. Each bit is one attribute that is established on a TE LSP. Standby LSPs are selected based on the limit of the LSP affinity attribute.";
          }
          leaf-list admin-groups-name {
            type leafref {
              path "/ncs:devices/ncs:device/ncs:config/te:te/te:affinity-define/te:affinity-mappings/te:affinity-mapping/te:attribute-name" {
                tailf:xpath-root 3;
              }
            }
            max-elements 32;
            description
              "Configure the interface management attributes. They are total 32 bits. Each bit is one attribute that is established on a TE LSP. Standby LSPs are selected based on the limit of the LSP affinity attribute.";
          }
          leaf-list srlg-group {
            type uint32 {
              range "0..4294967295";
            }
            max-elements 64;
            description
              "Configure a list of risk-shared link groups of TE interfaces.";
          }
          container bandwidth {
            must "/mpls:mpls/mpls-te:te/mpls-te:global/mpls-te:ds-te-mode='non-ietf' or (/mpls:mpls/mpls-te:te/mpls-te:global/mpls-te:bcm-model/mpls-te:bcm-mode='mam' and max-reserved>=(bc0+bc1+bc2+bc3+bc4+bc5+bc6+bc7)) or /mpls:mpls/mpls-te:te/mpls-te:global/mpls-te:bcm-model/mpls-te:bcm-mode='rdm'" {
              tailf:xpath-root 3;
            }
            description
              "Configure TE link bandwidth attributes.";
            leaf max-reserved {
              type uint32 {
                range "0..4294967295";
                ext:value-meaning {
                  ext:item "0" {
                    ext:meaning "Physical interface bandwidth.";
                  }
                }
              }
              units "kbit/s";
              default "0";
              description
                "Specifies the maximum reserved bandwidth (kbit/s) of TE interfaces.
                 Special explanation:
                 Constraint: If a static BC0 or dynamic BC0 bandwidth is configured, the value of the static maximum reservable bandwidth node must be higher than or equal to the static or dynamic BC0 bandwidth. The configured bandwidth of the static maximum reservable bandwidth on a TE interface cannot exceed the physical bandwidth of the interface. The value of the static maximum reservable bandwidth is mutually exclusive with the dynamic maximum reservable bandwidth.";
            }
            leaf bc0 {
              type uint32 {
                range "0..4294967295";
                ext:value-meaning {
                  ext:item "0" {
                    ext:meaning "Physical interface bandwidth.";
                  }
                }
              }
              units "kbit/s";
              must '../max-reserved and (../max-reserved>=../bc0)' {
                tailf:xpath-root 3;
              }
              default "0";
              description
                "Bc0 bandwidth value in kbps.
                 Special explanation:
                 Constraint: When a static BC0 bandwidth is configured, the value of the static maximum reservable bandwidth must be higher than or equal to the static BC0 bandwidth. And the value of the static BC0 bandwidth is mutually exclusive with the dynamic BC0 bandwidth and the dynamic maximum reservable bandwidth.";
            }
            leaf bc1 {
              when "/mpls:mpls/mpls-te:te/mpls-te:global/mpls-te:ds-te-mode='ietf'" {
                tailf:xpath-root 3;
              }
              type uint32 {
                range "0..4294967295";
                ext:value-meaning {
                  ext:item "0" {
                    ext:meaning "Physical interface bandwidth.";
                  }
                }
              }
              units "kbit/s";
              must "../max-reserved and (../max-reserved>=../bc1) and ((/mpls:mpls/mpls-te:te/mpls-te:global/mpls-te:bcm-model/mpls-te:bcm-mode = 'mam') or (../bc0 >= ../bc1))" {
                tailf:xpath-root 3;
              }
              default "0";
              description
                "Bc1 bandwidth value in kbps.
                 Special explanation:
                 Constraint: When a static BC1 bandwidth is configured, the value of the static maximum reservable bandwidth must be higher than or equal to the static BC1 bandwidth. And the value of the static BC1 bandwidth is mutually exclusive with the dynamic BC1 bandwidth and the dynamic maximum reservable bandwidth.";
            }
            leaf bc2 {
              when "/mpls:mpls/mpls-te:te/mpls-te:global/mpls-te:ds-te-mode='ietf'" {
                tailf:xpath-root 3;
              }
              type uint32 {
                range "0..4294967295";
                ext:value-meaning {
                  ext:item "0" {
                    ext:meaning "Physical interface bandwidth.";
                  }
                }
              }
              units "kbit/s";
              must "../max-reserved and (../max-reserved>=../bc2) and ((/mpls:mpls/mpls-te:te/mpls-te:global/mpls-te:bcm-model/mpls-te:bcm-mode = 'mam') or (../bc1 >= ../bc2))" {
                tailf:xpath-root 3;
              }
              default "0";
              description
                "Bc2 bandwidth value in kbps.
                 Special explanation:
                 Constraint: When a static BC2 bandwidth is configured, the value of the static maximum reservable bandwidth must be higher than or equal to the static BC2 bandwidth. And the value of the static BC2 bandwidth is mutually exclusive with the dynamic BC2 bandwidth and the dynamic maximum reservable bandwidth.";
            }
            leaf bc3 {
              when "/mpls:mpls/mpls-te:te/mpls-te:global/mpls-te:ds-te-mode='ietf'" {
                tailf:xpath-root 3;
              }
              type uint32 {
                range "0..4294967295";
                ext:value-meaning {
                  ext:item "0" {
                    ext:meaning "Physical interface bandwidth.";
                  }
                }
              }
              units "kbit/s";
              must "../max-reserved and (../max-reserved>=../bc3) and ((/mpls:mpls/mpls-te:te/mpls-te:global/mpls-te:bcm-model/mpls-te:bcm-mode = 'mam') or (../bc2 >= ../bc3))" {
                tailf:xpath-root 3;
              }
              default "0";
              description
                "Bc3 bandwidth value in kbps.
                 Special explanation:
                 Constraint: When a static BC3 bandwidth is configured, the value of the static maximum reservable bandwidth must be higher than or equal to the static BC3 bandwidth. And the value of the static BC3 bandwidth is mutually exclusive with the dynamic BC3 bandwidth and the dynamic maximum reservable bandwidth.";
            }
            leaf bc4 {
              when "/mpls:mpls/mpls-te:te/mpls-te:global/mpls-te:ds-te-mode='ietf'" {
                tailf:xpath-root 3;
              }
              type uint32 {
                range "0..4294967295";
                ext:value-meaning {
                  ext:item "0" {
                    ext:meaning "Physical interface bandwidth.";
                  }
                }
              }
              units "kbit/s";
              must "../max-reserved and (../max-reserved>=../bc4) and ((/mpls:mpls/mpls-te:te/mpls-te:global/mpls-te:bcm-model/mpls-te:bcm-mode = 'mam') or (../bc3 >= ../bc4))" {
                tailf:xpath-root 3;
              }
              default "0";
              description
                "Bc4 bandwidth value in kbps.
                 Special explanation:
                 Constraint: When a static BC4 bandwidth is configured, the value of the static maximum reservable bandwidth must be higher than or equal to the static BC4 bandwidth. And the value of the static BC4 bandwidth is mutually exclusive with the dynamic BC4 bandwidth and the dynamic maximum reservable bandwidth.";
            }
            leaf bc5 {
              when "/mpls:mpls/mpls-te:te/mpls-te:global/mpls-te:ds-te-mode='ietf'" {
                tailf:xpath-root 3;
              }
              type uint32 {
                range "0..4294967295";
                ext:value-meaning {
                  ext:item "0" {
                    ext:meaning "Physical interface bandwidth.";
                  }
                }
              }
              units "kbit/s";
              must "../max-reserved and (../max-reserved>=../bc5) and ((/mpls:mpls/mpls-te:te/mpls-te:global/mpls-te:bcm-model/mpls-te:bcm-mode = 'mam') or (../bc4 >= ../bc5))" {
                tailf:xpath-root 3;
              }
              default "0";
              description
                "Bc5 bandwidth value in kbps.
                 Special explanation:
                 Constraint: When a static BC5 bandwidth is configured, the value of the static maximum reservable bandwidth must be higher than or equal to the static BC5 bandwidth. And the value of the static BC5 bandwidth is mutually exclusive with the dynamic BC5 bandwidth and the dynamic maximum reservable bandwidth.";
            }
            leaf bc6 {
              when "/mpls:mpls/mpls-te:te/mpls-te:global/mpls-te:ds-te-mode='ietf'" {
                tailf:xpath-root 3;
              }
              type uint32 {
                range "0..4294967295";
                ext:value-meaning {
                  ext:item "0" {
                    ext:meaning "Physical interface bandwidth.";
                  }
                }
              }
              units "kbit/s";
              must "../max-reserved and (../max-reserved>=../bc6) and ((/mpls:mpls/mpls-te:te/mpls-te:global/mpls-te:bcm-model/mpls-te:bcm-mode = 'mam') or (../bc5 >= ../bc6))" {
                tailf:xpath-root 3;
              }
              default "0";
              description
                "Bc6 bandwidth value in kbps.
                 Special explanation:
                 Constraint: When a static BC6 bandwidth is configured, the value of the static maximum reservable bandwidth must be higher than or equal to the static BC6 bandwidth. And the value of the static BC6 bandwidth is mutually exclusive with the dynamic BC6 bandwidth and the dynamic maximum reservable bandwidth.";
            }
            leaf bc7 {
              when "/mpls:mpls/mpls-te:te/mpls-te:global/mpls-te:ds-te-mode='ietf'" {
                tailf:xpath-root 3;
              }
              type uint32 {
                range "0..4294967295";
                ext:value-meaning {
                  ext:item "0" {
                    ext:meaning "Physical interface bandwidth.";
                  }
                }
              }
              units "kbit/s";
              must "../max-reserved and (../max-reserved>=../bc7) and ((/mpls:mpls/mpls-te:te/mpls-te:global/mpls-te:bcm-model/mpls-te:bcm-mode = 'mam') or (../bc6 >= ../bc7))" {
                tailf:xpath-root 3;
              }
              default "0";
              description
                "Bc7 bandwidth value in kbps.
                 Special explanation:
                 Constraint: When a static BC7 bandwidth is configured, the value of the static maximum reservable bandwidth must be higher than or equal to the static BC7 bandwidth. And the value of the static BC7 bandwidth is mutually exclusive with the dynamic BC7 bandwidth and the dynamic maximum reservable bandwidth.";
            }
            leaf dynamic-max-reserved-percent {
              type uint16 {
                range "1..1000";
              }
              must '../max-reserved=0' {
                tailf:xpath-root 3;
              }
              description
                "Specifies the dynamic maximum reserved bandwidth percent of TE interfaces.
                 Special explanation:
                 Constraint: If a dynamic BC0 bandwidth node is configured, the value of dynamic maximum reservable bandwidth cannot be deleted and is mutually exclusive with the static maximum reservable bandwidth.";
            }
            leaf dynamic-bc0-percent {
              type uint8 {
                range "1..100";
              }
              units "%";
              must '(../dynamic-max-reserved-percent or (../max-reserved>0)) and ../bc0=0' {
                tailf:xpath-root 3;
              }
              description
                "Specifies the dynamic Bc0 bandwidth percent.
                 Special explanation:
                 Constraint: When a dynamic BC0 bandwidth node is configured, either of the dynamic and static maximum reservable bandwidth must be configured. If a static maximum reservable bandwidth is configured, the value of the dynamic BC0 bandwidth must be lower than or equal to the static maximum reservable bandwidth. And the value of dynamic BC0 bandwidth is mutually exclusive with the static BC0 bandwidth.";
            }
            leaf change-threshold-down {
              type int32 {
                range "0..100";
              }
              units "%";
              default "10";
              description
                "Specifies the flooding threshold of bandwidth consumption percentage. Establishing TE LSPs consumes the bandwidth of the TE interface, and the available bandwidth of the interface is therefore reduced. If the percentage of the reduced bandwidth is larger than the configured flooding threshold, the bandwidth of the TE interface will be flooded to the network.";
            }
            leaf change-threshold-up {
              type int32 {
                range "0..100";
              }
              units "%";
              default "10";
              description
                "Specifies the flooding threshold of the percentage of released bandwidth compared with the available interface bandwidth. When a TE LSP of an interface is removed, the bandwidth of the TE LSP is released. The available bandwidth of the interface is therefore increased. If the percentage of the increased bandwidth is larger than the configured flooding threshold, the bandwidth of the TE interface will be flooded over the network.";
            }
          }
          // NCS drop config false container status
        }
        container mpls-te-attribute {
          when "../mpls-te-enable='true'" {
            tailf:xpath-root 3;
          }
          description
            "Configure MPLS TE link parameters.";
          leaf auto-frr-mode {
            type rsvp-fast-reroute-mode;
            default "default";
            description
              "Auto FRR protection modes: global inheritance, link protection, node protection and self-adapting. By default, global AutoFRR is global inheritance. Link protection: A bypass tunnel can be used to protect only the links where the outbound interface of the primary LSP resides. Node protection: A bypass tunnel can be used to protect the downstream node of the links where the outbound interface of the primary LSP resides. Self-adapting: A bypass tunnel can be dynamically selected node protection or link protection according to the network conditions.";
          }
          container auto-frr-attributes {
            description
              "Configure MPLS TE link frr parameters.";
            leaf bandwidth {
              type uint32 {
                range "0..4000000000";
              }
              units "kbit/s";
              description
                "TE link auto bypass tunnel bandwidth (kbits/s) requested by an active tunnel. The value cannot exceed the bandwidth of the active tunnel.";
            }
            leaf setup-priority {
              type uint32 {
                range "0..7";
              }
              must '(../hold-priority and (../setup-priority>=../hold-priority)) or not(../hold-priority)' {
                tailf:xpath-root 3;
              }
              default "7";
              description
                "TE link auto bypass tunnel setup priority.";
            }
            leaf hold-priority {
              type uint32 {
                range "0..7";
              }
              default "7";
              description
                "TE link auto bypass tunnel hold priority.";
            }
            leaf hop-limit {
              type uint32 {
                range "1..32";
              }
              description
                "TE link auto bypass tunnel hop limit.";
            }
            leaf include-any {
              type pub-type:hex-binary;
              description
                "TE link auto bypass tunnel administrative group attribute (include any).";
            }
            leaf exclude-any {
              type pub-type:hex-binary;
              description
                "TE link auto bypass tunnel administrative group attribute (exclude).";
            }
            // NCS drop config false leaf 'include-all'
            leaf-list include-any-affinity-name {
              type leafref {
                path "/ncs:devices/ncs:device/ncs:config/te:te/te:affinity-define/te:affinity-mappings/te:affinity-mapping/te:attribute-name" {
                  tailf:xpath-root 3;
                }
              }
              must 'not(../include-any or ../exclude-any)' {
                tailf:xpath-root 3;
              }
              max-elements 32;
              description
                "Configure a list of affinity names that can be refer to a tunnel to include any.";
            }
            leaf-list exclude-any-affinity-name {
              type leafref {
                path "/ncs:devices/ncs:device/ncs:config/te:te/te:affinity-define/te:affinity-mappings/te:affinity-mapping/te:attribute-name" {
                  tailf:xpath-root 3;
                }
              }
              must 'not(../include-any or ../exclude-any)' {
                tailf:xpath-root 3;
              }
              max-elements 32;
              description
                "Configure tunnel path affinity attribute: exclude.";
            }
            leaf-list include-all-affinity-name {
              type leafref {
                path "/ncs:devices/ncs:device/ncs:config/te:te/te:affinity-define/te:affinity-mappings/te:affinity-mapping/te:attribute-name" {
                  tailf:xpath-root 3;
                }
              }
              must 'not(../include-any or ../exclude-any)' {
                tailf:xpath-root 3;
              }
              max-elements 32;
              description
                "Configure a list of affinity names that can be refer to a tunnel to include all.";
            }
          }
        }
      }
    }
  }
}
