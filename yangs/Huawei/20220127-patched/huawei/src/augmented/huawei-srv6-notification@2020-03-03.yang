module huawei-srv6-notification {
  // Generated by yanger -t ncs
  tailf:mount-id "huawei-nc-1.0:huawei-nc-1.0";
  tailf:ncs-device-type "netconf";

  yang-version 1;
  namespace "urn:huawei:yang:huawei-srv6-notification";
  prefix srv6-notification;

  import ietf-inet-types {
    prefix inet;
  }
  import huawei-extension {
    prefix ext;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Notification of segment routing IPv6.";

  revision 2020-03-03 {
    description
      "Init revision.";
    reference "Huawei private.";
  }
  ext:task-name "segr";

  augment "/ncs:devices/ncs:device/ncs:notifications/ncs:received-notifications/ncs:notification/ncs:data" {
    container local-sid-route-conflict-resume {
      presence "";
      config false;
      description
        "The conflict between the SRv6 local SID and route was removed.";
      leaf local-sid {
        type inet:ipv6-address-no-zone;
        description
          "Local SID.";
      }
      leaf prefix-length {
        type uint32;
        description
          "Mask length of local SID.";
      }
    }
  }
  augment "/ncs:devices/ncs:device/ncs:notifications/ncs:received-notifications/ncs:notification/ncs:data" {
    container local-sid-route-conflict {
      presence "";
      config false;
      description
        "Conflict between an SRv6 local SID and a route.";
      leaf local-sid {
        type inet:ipv6-address-no-zone;
        description
          "Local SID.";
      }
      leaf prefix-length {
        type uint32;
        description
          "Mask length of local SID.";
      }
    }
  }
  augment "/ncs:devices/ncs:device/ncs:netconf-notifications/ncs:received-notifications/ncs:notification/ncs:data" {
    container local-sid-route-conflict-resume {
      presence "";
      config false;
      description
        "The conflict between the SRv6 local SID and route was removed.";
      leaf local-sid {
        type inet:ipv6-address-no-zone;
        description
          "Local SID.";
      }
      leaf prefix-length {
        type uint32;
        description
          "Mask length of local SID.";
      }
    }
  }
  augment "/ncs:devices/ncs:device/ncs:netconf-notifications/ncs:received-notifications/ncs:notification/ncs:data" {
    container local-sid-route-conflict {
      presence "";
      config false;
      description
        "Conflict between an SRv6 local SID and a route.";
      leaf local-sid {
        type inet:ipv6-address-no-zone;
        description
          "Local SID.";
      }
      leaf prefix-length {
        type uint32;
        description
          "Mask length of local SID.";
      }
    }
  }
}
