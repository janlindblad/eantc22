module huawei-evpl {
  // Generated by yanger -t ncs
  tailf:mount-id "huawei-nc-1.0:huawei-nc-1.0";
  tailf:ncs-device-type "netconf";

  namespace "urn:huawei:yang:huawei-evpl";
  prefix evpl;

  import huawei-ifm {
    prefix ifm;
  }
  import ietf-inet-types {
    prefix inet;
  }
  import huawei-extension {
    prefix ext;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Management of Ethernet virtual private line.";

  revision 2020-07-21 {
    description
      "Add node ignore-ac-state.";
    reference "Huawei private.";
  }
  revision 2019-03-01 {
    description
      "Initial revision.";
    reference "Huawei private.";
  }
  ext:task-name "evpl";

  typedef ncs_template_evpl-mode {
    type string;
    description
      "The mode of EVPL instance.";
  }

  typedef ncs_rpc_notif_evpl-mode {
    type enumeration {
      enum "vxlan-mode" {
        value 0;
        description
          "VXLAN mode.";
      }
      enum "mpls-mode" {
        value 1;
        description
          "MPLS mode.";
      }
      enum "srv6-mode" {
        value 2;
        description
          "SRv6 mode.";
      }
    }
    description
      "The mode of EVPL instance.";
  }

  typedef live_ncs_evpl-mode {
    type enumeration {
      enum "vxlan-mode" {
        value 0;
        description
          "VXLAN mode.";
      }
      enum "mpls-mode" {
        value 1;
        description
          "MPLS mode.";
      }
      enum "srv6-mode" {
        value 2;
        description
          "SRv6 mode.";
      }
    }
    description
      "The mode of EVPL instance.";
  }

  typedef evpl-mode {
    type enumeration {
      enum "vxlan-mode" {
        value 0;
        description
          "VXLAN mode.";
      }
      enum "mpls-mode" {
        value 1;
        description
          "MPLS mode.";
      }
      enum "srv6-mode" {
        value 2;
        description
          "SRv6 mode.";
      }
    }
    description
      "The mode of EVPL instance.";
  }

  augment "/ncs:devices/ncs:device/ncs:config" {
    container evpl {
      tailf:ncs-device-type "netconf";
      tailf:display-when "not(../../ncs:module) or ../../ncs:module[ncs:name='huawei-evpl']";
      description
        "Management of EVPL.";
      container instances {
        description
          "List of EVPL instances.";
        list instance {
          key "id";
          description
            "Configure attribute of EVPL instance.";
          leaf id {
            type uint32 {
              range "1..16777215";
            }
            description
              "The identification of the EVPL instance.";
          }
          leaf mode {
            type evpl-mode;
            ext:operation-exclude "update";
            mandatory true;
            description
              "The mode of the EVPL instance, that not support modification.";
          }
          container interfaces {
            when "(../mode != 'vxlan-mode')" {
              tailf:xpath-root 3;
            }
            description
              "List of service interfaces that a EVPL instance corresponds.";
            list interface {
              key "name";
              max-elements 1;
              description
                "Configure the service interface that a EVPL instance corresponds.";
              leaf name {
                type leafref {
                  path "/ncs:devices/ncs:device/ncs:config/ifm:ifm/ifm:interfaces/ifm:interface/ifm:name" {
                    tailf:xpath-root 3;
                  }
                }
                must "(/ifm:ifm/ifm:interfaces/ifm:interface[ifm:name=current()]/ifm:type = 'PW-VE' and /ifm:ifm/ifm:interfaces/ifm:interface[ifm:name=current()]/ifm:class != 'main-interface') or (/ifm:ifm/ifm:interfaces/ifm:interface[ifm:name=current()]/ifm:type != 'PW-VE')" {
                  tailf:xpath-root 3;
                }
                description
                  "The name of interface.";
              }
              leaf ignore-ac-state {
                type boolean;
                default "false";
                description
                  "Enable/disable ignore the attachment circuit status on an interface.";
              }
            }
          }
          container peers {
            when "(../mode = 'vxlan-mode')" {
              tailf:xpath-root 3;
            }
            description
              "List of provider edge nodes that a EVPL instance corresponds with VXLAN encapsulation.";
            list peer {
              key "name peer-ip";
              max-elements 1;
              description
                "Configure provider edge node that a EVPL instance corresponds with VXLAN encapsulation.";
              leaf name {
                type leafref {
                  path "/ncs:devices/ncs:device/ncs:config/ifm:ifm/ifm:interfaces/ifm:interface/ifm:name" {
                    tailf:xpath-root 3;
                  }
                }
                must "/ifm:ifm/ifm:interfaces/ifm:interface[ifm:name=current()]/ifm:type = 'PW-VE' and /ifm:ifm/ifm:interfaces/ifm:interface[ifm:name=current()]/ifm:class = 'main-interface'" {
                  tailf:xpath-root 3;
                }
                description
                  "The name of interface.";
              }
              leaf peer-ip {
                type inet:ipv4-address-no-zone;
                description
                  "The address of provider edge node.";
              }
            }
          }
          container evpl-statistics {
            when "(../mode = 'vxlan-mode')" {
              tailf:xpath-root 3;
            }
            description
              "Configure an EVPL instance.";
            leaf statistics-enable {
              type boolean;
              default "false";
              description
                "Enable/disable EVPL message statistical function.";
            }
          }
        }
      }
    }
  }
  augment "/ncs:devices/ncs:device/ncs:live-status" {
    container evpl {
      tailf:ncs-device-type "netconf";
      tailf:display-when "not(../../ncs:module) or ../../ncs:module[ncs:name='huawei-evpl'] or (../../ncs:live-status-protocol[not(ncs:capability)]) or (../../ncs:live-status-protocol/ncs:capability/ncs:module[.='huawei-evpl'])";
      description
        "Management of EVPL.";
      container instances {
        description
          "List of EVPL instances.";
        list instance {
          key "id";
          description
            "Configure attribute of EVPL instance.";
          leaf id {
            type uint32 {
              range "1..16777215";
            }
            description
              "The identification of the EVPL instance.";
          }
          leaf mode {
            type live_ncs_evpl-mode;
            ext:operation-exclude "update";
            // NCS drop mandatory statement
            description
              "The mode of the EVPL instance, that not support modification.";
          }
          container interfaces {
            // NCS drop when statement
            description
              "List of service interfaces that a EVPL instance corresponds.";
            list interface {
              key "name";
              // NCS drop max-elements statement
              description
                "Configure the service interface that a EVPL instance corresponds.";
              leaf name {
                type leafref {
                  path "/ncs:devices/ncs:device/ncs:live-status/ifm:ifm/ifm:interfaces/ifm:interface/ifm:name" {
                    tailf:xpath-root 3;
                  }
                }
                // NCS drop must statement
                description
                  "The name of interface.";
              }
              leaf ignore-ac-state {
                type boolean;
                // NCS drop default statement
                description
                  "Enable/disable ignore the attachment circuit status on an interface.";
              }
            }
          }
          container peers {
            // NCS drop when statement
            description
              "List of provider edge nodes that a EVPL instance corresponds with VXLAN encapsulation.";
            list peer {
              key "name peer-ip";
              // NCS drop max-elements statement
              description
                "Configure provider edge node that a EVPL instance corresponds with VXLAN encapsulation.";
              leaf name {
                type leafref {
                  path "/ncs:devices/ncs:device/ncs:live-status/ifm:ifm/ifm:interfaces/ifm:interface/ifm:name" {
                    tailf:xpath-root 3;
                  }
                }
                // NCS drop must statement
                description
                  "The name of interface.";
              }
              leaf peer-ip {
                type inet:ipv4-address-no-zone;
                description
                  "The address of provider edge node.";
              }
            }
          }
          container evpl-statistics {
            // NCS drop when statement
            description
              "Configure an EVPL instance.";
            leaf statistics-enable {
              type boolean;
              // NCS drop default statement
              description
                "Enable/disable EVPL message statistical function.";
            }
          }
        }
      }
    }
  }
  augment "/ncs:devices/ncs:template/ncs:ned-id/ncs:config" {
    container evpl {
      description
        "Management of EVPL.";
      container instances {
        description
          "List of EVPL instances.";
        list instance {
          // NCS patched for predictable order
          ordered-by user;
          key "id";
          description
            "Configure attribute of EVPL instance.";
          leaf id {
            type string;
            description
              "The identification of the EVPL instance.";
          }
          leaf mode {
            type ncs_template_evpl-mode;
            ext:operation-exclude "update";
            // NCS drop mandatory statement
            description
              "The mode of the EVPL instance, that not support modification.";
          }
          container interfaces {
            // NCS drop when statement
            description
              "List of service interfaces that a EVPL instance corresponds.";
            list interface {
              // NCS patched for predictable order
              ordered-by user;
              key "name";
              // NCS drop max-elements statement
              description
                "Configure the service interface that a EVPL instance corresponds.";
              leaf name {
                type string;
                // NCS drop must statement
                description
                  "The name of interface.";
              }
              leaf ignore-ac-state {
                type string;
                // NCS drop default statement
                description
                  "Enable/disable ignore the attachment circuit status on an interface.";
              }
            }
          }
          container peers {
            // NCS drop when statement
            description
              "List of provider edge nodes that a EVPL instance corresponds with VXLAN encapsulation.";
            list peer {
              // NCS patched for predictable order
              ordered-by user;
              key "name peer-ip";
              // NCS drop max-elements statement
              description
                "Configure provider edge node that a EVPL instance corresponds with VXLAN encapsulation.";
              leaf name {
                type string;
                // NCS drop must statement
                description
                  "The name of interface.";
              }
              leaf peer-ip {
                type string;
                description
                  "The address of provider edge node.";
              }
            }
          }
          container evpl-statistics {
            // NCS drop when statement
            description
              "Configure an EVPL instance.";
            leaf statistics-enable {
              type string;
              // NCS drop default statement
              description
                "Enable/disable EVPL message statistical function.";
            }
          }
        }
      }
    }
  }
}
