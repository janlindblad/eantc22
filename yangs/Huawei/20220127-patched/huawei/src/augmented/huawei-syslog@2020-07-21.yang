module huawei-syslog {
  // Generated by yanger -t ncs
  tailf:mount-id "huawei-nc-1.0:huawei-nc-1.0";
  tailf:ncs-device-type "netconf";

  namespace "urn:huawei:yang:huawei-syslog";
  prefix syslog;

  import ietf-inet-types {
    prefix inet;
  }
  import ietf-yang-types {
    prefix yang;
  }
  import huawei-extension {
    prefix ext;
  }
  import huawei-network-instance {
    prefix ni;
  }
  import huawei-ssl {
    prefix ssl;
  }
  import huawei-ifm {
    prefix ifm;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "System log.";

  revision 2020-07-21 {
    description
      "Add character-set node.";
    reference "Huawei private.";
  }
  revision 2020-06-02 {
    description
      "Modify information of leafs.";
    reference "Huawei private.";
  }
  revision 2020-05-22 {
    description
      "Add the brief format of syslog host.";
    reference "Huawei private.";
  }
  revision 2020-02-24 {
    description
      "Add the syslog node.";
    reference "Huawei private.";
  }
  revision 2020-02-19 {
    description
      "Add the name and activated of syslog host.";
    reference "Huawei private.";
  }
  revision 2020-02-11 {
    description
      "Add the severity mask and facility mask of syslog host.";
    reference "Huawei private.";
  }
  revision 2020-01-20 {
    description
      "Add syslogserver.";
    reference "Huawei private.";
  }
  revision 2019-09-24 {
    description
      "Initial revision.";
    reference "Huawei private.";
  }
  ext:task-name "log";

  typedef ncs_template_loghost-facility {
    type string;
    description
      "The type of log host facility.";
  }

  typedef ncs_template_log-level {
    type string;
    description
      "The type of log level.";
  }

  typedef ncs_template_log-type {
    type string;
    description
      "The log type.";
  }

  typedef ncs_template_address-family-type {
    type string;
    description
      "The type of IP address.";
  }

  typedef ncs_template_timestamp {
    type string;
    description
      "The type of time stamp.";
  }

  typedef ncs_template_timestamp-format {
    type string;
    description
      "The time stamp format.";
  }

  typedef ncs_template_version-format {
    type string;
    description
      "The version format.";
  }

  typedef ncs_template_terminal-type {
    type string;
    description
      "The terminal type.";
  }

  typedef ncs_template_logfile-type {
    type string;
    description
      "The type of log.";
  }

  typedef ncs_template_report-channel-type {
    type string;
    description
      "The type of report channel.";
  }

  typedef ncs_template_transport-mode-type {
    type string;
    description
      "The type of transport mode.";
  }

  typedef ncs_template_language-type {
    type string;
    description
      "The type of language.";
  }

  typedef ncs_template_switch-type {
    type string;
    description
      "The type of switch.";
  }

  typedef ncs_template_hostname-type {
    type string;
    description
      "The type of hostname.";
  }

  typedef ncs_template_save-log-type {
    type string;
    description
      "The saved log type.";
  }

  typedef ncs_template_prefix-file-type {
    type string;
    description
      "The type of log.";
  }

  typedef ncs_template_character-set {
    type string;
    description
      "The character set of syslog.";
  }

  typedef ncs_rpc_notif_loghost-facility {
    type enumeration {
      enum "local0" {
        value 16;
        description
          "Log server local 0.";
      }
      enum "local1" {
        value 17;
        description
          "Log server local 1.";
      }
      enum "local2" {
        value 18;
        description
          "Log server local 2.";
      }
      enum "local3" {
        value 19;
        description
          "Log server local 3.";
      }
      enum "local4" {
        value 20;
        description
          "Log server local 4.";
      }
      enum "local5" {
        value 21;
        description
          "Log server local 5.";
      }
      enum "local6" {
        value 22;
        description
          "Log server local 6.";
      }
      enum "local7" {
        value 23;
        description
          "Log server local 7.";
      }
    }
    description
      "The type of log host facility.";
  }

  typedef ncs_rpc_notif_log-level {
    type enumeration {
      enum "emergencies" {
        value 0;
        description
          "The log host level is emergencies.";
      }
      enum "alert" {
        value 1;
        description
          "The log host level is alert.";
      }
      enum "critical" {
        value 2;
        description
          "The log host level is critical.";
      }
      enum "error" {
        value 3;
        description
          "The log host level is error.";
      }
      enum "warning" {
        value 4;
        description
          "The log host level is warning.";
      }
      enum "notification" {
        value 5;
        description
          "The log host level is notification.";
      }
      enum "informational" {
        value 6;
        description
          "The log host level is informational.";
      }
      enum "debugging" {
        value 7;
        description
          "The log host level is debugging.";
      }
    }
    description
      "The type of log level.";
  }

  typedef ncs_rpc_notif_log-type {
    type enumeration {
      enum "eventlog" {
        value 2;
        description
          "The event log.";
      }
      enum "operlog" {
        value 1;
        description
          "The operation log.";
      }
      enum "alarmlog" {
        value 5;
        description
          "The alarm log.";
      }
      enum "diaglog" {
        value 4;
        description
          "The diagnose log.";
      }
      enum "notificationlog" {
        value 10;
        description
          "The notification Log.";
      }
      enum "maintainlog" {
        value 11;
        description
          "The maintain Log.";
      }
      enum "servicelog" {
        value 18;
        description
          "The service log.";
      }
    }
    description
      "The log type.";
  }

  typedef ncs_rpc_notif_address-family-type {
    type enumeration {
      enum "ipv4" {
        value 1;
        description
          "The address type is IPv4.";
      }
      enum "ipv6" {
        value 2;
        description
          "The address type is IPv6.";
      }
    }
    description
      "The type of IP address.";
  }

  typedef ncs_rpc_notif_timestamp {
    type enumeration {
      enum "date-boot" {
        value 11;
        description
          "Time elapsed since the system started. It is a relative time period.";
      }
      enum "date-second" {
        value 12;
        description
          "Date format with second precision.";
      }
      enum "date-tenthsecond" {
        value 13;
        description
          "Date format with tenth-second precision.";
      }
      enum "date-millisecond" {
        value 14;
        description
          "Date format with millisecond precision.";
      }
      enum "shortdate-second" {
        value 15;
        description
          "Short date format second precision.";
      }
      enum "shortdate-tenthsecond" {
        value 16;
        description
          "Short date format with tenth-second precision.";
      }
      enum "shortdate-millisecond" {
        value 17;
        description
          "Short date format with millisecond precision.";
      }
      enum "formatdate-second" {
        value 18;
        description
          "Format date format with second precision.";
      }
      enum "formatdate-tenthsecond" {
        value 19;
        description
          "Format date format with tenth-second precision.";
      }
      enum "formatdate-millisecond" {
        value 20;
        description
          "Format date format with millisecond precision.";
      }
    }
    description
      "The type of time stamp.";
  }

  typedef ncs_rpc_notif_timestamp-format {
    type enumeration {
      enum "UTC" {
        value 0;
        description
          "UTC format.";
      }
      enum "localtime" {
        value 1;
        description
          "Local time format.";
      }
    }
    description
      "The time stamp format.";
  }

  typedef ncs_rpc_notif_version-format {
    type enumeration {
      enum "rfc3164" {
        value 0;
        description
          "RFC3164.";
      }
      enum "rfc5424" {
        value 1;
        description
          "RFC5424.";
      }
    }
    description
      "The version format.";
  }

  typedef ncs_rpc_notif_terminal-type {
    type enumeration {
      enum "CONSOLE" {
        value 1;
        description
          "Console access.";
      }
      enum "AUX" {
        value 2;
        description
          "Aux access.";
      }
      enum "TELNET" {
        value 3;
        description
          "Telnet access.";
      }
      enum "SSH" {
        value 4;
        description
          "SSH access.";
      }
      enum "MODEM" {
        value 5;
        description
          "Modem access.";
      }
      enum "FTP" {
        value 6;
        description
          "FTP access.";
      }
      enum "SWITCHLR" {
        value 7;
        description
          "SWITCHLR access.";
      }
      enum "SNMP" {
        value 8;
        description
          "SNMP access.";
      }
      enum "OPS" {
        value 9;
        description
          "OPS access.";
      }
      enum "EMS" {
        value 10;
        description
          "EMS access.";
      }
      enum "TM" {
        value 11;
        description
          "TM access.";
      }
      enum "LCT" {
        value 12;
        description
          "LCT access.";
      }
      enum "TL1" {
        value 13;
        description
          "TL1 access.";
      }
    }
    description
      "The terminal type.";
  }

  typedef ncs_rpc_notif_logfile-type {
    type enumeration {
      enum "log" {
        value 1;
        description
          "Log logfile.";
      }
      enum "security" {
        value 3;
        description
          "Security logfile.";
      }
      enum "operation" {
        value 4;
        description
          "Operation logfile.";
      }
      enum "debug" {
        value 6;
        description
          "Debug logfile.";
      }
    }
    description
      "The type of log.";
  }

  typedef ncs_rpc_notif_report-channel-type {
    type enumeration {
      enum "IETF" {
        value 0;
        description
          "Using an IETF channel to send alarm.";
      }
      enum "ITUT" {
        value 1;
        description
          "Using an ITU-T channel to send alarm.";
      }
    }
    description
      "The type of report channel.";
  }

  typedef ncs_rpc_notif_transport-mode-type {
    type enumeration {
      enum "udp" {
        value 2;
        description
          "UDP transport mode.";
      }
      enum "tcp" {
        value 1;
        description
          "TCP transport mode.";
      }
    }
    description
      "The type of transport mode.";
  }

  typedef ncs_rpc_notif_language-type {
    type enumeration {
      enum "english" {
        value 0;
        description
          "English mode.";
      }
      enum "chinese" {
        value 1;
        description
          "Chinese mode.";
      }
    }
    description
      "The type of language.";
  }

  typedef ncs_rpc_notif_switch-type {
    type enumeration {
      enum "on" {
        value 0;
        description
          "On mode.";
      }
      enum "off" {
        value 1;
        description
          "Off mode.";
      }
    }
    description
      "The type of switch.";
  }

  typedef ncs_rpc_notif_hostname-type {
    type enumeration {
      enum "sysname" {
        value 0;
        description
          "Sysname.";
      }
      enum "esn" {
        value 1;
        description
          "Esn.";
      }
      enum "user-defined" {
        value 2;
        description
          "User-defined.";
      }
    }
    description
      "The type of hostname.";
  }

  typedef ncs_rpc_notif_save-log-type {
    type enumeration {
      enum "log" {
        value 0;
        description
          "Common logs.";
      }
      enum "diaglog" {
        value 1;
        description
          "Diagnoseic logs.";
      }
    }
    description
      "The saved log type.";
  }

  typedef ncs_rpc_notif_prefix-file-type {
    type enumeration {
      enum "debug" {
        value 6;
        description
          "Debug logfile.";
      }
    }
    description
      "The type of log.";
  }

  typedef ncs_rpc_notif_character-set {
    type enumeration {
      enum "UTF-8" {
        value 1;
        description
          "Character set is UTF-8.";
      }
      enum "ISO8859-1" {
        value 2;
        description
          "Character set is ISO8859-1.";
      }
      enum "GBK" {
        value 3;
        description
          "Character set is GBK.";
      }
    }
    description
      "The character set of syslog.";
  }

  typedef live_ncs_loghost-facility {
    type enumeration {
      enum "local0" {
        value 16;
        description
          "Log server local 0.";
      }
      enum "local1" {
        value 17;
        description
          "Log server local 1.";
      }
      enum "local2" {
        value 18;
        description
          "Log server local 2.";
      }
      enum "local3" {
        value 19;
        description
          "Log server local 3.";
      }
      enum "local4" {
        value 20;
        description
          "Log server local 4.";
      }
      enum "local5" {
        value 21;
        description
          "Log server local 5.";
      }
      enum "local6" {
        value 22;
        description
          "Log server local 6.";
      }
      enum "local7" {
        value 23;
        description
          "Log server local 7.";
      }
    }
    description
      "The type of log host facility.";
  }

  typedef live_ncs_log-level {
    type enumeration {
      enum "emergencies" {
        value 0;
        description
          "The log host level is emergencies.";
      }
      enum "alert" {
        value 1;
        description
          "The log host level is alert.";
      }
      enum "critical" {
        value 2;
        description
          "The log host level is critical.";
      }
      enum "error" {
        value 3;
        description
          "The log host level is error.";
      }
      enum "warning" {
        value 4;
        description
          "The log host level is warning.";
      }
      enum "notification" {
        value 5;
        description
          "The log host level is notification.";
      }
      enum "informational" {
        value 6;
        description
          "The log host level is informational.";
      }
      enum "debugging" {
        value 7;
        description
          "The log host level is debugging.";
      }
    }
    description
      "The type of log level.";
  }

  typedef live_ncs_log-type {
    type enumeration {
      enum "eventlog" {
        value 2;
        description
          "The event log.";
      }
      enum "operlog" {
        value 1;
        description
          "The operation log.";
      }
      enum "alarmlog" {
        value 5;
        description
          "The alarm log.";
      }
      enum "diaglog" {
        value 4;
        description
          "The diagnose log.";
      }
      enum "notificationlog" {
        value 10;
        description
          "The notification Log.";
      }
      enum "maintainlog" {
        value 11;
        description
          "The maintain Log.";
      }
      enum "servicelog" {
        value 18;
        description
          "The service log.";
      }
    }
    description
      "The log type.";
  }

  typedef live_ncs_address-family-type {
    type enumeration {
      enum "ipv4" {
        value 1;
        description
          "The address type is IPv4.";
      }
      enum "ipv6" {
        value 2;
        description
          "The address type is IPv6.";
      }
    }
    description
      "The type of IP address.";
  }

  typedef live_ncs_timestamp {
    type enumeration {
      enum "date-boot" {
        value 11;
        description
          "Time elapsed since the system started. It is a relative time period.";
      }
      enum "date-second" {
        value 12;
        description
          "Date format with second precision.";
      }
      enum "date-tenthsecond" {
        value 13;
        description
          "Date format with tenth-second precision.";
      }
      enum "date-millisecond" {
        value 14;
        description
          "Date format with millisecond precision.";
      }
      enum "shortdate-second" {
        value 15;
        description
          "Short date format second precision.";
      }
      enum "shortdate-tenthsecond" {
        value 16;
        description
          "Short date format with tenth-second precision.";
      }
      enum "shortdate-millisecond" {
        value 17;
        description
          "Short date format with millisecond precision.";
      }
      enum "formatdate-second" {
        value 18;
        description
          "Format date format with second precision.";
      }
      enum "formatdate-tenthsecond" {
        value 19;
        description
          "Format date format with tenth-second precision.";
      }
      enum "formatdate-millisecond" {
        value 20;
        description
          "Format date format with millisecond precision.";
      }
    }
    description
      "The type of time stamp.";
  }

  typedef live_ncs_timestamp-format {
    type enumeration {
      enum "UTC" {
        value 0;
        description
          "UTC format.";
      }
      enum "localtime" {
        value 1;
        description
          "Local time format.";
      }
    }
    description
      "The time stamp format.";
  }

  typedef live_ncs_version-format {
    type enumeration {
      enum "rfc3164" {
        value 0;
        description
          "RFC3164.";
      }
      enum "rfc5424" {
        value 1;
        description
          "RFC5424.";
      }
    }
    description
      "The version format.";
  }

  typedef live_ncs_terminal-type {
    type enumeration {
      enum "CONSOLE" {
        value 1;
        description
          "Console access.";
      }
      enum "AUX" {
        value 2;
        description
          "Aux access.";
      }
      enum "TELNET" {
        value 3;
        description
          "Telnet access.";
      }
      enum "SSH" {
        value 4;
        description
          "SSH access.";
      }
      enum "MODEM" {
        value 5;
        description
          "Modem access.";
      }
      enum "FTP" {
        value 6;
        description
          "FTP access.";
      }
      enum "SWITCHLR" {
        value 7;
        description
          "SWITCHLR access.";
      }
      enum "SNMP" {
        value 8;
        description
          "SNMP access.";
      }
      enum "OPS" {
        value 9;
        description
          "OPS access.";
      }
      enum "EMS" {
        value 10;
        description
          "EMS access.";
      }
      enum "TM" {
        value 11;
        description
          "TM access.";
      }
      enum "LCT" {
        value 12;
        description
          "LCT access.";
      }
      enum "TL1" {
        value 13;
        description
          "TL1 access.";
      }
    }
    description
      "The terminal type.";
  }

  typedef live_ncs_logfile-type {
    type enumeration {
      enum "log" {
        value 1;
        description
          "Log logfile.";
      }
      enum "security" {
        value 3;
        description
          "Security logfile.";
      }
      enum "operation" {
        value 4;
        description
          "Operation logfile.";
      }
      enum "debug" {
        value 6;
        description
          "Debug logfile.";
      }
    }
    description
      "The type of log.";
  }

  typedef live_ncs_report-channel-type {
    type enumeration {
      enum "IETF" {
        value 0;
        description
          "Using an IETF channel to send alarm.";
      }
      enum "ITUT" {
        value 1;
        description
          "Using an ITU-T channel to send alarm.";
      }
    }
    description
      "The type of report channel.";
  }

  typedef live_ncs_transport-mode-type {
    type enumeration {
      enum "udp" {
        value 2;
        description
          "UDP transport mode.";
      }
      enum "tcp" {
        value 1;
        description
          "TCP transport mode.";
      }
    }
    description
      "The type of transport mode.";
  }

  typedef live_ncs_language-type {
    type enumeration {
      enum "english" {
        value 0;
        description
          "English mode.";
      }
      enum "chinese" {
        value 1;
        description
          "Chinese mode.";
      }
    }
    description
      "The type of language.";
  }

  typedef live_ncs_switch-type {
    type enumeration {
      enum "on" {
        value 0;
        description
          "On mode.";
      }
      enum "off" {
        value 1;
        description
          "Off mode.";
      }
    }
    description
      "The type of switch.";
  }

  typedef live_ncs_hostname-type {
    type enumeration {
      enum "sysname" {
        value 0;
        description
          "Sysname.";
      }
      enum "esn" {
        value 1;
        description
          "Esn.";
      }
      enum "user-defined" {
        value 2;
        description
          "User-defined.";
      }
    }
    description
      "The type of hostname.";
  }

  typedef live_ncs_save-log-type {
    type enumeration {
      enum "log" {
        value 0;
        description
          "Common logs.";
      }
      enum "diaglog" {
        value 1;
        description
          "Diagnoseic logs.";
      }
    }
    description
      "The saved log type.";
  }

  typedef live_ncs_prefix-file-type {
    type enumeration {
      enum "debug" {
        value 6;
        description
          "Debug logfile.";
      }
    }
    description
      "The type of log.";
  }

  typedef live_ncs_character-set {
    type enumeration {
      enum "UTF-8" {
        value 1;
        description
          "Character set is UTF-8.";
      }
      enum "ISO8859-1" {
        value 2;
        description
          "Character set is ISO8859-1.";
      }
      enum "GBK" {
        value 3;
        description
          "Character set is GBK.";
      }
    }
    description
      "The character set of syslog.";
  }

  typedef loghost-facility {
    type enumeration {
      enum "local0" {
        value 16;
        description
          "Log server local 0.";
      }
      enum "local1" {
        value 17;
        description
          "Log server local 1.";
      }
      enum "local2" {
        value 18;
        description
          "Log server local 2.";
      }
      enum "local3" {
        value 19;
        description
          "Log server local 3.";
      }
      enum "local4" {
        value 20;
        description
          "Log server local 4.";
      }
      enum "local5" {
        value 21;
        description
          "Log server local 5.";
      }
      enum "local6" {
        value 22;
        description
          "Log server local 6.";
      }
      enum "local7" {
        value 23;
        description
          "Log server local 7.";
      }
    }
    description
      "The type of log host facility.";
  }

  typedef log-level {
    type enumeration {
      enum "emergencies" {
        value 0;
        description
          "The log host level is emergencies.";
      }
      enum "alert" {
        value 1;
        description
          "The log host level is alert.";
      }
      enum "critical" {
        value 2;
        description
          "The log host level is critical.";
      }
      enum "error" {
        value 3;
        description
          "The log host level is error.";
      }
      enum "warning" {
        value 4;
        description
          "The log host level is warning.";
      }
      enum "notification" {
        value 5;
        description
          "The log host level is notification.";
      }
      enum "informational" {
        value 6;
        description
          "The log host level is informational.";
      }
      enum "debugging" {
        value 7;
        description
          "The log host level is debugging.";
      }
    }
    description
      "The type of log level.";
  }

  typedef log-type {
    type enumeration {
      enum "eventlog" {
        value 2;
        description
          "The event log.";
      }
      enum "operlog" {
        value 1;
        description
          "The operation log.";
      }
      enum "alarmlog" {
        value 5;
        description
          "The alarm log.";
      }
      enum "diaglog" {
        value 4;
        description
          "The diagnose log.";
      }
      enum "notificationlog" {
        value 10;
        description
          "The notification Log.";
      }
      enum "maintainlog" {
        value 11;
        description
          "The maintain Log.";
      }
      enum "servicelog" {
        value 18;
        description
          "The service log.";
      }
    }
    description
      "The log type.";
  }

  typedef address-family-type {
    type enumeration {
      enum "ipv4" {
        value 1;
        description
          "The address type is IPv4.";
      }
      enum "ipv6" {
        value 2;
        description
          "The address type is IPv6.";
      }
    }
    description
      "The type of IP address.";
  }

  typedef timestamp {
    type enumeration {
      enum "date-boot" {
        value 11;
        description
          "Time elapsed since the system started. It is a relative time period.";
      }
      enum "date-second" {
        value 12;
        description
          "Date format with second precision.";
      }
      enum "date-tenthsecond" {
        value 13;
        description
          "Date format with tenth-second precision.";
      }
      enum "date-millisecond" {
        value 14;
        description
          "Date format with millisecond precision.";
      }
      enum "shortdate-second" {
        value 15;
        description
          "Short date format second precision.";
      }
      enum "shortdate-tenthsecond" {
        value 16;
        description
          "Short date format with tenth-second precision.";
      }
      enum "shortdate-millisecond" {
        value 17;
        description
          "Short date format with millisecond precision.";
      }
      enum "formatdate-second" {
        value 18;
        description
          "Format date format with second precision.";
      }
      enum "formatdate-tenthsecond" {
        value 19;
        description
          "Format date format with tenth-second precision.";
      }
      enum "formatdate-millisecond" {
        value 20;
        description
          "Format date format with millisecond precision.";
      }
    }
    description
      "The type of time stamp.";
  }

  typedef timestamp-format {
    type enumeration {
      enum "UTC" {
        value 0;
        description
          "UTC format.";
      }
      enum "localtime" {
        value 1;
        description
          "Local time format.";
      }
    }
    description
      "The time stamp format.";
  }

  typedef version-format {
    type enumeration {
      enum "rfc3164" {
        value 0;
        description
          "RFC3164.";
      }
      enum "rfc5424" {
        value 1;
        description
          "RFC5424.";
      }
    }
    description
      "The version format.";
  }

  typedef terminal-type {
    type enumeration {
      enum "CONSOLE" {
        value 1;
        description
          "Console access.";
      }
      enum "AUX" {
        value 2;
        description
          "Aux access.";
      }
      enum "TELNET" {
        value 3;
        description
          "Telnet access.";
      }
      enum "SSH" {
        value 4;
        description
          "SSH access.";
      }
      enum "MODEM" {
        value 5;
        description
          "Modem access.";
      }
      enum "FTP" {
        value 6;
        description
          "FTP access.";
      }
      enum "SWITCHLR" {
        value 7;
        description
          "SWITCHLR access.";
      }
      enum "SNMP" {
        value 8;
        description
          "SNMP access.";
      }
      enum "OPS" {
        value 9;
        description
          "OPS access.";
      }
      enum "EMS" {
        value 10;
        description
          "EMS access.";
      }
      enum "TM" {
        value 11;
        description
          "TM access.";
      }
      enum "LCT" {
        value 12;
        description
          "LCT access.";
      }
      enum "TL1" {
        value 13;
        description
          "TL1 access.";
      }
    }
    description
      "The terminal type.";
  }

  typedef logfile-type {
    type enumeration {
      enum "log" {
        value 1;
        description
          "Log logfile.";
      }
      enum "security" {
        value 3;
        description
          "Security logfile.";
      }
      enum "operation" {
        value 4;
        description
          "Operation logfile.";
      }
      enum "debug" {
        value 6;
        description
          "Debug logfile.";
      }
    }
    description
      "The type of log.";
  }

  typedef report-channel-type {
    type enumeration {
      enum "IETF" {
        value 0;
        description
          "Using an IETF channel to send alarm.";
      }
      enum "ITUT" {
        value 1;
        description
          "Using an ITU-T channel to send alarm.";
      }
    }
    description
      "The type of report channel.";
  }

  typedef transport-mode-type {
    type enumeration {
      enum "udp" {
        value 2;
        description
          "UDP transport mode.";
      }
      enum "tcp" {
        value 1;
        description
          "TCP transport mode.";
      }
    }
    description
      "The type of transport mode.";
  }

  typedef language-type {
    type enumeration {
      enum "english" {
        value 0;
        description
          "English mode.";
      }
      enum "chinese" {
        value 1;
        description
          "Chinese mode.";
      }
    }
    description
      "The type of language.";
  }

  typedef switch-type {
    type enumeration {
      enum "on" {
        value 0;
        description
          "On mode.";
      }
      enum "off" {
        value 1;
        description
          "Off mode.";
      }
    }
    description
      "The type of switch.";
  }

  typedef hostname-type {
    type enumeration {
      enum "sysname" {
        value 0;
        description
          "Sysname.";
      }
      enum "esn" {
        value 1;
        description
          "Esn.";
      }
      enum "user-defined" {
        value 2;
        description
          "User-defined.";
      }
    }
    description
      "The type of hostname.";
  }

  typedef save-log-type {
    type enumeration {
      enum "log" {
        value 0;
        description
          "Common logs.";
      }
      enum "diaglog" {
        value 1;
        description
          "Diagnoseic logs.";
      }
    }
    description
      "The saved log type.";
  }

  typedef prefix-file-type {
    type enumeration {
      enum "debug" {
        value 6;
        description
          "Debug logfile.";
      }
    }
    description
      "The type of log.";
  }

  typedef character-set {
    type enumeration {
      enum "UTF-8" {
        value 1;
        description
          "Character set is UTF-8.";
      }
      enum "ISO8859-1" {
        value 2;
        description
          "Character set is ISO8859-1.";
      }
      enum "GBK" {
        value 3;
        description
          "Character set is GBK.";
      }
    }
    description
      "The character set of syslog.";
  }

  augment "/ncs:devices/ncs:device/ncs:rpc" {
    container rpc-save-logfile {
      tailf:ncs-device-type "netconf";
      tailf:display-when "not(../../ncs:module) or ../../ncs:module[ncs:name='huawei-syslog']";
      tailf:action save-logfile {
        tailf:actionpoint ncsproxy {
          tailf:internal;
        }
        description
          "Save logs to file.";
        input {
          leaf log-type {
            type ncs_rpc_notif_save-log-type;
            mandatory true;
            description
              "Log type.";
          }
        }
      }
    }
  }
  augment "/ncs:devices/ncs:device-group/ncs:ned-id/ncs:rpc" {
    container rpc-save-logfile {
      tailf:ncs-device-type "netconf";
      tailf:display-when "/ncs:devices/ncs:device[ncs:name=current()/../../../ncs:member]/ncs:module[ncs:name='huawei-syslog']";
      tailf:action save-logfile {
        tailf:actionpoint ncsproxy {
          tailf:internal;
        }
        description
          "Save logs to file.";
        input {
          leaf log-type {
            type ncs_rpc_notif_save-log-type;
            mandatory true;
            description
              "Log type.";
          }
        }
      }
    }
  }
  augment "/ncs:devices/ncs:device/ncs:config" {
    container syslog {
      tailf:ncs-device-type "netconf";
      tailf:display-when "not(../../ncs:module) or ../../ncs:module[ncs:name='huawei-syslog']";
      description
        "System log.";
      container servers {
        description
          "List of syslog servers.";
        list server {
          key "ip-type ipaddress is-default-vpn vrf-name";
          max-elements 8;
          description
            "Configure attributes of log server.";
          leaf ip-type {
            type address-family-type;
            description
              "Log server address type, IPv4 or IPv6.";
          }
          leaf ipaddress {
            type inet:ip-address-no-zone;
            description
              "Log server address, IPv4 or IPv6 type.";
          }
          leaf is-default-vpn {
            type boolean;
            description
              "Enable/disable the default VPN.";
          }
          leaf vrf-name {
            type leafref {
              path "/ncs:devices/ncs:device/ncs:config/ni:network-instance/ni:instances/ni:instance/ni:name" {
                tailf:xpath-root 3;
              }
            }
            must "not(../is-default-vpn='true') or (../is-default-vpn='true' and ../vrf-name='_public_')" {
              tailf:xpath-root 3;
            }
            description
              "VPN name on a log server.";
          }
          leaf host-name {
            type string {
              length "1..31";
            }
            mandatory true;
            description
              "Configure host name of log server.";
          }
          leaf is-activated {
            type boolean;
            default "false";
            description
              "Enable/disable the log host.";
          }
          leaf level {
            type log-level;
            default "debugging";
            description
              "Level of logs saved on a log server.";
            ext:support-filter "true";
          }
          leaf port {
            type uint32 {
              range "1..65535";
            }
            default "514";
            description
              "Number of a port recving logs.";
            ext:support-filter "true";
          }
          leaf facility {
            type loghost-facility;
            default "local7";
            description
              "Log record tool.";
            ext:support-filter "true";
          }
          leaf channel-id {
            type leafref {
              path "/ncs:devices/ncs:device/ncs:config/syslog:syslog/syslog:info-center-channels/syslog:info-center-channel/syslog:channel-id" {
                tailf:xpath-root 3;
              }
            }
            default "2";
            description
              "Channel number.";
            ext:support-filter "true";
          }
          // NCS drop config false leaf 'channel-name'
          leaf timestamp {
            type timestamp-format;
            default "UTC";
            description
              "Log server timestamp.";
            ext:support-filter "true";
          }
          leaf transport-mode {
            type transport-mode-type;
            default "udp";
            description
              "Transport mode.";
            ext:support-filter "true";
          }
          leaf ssl-policy-name {
            type leafref {
              path "/ncs:devices/ncs:device/ncs:config/ssl:ssl/ssl:ssl-policys/ssl:ssl-policy/ssl:policy-name" {
                tailf:xpath-root 3;
              }
            }
            must "../transport-mode='tcp'" {
              tailf:xpath-root 3;
            }
            description
              "SSL policy name.";
          }
          leaf source-ip {
            ext:support-filter "true";
            type inet:ip-address-no-zone;
            description
              "Syslog source IP address.";
          }
          leaf dns-identifier-name {
            type string {
              length "1..255";
            }
            must "../transport-mode='tcp' and ../ssl-policy-name" {
              tailf:xpath-root 3;
            }
            description
              "DNS Identifier Name.";
          }
          leaf is-brief-format {
            type boolean;
            default "false";
            description
              "Enable/disable syslog Brief Format.";
          }
          leaf is-security-only {
            type boolean;
            must "../is-security-only='false' or (../is-security-only='true' and ../ssl-policy-name)" {
              tailf:xpath-root 3;
            }
            default "false";
            description
              "Enable/disable security log server.";
          }
          leaf facility-mask {
            type bits {
              bit local0 {
                description
                  "The bit can be used to configure local0 facility.";
              }
              bit local1 {
                description
                  "The bit can be used to configure local1 facility.";
              }
              bit local2 {
                description
                  "The bit can be used to configure local2 facility.";
              }
              bit local3 {
                description
                  "The bit can be used to configure local3 facility.";
              }
              bit local4 {
                description
                  "The bit can be used to configure local4 facility.";
              }
              bit local5 {
                description
                  "The bit can be used to configure local5 facility.";
              }
              bit local6 {
                description
                  "The bit can be used to configure local6 facility.";
              }
              bit local7 {
                description
                  "The bit can be used to configure local7 facility.";
              }
            }
            default "local0 local1 local2 local3 local4 local5 local6 local7";
            description
              "Configure facility of the syslog host.";
          }
          leaf severity-mask {
            type bits {
              bit emergency {
                description
                  "The bit can be used to configure emergency severity.";
              }
              bit alert {
                description
                  "The bit can be used to configure alert severity.";
              }
              bit critical {
                description
                  "The bit can be used to configure critical severity.";
              }
              bit error {
                description
                  "The bit can be used to configure error severity.";
              }
              bit warning {
                description
                  "The bit can be used to configure warning severity.";
              }
              bit notice {
                description
                  "The bit can be used to configure notice severity.";
              }
              bit informational {
                description
                  "The bit can be used to configure informational severity.";
              }
              bit debug {
                description
                  "The bit can be used to configure debug severity.";
              }
            }
            default "emergency alert critical error warning notice informational debug";
            description
              "Configure severity of logs received by the syslog host.";
          }
        }
      }
      container global-parameter {
        description
          "Configure global parameter.";
        leaf info-center-enable {
          type boolean;
          default "true";
          description
            "Enable/disable the info-center function.";
        }
        leaf buffer-size {
          type int32 {
            range "0..102400";
          }
          default "512";
          description
            "Size of a log buffer, the maximum value is configured by the PAF.";
        }
        leaf suppress-enable {
          type boolean;
          default "true";
          description
            "Enable/disable suppression function of duplicate logs.";
        }
        leaf log-timestamp {
          type timestamp;
          default "date-second";
          description
            "Timestamp format of log information.";
        }
        leaf trap-timestamp {
          type timestamp;
          default "date-second";
          description
            "Timestamp format of alarm information.";
        }
        leaf debug-timestamp {
          type timestamp;
          default "date-millisecond";
          description
            "Timestamp type of debugging information.";
        }
        leaf interface-name {
          type leafref {
            path "/ncs:devices/ncs:device/ncs:config/ifm:ifm/ifm:interfaces/ifm:interface/ifm:name" {
              tailf:xpath-root 3;
            }
          }
          description
            "Name of a log host interface sending logs.";
        }
        leaf logbuffer-enable {
          type boolean;
          default "true";
          description
            "Enable/disable log buffer to output information.";
        }
        leaf trapbuffer-enable {
          type boolean;
          default "true";
          description
            "Enable/disable trap buffer to output information.";
        }
        leaf trapbuffer-size {
          type int32 {
            range "0..1024";
          }
          default "256";
          description
            "Size of a trap buffer.";
        }
        leaf packet-priority {
          type int32 {
            range "0..7";
          }
          default "0";
          description
            "Set the priority of the syslog packet.";
        }
        leaf source-port {
          type uint32 {
            range "1025..65535";
          }
          default "38514";
          description
            "Port of the loghost.";
        }
        leaf log-none-timezone {
          type boolean;
          default "false";
          description
            "Enable/disable log Timestamp Without Timezone.";
        }
        leaf trap-none-timezone {
          type boolean;
          default "false";
          description
            "Enable/disable trap Timestamp Without Timezone.";
        }
        leaf debug-none-timezone {
          type boolean;
          default "false";
          description
            "Enable/disable debug Timestamp Without Timezone.";
        }
        leaf delay-suppress-enable {
          type boolean;
          default "true";
          description
            "Enable/disable event delay suppress is enabled.";
        }
        leaf event-logging-all {
          type boolean;
          default "false";
          description
            "Enable/disable logging flag of global event.";
        }
        leaf character-set {
          type character-set;
          default "UTF-8";
          description
            "This leaf means the character set when sending log to syslog host.";
        }
      }
      container info-center-channels {
        description
          "List of Channel.";
        list info-center-channel {
          key "channel-id";
          max-elements 10;
          description
            "Configure info center channel.";
          ext:generated-by "system";
          ext:operation-exclude "create";
          leaf channel-id {
            type uint32 {
              range "0..9";
            }
            description
              "Number for channel.";
          }
          // NCS drop config false leaf 'channel-default-name'
          leaf channel-name {
            type string {
              length "1..30";
              pattern '[a-zA-Z][a-zA-Z0-9]*';
            }
            ext:dynamic-default;
            description
              "Channel name.";
          }
        }
      }
      container info-center-sources {
        description
          "List of rules in channel for outputting information.";
        list info-center-source {
          key "module-name channel-id";
          description
            "Configure rule in channel for outputting information.";
          ext:generated-by "system" {
            ext:can-be-deleted;
          }
          leaf module-name {
            type string {
              length "1..31";
              pattern '[^A-Z]*';
            }
            ext:case-sensitivity "lower-only";
            description
              "Module name of the rule.";
          }
          leaf channel-id {
            type leafref {
              path "/ncs:devices/ncs:device/ncs:config/syslog:syslog/syslog:info-center-channels/syslog:info-center-channel/syslog:channel-id" {
                tailf:xpath-root 3;
              }
            }
            description
              "Number of a channel.";
          }
          // NCS drop config false leaf 'channel-name'
          leaf enable-log {
            type boolean;
            ext:dynamic-default;
            description
              "Enable/disable the log output function.";
          }
          leaf enable-log-level {
            type log-level;
            ext:dynamic-default;
            description
              "Log level permitted to output.";
          }
          leaf enable-trap {
            type boolean;
            ext:dynamic-default;
            description
              "Enable/disable the alarm output function.";
          }
          leaf enable-trap-level {
            type log-level;
            default "debugging";
            description
              "Trap level permitted to output.";
          }
          leaf enable-debug {
            type boolean;
            ext:dynamic-default;
            description
              "Enable/disable the debug output function.";
          }
          leaf enable-debug-level {
            type log-level;
            default "debugging";
            description
              "Debug level permitted to output.";
          }
        }
      }
      container log-switch-list {
        description
          "Configure the log switch.";
        list log-switch {
          key "feature-name log-name";
          max-elements 65535;
          description
            "Configure log switch.";
          ext:generated-by "system";
          ext:operation-exclude "create";
          leaf feature-name {
            type string {
              length "1..31";
            }
            description
              "Feature name of a log.";
          }
          leaf log-name {
            type string {
              length "1..63";
            }
            description
              "Log name.";
          }
          leaf log-level {
            type log-level;
            ext:dynamic-default;
            description
              "Log level.";
          }
          // NCS drop config false leaf 'security-log-flag'
          // NCS drop config false leaf 'log-type'
        }
      }
      container info-center-filters {
        description
          "List of info-center filter.";
        list info-center-filter {
          key "feature-name filter-log-name";
          max-elements 65535;
          description
            "Configure filter item.";
          leaf feature-name {
            type leafref {
              path "/ncs:devices/ncs:device/ncs:config/syslog:syslog/syslog:log-switch-list/syslog:log-switch/syslog:feature-name" {
                tailf:xpath-root 3;
              }
            }
            description
              "Feature name of the filtered log.";
          }
          leaf filter-log-name {
            type leafref {
              path "/ncs:devices/ncs:device/ncs:config/syslog:syslog/syslog:log-switch-list/syslog:log-switch/syslog:log-name" {
                tailf:xpath-root 3;
              }
            }
            description
              "Name of the filtered log.";
          }
        }
      }
      container domain-servers {
        description
          "List of domain syslog servers.";
        list domain-server {
          key "server-domain is-default-vpn vrf-name";
          max-elements 8;
          description
            "Configure the domain log sever that receives logs.";
          leaf server-domain {
            type string {
              length "1..255";
            }
            description
              "Log server domian address.";
          }
          leaf is-default-vpn {
            type boolean;
            description
              "Enable/disable the default VPN.";
          }
          leaf vrf-name {
            type leafref {
              path "/ncs:devices/ncs:device/ncs:config/ni:network-instance/ni:instances/ni:instance/ni:name" {
                tailf:xpath-root 3;
              }
            }
            must "not(../is-default-vpn='true') or (../is-default-vpn='true' and ../vrf-name='_public_')" {
              tailf:xpath-root 3;
            }
            description
              "VPN name on a log server.";
          }
          leaf level {
            type log-level;
            default "debugging";
            description
              "Level of logs saved on a log server.";
          }
          leaf server-port {
            type uint32 {
              range "1..65535";
            }
            default "514";
            description
              "Number of a port recving logs.";
          }
          leaf facility {
            type loghost-facility;
            default "local7";
            description
              "Log record tool.";
          }
          leaf channel-id {
            type leafref {
              path "/ncs:devices/ncs:device/ncs:config/syslog:syslog/syslog:info-center-channels/syslog:info-center-channel/syslog:channel-id" {
                tailf:xpath-root 3;
              }
            }
            default "2";
            description
              "Channel number.";
          }
          // NCS drop config false leaf 'channel-name'
          leaf timestamp {
            type timestamp-format;
            default "UTC";
            description
              "Log server timestamp.";
          }
          leaf transport-mode {
            type transport-mode-type;
            default "udp";
            description
              "Transport mode.";
          }
          leaf ssl-policy-name {
            type leafref {
              path "/ncs:devices/ncs:device/ncs:config/ssl:ssl/ssl:ssl-policys/ssl:ssl-policy/ssl:policy-name" {
                tailf:xpath-root 3;
              }
            }
            must "../transport-mode='tcp'" {
              tailf:xpath-root 3;
            }
            description
              "SSL policy name.";
          }
          leaf source-ip {
            ext:support-filter "true";
            type inet:ipv4-address-no-zone;
            description
              "Syslog source IP address.";
          }
          leaf is-brief-format {
            type boolean;
            default "false";
            description
              "Enable/disable Syslog Brief Format.";
          }
          leaf is-security-only {
            type boolean;
            must "../is-security-only='false' or (../is-security-only='true' and ../ssl-policy-name)" {
              tailf:xpath-root 3;
            }
            default "false";
            description
              "Enable/disable Syslog support security log.";
          }
        }
      }
      container logfiles {
        description
          "List of log file info.";
        list logfile {
          key "logfile-type";
          max-elements 4;
          description
            "Specify Log file info.";
          ext:generated-by "system";
          ext:operation-exclude "create|delete";
          leaf logfile-type {
            type logfile-type;
            description
              "Log file type.";
          }
          leaf max-file-num {
            type uint32 {
              range "1..500";
            }
            ext:dynamic-default;
            must "(../logfile-type='debug' and (../max-file-num>=1 and ../max-file-num<=50)) or (../logfile-type!='debug' and (../max-file-num>=3 and ../max-file-num<=500))" {
              tailf:xpath-root 3;
            }
            description
              "Maximum number of log files of the same type.";
          }
          leaf max-file-size {
            type uint32 {
              range "1..32";
            }
            units "MB";
            ext:dynamic-default;
            must "(../logfile-type='debug' and ../max-file-size='8') or ((../logfile-type='security' or ../logfile-type='operation') and (../max-file-size>=1 and ../max-file-size<=4))or (../logfile-type='log' and (../max-file-size='4' or ../max-file-size='8' or ../max-file-size='16' or ../max-file-size='32'))" {
              tailf:xpath-root 3;
            }
            description
              "Maximum size (in MB) of a log file. The value range for log files is [4, 8, 16, 32], for security files is [1~4], and for operation files is [1~4].";
          }
        }
      }
      container direction-channels {
        description
          "List of mappings of output directions and channels of the information center.";
        list direction-channel {
          key "output-direction";
          max-elements 7;
          description
            "Specify the relation of direction and channel.";
          ext:generated-by "system";
          ext:operation-exclude "create";
          leaf output-direction {
            type string {
              length "1..30";
            }
            description
              "Direction of information output.";
          }
          // NCS drop config false leaf 'default-channel-id'
          leaf channel-id {
            type leafref {
              path "/ncs:devices/ncs:device/ncs:config/syslog:syslog/syslog:info-center-channels/syslog:info-center-channel/syslog:channel-id" {
                tailf:xpath-root 3;
              }
            }
            ext:dynamic-default;
            description
              "Number of a configured channel.";
          }
          // NCS drop config false leaf 'channel-name'
        }
      }
      // NCS drop config false container 'info-center-statistics'
      // NCS drop config false container 'info-center-buffers'
      // NCS drop config false container modules
      // NCS drop config false container logbuffers
      // NCS drop config false container trapbuffers
      // NCS drop config false container securitybuffers
      container logfile-prefixs {
        description
          "List of log file prefix.";
        list logfile-prefix {
          key "type name";
          max-elements 1;
          description
            "Specify Log file prefixs.";
          leaf type {
            type prefix-file-type;
            description
              "Log file type.";
          }
          leaf name {
            type string {
              length "1..16";
              pattern '[a-zA-Z0-9]*';
            }
            description
              "File name.";
          }
        }
      }
    }
  }
  augment "/ncs:devices/ncs:device/ncs:live-status" {
    container syslog {
      tailf:ncs-device-type "netconf";
      tailf:display-when "not(../../ncs:module) or ../../ncs:module[ncs:name='huawei-syslog'] or (../../ncs:live-status-protocol[not(ncs:capability)]) or (../../ncs:live-status-protocol/ncs:capability/ncs:module[.='huawei-syslog'])";
      description
        "System log.";
      container servers {
        description
          "List of syslog servers.";
        list server {
          key "ip-type ipaddress is-default-vpn vrf-name";
          // NCS drop max-elements statement
          description
            "Configure attributes of log server.";
          leaf ip-type {
            type live_ncs_address-family-type;
            description
              "Log server address type, IPv4 or IPv6.";
          }
          leaf ipaddress {
            type inet:ip-address-no-zone;
            description
              "Log server address, IPv4 or IPv6 type.";
          }
          leaf is-default-vpn {
            type boolean;
            description
              "Enable/disable the default VPN.";
          }
          leaf vrf-name {
            type leafref {
              path "/ncs:devices/ncs:device/ncs:live-status/ni:network-instance/ni:instances/ni:instance/ni:name" {
                tailf:xpath-root 3;
              }
            }
            // NCS drop must statement
            description
              "VPN name on a log server.";
          }
          leaf host-name {
            type string {
              length "1..31";
            }
            // NCS drop mandatory statement
            description
              "Configure host name of log server.";
          }
          leaf is-activated {
            type boolean;
            // NCS drop default statement
            description
              "Enable/disable the log host.";
          }
          leaf level {
            type live_ncs_log-level;
            // NCS drop default statement
            description
              "Level of logs saved on a log server.";
            ext:support-filter "true";
          }
          leaf port {
            type uint32 {
              range "1..65535";
            }
            // NCS drop default statement
            description
              "Number of a port recving logs.";
            ext:support-filter "true";
          }
          leaf facility {
            type live_ncs_loghost-facility;
            // NCS drop default statement
            description
              "Log record tool.";
            ext:support-filter "true";
          }
          leaf channel-id {
            type leafref {
              path "/ncs:devices/ncs:device/ncs:live-status/syslog:syslog/syslog:info-center-channels/syslog:info-center-channel/syslog:channel-id" {
                tailf:xpath-root 3;
              }
            }
            // NCS drop default statement
            description
              "Channel number.";
            ext:support-filter "true";
          }
          leaf channel-name {
            type string {
              length "1..30";
            }
            // NCS drop default statement
            description
              "Channel name.";
          }
          leaf timestamp {
            type live_ncs_timestamp-format;
            // NCS drop default statement
            description
              "Log server timestamp.";
            ext:support-filter "true";
          }
          leaf transport-mode {
            type live_ncs_transport-mode-type;
            // NCS drop default statement
            description
              "Transport mode.";
            ext:support-filter "true";
          }
          leaf ssl-policy-name {
            type leafref {
              path "/ncs:devices/ncs:device/ncs:live-status/ssl:ssl/ssl:ssl-policys/ssl:ssl-policy/ssl:policy-name" {
                tailf:xpath-root 3;
              }
            }
            // NCS drop must statement
            description
              "SSL policy name.";
          }
          leaf source-ip {
            ext:support-filter "true";
            type inet:ip-address-no-zone;
            description
              "Syslog source IP address.";
          }
          leaf dns-identifier-name {
            type string {
              length "1..255";
            }
            // NCS drop must statement
            description
              "DNS Identifier Name.";
          }
          leaf is-brief-format {
            type boolean;
            // NCS drop default statement
            description
              "Enable/disable syslog Brief Format.";
          }
          leaf is-security-only {
            type boolean;
            // NCS drop must statement
            // NCS drop default statement
            description
              "Enable/disable security log server.";
          }
          leaf facility-mask {
            type bits {
              bit local0 {
                description
                  "The bit can be used to configure local0 facility.";
              }
              bit local1 {
                description
                  "The bit can be used to configure local1 facility.";
              }
              bit local2 {
                description
                  "The bit can be used to configure local2 facility.";
              }
              bit local3 {
                description
                  "The bit can be used to configure local3 facility.";
              }
              bit local4 {
                description
                  "The bit can be used to configure local4 facility.";
              }
              bit local5 {
                description
                  "The bit can be used to configure local5 facility.";
              }
              bit local6 {
                description
                  "The bit can be used to configure local6 facility.";
              }
              bit local7 {
                description
                  "The bit can be used to configure local7 facility.";
              }
            }
            // NCS drop default statement
            description
              "Configure facility of the syslog host.";
          }
          leaf severity-mask {
            type bits {
              bit emergency {
                description
                  "The bit can be used to configure emergency severity.";
              }
              bit alert {
                description
                  "The bit can be used to configure alert severity.";
              }
              bit critical {
                description
                  "The bit can be used to configure critical severity.";
              }
              bit error {
                description
                  "The bit can be used to configure error severity.";
              }
              bit warning {
                description
                  "The bit can be used to configure warning severity.";
              }
              bit notice {
                description
                  "The bit can be used to configure notice severity.";
              }
              bit informational {
                description
                  "The bit can be used to configure informational severity.";
              }
              bit debug {
                description
                  "The bit can be used to configure debug severity.";
              }
            }
            // NCS drop default statement
            description
              "Configure severity of logs received by the syslog host.";
          }
        }
      }
      container global-parameter {
        description
          "Configure global parameter.";
        leaf info-center-enable {
          type boolean;
          // NCS drop default statement
          description
            "Enable/disable the info-center function.";
        }
        leaf buffer-size {
          type int32 {
            range "0..102400";
          }
          // NCS drop default statement
          description
            "Size of a log buffer, the maximum value is configured by the PAF.";
        }
        leaf suppress-enable {
          type boolean;
          // NCS drop default statement
          description
            "Enable/disable suppression function of duplicate logs.";
        }
        leaf log-timestamp {
          type live_ncs_timestamp;
          // NCS drop default statement
          description
            "Timestamp format of log information.";
        }
        leaf trap-timestamp {
          type live_ncs_timestamp;
          // NCS drop default statement
          description
            "Timestamp format of alarm information.";
        }
        leaf debug-timestamp {
          type live_ncs_timestamp;
          // NCS drop default statement
          description
            "Timestamp type of debugging information.";
        }
        leaf interface-name {
          type leafref {
            path "/ncs:devices/ncs:device/ncs:live-status/ifm:ifm/ifm:interfaces/ifm:interface/ifm:name" {
              tailf:xpath-root 3;
            }
          }
          description
            "Name of a log host interface sending logs.";
        }
        leaf logbuffer-enable {
          type boolean;
          // NCS drop default statement
          description
            "Enable/disable log buffer to output information.";
        }
        leaf trapbuffer-enable {
          type boolean;
          // NCS drop default statement
          description
            "Enable/disable trap buffer to output information.";
        }
        leaf trapbuffer-size {
          type int32 {
            range "0..1024";
          }
          // NCS drop default statement
          description
            "Size of a trap buffer.";
        }
        leaf packet-priority {
          type int32 {
            range "0..7";
          }
          // NCS drop default statement
          description
            "Set the priority of the syslog packet.";
        }
        leaf source-port {
          type uint32 {
            range "1025..65535";
          }
          // NCS drop default statement
          description
            "Port of the loghost.";
        }
        leaf log-none-timezone {
          type boolean;
          // NCS drop default statement
          description
            "Enable/disable log Timestamp Without Timezone.";
        }
        leaf trap-none-timezone {
          type boolean;
          // NCS drop default statement
          description
            "Enable/disable trap Timestamp Without Timezone.";
        }
        leaf debug-none-timezone {
          type boolean;
          // NCS drop default statement
          description
            "Enable/disable debug Timestamp Without Timezone.";
        }
        leaf delay-suppress-enable {
          type boolean;
          // NCS drop default statement
          description
            "Enable/disable event delay suppress is enabled.";
        }
        leaf event-logging-all {
          type boolean;
          // NCS drop default statement
          description
            "Enable/disable logging flag of global event.";
        }
        leaf character-set {
          type live_ncs_character-set;
          // NCS drop default statement
          description
            "This leaf means the character set when sending log to syslog host.";
        }
      }
      container info-center-channels {
        description
          "List of Channel.";
        list info-center-channel {
          key "channel-id";
          // NCS drop max-elements statement
          description
            "Configure info center channel.";
          ext:generated-by "system";
          ext:operation-exclude "create";
          leaf channel-id {
            type uint32 {
              range "0..9";
            }
            description
              "Number for channel.";
          }
          leaf channel-default-name {
            type string {
              length "1..30";
            }
            description
              "Info-center channel default name.";
          }
          leaf channel-name {
            type string {
              length "1..30";
              pattern '[a-zA-Z][a-zA-Z0-9]*';
            }
            ext:dynamic-default;
            description
              "Channel name.";
          }
        }
      }
      container info-center-sources {
        description
          "List of rules in channel for outputting information.";
        list info-center-source {
          key "module-name channel-id";
          description
            "Configure rule in channel for outputting information.";
          ext:generated-by "system" {
            ext:can-be-deleted;
          }
          leaf module-name {
            type string {
              length "1..31";
              pattern '[^A-Z]*';
            }
            ext:case-sensitivity "lower-only";
            description
              "Module name of the rule.";
          }
          leaf channel-id {
            type leafref {
              path "/ncs:devices/ncs:device/ncs:live-status/syslog:syslog/syslog:info-center-channels/syslog:info-center-channel/syslog:channel-id" {
                tailf:xpath-root 3;
              }
            }
            description
              "Number of a channel.";
          }
          leaf channel-name {
            type string {
              length "1..30";
            }
            description
              "Name of a channel.";
          }
          leaf enable-log {
            type boolean;
            ext:dynamic-default;
            description
              "Enable/disable the log output function.";
          }
          leaf enable-log-level {
            type live_ncs_log-level;
            ext:dynamic-default;
            description
              "Log level permitted to output.";
          }
          leaf enable-trap {
            type boolean;
            ext:dynamic-default;
            description
              "Enable/disable the alarm output function.";
          }
          leaf enable-trap-level {
            type live_ncs_log-level;
            // NCS drop default statement
            description
              "Trap level permitted to output.";
          }
          leaf enable-debug {
            type boolean;
            ext:dynamic-default;
            description
              "Enable/disable the debug output function.";
          }
          leaf enable-debug-level {
            type live_ncs_log-level;
            // NCS drop default statement
            description
              "Debug level permitted to output.";
          }
        }
      }
      container log-switch-list {
        description
          "Configure the log switch.";
        list log-switch {
          key "feature-name log-name";
          // NCS drop max-elements statement
          description
            "Configure log switch.";
          ext:generated-by "system";
          ext:operation-exclude "create";
          leaf feature-name {
            type string {
              length "1..31";
            }
            description
              "Feature name of a log.";
          }
          leaf log-name {
            type string {
              length "1..63";
            }
            description
              "Log name.";
          }
          leaf log-level {
            type live_ncs_log-level;
            ext:dynamic-default;
            description
              "Log level.";
          }
          leaf security-log-flag {
            type boolean;
            description
              "Enable/disable flag of security log.";
          }
          leaf log-type {
            type live_ncs_log-type;
            description
              "Log Type.";
          }
        }
      }
      container info-center-filters {
        description
          "List of info-center filter.";
        list info-center-filter {
          key "feature-name filter-log-name";
          // NCS drop max-elements statement
          description
            "Configure filter item.";
          leaf feature-name {
            type leafref {
              path "/ncs:devices/ncs:device/ncs:live-status/syslog:syslog/syslog:log-switch-list/syslog:log-switch/syslog:feature-name" {
                tailf:xpath-root 3;
              }
            }
            description
              "Feature name of the filtered log.";
          }
          leaf filter-log-name {
            type leafref {
              path "/ncs:devices/ncs:device/ncs:live-status/syslog:syslog/syslog:log-switch-list/syslog:log-switch/syslog:log-name" {
                tailf:xpath-root 3;
              }
            }
            description
              "Name of the filtered log.";
          }
        }
      }
      container domain-servers {
        description
          "List of domain syslog servers.";
        list domain-server {
          key "server-domain is-default-vpn vrf-name";
          // NCS drop max-elements statement
          description
            "Configure the domain log sever that receives logs.";
          leaf server-domain {
            type string {
              length "1..255";
            }
            description
              "Log server domian address.";
          }
          leaf is-default-vpn {
            type boolean;
            description
              "Enable/disable the default VPN.";
          }
          leaf vrf-name {
            type leafref {
              path "/ncs:devices/ncs:device/ncs:live-status/ni:network-instance/ni:instances/ni:instance/ni:name" {
                tailf:xpath-root 3;
              }
            }
            // NCS drop must statement
            description
              "VPN name on a log server.";
          }
          leaf level {
            type live_ncs_log-level;
            // NCS drop default statement
            description
              "Level of logs saved on a log server.";
          }
          leaf server-port {
            type uint32 {
              range "1..65535";
            }
            // NCS drop default statement
            description
              "Number of a port recving logs.";
          }
          leaf facility {
            type live_ncs_loghost-facility;
            // NCS drop default statement
            description
              "Log record tool.";
          }
          leaf channel-id {
            type leafref {
              path "/ncs:devices/ncs:device/ncs:live-status/syslog:syslog/syslog:info-center-channels/syslog:info-center-channel/syslog:channel-id" {
                tailf:xpath-root 3;
              }
            }
            // NCS drop default statement
            description
              "Channel number.";
          }
          leaf channel-name {
            type string {
              length "1..30";
            }
            // NCS drop default statement
            description
              "Channel name.";
          }
          leaf timestamp {
            type live_ncs_timestamp-format;
            // NCS drop default statement
            description
              "Log server timestamp.";
          }
          leaf transport-mode {
            type live_ncs_transport-mode-type;
            // NCS drop default statement
            description
              "Transport mode.";
          }
          leaf ssl-policy-name {
            type leafref {
              path "/ncs:devices/ncs:device/ncs:live-status/ssl:ssl/ssl:ssl-policys/ssl:ssl-policy/ssl:policy-name" {
                tailf:xpath-root 3;
              }
            }
            // NCS drop must statement
            description
              "SSL policy name.";
          }
          leaf source-ip {
            ext:support-filter "true";
            type inet:ipv4-address-no-zone;
            description
              "Syslog source IP address.";
          }
          leaf is-brief-format {
            type boolean;
            // NCS drop default statement
            description
              "Enable/disable Syslog Brief Format.";
          }
          leaf is-security-only {
            type boolean;
            // NCS drop must statement
            // NCS drop default statement
            description
              "Enable/disable Syslog support security log.";
          }
        }
      }
      container logfiles {
        description
          "List of log file info.";
        list logfile {
          key "logfile-type";
          // NCS drop max-elements statement
          description
            "Specify Log file info.";
          ext:generated-by "system";
          ext:operation-exclude "create|delete";
          leaf logfile-type {
            type live_ncs_logfile-type;
            description
              "Log file type.";
          }
          leaf max-file-num {
            type uint32 {
              range "1..500";
            }
            ext:dynamic-default;
            // NCS drop must statement
            description
              "Maximum number of log files of the same type.";
          }
          leaf max-file-size {
            type uint32 {
              range "1..32";
            }
            units "MB";
            ext:dynamic-default;
            // NCS drop must statement
            description
              "Maximum size (in MB) of a log file. The value range for log files is [4, 8, 16, 32], for security files is [1~4], and for operation files is [1~4].";
          }
        }
      }
      container direction-channels {
        description
          "List of mappings of output directions and channels of the information center.";
        list direction-channel {
          key "output-direction";
          // NCS drop max-elements statement
          description
            "Specify the relation of direction and channel.";
          ext:generated-by "system";
          ext:operation-exclude "create";
          leaf output-direction {
            type string {
              length "1..30";
            }
            description
              "Direction of information output.";
          }
          leaf default-channel-id {
            type uint32 {
              range "0..9";
            }
            description
              "Number of the default channel.";
          }
          leaf channel-id {
            type leafref {
              path "/ncs:devices/ncs:device/ncs:live-status/syslog:syslog/syslog:info-center-channels/syslog:info-center-channel/syslog:channel-id" {
                tailf:xpath-root 3;
              }
            }
            ext:dynamic-default;
            description
              "Number of a configured channel.";
          }
          leaf channel-name {
            type string {
              length "1..30";
            }
            description
              "Name of a configured channel.";
          }
        }
      }
      container info-center-statistics {
        description
          "List of info-center statistics.";
        list info-center-statistic {
          key "module-name";
          description
            "Statistics of info-center item.";
          leaf module-name {
            type string {
              length "1..31";
            }
            description
              "Module name of the log.";
          }
          leaf receive-log {
            type uint32;
            description
              "Number of received logs.";
          }
          leaf drop-log {
            type uint32;
            description
              "Number of dropped logs.";
          }
          leaf receive-diaglog {
            type uint32;
            description
              "Number of received diagnostic logs.";
          }
          leaf drop-diaglog {
            type uint32;
            description
              "Number of dropped diagnostic logs.";
          }
          leaf receive-eventtrap {
            type uint32;
            description
              "Number of received event traps.";
          }
          leaf drop-eventtrap {
            type uint32;
            description
              "Number of dropped event traps.";
          }
          leaf receive-debug {
            type uint32;
            description
              "Number of received debugging logs.";
          }
          leaf drop-debug {
            type uint32;
            description
              "Number of dropped debugging logs.";
          }
        }
      }
      container info-center-buffers {
        description
          "List of the buffer statistics.";
        list info-center-buffer {
          key "buffer-name";
          // NCS drop max-elements statement
          description
            "Display buffer statistics.";
          leaf buffer-name {
            type string {
              length "1..31";
            }
            description
              "Buffer name.";
          }
          leaf enable-flag {
            type boolean;
            // NCS drop default statement
            description
              "Enable/disable Buffer enable state.";
          }
          leaf max-buffer-size {
            type uint32 {
              range "1..10240";
            }
            units "Byte";
            description
              "Maximum buffer size.";
          }
          leaf cur-buffer-size {
            type uint32 {
              range "1..10240";
            }
            units "Byte";
            description
              "Configured buffer size.";
          }
          leaf current-message {
            type uint32;
            description
              "Number of existing messages in the buffer.";
          }
          leaf dropped-message {
            type uint32;
            description
              "Number of dropped messages in the buffer.";
          }
          leaf overwrite-message {
            type uint32;
            description
              "Number of overwritten messages in the buffer.";
          }
          leaf channel-id {
            type uint32 {
              range "0..9";
            }
            // NCS drop default statement
            description
              "ID of channel bind to the buffer.";
          }
          leaf channel-name {
            type string {
              length "1..30";
            }
            description
              "Name of channel bind to the buffer.";
          }
        }
      }
      container modules {
        description
          "List of module name information.";
        list module {
          key "module-name";
          description
            "Operational data of module name information item.";
          leaf module-name {
            type string {
              length "1..31";
            }
            description
              "Module name.";
          }
        }
      }
      container logbuffers {
        description
          "List of of log buffer.";
        list logbuffer {
          key "sequence";
          description
            "Statistics of log buffer item.";
          leaf sequence {
            type int32 {
              range "1..102400";
            }
            description
              "Sequence number of a queried log.";
          }
          leaf starttime {
            type yang:date-and-time;
            description
              "Query start time. The valid value range is after 1970-01-01.";
            ext:support-filter "true";
          }
          leaf endtime {
            type yang:date-and-time;
            description
              "Query end time. The valid value range is after 1970-01-01.";
            ext:support-filter "true";
          }
          leaf level {
            type live_ncs_log-level;
            description
              "Level of queried logs.";
            ext:support-filter "true";
          }
          leaf log-content {
            type string {
              length "0..1200";
            }
            description
              "Content of queried logs.";
          }
        }
      }
      container trapbuffers {
        description
          "List of trap buffer table.";
        list trapbuffer {
          key "sequence";
          description
            "Statistics of trap buffer item.";
          leaf sequence {
            type int32 {
              range "1..1024";
            }
            description
              "Sequence number of a queried trap.";
          }
          leaf trap-content {
            type string {
              length "0..1200";
            }
            description
              "Content of query trap.";
          }
        }
      }
      container securitybuffers {
        description
          "List of security of a log buffer.";
        list securitybuffer {
          key "sequence";
          description
            "Operational data of the security of a log buffer item.";
          leaf sequence {
            type int32 {
              range "1..102400";
            }
            description
              "Sequence number of a queried log.";
          }
          leaf starttime {
            type yang:date-and-time;
            description
              "Query start time. The valid value range is after 1970-01-01.";
            ext:support-filter "true";
          }
          leaf endtime {
            type yang:date-and-time;
            description
              "Query end time. The valid value range is after 1970-01-01.";
            ext:support-filter "true";
          }
          leaf level {
            type live_ncs_log-level;
            description
              "Level of queried logs.";
            ext:support-filter "true";
          }
          leaf log-content {
            type string {
              length "0..1200";
            }
            description
              "Content of queried logs.";
          }
        }
      }
      container logfile-prefixs {
        description
          "List of log file prefix.";
        list logfile-prefix {
          key "type name";
          // NCS drop max-elements statement
          description
            "Specify Log file prefixs.";
          leaf type {
            type live_ncs_prefix-file-type;
            description
              "Log file type.";
          }
          leaf name {
            type string {
              length "1..16";
              pattern '[a-zA-Z0-9]*';
            }
            description
              "File name.";
          }
        }
      }
    }
  }
  augment "/ncs:devices/ncs:template/ncs:ned-id/ncs:config" {
    container syslog {
      description
        "System log.";
      container servers {
        description
          "List of syslog servers.";
        list server {
          // NCS patched for predictable order
          ordered-by user;
          key "ip-type ipaddress is-default-vpn vrf-name";
          // NCS drop max-elements statement
          description
            "Configure attributes of log server.";
          leaf ip-type {
            type ncs_template_address-family-type;
            description
              "Log server address type, IPv4 or IPv6.";
          }
          leaf ipaddress {
            type string;
            description
              "Log server address, IPv4 or IPv6 type.";
          }
          leaf is-default-vpn {
            type string;
            description
              "Enable/disable the default VPN.";
          }
          leaf vrf-name {
            type string;
            // NCS drop must statement
            description
              "VPN name on a log server.";
          }
          leaf host-name {
            type string;
            // NCS drop mandatory statement
            description
              "Configure host name of log server.";
          }
          leaf is-activated {
            type string;
            // NCS drop default statement
            description
              "Enable/disable the log host.";
          }
          leaf level {
            type ncs_template_log-level;
            // NCS drop default statement
            description
              "Level of logs saved on a log server.";
            ext:support-filter "true";
          }
          leaf port {
            type string;
            // NCS drop default statement
            description
              "Number of a port recving logs.";
            ext:support-filter "true";
          }
          leaf facility {
            type ncs_template_loghost-facility;
            // NCS drop default statement
            description
              "Log record tool.";
            ext:support-filter "true";
          }
          leaf channel-id {
            type string;
            // NCS drop default statement
            description
              "Channel number.";
            ext:support-filter "true";
          }
          // NCS drop config false leaf 'channel-name'
          leaf timestamp {
            type ncs_template_timestamp-format;
            // NCS drop default statement
            description
              "Log server timestamp.";
            ext:support-filter "true";
          }
          leaf transport-mode {
            type ncs_template_transport-mode-type;
            // NCS drop default statement
            description
              "Transport mode.";
            ext:support-filter "true";
          }
          leaf ssl-policy-name {
            type string;
            // NCS drop must statement
            description
              "SSL policy name.";
          }
          leaf source-ip {
            ext:support-filter "true";
            type string;
            description
              "Syslog source IP address.";
          }
          leaf dns-identifier-name {
            type string;
            // NCS drop must statement
            description
              "DNS Identifier Name.";
          }
          leaf is-brief-format {
            type string;
            // NCS drop default statement
            description
              "Enable/disable syslog Brief Format.";
          }
          leaf is-security-only {
            type string;
            // NCS drop must statement
            // NCS drop default statement
            description
              "Enable/disable security log server.";
          }
          leaf facility-mask {
            type string;
            // NCS drop default statement
            description
              "Configure facility of the syslog host.";
          }
          leaf severity-mask {
            type string;
            // NCS drop default statement
            description
              "Configure severity of logs received by the syslog host.";
          }
        }
      }
      container global-parameter {
        description
          "Configure global parameter.";
        leaf info-center-enable {
          type string;
          // NCS drop default statement
          description
            "Enable/disable the info-center function.";
        }
        leaf buffer-size {
          type string;
          // NCS drop default statement
          description
            "Size of a log buffer, the maximum value is configured by the PAF.";
        }
        leaf suppress-enable {
          type string;
          // NCS drop default statement
          description
            "Enable/disable suppression function of duplicate logs.";
        }
        leaf log-timestamp {
          type ncs_template_timestamp;
          // NCS drop default statement
          description
            "Timestamp format of log information.";
        }
        leaf trap-timestamp {
          type ncs_template_timestamp;
          // NCS drop default statement
          description
            "Timestamp format of alarm information.";
        }
        leaf debug-timestamp {
          type ncs_template_timestamp;
          // NCS drop default statement
          description
            "Timestamp type of debugging information.";
        }
        leaf interface-name {
          type string;
          description
            "Name of a log host interface sending logs.";
        }
        leaf logbuffer-enable {
          type string;
          // NCS drop default statement
          description
            "Enable/disable log buffer to output information.";
        }
        leaf trapbuffer-enable {
          type string;
          // NCS drop default statement
          description
            "Enable/disable trap buffer to output information.";
        }
        leaf trapbuffer-size {
          type string;
          // NCS drop default statement
          description
            "Size of a trap buffer.";
        }
        leaf packet-priority {
          type string;
          // NCS drop default statement
          description
            "Set the priority of the syslog packet.";
        }
        leaf source-port {
          type string;
          // NCS drop default statement
          description
            "Port of the loghost.";
        }
        leaf log-none-timezone {
          type string;
          // NCS drop default statement
          description
            "Enable/disable log Timestamp Without Timezone.";
        }
        leaf trap-none-timezone {
          type string;
          // NCS drop default statement
          description
            "Enable/disable trap Timestamp Without Timezone.";
        }
        leaf debug-none-timezone {
          type string;
          // NCS drop default statement
          description
            "Enable/disable debug Timestamp Without Timezone.";
        }
        leaf delay-suppress-enable {
          type string;
          // NCS drop default statement
          description
            "Enable/disable event delay suppress is enabled.";
        }
        leaf event-logging-all {
          type string;
          // NCS drop default statement
          description
            "Enable/disable logging flag of global event.";
        }
        leaf character-set {
          type ncs_template_character-set;
          // NCS drop default statement
          description
            "This leaf means the character set when sending log to syslog host.";
        }
      }
      container info-center-channels {
        description
          "List of Channel.";
        list info-center-channel {
          // NCS patched for predictable order
          ordered-by user;
          key "channel-id";
          // NCS drop max-elements statement
          description
            "Configure info center channel.";
          ext:generated-by "system";
          ext:operation-exclude "create";
          leaf channel-id {
            type string;
            description
              "Number for channel.";
          }
          // NCS drop config false leaf 'channel-default-name'
          leaf channel-name {
            type string;
            ext:dynamic-default;
            description
              "Channel name.";
          }
        }
      }
      container info-center-sources {
        description
          "List of rules in channel for outputting information.";
        list info-center-source {
          // NCS patched for predictable order
          ordered-by user;
          key "module-name channel-id";
          description
            "Configure rule in channel for outputting information.";
          ext:generated-by "system" {
            ext:can-be-deleted;
          }
          leaf module-name {
            type string;
            ext:case-sensitivity "lower-only";
            description
              "Module name of the rule.";
          }
          leaf channel-id {
            type string;
            description
              "Number of a channel.";
          }
          // NCS drop config false leaf 'channel-name'
          leaf enable-log {
            type string;
            ext:dynamic-default;
            description
              "Enable/disable the log output function.";
          }
          leaf enable-log-level {
            type ncs_template_log-level;
            ext:dynamic-default;
            description
              "Log level permitted to output.";
          }
          leaf enable-trap {
            type string;
            ext:dynamic-default;
            description
              "Enable/disable the alarm output function.";
          }
          leaf enable-trap-level {
            type ncs_template_log-level;
            // NCS drop default statement
            description
              "Trap level permitted to output.";
          }
          leaf enable-debug {
            type string;
            ext:dynamic-default;
            description
              "Enable/disable the debug output function.";
          }
          leaf enable-debug-level {
            type ncs_template_log-level;
            // NCS drop default statement
            description
              "Debug level permitted to output.";
          }
        }
      }
      container log-switch-list {
        description
          "Configure the log switch.";
        list log-switch {
          // NCS patched for predictable order
          ordered-by user;
          key "feature-name log-name";
          // NCS drop max-elements statement
          description
            "Configure log switch.";
          ext:generated-by "system";
          ext:operation-exclude "create";
          leaf feature-name {
            type string;
            description
              "Feature name of a log.";
          }
          leaf log-name {
            type string;
            description
              "Log name.";
          }
          leaf log-level {
            type ncs_template_log-level;
            ext:dynamic-default;
            description
              "Log level.";
          }
          // NCS drop config false leaf 'security-log-flag'
          // NCS drop config false leaf 'log-type'
        }
      }
      container info-center-filters {
        description
          "List of info-center filter.";
        list info-center-filter {
          // NCS patched for predictable order
          ordered-by user;
          key "feature-name filter-log-name";
          // NCS drop max-elements statement
          description
            "Configure filter item.";
          leaf feature-name {
            type string;
            description
              "Feature name of the filtered log.";
          }
          leaf filter-log-name {
            type string;
            description
              "Name of the filtered log.";
          }
        }
      }
      container domain-servers {
        description
          "List of domain syslog servers.";
        list domain-server {
          // NCS patched for predictable order
          ordered-by user;
          key "server-domain is-default-vpn vrf-name";
          // NCS drop max-elements statement
          description
            "Configure the domain log sever that receives logs.";
          leaf server-domain {
            type string;
            description
              "Log server domian address.";
          }
          leaf is-default-vpn {
            type string;
            description
              "Enable/disable the default VPN.";
          }
          leaf vrf-name {
            type string;
            // NCS drop must statement
            description
              "VPN name on a log server.";
          }
          leaf level {
            type ncs_template_log-level;
            // NCS drop default statement
            description
              "Level of logs saved on a log server.";
          }
          leaf server-port {
            type string;
            // NCS drop default statement
            description
              "Number of a port recving logs.";
          }
          leaf facility {
            type ncs_template_loghost-facility;
            // NCS drop default statement
            description
              "Log record tool.";
          }
          leaf channel-id {
            type string;
            // NCS drop default statement
            description
              "Channel number.";
          }
          // NCS drop config false leaf 'channel-name'
          leaf timestamp {
            type ncs_template_timestamp-format;
            // NCS drop default statement
            description
              "Log server timestamp.";
          }
          leaf transport-mode {
            type ncs_template_transport-mode-type;
            // NCS drop default statement
            description
              "Transport mode.";
          }
          leaf ssl-policy-name {
            type string;
            // NCS drop must statement
            description
              "SSL policy name.";
          }
          leaf source-ip {
            ext:support-filter "true";
            type string;
            description
              "Syslog source IP address.";
          }
          leaf is-brief-format {
            type string;
            // NCS drop default statement
            description
              "Enable/disable Syslog Brief Format.";
          }
          leaf is-security-only {
            type string;
            // NCS drop must statement
            // NCS drop default statement
            description
              "Enable/disable Syslog support security log.";
          }
        }
      }
      container logfiles {
        description
          "List of log file info.";
        list logfile {
          // NCS patched for predictable order
          ordered-by user;
          key "logfile-type";
          // NCS drop max-elements statement
          description
            "Specify Log file info.";
          ext:generated-by "system";
          ext:operation-exclude "create|delete";
          leaf logfile-type {
            type ncs_template_logfile-type;
            description
              "Log file type.";
          }
          leaf max-file-num {
            type string;
            ext:dynamic-default;
            // NCS drop must statement
            description
              "Maximum number of log files of the same type.";
          }
          leaf max-file-size {
            type string;
            units "MB";
            ext:dynamic-default;
            // NCS drop must statement
            description
              "Maximum size (in MB) of a log file. The value range for log files is [4, 8, 16, 32], for security files is [1~4], and for operation files is [1~4].";
          }
        }
      }
      container direction-channels {
        description
          "List of mappings of output directions and channels of the information center.";
        list direction-channel {
          // NCS patched for predictable order
          ordered-by user;
          key "output-direction";
          // NCS drop max-elements statement
          description
            "Specify the relation of direction and channel.";
          ext:generated-by "system";
          ext:operation-exclude "create";
          leaf output-direction {
            type string;
            description
              "Direction of information output.";
          }
          // NCS drop config false leaf 'default-channel-id'
          leaf channel-id {
            type string;
            ext:dynamic-default;
            description
              "Number of a configured channel.";
          }
          // NCS drop config false leaf 'channel-name'
        }
      }
      // NCS drop config false container 'info-center-statistics'
      // NCS drop config false container 'info-center-buffers'
      // NCS drop config false container modules
      // NCS drop config false container logbuffers
      // NCS drop config false container trapbuffers
      // NCS drop config false container securitybuffers
      container logfile-prefixs {
        description
          "List of log file prefix.";
        list logfile-prefix {
          // NCS patched for predictable order
          ordered-by user;
          key "type name";
          // NCS drop max-elements statement
          description
            "Specify Log file prefixs.";
          leaf type {
            type ncs_template_prefix-file-type;
            description
              "Log file type.";
          }
          leaf name {
            type string;
            description
              "File name.";
          }
        }
      }
    }
  }
}
