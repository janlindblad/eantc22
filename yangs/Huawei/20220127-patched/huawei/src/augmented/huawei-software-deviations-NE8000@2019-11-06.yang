module huawei-software-deviations-NE8000 {
  // Generated by yanger -t ncs
  tailf:mount-id "huawei-nc-1.0:huawei-nc-1.0";
  tailf:ncs-device-type "netconf";

  namespace "urn:huawei:yang:huawei-software-deviations-NE8000";
  prefix software-devs-NE8000;

  import huawei-software {
    prefix software;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "This module defines deviation statements for huawei-software module.";

  revision 2019-11-06 {
    description
      "Initial revision.";
    reference "Huawei private.";
  }

  deviation "/ncs:devices/ncs:template/ncs:ned-id/ncs:config/software:software/software:global" {
    deviate not-supported;
  }
  deviation "/ncs:devices/ncs:device/ncs:live-status/software:software/software:global" {
    deviate not-supported;
  }
  deviation "/ncs:devices/ncs:device/ncs:config/software:software/software:global" {
    deviate not-supported;
  }
  deviation "/ncs:devices/ncs:device/ncs:live-status/software:software/software:packages/software:package/software:package-type" {
    deviate not-supported;
  }
  deviation "/ncs:devices/ncs:device/ncs:live-status/software:software/software:checkpoint-infos" {
    deviate not-supported;
  }
  deviation "/ncs:devices/ncs:device/ncs:rpc/software:rpc-install-feature-software/software:install-feature-software" {
    deviate not-supported;
  }
  deviation "/ncs:devices/ncs:device/ncs:rpc/software:rpc-uninstall-feature-software/software:uninstall-feature-software" {
    deviate not-supported;
  }
  deviation "/ncs:devices/ncs:device/ncs:rpc/software:rpc-upgrade-feature-software/software:upgrade-feature-software" {
    deviate not-supported;
  }
  deviation "/ncs:devices/ncs:device/ncs:rpc/software:rpc-startup-feature-software/software:startup-feature-software" {
    deviate not-supported;
  }
  deviation "/ncs:devices/ncs:device/ncs:rpc/software:rpc-create-startup-checkpoint/software:create-startup-checkpoint" {
    deviate not-supported;
  }
  deviation "/ncs:devices/ncs:device/ncs:rpc/software:rpc-delete-startup-checkpoint/software:delete-startup-checkpoint" {
    deviate not-supported;
  }
  deviation "/ncs:devices/ncs:device/ncs:rpc/software:rpc-check-startup-checkpoint/software:check-startup-checkpoint" {
    deviate not-supported;
  }
  deviation "/ncs:devices/ncs:device/ncs:rpc/software:rpc-restore-startup-checkpoint/software:restore-startup-checkpoint" {
    deviate not-supported;
  }
  deviation "/ncs:devices/ncs:device/ncs:rpc/software:rpc-refresh-startup-secure-version-configuration/software:refresh-startup-secure-version-configuration" {
    deviate not-supported;
  }
}
