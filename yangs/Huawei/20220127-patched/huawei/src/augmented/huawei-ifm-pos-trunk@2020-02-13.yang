module huawei-ifm-pos-trunk {
  // Generated by yanger -t ncs
  tailf:mount-id "huawei-nc-1.0:huawei-nc-1.0";
  tailf:ncs-device-type "netconf";

  namespace "urn:huawei:yang:huawei-ifm-pos-trunk";
  prefix ifm-pos-trunk;

  import huawei-ifm {
    prefix ifm;
  }
  import huawei-extension {
    prefix ext;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Defines the Pos-Trunk bundling technology, which bundles multiple physical interfaces into a logical interface.";

  revision 2020-02-13 {
    description
      "Initial revision.";
    reference "Huawei private.";
  }
  ext:task-name "trunk";

  typedef ncs_template_active-status-type {
    type string;
    description
      "Pos trunk member active state.";
  }

  typedef ncs_rpc_notif_active-status-type {
    type enumeration {
      enum "invalid" {
        value 0;
        description
          "Invalid.";
      }
      enum "active" {
        value 1;
        description
          "The interface is in Active state.";
      }
      enum "inactive" {
        value 2;
        description
          "The interface is in InActive state.";
      }
    }
    description
      "Pos trunk member active state.";
  }

  typedef live_ncs_active-status-type {
    type enumeration {
      enum "invalid" {
        value 0;
        description
          "Invalid.";
      }
      enum "active" {
        value 1;
        description
          "The interface is in Active state.";
      }
      enum "inactive" {
        value 2;
        description
          "The interface is in InActive state.";
      }
    }
    description
      "Pos trunk member active state.";
  }

  typedef active-status-type {
    type enumeration {
      enum "invalid" {
        value 0;
        description
          "Invalid.";
      }
      enum "active" {
        value 1;
        description
          "The interface is in Active state.";
      }
      enum "inactive" {
        value 2;
        description
          "The interface is in InActive state.";
      }
    }
    description
      "Pos trunk member active state.";
  }

  augment "/ncs:devices/ncs:template/ncs:ned-id/ncs:config/ifm:ifm/ifm:interfaces/ifm:interface" {
    // NCS drop when statement
    description
      "Active when the interface is set to type Pos-Trunk.";
    container pos-trunk {
      description
        "Configure Pos-Trunk interfaces. It is a logical interface with multiple physical interfaces being bundled.";
      // NCS drop config false leaf 'up-member-num'
      container members {
        description
          "List of pos-trunk member interfaces.";
        list member {
          // NCS patched for predictable order
          ordered-by user;
          key "name";
          // NCS drop max-elements statement
          description
            "Configure pos-trunk member interfaces.";
          leaf name {
            type string;
            // NCS drop must statement
            description
              "Configures a name for a pos-trunk member interface.";
          }
          // NCS drop config false leaf 'port-status'
          // NCS drop config false leaf 'active-status'
        }
      }
    }
  }
  augment "/ncs:devices/ncs:device/ncs:live-status/ifm:ifm/ifm:interfaces/ifm:interface" {
    // NCS drop when statement
    description
      "Active when the interface is set to type Pos-Trunk.";
    container pos-trunk {
      tailf:ncs-device-type "netconf";
      tailf:display-when "not(../../../../../ncs:module) or ../../../../../ncs:module[ncs:name='huawei-ifm-pos-trunk'] or (../../../../../ncs:live-status-protocol[not(ncs:capability)]) or (../../../../../ncs:live-status-protocol/ncs:capability/ncs:module[.='huawei-ifm-pos-trunk'])";
      description
        "Configure Pos-Trunk interfaces. It is a logical interface with multiple physical interfaces being bundled.";
      leaf up-member-num {
        type uint32 {
          range "0..2";
        }
        description
          "Specifies the number of member interfaces in the Up state.";
      }
      container members {
        description
          "List of pos-trunk member interfaces.";
        list member {
          key "name";
          // NCS drop max-elements statement
          description
            "Configure pos-trunk member interfaces.";
          leaf name {
            type leafref {
              path "/ncs:devices/ncs:device/ncs:live-status/ifm:ifm/ifm:interfaces/ifm:interface/ifm:name" {
                tailf:xpath-root 3;
              }
            }
            // NCS drop must statement
            description
              "Configures a name for a pos-trunk member interface.";
          }
          leaf port-status {
            type ifm:live_ncs_port-status;
            description
              "Displays the status of a pos-trunk member interface.";
          }
          leaf active-status {
            type live_ncs_active-status-type;
            description
              "Displays the active status of a pos-trunk member interface.";
          }
        }
      }
    }
  }
  augment "/ncs:devices/ncs:device/ncs:config/ifm:ifm/ifm:interfaces/ifm:interface" {
    when "ifm:type='Pos-Trunk'" {
      tailf:xpath-root 3;
    }
    description
      "Active when the interface is set to type Pos-Trunk.";
    container pos-trunk {
      tailf:ncs-device-type "netconf";
      tailf:display-when "not(../../../../../ncs:module) or ../../../../../ncs:module[ncs:name='huawei-ifm-pos-trunk']";
      description
        "Configure Pos-Trunk interfaces. It is a logical interface with multiple physical interfaces being bundled.";
      // NCS drop config false leaf 'up-member-num'
      container members {
        description
          "List of pos-trunk member interfaces.";
        list member {
          key "name";
          max-elements 2;
          description
            "Configure pos-trunk member interfaces.";
          leaf name {
            type leafref {
              path "/ncs:devices/ncs:device/ncs:config/ifm:ifm/ifm:interfaces/ifm:interface/ifm:name" {
                tailf:xpath-root 3;
              }
            }
            must "/ifm:ifm/ifm:interfaces/ifm:interface[ifm:name=current()]/ifm:type='Pos'" {
              tailf:xpath-root 3;
            }
            description
              "Configures a name for a pos-trunk member interface.";
          }
          // NCS drop config false leaf 'port-status'
          // NCS drop config false leaf 'active-status'
        }
      }
    }
  }
}
