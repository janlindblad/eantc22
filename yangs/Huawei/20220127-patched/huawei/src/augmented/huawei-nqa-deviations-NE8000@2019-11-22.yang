module huawei-nqa-deviations-NE8000 {
  // Generated by yanger -t ncs
  tailf:mount-id "huawei-nc-1.0:huawei-nc-1.0";
  tailf:ncs-device-type "netconf";

  namespace "urn:huawei:yang:huawei-nqa-deviations-NE8000";
  prefix nqa-devs-NE8000;

  import huawei-nqa {
    prefix nqa;
  }
  import huawei-network-instance {
    prefix ni;
  }
  import huawei-ifm {
    prefix ifm;
  }
  import huawei-tunnel-management {
    prefix tnlm;
  }
  import huawei-mpls-te {
    prefix mpls-te;
  }
  import huawei-segment-routing {
    prefix sr;
  }
  import huawei-srpolicy {
    prefix srpolicy;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Network quality analysis.";

  revision 2019-11-22 {
    description
      "Initial revision.";
    reference "Huawei private.";
  }

  typedef ncs_template_pw-type-deviations {
    type string;
    description
      "Description of pw-type.";
  }

  typedef ncs_rpc_notif_pw-type-deviations {
    type enumeration {
      enum "atm-cell-transport" {
        value 3;
        description
          "ATM cell transport.";
      }
      enum "vlan" {
        value 4;
        description
          "VLAN.";
      }
      enum "ethernet" {
        value 5;
        description
          "Ethernet.";
      }
      enum "hdlc" {
        value 6;
        description
          "High - level Data Link Control.";
      }
      enum "ppp" {
        value 7;
        description
          "Point - to - Point Protocol.";
      }
      enum "atm-nto1-vcc" {
        value 9;
        description
          "ATM n to one VCC cell mode.";
      }
      enum "atm-nto1-vpc" {
        value 10;
        description
          "ATM n to one VPC cell mode.";
      }
      enum "ip-layer2" {
        value 11;
        description
          "IP layer 2.";
      }
      enum "atm-1to1-vcc" {
        value 12;
        description
          "ATM one to one VCC cell mode.";
      }
      enum "atm-1to1-vpc" {
        value 13;
        description
          "ATM one to one VPC cell mode.";
      }
      enum "satop-e1" {
        value 17;
        description
          "Satop e1.";
      }
      enum "cesopsn-basic" {
        value 21;
        description
          "Cesopsn basi.";
      }
      enum "ip-interworking" {
        value 64;
        description
          "IP interworking.";
      }
    }
    description
      "Description of pw-type.";
  }

  typedef live_ncs_pw-type-deviations {
    type enumeration {
      enum "atm-cell-transport" {
        value 3;
        description
          "ATM cell transport.";
      }
      enum "vlan" {
        value 4;
        description
          "VLAN.";
      }
      enum "ethernet" {
        value 5;
        description
          "Ethernet.";
      }
      enum "hdlc" {
        value 6;
        description
          "High - level Data Link Control.";
      }
      enum "ppp" {
        value 7;
        description
          "Point - to - Point Protocol.";
      }
      enum "atm-nto1-vcc" {
        value 9;
        description
          "ATM n to one VCC cell mode.";
      }
      enum "atm-nto1-vpc" {
        value 10;
        description
          "ATM n to one VPC cell mode.";
      }
      enum "ip-layer2" {
        value 11;
        description
          "IP layer 2.";
      }
      enum "atm-1to1-vcc" {
        value 12;
        description
          "ATM one to one VCC cell mode.";
      }
      enum "atm-1to1-vpc" {
        value 13;
        description
          "ATM one to one VPC cell mode.";
      }
      enum "satop-e1" {
        value 17;
        description
          "Satop e1.";
      }
      enum "cesopsn-basic" {
        value 21;
        description
          "Cesopsn basi.";
      }
      enum "ip-interworking" {
        value 64;
        description
          "IP interworking.";
      }
    }
    description
      "Description of pw-type.";
  }

  typedef pw-type-deviations {
    type enumeration {
      enum "atm-cell-transport" {
        value 3;
        description
          "ATM cell transport.";
      }
      enum "vlan" {
        value 4;
        description
          "VLAN.";
      }
      enum "ethernet" {
        value 5;
        description
          "Ethernet.";
      }
      enum "hdlc" {
        value 6;
        description
          "High - level Data Link Control.";
      }
      enum "ppp" {
        value 7;
        description
          "Point - to - Point Protocol.";
      }
      enum "atm-nto1-vcc" {
        value 9;
        description
          "ATM n to one VCC cell mode.";
      }
      enum "atm-nto1-vpc" {
        value 10;
        description
          "ATM n to one VPC cell mode.";
      }
      enum "ip-layer2" {
        value 11;
        description
          "IP layer 2.";
      }
      enum "atm-1to1-vcc" {
        value 12;
        description
          "ATM one to one VCC cell mode.";
      }
      enum "atm-1to1-vpc" {
        value 13;
        description
          "ATM one to one VPC cell mode.";
      }
      enum "satop-e1" {
        value 17;
        description
          "Satop e1.";
      }
      enum "cesopsn-basic" {
        value 21;
        description
          "Cesopsn basi.";
      }
      enum "ip-interworking" {
        value 64;
        description
          "IP interworking.";
      }
    }
    description
      "Description of pw-type.";
  }

  deviation "/ncs:devices/ncs:template/ncs:ned-id/ncs:config/nqa:nqa/nqa:instances/nqa:instance/nqa:type/nqa:pwe3-trace/nqa:pwe3-trace-input/nqa:local-pw-type" {
    deviate replace {
      type nqa-devs-NE8000:ncs_template_pw-type-deviations;
    }
  }
  deviation "/ncs:devices/ncs:device/ncs:live-status/nqa:nqa/nqa:instances/nqa:instance/nqa:type/nqa:pwe3-trace/nqa:pwe3-trace-input/nqa:local-pw-type" {
    deviate replace {
      type nqa-devs-NE8000:live_ncs_pw-type-deviations;
    }
  }
  deviation "/ncs:devices/ncs:device/ncs:config/nqa:nqa/nqa:instances/nqa:instance/nqa:type/nqa:pwe3-trace/nqa:pwe3-trace-input/nqa:local-pw-type" {
    deviate replace {
      type nqa-devs-NE8000:pw-type-deviations;
    }
  }
  deviation "/ncs:devices/ncs:template/ncs:ned-id/ncs:config/nqa:nqa/nqa:instances/nqa:instance/nqa:type/nqa:lsp-jitter/nqa:lsp-jitter-input/nqa:lsp-protocol/nqa:te/nqa:te-lsp-jitter/nqa:tunnel-name" {
    deviate add {
      // NCS drop must statement
    }
  }
  deviation "/ncs:devices/ncs:device/ncs:live-status/nqa:nqa/nqa:instances/nqa:instance/nqa:type/nqa:lsp-jitter/nqa:lsp-jitter-input/nqa:lsp-protocol/nqa:te/nqa:te-lsp-jitter/nqa:tunnel-name" {
    deviate add {
      // NCS drop must statement
    }
  }
  deviation "/ncs:devices/ncs:device/ncs:config/nqa:nqa/nqa:instances/nqa:instance/nqa:type/nqa:lsp-jitter/nqa:lsp-jitter-input/nqa:lsp-protocol/nqa:te/nqa:te-lsp-jitter/nqa:tunnel-name" {
    deviate add {
      must "/ifm:ifm/ifm:interfaces/ifm:interface[ifm:name=current()]/tnlm:tunnel-protocol/mpls-te:te-tunnel/mpls-te:common-attributes/mpls-te:signal-protocol='rsvp-te' or /ifm:ifm/ifm:interfaces/ifm:interface[ifm:name=current()]/tnlm:tunnel-protocol/mpls-te:te-tunnel/mpls-te:common-attributes/mpls-te:signal-protocol='cr-static'" {
        tailf:xpath-root 3;
      }
    }
  }
  deviation "/ncs:devices/ncs:template/ncs:ned-id/ncs:config/nqa:nqa/nqa:instances/nqa:instance/nqa:type/nqa:lsp-ping/nqa:lsp-ping-input/nqa:lsp-protocol/nqa:te/nqa:te-lsp-ping/nqa:tunnel-name" {
    deviate add {
      // NCS drop must statement
    }
  }
  deviation "/ncs:devices/ncs:device/ncs:live-status/nqa:nqa/nqa:instances/nqa:instance/nqa:type/nqa:lsp-ping/nqa:lsp-ping-input/nqa:lsp-protocol/nqa:te/nqa:te-lsp-ping/nqa:tunnel-name" {
    deviate add {
      // NCS drop must statement
    }
  }
  deviation "/ncs:devices/ncs:device/ncs:config/nqa:nqa/nqa:instances/nqa:instance/nqa:type/nqa:lsp-ping/nqa:lsp-ping-input/nqa:lsp-protocol/nqa:te/nqa:te-lsp-ping/nqa:tunnel-name" {
    deviate add {
      must "/ifm:ifm/ifm:interfaces/ifm:interface[ifm:name=current()]/tnlm:tunnel-protocol/mpls-te:te-tunnel/mpls-te:common-attributes/mpls-te:signal-protocol='rsvp-te' or /ifm:ifm/ifm:interfaces/ifm:interface[ifm:name=current()]/tnlm:tunnel-protocol/mpls-te:te-tunnel/mpls-te:common-attributes/mpls-te:signal-protocol='cr-static'" {
        tailf:xpath-root 3;
      }
    }
  }
  deviation "/ncs:devices/ncs:template/ncs:ned-id/ncs:config/nqa:nqa/nqa:instances/nqa:instance/nqa:type/nqa:lsp-ping/nqa:lsp-ping-input/nqa:lsp-protocol/nqa:srte/nqa:srte-lsp-ping/nqa:tunnel-name" {
    deviate add {
      // NCS drop must statement
    }
  }
  deviation "/ncs:devices/ncs:device/ncs:live-status/nqa:nqa/nqa:instances/nqa:instance/nqa:type/nqa:lsp-ping/nqa:lsp-ping-input/nqa:lsp-protocol/nqa:srte/nqa:srte-lsp-ping/nqa:tunnel-name" {
    deviate add {
      // NCS drop must statement
    }
  }
  deviation "/ncs:devices/ncs:device/ncs:config/nqa:nqa/nqa:instances/nqa:instance/nqa:type/nqa:lsp-ping/nqa:lsp-ping-input/nqa:lsp-protocol/nqa:srte/nqa:srte-lsp-ping/nqa:tunnel-name" {
    deviate add {
      must "/ifm:ifm/ifm:interfaces/ifm:interface[ifm:name=current()]/tnlm:tunnel-protocol/mpls-te:te-tunnel/mpls-te:common-attributes/mpls-te:signal-protocol='segment-routing'" {
        tailf:xpath-root 3;
      }
    }
  }
  deviation "/ncs:devices/ncs:template/ncs:ned-id/ncs:config/nqa:nqa/nqa:instances/nqa:instance/nqa:type/nqa:lsp-ping/nqa:lsp-ping-input/nqa:lsp-protocol/nqa:srte-policy/nqa:srte-policy-lsp-ping/nqa:probe-type/nqa:policy-name/nqa:policy-name" {
    deviate replace {
      type string;
    }
  }
  deviation "/ncs:devices/ncs:device/ncs:live-status/nqa:nqa/nqa:instances/nqa:instance/nqa:type/nqa:lsp-ping/nqa:lsp-ping-input/nqa:lsp-protocol/nqa:srte-policy/nqa:srte-policy-lsp-ping/nqa:probe-type/nqa:policy-name/nqa:policy-name" {
    deviate replace {
      type leafref {
        path "/ncs:devices/ncs:device/ncs:live-status/ni:network-instance/ni:instances/ni:instance/sr:segment-routing/srpolicy:srpolicy/srpolicy:policys/srpolicy:policy/srpolicy:name" {
          tailf:xpath-root 3;
        }
      }
    }
  }
  deviation "/ncs:devices/ncs:device/ncs:config/nqa:nqa/nqa:instances/nqa:instance/nqa:type/nqa:lsp-ping/nqa:lsp-ping-input/nqa:lsp-protocol/nqa:srte-policy/nqa:srte-policy-lsp-ping/nqa:probe-type/nqa:policy-name/nqa:policy-name" {
    deviate replace {
      type leafref {
        path "/ncs:devices/ncs:device/ncs:config/ni:network-instance/ni:instances/ni:instance/sr:segment-routing/srpolicy:srpolicy/srpolicy:policys/srpolicy:policy/srpolicy:name" {
          tailf:xpath-root 3;
        }
      }
    }
  }
  deviation "/ncs:devices/ncs:template/ncs:ned-id/ncs:config/nqa:nqa/nqa:instances/nqa:instance/nqa:type/nqa:lsp-trace/nqa:lsp-trace-input/nqa:lsp-protocol/nqa:te/nqa:te-lsp-trace/nqa:tunnel-name" {
    deviate add {
      // NCS drop must statement
    }
  }
  deviation "/ncs:devices/ncs:device/ncs:live-status/nqa:nqa/nqa:instances/nqa:instance/nqa:type/nqa:lsp-trace/nqa:lsp-trace-input/nqa:lsp-protocol/nqa:te/nqa:te-lsp-trace/nqa:tunnel-name" {
    deviate add {
      // NCS drop must statement
    }
  }
  deviation "/ncs:devices/ncs:device/ncs:config/nqa:nqa/nqa:instances/nqa:instance/nqa:type/nqa:lsp-trace/nqa:lsp-trace-input/nqa:lsp-protocol/nqa:te/nqa:te-lsp-trace/nqa:tunnel-name" {
    deviate add {
      must "/ifm:ifm/ifm:interfaces/ifm:interface[ifm:name=current()]/tnlm:tunnel-protocol/mpls-te:te-tunnel/mpls-te:common-attributes/mpls-te:signal-protocol='rsvp-te' or /ifm:ifm/ifm:interfaces/ifm:interface[ifm:name=current()]/tnlm:tunnel-protocol/mpls-te:te-tunnel/mpls-te:common-attributes/mpls-te:signal-protocol='cr-static'" {
        tailf:xpath-root 3;
      }
    }
  }
  deviation "/ncs:devices/ncs:template/ncs:ned-id/ncs:config/nqa:nqa/nqa:instances/nqa:instance/nqa:type/nqa:lsp-trace/nqa:lsp-trace-input/nqa:lsp-protocol/nqa:srte/nqa:srte-lsp-trace/nqa:tunnel-name" {
    deviate add {
      // NCS drop must statement
    }
  }
  deviation "/ncs:devices/ncs:device/ncs:live-status/nqa:nqa/nqa:instances/nqa:instance/nqa:type/nqa:lsp-trace/nqa:lsp-trace-input/nqa:lsp-protocol/nqa:srte/nqa:srte-lsp-trace/nqa:tunnel-name" {
    deviate add {
      // NCS drop must statement
    }
  }
  deviation "/ncs:devices/ncs:device/ncs:config/nqa:nqa/nqa:instances/nqa:instance/nqa:type/nqa:lsp-trace/nqa:lsp-trace-input/nqa:lsp-protocol/nqa:srte/nqa:srte-lsp-trace/nqa:tunnel-name" {
    deviate add {
      must "/ifm:ifm/ifm:interfaces/ifm:interface[ifm:name=current()]/tnlm:tunnel-protocol/mpls-te:te-tunnel/mpls-te:common-attributes/mpls-te:signal-protocol='segment-routing'" {
        tailf:xpath-root 3;
      }
    }
  }
  deviation "/ncs:devices/ncs:template/ncs:ned-id/ncs:config/nqa:nqa/nqa:instances/nqa:instance/nqa:type/nqa:lsp-trace/nqa:lsp-trace-input/nqa:lsp-protocol/nqa:srte-policy/nqa:srte-policy-lsp-trace/nqa:probe-type/nqa:policy-name/nqa:policy-name" {
    deviate replace {
      type string;
    }
  }
  deviation "/ncs:devices/ncs:device/ncs:live-status/nqa:nqa/nqa:instances/nqa:instance/nqa:type/nqa:lsp-trace/nqa:lsp-trace-input/nqa:lsp-protocol/nqa:srte-policy/nqa:srte-policy-lsp-trace/nqa:probe-type/nqa:policy-name/nqa:policy-name" {
    deviate replace {
      type leafref {
        path "/ncs:devices/ncs:device/ncs:live-status/ni:network-instance/ni:instances/ni:instance/sr:segment-routing/srpolicy:srpolicy/srpolicy:policys/srpolicy:policy/srpolicy:name" {
          tailf:xpath-root 3;
        }
      }
    }
  }
  deviation "/ncs:devices/ncs:device/ncs:config/nqa:nqa/nqa:instances/nqa:instance/nqa:type/nqa:lsp-trace/nqa:lsp-trace-input/nqa:lsp-protocol/nqa:srte-policy/nqa:srte-policy-lsp-trace/nqa:probe-type/nqa:policy-name/nqa:policy-name" {
    deviate replace {
      type leafref {
        path "/ncs:devices/ncs:device/ncs:config/ni:network-instance/ni:instances/ni:instance/sr:segment-routing/srpolicy:srpolicy/srpolicy:policys/srpolicy:policy/srpolicy:name" {
          tailf:xpath-root 3;
        }
      }
    }
  }
  deviation "/ncs:devices/ncs:template/ncs:ned-id/ncs:config/nqa:nqa/nqa:instances/nqa:instance/nqa:type/nqa:arp-ping-ip" {
    deviate not-supported;
  }
  deviation "/ncs:devices/ncs:device/ncs:live-status/nqa:nqa/nqa:instances/nqa:instance/nqa:type/nqa:arp-ping-ip" {
    deviate not-supported;
  }
  deviation "/ncs:devices/ncs:device/ncs:config/nqa:nqa/nqa:instances/nqa:instance/nqa:type/nqa:arp-ping-ip" {
    deviate not-supported;
  }
  deviation "/ncs:devices/ncs:device/ncs:live-status/nqa:nqa/nqa:record/nqa:arp-ping-ip-results" {
    deviate not-supported;
  }
  deviation "/ncs:devices/ncs:template/ncs:ned-id/ncs:config/nqa:nqa/nqa:instances/nqa:instance/nqa:type/nqa:trace/nqa:trace-input" {
    deviate add {
      // NCS drop must statement
    }
  }
  deviation "/ncs:devices/ncs:device/ncs:live-status/nqa:nqa/nqa:instances/nqa:instance/nqa:type/nqa:trace/nqa:trace-input" {
    deviate add {
      // NCS drop must statement
    }
  }
  deviation "/ncs:devices/ncs:device/ncs:config/nqa:nqa/nqa:instances/nqa:instance/nqa:type/nqa:trace/nqa:trace-input" {
    deviate add {
      must "not(ni-name != '_public_' and (ipv6-next-hop or ipv4-next-hop))" {
        tailf:xpath-root 3;
      }
    }
  }
}
