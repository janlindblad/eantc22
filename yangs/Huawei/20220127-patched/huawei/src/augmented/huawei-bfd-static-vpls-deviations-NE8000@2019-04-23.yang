module huawei-bfd-static-vpls-deviations-NE8000 {
  // Generated by yanger -t ncs
  tailf:mount-id "huawei-nc-1.0:huawei-nc-1.0";
  tailf:ncs-device-type "netconf";

  yang-version 1;
  namespace "urn:huawei:yang:huawei-bfd-static-vpls-deviations-NE8000";
  prefix bfd-vpls-devs-NE8000;

  import huawei-bfd {
    prefix bfd;
  }
  import huawei-bfd-static-vpls {
    prefix bfd-static-vpls;
  }
  import huawei-devm {
    prefix devm;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Bidirectional Forwarding Detection (BFD) is a detection mechanism used uniformly on the entire network. BFD is used to rapidly detect and monitor the connectivity of links or IP routes on a network.";

  revision 2019-04-23 {
    description
      "Initial revision.";
    reference "Huawei private.";
  }

  deviation "/ncs:devices/ncs:template/ncs:ned-id/ncs:config/bfd:bfd/bfd:sessions/bfd:session/bfd-static-vpls:vpls-groups/bfd-static-vpls:vpls-group/bfd-static-vpls:sub-select-slot-id" {
    deviate replace {
      type string;
    }
  }
  deviation "/ncs:devices/ncs:device/ncs:live-status/bfd:bfd/bfd:sessions/bfd:session/bfd-static-vpls:vpls-groups/bfd-static-vpls:vpls-group/bfd-static-vpls:sub-select-slot-id" {
    deviate replace {
      type leafref {
        path "/ncs:devices/ncs:device/ncs:live-status/devm:devm/devm:lpu-boards/devm:lpu-board/devm:position" {
          tailf:xpath-root 3;
        }
      }
    }
  }
  deviation "/ncs:devices/ncs:device/ncs:config/bfd:bfd/bfd:sessions/bfd:session/bfd-static-vpls:vpls-groups/bfd-static-vpls:vpls-group/bfd-static-vpls:sub-select-slot-id" {
    deviate replace {
      type leafref {
        path "/ncs:devices/ncs:device/ncs:config/devm:devm/devm:lpu-boards/devm:lpu-board/devm:position" {
          tailf:xpath-root 3;
        }
      }
    }
  }
}
