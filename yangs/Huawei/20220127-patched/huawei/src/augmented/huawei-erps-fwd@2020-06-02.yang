module huawei-erps-fwd {
  // Generated by yanger -t ncs
  tailf:mount-id "huawei-nc-1.0:huawei-nc-1.0";
  tailf:ncs-device-type "netconf";

  namespace "urn:huawei:yang:huawei-erps-fwd";
  prefix erps-fwd;

  import huawei-extension {
    prefix ext;
  }
  import huawei-erps {
    prefix erps;
  }
  ext:task-name "erps";

  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Ethernet ring protection switching.";

  revision 2020-06-02 {
    description
      "Init revision.";
    reference "Huawei private.";
  }

  augment "/ncs:devices/ncs:template/ncs:ned-id/ncs:config/erps:erps/erps:rings/erps:ring" {
    description
      "ERPS ring configuration.";
    container fast-switch {
      description
        "Configure ERPS fast switch.";
      leaf force-bc-time {
        type string;
        units "s";
        // NCS drop default statement
        description
          "ERPS fast switch force broadcast time (in seconds), ranging from 0 to 30.";
      }
    }
  }
  augment "/ncs:devices/ncs:device/ncs:live-status/erps:erps/erps:rings/erps:ring" {
    description
      "ERPS ring configuration.";
    container fast-switch {
      tailf:ncs-device-type "netconf";
      tailf:display-when "not(../../../../../ncs:module) or ../../../../../ncs:module[ncs:name='huawei-erps-fwd'] or (../../../../../ncs:live-status-protocol[not(ncs:capability)]) or (../../../../../ncs:live-status-protocol/ncs:capability/ncs:module[.='huawei-erps-fwd'])";
      description
        "Configure ERPS fast switch.";
      leaf force-bc-time {
        type uint32 {
          range "0..30";
        }
        units "s";
        // NCS drop default statement
        description
          "ERPS fast switch force broadcast time (in seconds), ranging from 0 to 30.";
      }
    }
  }
  augment "/ncs:devices/ncs:device/ncs:config/erps:erps/erps:rings/erps:ring" {
    description
      "ERPS ring configuration.";
    container fast-switch {
      tailf:ncs-device-type "netconf";
      tailf:display-when "not(../../../../../ncs:module) or ../../../../../ncs:module[ncs:name='huawei-erps-fwd']";
      description
        "Configure ERPS fast switch.";
      leaf force-bc-time {
        type uint32 {
          range "0..30";
        }
        units "s";
        default "15";
        description
          "ERPS fast switch force broadcast time (in seconds), ranging from 0 to 30.";
      }
    }
  }
}
