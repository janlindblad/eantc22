module huawei-nd-deviations-NE8000 {
  // Generated by yanger -t ncs
  tailf:mount-id "huawei-nc-1.0:huawei-nc-1.0";
  tailf:ncs-device-type "netconf";

  namespace "urn:huawei:yang:huawei-nd-deviations-NE8000";
  prefix nd-devs-NE8000;

  import huawei-nd {
    prefix nd;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "ND management.";

  revision 2019-04-24 {
    description
      "Initial revision.";
    reference "Huawei private.";
  }

  deviation "/ncs:devices/ncs:device/ncs:live-status/nd:nd/nd:ipv6-neighbors/nd:ipv6-neighbor/nd:nickname" {
    deviate not-supported;
  }
  deviation "/ncs:devices/ncs:device/ncs:live-status/nd:nd/nd:ipv6-neighbors/nd:ipv6-neighbor/nd:bd-id" {
    deviate replace {
      type uint32 {
        range "1..32768";
      }
    }
  }
}
