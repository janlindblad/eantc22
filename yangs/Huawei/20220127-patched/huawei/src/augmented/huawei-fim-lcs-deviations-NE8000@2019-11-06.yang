module huawei-fim-lcs-deviations-NE8000 {
  // Generated by yanger -t ncs
  tailf:mount-id "huawei-nc-1.0:huawei-nc-1.0";
  tailf:ncs-device-type "netconf";

  namespace "urn:huawei:yang:huawei-fim-lcs-deviations-NE8000";
  prefix fim-lcs-devs-NE8000;

  import huawei-fim-lcs {
    prefix fim-lcs;
  }
  import huawei-license {
    prefix lcs;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "This module defines deviation statements for huawei-fim-lcs module.";

  revision 2019-11-06 {
    description
      "Initial revision.";
    reference "Huawei private.";
  }

  deviation "/ncs:devices/ncs:template/ncs:ned-id/ncs:config/lcs:license/lcs:license-items/lcs:license-item/fim-lcs:port-mode-channels" {
    deviate not-supported;
  }
  deviation "/ncs:devices/ncs:device/ncs:live-status/lcs:license/lcs:license-items/lcs:license-item/fim-lcs:port-mode-channels" {
    deviate not-supported;
  }
  deviation "/ncs:devices/ncs:device/ncs:config/lcs:license/lcs:license-items/lcs:license-item/fim-lcs:port-mode-channels" {
    deviate not-supported;
  }
}
