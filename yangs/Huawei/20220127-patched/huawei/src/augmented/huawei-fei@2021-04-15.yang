module huawei-fei {
  // Generated by yanger -t ncs
  tailf:mount-id "huawei-nc-1.0:huawei-nc-1.0";
  tailf:ncs-device-type "netconf";

  yang-version 1;
  namespace "urn:huawei:yang:huawei-fei";
  prefix fei;

  import huawei-extension {
    prefix ext;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com
    ";
  description
    "System hardware difference specifications.";

  revision 2021-04-15 {
    description
      "Init revision.";
    reference "Huawei private.";
  }
  ext:task-name "forward-system";

  augment "/ncs:devices/ncs:device/ncs:config" {
    // NCS drop config false container fei
  }
  augment "/ncs:devices/ncs:device/ncs:live-status" {
    container fei {
      tailf:ncs-device-type "netconf";
      tailf:display-when "not(../../ncs:module) or ../../ncs:module[ncs:name='huawei-fei'] or (../../ncs:live-status-protocol[not(ncs:capability)]) or (../../ncs:live-status-protocol/ncs:capability/ncs:module[.='huawei-fei'])";
      description
        "Global configuration.";
      container hard-diffs {
        description
          "List of hard rule tables.";
        list hard-diff {
          key "op-mode entity-para parent-para schema-spec element-xpath bind-type bind-node-xpath bind-parent-xpath board-type board-version subcard-type interface-type if-main-sub-type";
          description
            "Statistics of hard rule table.";
          leaf op-mode {
            type uint32;
            description
              "Operate mode.";
          }
          leaf entity-para {
            type string {
              length "1..256";
            }
            description
              "Entity parameter.";
          }
          leaf parent-para {
            type string {
              length "1..256";
            }
            description
              "Entity parent parameter.";
          }
          leaf schema-spec {
            type string {
              length "1..256";
            }
            description
              "Schema name.";
          }
          leaf element-xpath {
            type string {
              length "1..256";
            }
            description
              "The xpath of element.";
          }
          leaf bind-type {
            type uint32;
            description
              "Bind type.";
          }
          leaf bind-node-xpath {
            type string {
              length "1..256";
            }
            description
              "The xpath of bind node.";
          }
          leaf bind-parent-xpath {
            type string {
              length "1..256";
            }
            description
              "The xpath of bind parent node.";
          }
          leaf board-type {
            type uint32;
            description
              "Board type.";
          }
          leaf board-version {
            type uint32;
            description
              "Board version.";
          }
          leaf subcard-type {
            type uint32;
            description
              "Subcard type.";
          }
          leaf interface-type {
            type uint32;
            description
              "Interface type.";
          }
          leaf if-main-sub-type {
            type uint32;
            description
              "Main or sub type.";
          }
          leaf is-support {
            type uint32;
            description
              "Support or not.";
          }
          leaf range {
            type string {
              length "1..1024";
            }
            description
              "Range of record.";
          }
          leaf default {
            type string {
              length "1..256";
            }
            description
              "Default value of record.";
          }
        }
      }
    }
  }
  augment "/ncs:devices/ncs:template/ncs:ned-id/ncs:config" {
    // NCS drop config false container fei
  }
}
