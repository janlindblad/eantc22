module huawei-routing-policy-ext {
  // Generated by yanger -t ncs
  tailf:mount-id "huawei-nc-1.0:huawei-nc-1.0";
  tailf:ncs-device-type "netconf";

  yang-version 1;
  namespace "urn:huawei:yang:huawei-routing-policy-ext";
  prefix rtp-ext;

  import ietf-inet-types {
    prefix inet;
  }
  import huawei-extension {
    prefix ext;
  }
  import huawei-qos {
    prefix qos;
  }
  import huawei-routing-policy {
    prefix rtp;
  }
  import huawei-mpls {
    prefix mpls;
  }
  import huawei-mpls-te {
    prefix mpls-te;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Routing policies are used to filter routes and control the receiving and advertising of routes. By changing the route attributes, such as reachability, you can change the path through which the traffic passes.";

  revision 2019-04-27 {
    description
      "Initial revision.";
    reference "Huawei private.";
  }
  ext:task-name "route-base";

  augment "/ncs:devices/ncs:template/ncs:ned-id/ncs:config/rtp:routing-policy/rtp:policy-definitions/rtp:policy-definition/rtp:nodes/rtp:node/rtp:actions/rtp:apply-qos-parameter/rtp:set-qos-parameter" {
    description
      "Augment the huawei-routing-policy model to add apply behavior configuration.";
    case behavior {
      description
        "Set behavior.";
      leaf name {
        type string;
        description
          "Name of traffic behavior.";
      }
    }
  }
  augment "/ncs:devices/ncs:device/ncs:live-status/rtp:routing-policy/rtp:policy-definitions/rtp:policy-definition/rtp:nodes/rtp:node/rtp:actions/rtp:apply-qos-parameter/rtp:set-qos-parameter" {
    description
      "Augment the huawei-routing-policy model to add apply behavior configuration.";
    case behavior {
      description
        "Set behavior.";
      leaf name {
        type leafref {
          path "/ncs:devices/ncs:device/ncs:live-status/qos:qos/qos:classifier-template/qos:traffic-behaviors/qos:traffic-behavior/qos:name" {
            tailf:xpath-root 3;
          }
        }
        description
          "Name of traffic behavior.";
      }
    }
  }
  augment "/ncs:devices/ncs:device/ncs:config/rtp:routing-policy/rtp:policy-definitions/rtp:policy-definition/rtp:nodes/rtp:node/rtp:actions/rtp:apply-qos-parameter/rtp:set-qos-parameter" {
    description
      "Augment the huawei-routing-policy model to add apply behavior configuration.";
    case behavior {
      description
        "Set behavior.";
      leaf name {
        type leafref {
          path "/ncs:devices/ncs:device/ncs:config/qos:qos/qos:classifier-template/qos:traffic-behaviors/qos:traffic-behavior/qos:name" {
            tailf:xpath-root 3;
          }
        }
        description
          "Name of traffic behavior.";
      }
    }
  }
  augment "/ncs:devices/ncs:template/ncs:ned-id/ncs:config/rtp:routing-policy/rtp:policy-definitions/rtp:policy-definition/rtp:nodes/rtp:node/rtp:actions" {
    description
      "Augment the huawei-routing-policy model to add actions configuration.";
    container apply-stitch-pmsi {
      // NCS drop must statement
      presence "Create parameters of apply stitch-pmsi.";
      description
        "Enable/disable the PMSI attribute.";
      leaf pmsi-type {
        type string;
        // NCS drop mandatory statement
        description
          "PMSI attribute type.";
      }
      leaf root-ip {
        // NCS drop when statement
        type string;
        // NCS drop must statement
        description
          "MLDP root ip address.";
      }
      leaf p2mp-template {
        // NCS drop when statement
        type string;
        // NCS drop must statement
        description
          "P2MP TE template.";
      }
    }
  }
  augment "/ncs:devices/ncs:device/ncs:live-status/rtp:routing-policy/rtp:policy-definitions/rtp:policy-definition/rtp:nodes/rtp:node/rtp:actions" {
    description
      "Augment the huawei-routing-policy model to add actions configuration.";
    container apply-stitch-pmsi {
      tailf:ncs-device-type "netconf";
      tailf:display-when "not(../../../../../../../../ncs:module) or ../../../../../../../../ncs:module[ncs:name='huawei-routing-policy-ext'] or (../../../../../../../../ncs:live-status-protocol[not(ncs:capability)]) or (../../../../../../../../ncs:live-status-protocol/ncs:capability/ncs:module[.='huawei-routing-policy-ext'])";
      // NCS drop must statement
      presence "Create parameters of apply stitch-pmsi.";
      description
        "Enable/disable the PMSI attribute.";
      leaf pmsi-type {
        type enumeration {
          enum "mldp" {
            value 0;
            description
              "MLDP type.";
          }
          enum "rsvp-te" {
            value 1;
            description
              "RSVP-TE type.";
          }
          enum "incoming" {
            value 2;
            description
              "Incoming type.";
          }
        }
        // NCS drop mandatory statement
        description
          "PMSI attribute type.";
      }
      leaf root-ip {
        // NCS drop when statement
        type inet:ipv4-address-no-zone;
        // NCS drop must statement
        description
          "MLDP root ip address.";
      }
      leaf p2mp-template {
        // NCS drop when statement
        type leafref {
          path "/ncs:devices/ncs:device/ncs:live-status/mpls:mpls/mpls-te:te/mpls-te:p2mp-templates/mpls-te:p2mp-template/mpls-te:name" {
            tailf:xpath-root 3;
          }
        }
        // NCS drop must statement
        description
          "P2MP TE template.";
      }
    }
  }
  augment "/ncs:devices/ncs:device/ncs:config/rtp:routing-policy/rtp:policy-definitions/rtp:policy-definition/rtp:nodes/rtp:node/rtp:actions" {
    description
      "Augment the huawei-routing-policy model to add actions configuration.";
    container apply-stitch-pmsi {
      tailf:ncs-device-type "netconf";
      tailf:display-when "not(../../../../../../../../ncs:module) or ../../../../../../../../ncs:module[ncs:name='huawei-routing-policy-ext']";
      must "(pmsi-type='incoming' and p2mp-template) or (pmsi-type='mldp' and not(p2mp-template)) or (pmsi-type='rsvp-te' and not(root-ip) and p2mp-template)" {
        tailf:xpath-root 3;
      }
      presence "Create parameters of apply stitch-pmsi.";
      description
        "Enable/disable the PMSI attribute.";
      leaf pmsi-type {
        type enumeration {
          enum "mldp" {
            value 0;
            description
              "MLDP type.";
          }
          enum "rsvp-te" {
            value 1;
            description
              "RSVP-TE type.";
          }
          enum "incoming" {
            value 2;
            description
              "Incoming type.";
          }
        }
        mandatory true;
        description
          "PMSI attribute type.";
      }
      leaf root-ip {
        when "not(../pmsi-type='rsvp-te')" {
          tailf:xpath-root 3;
        }
        type inet:ipv4-address-no-zone;
        must "(../pmsi-type='incoming' and ../p2mp-template) or (../pmsi-type='mldp' and not(../p2mp-template))" {
          tailf:xpath-root 3;
        }
        description
          "MLDP root ip address.";
      }
      leaf p2mp-template {
        when "not(../pmsi-type='mldp')" {
          tailf:xpath-root 3;
        }
        type leafref {
          path "/ncs:devices/ncs:device/ncs:config/mpls:mpls/mpls-te:te/mpls-te:p2mp-templates/mpls-te:p2mp-template/mpls-te:name" {
            tailf:xpath-root 3;
          }
        }
        must "../pmsi-type='incoming' or (../pmsi-type='rsvp-te' and not(../root-ip))" {
          tailf:xpath-root 3;
        }
        description
          "P2MP TE template.";
      }
    }
  }
}
