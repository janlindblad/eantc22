submodule huawei-te-type {
  // Generated by yanger -t ncs
  tailf:mount-id "huawei-nc-1.0:huawei-nc-1.0";

  belongs-to huawei-te {
    prefix te;
  }

  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Te Description of Type.";

  revision 2020-03-10 {
    description
      "Fixed some descriptions.";
    reference "Huawei private.";
  }
  revision 2019-06-14 {
    description
      "Init revision.";
    reference "Huawei private.";
  }

  typedef ncs_template_er-hop-mode {
    type string;
    description
      "ERHop Mode.";
  }

  typedef ncs_template_er-hop-type {
    type string;
    description
      "ErHop Type.";
  }

  typedef ncs_template_er-hop-interface-type {
    type string;
    description
      "ErHop Int Type.";
  }

  typedef ncs_template_te-hop-address-type {
    type string;
    description
      "Te Hop Address Type.";
  }

  typedef ncs_template_er-sid-label-type {
    type string;
    description
      "ERHop SID Label Type.";
  }

  typedef ncs_template_er-sid-ipv6-label-type {
    type string;
    description
      "ERHop SID IPv6 Label Type.";
  }

  typedef ncs_rpc_notif_er-hop-mode {
    type enumeration {
      enum "ipv4-ipv6-address" {
        value 1;
        description
          "IPv4 or IPv6 address.";
      }
      enum "sid-label" {
        value 2;
        description
          "SID label.";
      }
      enum "sid-ipv6" {
        value 3;
        description
          "SID IPv6 label.";
      }
    }
    description
      "ERHop Mode.";
  }

  typedef ncs_rpc_notif_er-hop-type {
    type enumeration {
      enum "include-strict" {
        value 1;
        description
          "Strictly included.";
      }
      enum "include-loose" {
        value 2;
        description
          "Loosely included.";
      }
      enum "exclude" {
        value 3;
        description
          "Exclude.";
      }
    }
    description
      "ErHop Type.";
  }

  typedef ncs_rpc_notif_er-hop-interface-type {
    type enumeration {
      enum "default" {
        value 0;
        description
          "Not configured.";
      }
      enum "incoming" {
        value 1;
        description
          "Incoming interface.";
      }
      enum "outgoing" {
        value 2;
        description
          "Outgoing interface.";
      }
    }
    description
      "ErHop Int Type.";
  }

  typedef ncs_rpc_notif_te-hop-address-type {
    type enumeration {
      enum "ipv4" {
        value 1;
        description
          "IPv4 type.";
      }
    }
    description
      "Te Hop Address Type.";
  }

  typedef ncs_rpc_notif_er-sid-label-type {
    type enumeration {
      enum "adjacency" {
        value 1;
        description
          "Adjacency label.";
      }
      enum "prefix" {
        value 2;
        description
          "Prefix label.";
      }
      enum "binding" {
        value 3;
        description
          "Binding label.";
      }
    }
    description
      "ERHop SID Label Type.";
  }

  typedef ncs_rpc_notif_er-sid-ipv6-label-type {
    type enumeration {
      enum "none" {
        value 0;
        description
          "None.";
      }
      enum "adjacency" {
        value 1;
        description
          "Adjacency label.";
      }
      enum "prefix" {
        value 2;
        description
          "Prefix label.";
      }
    }
    description
      "ERHop SID IPv6 Label Type.";
  }

  typedef live_ncs_er-hop-mode {
    type enumeration {
      enum "ipv4-ipv6-address" {
        value 1;
        description
          "IPv4 or IPv6 address.";
      }
      enum "sid-label" {
        value 2;
        description
          "SID label.";
      }
      enum "sid-ipv6" {
        value 3;
        description
          "SID IPv6 label.";
      }
    }
    description
      "ERHop Mode.";
  }

  typedef live_ncs_er-hop-type {
    type enumeration {
      enum "include-strict" {
        value 1;
        description
          "Strictly included.";
      }
      enum "include-loose" {
        value 2;
        description
          "Loosely included.";
      }
      enum "exclude" {
        value 3;
        description
          "Exclude.";
      }
    }
    description
      "ErHop Type.";
  }

  typedef live_ncs_er-hop-interface-type {
    type enumeration {
      enum "default" {
        value 0;
        description
          "Not configured.";
      }
      enum "incoming" {
        value 1;
        description
          "Incoming interface.";
      }
      enum "outgoing" {
        value 2;
        description
          "Outgoing interface.";
      }
    }
    description
      "ErHop Int Type.";
  }

  typedef live_ncs_te-hop-address-type {
    type enumeration {
      enum "ipv4" {
        value 1;
        description
          "IPv4 type.";
      }
    }
    description
      "Te Hop Address Type.";
  }

  typedef live_ncs_er-sid-label-type {
    type enumeration {
      enum "adjacency" {
        value 1;
        description
          "Adjacency label.";
      }
      enum "prefix" {
        value 2;
        description
          "Prefix label.";
      }
      enum "binding" {
        value 3;
        description
          "Binding label.";
      }
    }
    description
      "ERHop SID Label Type.";
  }

  typedef live_ncs_er-sid-ipv6-label-type {
    type enumeration {
      enum "none" {
        value 0;
        description
          "None.";
      }
      enum "adjacency" {
        value 1;
        description
          "Adjacency label.";
      }
      enum "prefix" {
        value 2;
        description
          "Prefix label.";
      }
    }
    description
      "ERHop SID IPv6 Label Type.";
  }

  typedef er-hop-mode {
    type enumeration {
      enum "ipv4-ipv6-address" {
        value 1;
        description
          "IPv4 or IPv6 address.";
      }
      enum "sid-label" {
        value 2;
        description
          "SID label.";
      }
      enum "sid-ipv6" {
        value 3;
        description
          "SID IPv6 label.";
      }
    }
    description
      "ERHop Mode.";
  }

  typedef er-hop-type {
    type enumeration {
      enum "include-strict" {
        value 1;
        description
          "Strictly included.";
      }
      enum "include-loose" {
        value 2;
        description
          "Loosely included.";
      }
      enum "exclude" {
        value 3;
        description
          "Exclude.";
      }
    }
    description
      "ErHop Type.";
  }

  typedef er-hop-interface-type {
    type enumeration {
      enum "default" {
        value 0;
        description
          "Not configured.";
      }
      enum "incoming" {
        value 1;
        description
          "Incoming interface.";
      }
      enum "outgoing" {
        value 2;
        description
          "Outgoing interface.";
      }
    }
    description
      "ErHop Int Type.";
  }

  typedef te-hop-address-type {
    type enumeration {
      enum "ipv4" {
        value 1;
        description
          "IPv4 type.";
      }
    }
    description
      "Te Hop Address Type.";
  }

  typedef er-sid-label-type {
    type enumeration {
      enum "adjacency" {
        value 1;
        description
          "Adjacency label.";
      }
      enum "prefix" {
        value 2;
        description
          "Prefix label.";
      }
      enum "binding" {
        value 3;
        description
          "Binding label.";
      }
    }
    description
      "ERHop SID Label Type.";
  }

  typedef er-sid-ipv6-label-type {
    type enumeration {
      enum "none" {
        value 0;
        description
          "None.";
      }
      enum "adjacency" {
        value 1;
        description
          "Adjacency label.";
      }
      enum "prefix" {
        value 2;
        description
          "Prefix label.";
      }
    }
    description
      "ERHop SID IPv6 Label Type.";
  }
}
