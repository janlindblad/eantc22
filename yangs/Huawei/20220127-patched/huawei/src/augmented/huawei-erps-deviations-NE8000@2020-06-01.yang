module huawei-erps-deviations-NE8000 {
  // Generated by yanger -t ncs
  tailf:mount-id "huawei-nc-1.0:huawei-nc-1.0";
  tailf:ncs-device-type "netconf";

  namespace "urn:huawei:yang:huawei-erps-deviations-NE8000";
  prefix erps-devs-NE8000;

  import huawei-erps {
    prefix erps;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Link layer discovery protocol.";

  revision 2020-06-01 {
    description
      "Initial revision.";
    reference "Huawei private.";
  }

  deviation "/ncs:devices/ncs:template/ncs:ned-id/ncs:config/erps:erps/erps:rings/erps:ring/erps:description" {
    deviate not-supported;
  }
  deviation "/ncs:devices/ncs:device/ncs:live-status/erps:erps/erps:rings/erps:ring/erps:description" {
    deviate not-supported;
  }
  deviation "/ncs:devices/ncs:device/ncs:config/erps:erps/erps:rings/erps:ring/erps:description" {
    deviate not-supported;
  }
  deviation "/ncs:devices/ncs:template/ncs:ned-id/ncs:config/erps:erps/erps:rings/erps:ring/erps:wait-restore-timer" {
    deviate not-supported;
  }
  deviation "/ncs:devices/ncs:device/ncs:live-status/erps:erps/erps:rings/erps:ring/erps:wait-restore-timer" {
    deviate not-supported;
  }
  deviation "/ncs:devices/ncs:device/ncs:config/erps:erps/erps:rings/erps:ring/erps:wait-restore-timer" {
    deviate not-supported;
  }
  deviation "/ncs:devices/ncs:template/ncs:ned-id/ncs:config/erps:erps/erps:rings/erps:ring/erps:raps-mel" {
    deviate not-supported;
  }
  deviation "/ncs:devices/ncs:device/ncs:live-status/erps:erps/erps:rings/erps:ring/erps:raps-mel" {
    deviate not-supported;
  }
  deviation "/ncs:devices/ncs:device/ncs:config/erps:erps/erps:rings/erps:ring/erps:raps-mel" {
    deviate not-supported;
  }
  deviation "/ncs:devices/ncs:template/ncs:ned-id/ncs:config/erps:erps/erps:rings/erps:ring/erps:revertive-enable" {
    deviate not-supported;
  }
  deviation "/ncs:devices/ncs:device/ncs:live-status/erps:erps/erps:rings/erps:ring/erps:revertive-enable" {
    deviate not-supported;
  }
  deviation "/ncs:devices/ncs:device/ncs:config/erps:erps/erps:rings/erps:ring/erps:revertive-enable" {
    deviate not-supported;
  }
  deviation "/ncs:devices/ncs:template/ncs:ned-id/ncs:config/erps:erps/erps:rings/erps:ring/erps:tc-protection-interval" {
    deviate not-supported;
  }
  deviation "/ncs:devices/ncs:device/ncs:live-status/erps:erps/erps:rings/erps:ring/erps:tc-protection-interval" {
    deviate not-supported;
  }
  deviation "/ncs:devices/ncs:device/ncs:config/erps:erps/erps:rings/erps:ring/erps:tc-protection-interval" {
    deviate not-supported;
  }
  deviation "/ncs:devices/ncs:template/ncs:ned-id/ncs:config/erps:erps/erps:rings/erps:ring/erps:tc-protection-threshold" {
    deviate not-supported;
  }
  deviation "/ncs:devices/ncs:device/ncs:live-status/erps:erps/erps:rings/erps:ring/erps:tc-protection-threshold" {
    deviate not-supported;
  }
  deviation "/ncs:devices/ncs:device/ncs:config/erps:erps/erps:rings/erps:ring/erps:tc-protection-threshold" {
    deviate not-supported;
  }
  deviation "/ncs:devices/ncs:template/ncs:ned-id/ncs:config/erps:erps/erps:rings/erps:ring/erps:version-v2" {
    deviate not-supported;
  }
  deviation "/ncs:devices/ncs:device/ncs:live-status/erps:erps/erps:rings/erps:ring/erps:version-v2" {
    deviate not-supported;
  }
  deviation "/ncs:devices/ncs:device/ncs:config/erps:erps/erps:rings/erps:ring/erps:version-v2" {
    deviate not-supported;
  }
  deviation "/ncs:devices/ncs:template/ncs:ned-id/ncs:config/erps:erps/erps:rings/erps:ring/erps:port-attributes" {
    deviate not-supported;
  }
  deviation "/ncs:devices/ncs:device/ncs:live-status/erps:erps/erps:rings/erps:ring/erps:port-attributes" {
    deviate not-supported;
  }
  deviation "/ncs:devices/ncs:device/ncs:config/erps:erps/erps:rings/erps:ring/erps:port-attributes" {
    deviate not-supported;
  }
}
