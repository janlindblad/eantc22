submodule huawei-diagnostic-tools-ipv4 {
  // Generated by yanger -t ncs
  tailf:mount-id "huawei-nc-1.0:huawei-nc-1.0";

  yang-version 1;
  belongs-to huawei-diagnostic-tools {
    prefix diagnostic-tools;
  }

  import huawei-pub-type {
    prefix pub-type;
  }
  import huawei-network-instance {
    prefix ni;
  }
  import huawei-ifm {
    prefix ifm;
  }
  import ietf-inet-types {
    prefix inet;
  }
  import ietf-yang-types {
    prefix yang;
  }
  import huawei-extension {
    prefix ext;
  }
  include huawei-diagnostic-tools-common;
  include huawei-diagnostic-tools-type;
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "IPv4 diagnosis tool.";

  revision 2020-09-10 {
    description
      "Add fast reply inbound node.";
    reference "Huawei private.";
  }
  revision 2019-10-29 {
    description
      "Initial revision.";
    reference "Huawei private.";
  }

  grouping ncs_template_ip-ping-trace-result-type {
    description
      "IP test result.";
    // NCS drop config false container 'ping-results'
    // NCS drop config false container 'trace-results'
  }

  grouping ncs_rpc_notif_ip-ping-trace-result-type {
    description
      "IP test result.";
    container ping-results {
      config false;
      description
        "List of ping test results.";
      list ping-result {
        key "test-name";
        config false;
        description
          "Statistics of ping test result.";
        leaf test-name {
          type string {
            length "1..32";
          }
          config false;
          description
            "Test name.";
        }
        leaf packet-recv {
          type uint32 {
            range "0..4294967295";
          }
          config false;
          description
            "Total number of received packets.";
        }
        leaf packet-send {
          type uint32 {
            range "0..4294967295";
          }
          config false;
          description
            "Total number of sent packets.";
        }
        leaf loss-ratio {
          type pub-type:ncs_rpc_notif_percent;
          units "%";
          config false;
          description
            "Packet loss ratio of a test.";
        }
        leaf rtt-min {
          type uint32 {
            range "0..4294967295";
          }
          units "ms";
          config false;
          description
            "Minimum RTT of all test packets.";
        }
        leaf rtt-max {
          type uint32 {
            range "0..4294967295";
          }
          units "ms";
          config false;
          description
            "Maximum RTT of all test packets.";
        }
        leaf average-rtt {
          type uint32 {
            range "0..4294967295";
          }
          units "ms";
          config false;
          description
            "Average RTT of all test packets.";
        }
        leaf status {
          type ncs_rpc_notif_dgntl-test-status-type;
          config false;
          description
            "Test status.";
        }
        leaf error-type {
          type ncs_rpc_notif_dgntl-error-type;
          config false;
          description
            "Test operation status.";
        }
        container details {
          config false;
          description
            "List of ping results of all packets in a test.";
          list detail {
            key "index";
            config false;
            description
              "Statistics of probe result.";
            leaf index {
              type uint32 {
                range "0..4294967295";
              }
              config false;
              description
                "Serial number of a test packet received.";
            }
            leaf ip-addr {
              type inet:ipv4-address-no-zone;
              config false;
              description
                "Reply address in a received response packet.";
            }
            leaf packet-size {
              type uint32 {
                range "0..4294967295";
              }
              config false;
              description
                "Number of bytes in a received response packet.";
            }
            leaf ttl {
              type uint8 {
                range "1..255";
              }
              config false;
              description
                "TTL of received response packets.";
            }
            leaf rtt {
              type uint32 {
                range "0..4294967295";
              }
              units "ms";
              config false;
              description
                "RTT of test packets.";
            }
            leaf result-type {
              type ncs_rpc_notif_detail-result-type;
              config false;
              description
                "Result of packet sending, which is either success or timeout.";
            }
            leaf system-time {
              type yang:date-and-time;
              config false;
              description
                "System time of response packets.";
            }
            leaf is-delete {
              type boolean;
              config false;
              description
                "Enable/disable the function of deleting test results.";
            }
          }
        }
      }
    }
    container trace-results {
      config false;
      description
        "List of trace test results.";
      list trace-result {
        key "test-name";
        config false;
        description
          "Statistics of trace test result.";
        leaf test-name {
          type string {
            length "1..32";
          }
          config false;
          description
            "Test name.";
        }
        leaf status {
          type ncs_rpc_notif_dgntl-test-status-type;
          config false;
          description
            "Test status.";
        }
        leaf error-type {
          type ncs_rpc_notif_dgntl-error-type;
          config false;
          description
            "Test operation status.";
        }
        container details {
          config false;
          description
            "List of ping results of all packets in a test.";
          list detail {
            key "hop-index";
            config false;
            description
              "Statistics of ping result of a single packet in a test.";
            leaf hop-index {
              type uint32;
              config false;
              description
                "Serial number of a hop in the test path. For a ping-type test such as the ping test or LSP ping test, there is only one hop in the test path, so the value is 1. For a trace-type test such as the trace test or LSP trace test, the value indicates the exact serial number of a hop in the test path.";
            }
            leaf ttl {
              type uint8 {
                range "1..255";
              }
              config false;
              description
                "TTL of received response packets.";
            }
            leaf rtt {
              type uint32;
              config false;
              description
                "RTT of test packets.";
            }
            leaf ds-ip-addr {
              type inet:ipv4-address-no-zone;
              config false;
              description
                "Destination address of the related hop in a test.";
            }
            leaf is-delete {
              type boolean;
              config false;
              description
                "Enable/disable the function of deleting test results.";
            }
          }
        }
      }
    }
  }

  grouping live_ncs_ip-ping-trace-result-type {
    description
      "IP test result.";
    container ping-results {
      description
        "List of ping test results.";
      list ping-result {
        key "test-name";
        description
          "Statistics of ping test result.";
        leaf test-name {
          type string {
            length "1..32";
          }
          description
            "Test name.";
        }
        leaf packet-recv {
          type uint32 {
            range "0..4294967295";
          }
          description
            "Total number of received packets.";
        }
        leaf packet-send {
          type uint32 {
            range "0..4294967295";
          }
          description
            "Total number of sent packets.";
        }
        leaf loss-ratio {
          type pub-type:live_ncs_percent;
          units "%";
          description
            "Packet loss ratio of a test.";
        }
        leaf rtt-min {
          type uint32 {
            range "0..4294967295";
          }
          units "ms";
          description
            "Minimum RTT of all test packets.";
        }
        leaf rtt-max {
          type uint32 {
            range "0..4294967295";
          }
          units "ms";
          description
            "Maximum RTT of all test packets.";
        }
        leaf average-rtt {
          type uint32 {
            range "0..4294967295";
          }
          units "ms";
          description
            "Average RTT of all test packets.";
        }
        leaf status {
          type live_ncs_dgntl-test-status-type;
          description
            "Test status.";
        }
        leaf error-type {
          type live_ncs_dgntl-error-type;
          description
            "Test operation status.";
        }
        container details {
          description
            "List of ping results of all packets in a test.";
          list detail {
            key "index";
            description
              "Statistics of probe result.";
            leaf index {
              type uint32 {
                range "0..4294967295";
              }
              description
                "Serial number of a test packet received.";
            }
            leaf ip-addr {
              type inet:ipv4-address-no-zone;
              description
                "Reply address in a received response packet.";
            }
            leaf packet-size {
              type uint32 {
                range "0..4294967295";
              }
              description
                "Number of bytes in a received response packet.";
            }
            leaf ttl {
              type uint8 {
                range "1..255";
              }
              description
                "TTL of received response packets.";
            }
            leaf rtt {
              type uint32 {
                range "0..4294967295";
              }
              units "ms";
              description
                "RTT of test packets.";
            }
            leaf result-type {
              type live_ncs_detail-result-type;
              description
                "Result of packet sending, which is either success or timeout.";
            }
            leaf system-time {
              type yang:date-and-time;
              description
                "System time of response packets.";
            }
            leaf is-delete {
              type boolean;
              description
                "Enable/disable the function of deleting test results.";
            }
          }
        }
      }
    }
    container trace-results {
      description
        "List of trace test results.";
      list trace-result {
        key "test-name";
        description
          "Statistics of trace test result.";
        leaf test-name {
          type string {
            length "1..32";
          }
          description
            "Test name.";
        }
        leaf status {
          type live_ncs_dgntl-test-status-type;
          description
            "Test status.";
        }
        leaf error-type {
          type live_ncs_dgntl-error-type;
          description
            "Test operation status.";
        }
        container details {
          description
            "List of ping results of all packets in a test.";
          list detail {
            key "hop-index";
            description
              "Statistics of ping result of a single packet in a test.";
            leaf hop-index {
              type uint32;
              description
                "Serial number of a hop in the test path. For a ping-type test such as the ping test or LSP ping test, there is only one hop in the test path, so the value is 1. For a trace-type test such as the trace test or LSP trace test, the value indicates the exact serial number of a hop in the test path.";
            }
            leaf ttl {
              type uint8 {
                range "1..255";
              }
              description
                "TTL of received response packets.";
            }
            leaf rtt {
              type uint32;
              description
                "RTT of test packets.";
            }
            leaf ds-ip-addr {
              type inet:ipv4-address-no-zone;
              description
                "Destination address of the related hop in a test.";
            }
            leaf is-delete {
              type boolean;
              description
                "Enable/disable the function of deleting test results.";
            }
          }
        }
      }
    }
  }

  grouping ip-ping-trace-result-type {
    description
      "IP test result.";
    // NCS drop config false container 'ping-results'
    // NCS drop config false container 'trace-results'
  }

  augment "/ncs:devices/ncs:device/ncs:rpc" {
    container rpc-ipv4-delete-ip-trace {
      tailf:ncs-device-type "netconf";
      tailf:display-when "not(../../ncs:module) or ../../ncs:module[ncs:name='huawei-diagnostic-tools']";
      tailf:action ipv4-delete-ip-trace {
        tailf:actionpoint ncsproxy {
          tailf:internal;
        }
        description
          "Delete IPv4 trace test.";
        ext:node-ref "/diagnostic-tools:diagnostic-tools/diagnostic-tools:ipv4/diagnostic-tools:trace-results";
        input {
          leaf test-name {
            type string;
            mandatory true;
            description
              "Test name.";
          }
        }
      }
    }
  }
  augment "/ncs:devices/ncs:device-group/ncs:ned-id/ncs:rpc" {
    container rpc-ipv4-delete-ip-trace {
      tailf:ncs-device-type "netconf";
      tailf:display-when "/ncs:devices/ncs:device[ncs:name=current()/../../../ncs:member]/ncs:module[ncs:name='huawei-diagnostic-tools']";
      tailf:action ipv4-delete-ip-trace {
        tailf:actionpoint ncsproxy {
          tailf:internal;
        }
        description
          "Delete IPv4 trace test.";
        ext:node-ref "/diagnostic-tools:diagnostic-tools/diagnostic-tools:ipv4/diagnostic-tools:trace-results";
        input {
          leaf test-name {
            type string;
            mandatory true;
            description
              "Test name.";
          }
        }
      }
    }
  }
  augment "/ncs:devices/ncs:device/ncs:rpc" {
    container rpc-ipv4-stop-ip-trace {
      tailf:ncs-device-type "netconf";
      tailf:display-when "not(../../ncs:module) or ../../ncs:module[ncs:name='huawei-diagnostic-tools']";
      tailf:action ipv4-stop-ip-trace {
        tailf:actionpoint ncsproxy {
          tailf:internal;
        }
        description
          "Stop IPv4 trace test.";
        ext:node-ref "/diagnostic-tools:diagnostic-tools/diagnostic-tools:ipv4/diagnostic-tools:trace-results";
        input {
          leaf test-name {
            type string;
            mandatory true;
            description
              "Test name.";
          }
        }
      }
    }
  }
  augment "/ncs:devices/ncs:device-group/ncs:ned-id/ncs:rpc" {
    container rpc-ipv4-stop-ip-trace {
      tailf:ncs-device-type "netconf";
      tailf:display-when "/ncs:devices/ncs:device[ncs:name=current()/../../../ncs:member]/ncs:module[ncs:name='huawei-diagnostic-tools']";
      tailf:action ipv4-stop-ip-trace {
        tailf:actionpoint ncsproxy {
          tailf:internal;
        }
        description
          "Stop IPv4 trace test.";
        ext:node-ref "/diagnostic-tools:diagnostic-tools/diagnostic-tools:ipv4/diagnostic-tools:trace-results";
        input {
          leaf test-name {
            type string;
            mandatory true;
            description
              "Test name.";
          }
        }
      }
    }
  }
  augment "/ncs:devices/ncs:device/ncs:rpc" {
    container rpc-ipv4-start-ip-trace {
      tailf:ncs-device-type "netconf";
      tailf:display-when "not(../../ncs:module) or ../../ncs:module[ncs:name='huawei-diagnostic-tools']";
      tailf:action ipv4-start-ip-trace {
        tailf:actionpoint ncsproxy {
          tailf:internal;
        }
        description
          "Start IPv4 trace test.";
        ext:node-ref "/diagnostic-tools:diagnostic-tools/diagnostic-tools:ipv4/diagnostic-tools:trace-results";
        input {
          leaf test-name {
            type string {
              length "1..32";
            }
            mandatory true;
            description
              "Test name.";
          }
          leaf dest-ip-addr {
            type pub-type:ncs_rpc_notif_host-name;
            mandatory true;
            description
              "Destination address of the string type. You can click this node to set different types of addresses and deploy the configurations together with the configuration of the destination address type node. If the destination address type is set to IPv4, this parameter is set to IPv4. If the destination address type is set to IPv6, this parameter is set to IPv6.";
          }
          leaf vrf-name {
            type string;
            description
              "Name of a VPN instance.";
          }
          choice priority {
            description
              "Priority type.";
            case dscp-value {
              description
                "DSCP value.";
              leaf dscp {
                type uint32 {
                  range "0..63";
                }
                default "0";
                description
                  "DSCP value.";
              }
            }
          }
        }
      }
    }
  }
  augment "/ncs:devices/ncs:device-group/ncs:ned-id/ncs:rpc" {
    container rpc-ipv4-start-ip-trace {
      tailf:ncs-device-type "netconf";
      tailf:display-when "/ncs:devices/ncs:device[ncs:name=current()/../../../ncs:member]/ncs:module[ncs:name='huawei-diagnostic-tools']";
      tailf:action ipv4-start-ip-trace {
        tailf:actionpoint ncsproxy {
          tailf:internal;
        }
        description
          "Start IPv4 trace test.";
        ext:node-ref "/diagnostic-tools:diagnostic-tools/diagnostic-tools:ipv4/diagnostic-tools:trace-results";
        input {
          leaf test-name {
            type string {
              length "1..32";
            }
            mandatory true;
            description
              "Test name.";
          }
          leaf dest-ip-addr {
            type pub-type:ncs_rpc_notif_host-name;
            mandatory true;
            description
              "Destination address of the string type. You can click this node to set different types of addresses and deploy the configurations together with the configuration of the destination address type node. If the destination address type is set to IPv4, this parameter is set to IPv4. If the destination address type is set to IPv6, this parameter is set to IPv6.";
          }
          leaf vrf-name {
            type string;
            description
              "Name of a VPN instance.";
          }
          choice priority {
            description
              "Priority type.";
            case dscp-value {
              description
                "DSCP value.";
              leaf dscp {
                type uint32 {
                  range "0..63";
                }
                default "0";
                description
                  "DSCP value.";
              }
            }
          }
        }
      }
    }
  }
  augment "/ncs:devices/ncs:device/ncs:rpc" {
    container rpc-ipv4-delete-ip-ping {
      tailf:ncs-device-type "netconf";
      tailf:display-when "not(../../ncs:module) or ../../ncs:module[ncs:name='huawei-diagnostic-tools']";
      tailf:action ipv4-delete-ip-ping {
        tailf:actionpoint ncsproxy {
          tailf:internal;
        }
        description
          "Delete IPv4 ping test.";
        ext:node-ref "/diagnostic-tools:diagnostic-tools/diagnostic-tools:ipv4/diagnostic-tools:ping-results";
        input {
          leaf test-name {
            type string;
            mandatory true;
            description
              "Test name.";
          }
        }
      }
    }
  }
  augment "/ncs:devices/ncs:device-group/ncs:ned-id/ncs:rpc" {
    container rpc-ipv4-delete-ip-ping {
      tailf:ncs-device-type "netconf";
      tailf:display-when "/ncs:devices/ncs:device[ncs:name=current()/../../../ncs:member]/ncs:module[ncs:name='huawei-diagnostic-tools']";
      tailf:action ipv4-delete-ip-ping {
        tailf:actionpoint ncsproxy {
          tailf:internal;
        }
        description
          "Delete IPv4 ping test.";
        ext:node-ref "/diagnostic-tools:diagnostic-tools/diagnostic-tools:ipv4/diagnostic-tools:ping-results";
        input {
          leaf test-name {
            type string;
            mandatory true;
            description
              "Test name.";
          }
        }
      }
    }
  }
  augment "/ncs:devices/ncs:device/ncs:rpc" {
    container rpc-ipv4-stop-ip-ping {
      tailf:ncs-device-type "netconf";
      tailf:display-when "not(../../ncs:module) or ../../ncs:module[ncs:name='huawei-diagnostic-tools']";
      tailf:action ipv4-stop-ip-ping {
        tailf:actionpoint ncsproxy {
          tailf:internal;
        }
        description
          "Stop IPv4 ping test.";
        ext:node-ref "/diagnostic-tools:diagnostic-tools/diagnostic-tools:ipv4/diagnostic-tools:ping-results";
        input {
          leaf test-name {
            type string;
            mandatory true;
            description
              "Test name.";
          }
        }
      }
    }
  }
  augment "/ncs:devices/ncs:device-group/ncs:ned-id/ncs:rpc" {
    container rpc-ipv4-stop-ip-ping {
      tailf:ncs-device-type "netconf";
      tailf:display-when "/ncs:devices/ncs:device[ncs:name=current()/../../../ncs:member]/ncs:module[ncs:name='huawei-diagnostic-tools']";
      tailf:action ipv4-stop-ip-ping {
        tailf:actionpoint ncsproxy {
          tailf:internal;
        }
        description
          "Stop IPv4 ping test.";
        ext:node-ref "/diagnostic-tools:diagnostic-tools/diagnostic-tools:ipv4/diagnostic-tools:ping-results";
        input {
          leaf test-name {
            type string;
            mandatory true;
            description
              "Test name.";
          }
        }
      }
    }
  }
  augment "/ncs:devices/ncs:device/ncs:rpc" {
    container rpc-ipv4-start-ip-ping {
      tailf:ncs-device-type "netconf";
      tailf:display-when "not(../../ncs:module) or ../../ncs:module[ncs:name='huawei-diagnostic-tools']";
      tailf:action ipv4-start-ip-ping {
        tailf:actionpoint ncsproxy {
          tailf:internal;
        }
        description
          "Start IPv4 ping test.";
        ext:node-ref "/diagnostic-tools:diagnostic-tools/diagnostic-tools:ipv4/diagnostic-tools:ping-results";
        input {
          leaf test-name {
            type string {
              length "1..32";
            }
            mandatory true;
            description
              "Test name.";
          }
          leaf dest-addr {
            type pub-type:ncs_rpc_notif_host-name;
            mandatory true;
            description
              "Destination address of the string type. You can click this node to set different types of addresses and deploy the configurations together with the configuration of the destination address type node. If the destination address type is set to IPv4, this parameter is set to IPv4. If the destination address type is set to IPv6, this parameter is set to IPv6.";
          }
          leaf source-address {
            type inet:ipv4-address-no-zone;
            description
              "Source address of the string type. You can click this node to set different types of addresses and deploy the configurations together with the configuration of the source address type node. If the source address type is set to IPv4, this parameter is set to IPv4. If the source address type is set to IPv6, this parameter is set to IPv6.";
          }
          leaf vrf-name {
            type string;
            description
              "Name of a VPN instance.";
          }
          leaf packet-count {
            type uint32 {
              range "1..4294967295";
            }
            default "5";
            description
              "Number of sent test packets.";
          }
          choice priority {
            description
              "Priority type.";
            case dscp-value {
              description
                "DSCP value.";
              leaf dscp {
                type uint32 {
                  range "0..63";
                }
                default "0";
                description
                  "DSCP value.";
              }
            }
          }
          leaf interval {
            type uint32 {
              range "1..10000";
            }
            units "ms";
            default "500";
            description
              "Interval for sending test packets.";
          }
          leaf timeout {
            type uint32 {
              range "0..65535";
            }
            units "ms";
            default "2000";
            description
              "Time to wait for a response packet after a test packet is sent. If no response packet is received within the timeout period, the system considers that the test packet times out.";
          }
          leaf if-name {
            type string;
            description
              "Name of the outbound interface for test packets.";
          }
          leaf inbound-reply-fast {
            type boolean;
            must '../if-name' {
              tailf:xpath-root 3;
            }
            description
              "Enable/disable fast reply from the specified Eth-Trunk member interface.";
          }
        }
      }
    }
  }
  augment "/ncs:devices/ncs:device-group/ncs:ned-id/ncs:rpc" {
    container rpc-ipv4-start-ip-ping {
      tailf:ncs-device-type "netconf";
      tailf:display-when "/ncs:devices/ncs:device[ncs:name=current()/../../../ncs:member]/ncs:module[ncs:name='huawei-diagnostic-tools']";
      tailf:action ipv4-start-ip-ping {
        tailf:actionpoint ncsproxy {
          tailf:internal;
        }
        description
          "Start IPv4 ping test.";
        ext:node-ref "/diagnostic-tools:diagnostic-tools/diagnostic-tools:ipv4/diagnostic-tools:ping-results";
        input {
          leaf test-name {
            type string {
              length "1..32";
            }
            mandatory true;
            description
              "Test name.";
          }
          leaf dest-addr {
            type pub-type:ncs_rpc_notif_host-name;
            mandatory true;
            description
              "Destination address of the string type. You can click this node to set different types of addresses and deploy the configurations together with the configuration of the destination address type node. If the destination address type is set to IPv4, this parameter is set to IPv4. If the destination address type is set to IPv6, this parameter is set to IPv6.";
          }
          leaf source-address {
            type inet:ipv4-address-no-zone;
            description
              "Source address of the string type. You can click this node to set different types of addresses and deploy the configurations together with the configuration of the source address type node. If the source address type is set to IPv4, this parameter is set to IPv4. If the source address type is set to IPv6, this parameter is set to IPv6.";
          }
          leaf vrf-name {
            type string;
            description
              "Name of a VPN instance.";
          }
          leaf packet-count {
            type uint32 {
              range "1..4294967295";
            }
            default "5";
            description
              "Number of sent test packets.";
          }
          choice priority {
            description
              "Priority type.";
            case dscp-value {
              description
                "DSCP value.";
              leaf dscp {
                type uint32 {
                  range "0..63";
                }
                default "0";
                description
                  "DSCP value.";
              }
            }
          }
          leaf interval {
            type uint32 {
              range "1..10000";
            }
            units "ms";
            default "500";
            description
              "Interval for sending test packets.";
          }
          leaf timeout {
            type uint32 {
              range "0..65535";
            }
            units "ms";
            default "2000";
            description
              "Time to wait for a response packet after a test packet is sent. If no response packet is received within the timeout period, the system considers that the test packet times out.";
          }
          leaf if-name {
            type string;
            description
              "Name of the outbound interface for test packets.";
          }
          leaf inbound-reply-fast {
            type boolean;
            must '../if-name' {
              tailf:xpath-root 4;
            }
            description
              "Enable/disable fast reply from the specified Eth-Trunk member interface.";
          }
        }
      }
    }
  }
  augment "/ncs:devices/ncs:device/ncs:live-status/diagnostic-tools:diagnostic-tools" {
    description
      "List of IPv4 tests.";
    container ipv4 {
      tailf:ncs-device-type "netconf";
      tailf:display-when "not(../../../ncs:module) or ../../../ncs:module[ncs:name='huawei-diagnostic-tools'] or (../../../ncs:live-status-protocol[not(ncs:capability)]) or (../../../ncs:live-status-protocol/ncs:capability/ncs:module[.='huawei-diagnostic-tools'])";
      description
        "Statistics of IPv4 tests.";
      uses live_ncs_ip-ping-trace-result-type;
    }
  }
}
