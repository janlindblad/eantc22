module huawei-ifm-fr {
  // Generated by yanger -t ncs
  tailf:mount-id "huawei-nc-1.0:huawei-nc-1.0";
  tailf:ncs-device-type "netconf";

  yang-version 1;
  namespace "urn:huawei:yang:huawei-ifm-fr";
  prefix ifm-fr;

  import huawei-ifm {
    prefix ifm;
  }
  import huawei-extension {
    prefix ext;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Frame relay protocol.";

  revision 2019-12-25 {
    description
      "Initial revision.";
    reference "Huawei private.";
  }
  ext:task-name "fr";

  typedef ncs_template_encapsulation-format {
    type string;
    description
      "FR interface encapsulation format.";
  }

  typedef ncs_template_lmi-type {
    type string;
    description
      "FR interface LMI type.";
  }

  typedef ncs_template_fr-type {
    type string;
    description
      "FR interface type.";
  }

  typedef ncs_rpc_notif_encapsulation-format {
    type enumeration {
      enum "ietf" {
        value 19;
        description
          "IETF.";
      }
      enum "nonstandard" {
        value 20;
        description
          "Nonstandard.";
      }
    }
    description
      "FR interface encapsulation format.";
  }

  typedef ncs_rpc_notif_lmi-type {
    type enumeration {
      enum "ansi" {
        value 0;
        description
          "LMI ANSI.";
      }
      enum "q933a" {
        value 1;
        description
          "LMI Q933A.";
      }
      enum "nonstandard" {
        value 2;
        description
          "LMI nonstandard.";
      }
    }
    description
      "FR interface LMI type.";
  }

  typedef ncs_rpc_notif_fr-type {
    type enumeration {
      enum "dte" {
        value 1;
        description
          "FR DTE.";
      }
      enum "dce" {
        value 2;
        description
          "FR DCE.";
      }
      enum "nni" {
        value 3;
        description
          "FR NNI.";
      }
    }
    description
      "FR interface type.";
  }

  typedef live_ncs_encapsulation-format {
    type enumeration {
      enum "ietf" {
        value 19;
        description
          "IETF.";
      }
      enum "nonstandard" {
        value 20;
        description
          "Nonstandard.";
      }
    }
    description
      "FR interface encapsulation format.";
  }

  typedef live_ncs_lmi-type {
    type enumeration {
      enum "ansi" {
        value 0;
        description
          "LMI ANSI.";
      }
      enum "q933a" {
        value 1;
        description
          "LMI Q933A.";
      }
      enum "nonstandard" {
        value 2;
        description
          "LMI nonstandard.";
      }
    }
    description
      "FR interface LMI type.";
  }

  typedef live_ncs_fr-type {
    type enumeration {
      enum "dte" {
        value 1;
        description
          "FR DTE.";
      }
      enum "dce" {
        value 2;
        description
          "FR DCE.";
      }
      enum "nni" {
        value 3;
        description
          "FR NNI.";
      }
    }
    description
      "FR interface type.";
  }

  typedef encapsulation-format {
    type enumeration {
      enum "ietf" {
        value 19;
        description
          "IETF.";
      }
      enum "nonstandard" {
        value 20;
        description
          "Nonstandard.";
      }
    }
    description
      "FR interface encapsulation format.";
  }

  typedef lmi-type {
    type enumeration {
      enum "ansi" {
        value 0;
        description
          "LMI ANSI.";
      }
      enum "q933a" {
        value 1;
        description
          "LMI Q933A.";
      }
      enum "nonstandard" {
        value 2;
        description
          "LMI nonstandard.";
      }
    }
    description
      "FR interface LMI type.";
  }

  typedef fr-type {
    type enumeration {
      enum "dte" {
        value 1;
        description
          "FR DTE.";
      }
      enum "dce" {
        value 2;
        description
          "FR DCE.";
      }
      enum "nni" {
        value 3;
        description
          "FR NNI.";
      }
    }
    description
      "FR interface type.";
  }

  augment "/ncs:devices/ncs:template/ncs:ned-id/ncs:config/ifm:ifm/ifm:interfaces/ifm:interface" {
    description
      "Configure extend attributes on the interface.";
    container fr-encapsulation {
      // NCS drop when statement
      description
        "Configure frame relay interface encapsulation format.";
      leaf encapsulation {
        type ncs_template_encapsulation-format;
        // NCS drop default statement
        description
          "FR interface encapsulation format.";
      }
    }
  }
  augment "/ncs:devices/ncs:device/ncs:live-status/ifm:ifm/ifm:interfaces/ifm:interface" {
    description
      "Configure extend attributes on the interface.";
    container fr-encapsulation {
      tailf:ncs-device-type "netconf";
      tailf:display-when "not(../../../../../ncs:module) or ../../../../../ncs:module[ncs:name='huawei-ifm-fr'] or (../../../../../ncs:live-status-protocol[not(ncs:capability)]) or (../../../../../ncs:live-status-protocol/ncs:capability/ncs:module[.='huawei-ifm-fr'])";
      // NCS drop when statement
      description
        "Configure frame relay interface encapsulation format.";
      leaf encapsulation {
        type live_ncs_encapsulation-format;
        // NCS drop default statement
        description
          "FR interface encapsulation format.";
      }
    }
  }
  augment "/ncs:devices/ncs:device/ncs:config/ifm:ifm/ifm:interfaces/ifm:interface" {
    description
      "Configure extend attributes on the interface.";
    container fr-encapsulation {
      tailf:ncs-device-type "netconf";
      tailf:display-when "not(../../../../../ncs:module) or ../../../../../ncs:module[ncs:name='huawei-ifm-fr']";
      when "../ifm:class='main-interface' and ../ifm:type='Pos' and ../ifm:link-protocol='fr'" {
        tailf:xpath-root 3;
      }
      description
        "Configure frame relay interface encapsulation format.";
      leaf encapsulation {
        type encapsulation-format;
        default "ietf";
        description
          "FR interface encapsulation format.";
      }
    }
  }
}
