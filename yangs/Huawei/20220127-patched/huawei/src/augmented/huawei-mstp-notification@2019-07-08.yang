module huawei-mstp-notification {
  // Generated by yanger -t ncs
  tailf:mount-id "huawei-nc-1.0:huawei-nc-1.0";
  tailf:ncs-device-type "netconf";

  yang-version 1;
  namespace "urn:huawei:yang:huawei-mstp-notification";
  prefix mstp-notification;

  import huawei-pub-type {
    prefix pub-type;
  }
  import huawei-extension {
    prefix ext;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Notification of mstp.";

  revision 2019-07-08 {
    description
      "Initial revision.";
    reference "Huawei private.";
  }
  ext:task-name "mstp";

  augment "/ncs:devices/ncs:device/ncs:notifications/ncs:received-notifications/ncs:notification/ncs:data" {
    container tc-flap-resume {
      presence "";
      config false;
      description
        "The STP topology of the local device stopped flapping.";
      leaf process-id {
        type uint32;
        description
          "MSTP process ID.";
      }
      leaf instance-id {
        type uint32;
        description
          "Multiple spanning tree instance (MSTI) ID.";
      }
    }
  }
  augment "/ncs:devices/ncs:device/ncs:notifications/ncs:received-notifications/ncs:notification/ncs:data" {
    container tc-flap {
      presence "";
      config false;
      description
        "The local device proactively detected that its STP topology was flapping.";
      leaf process-id {
        type uint32;
        description
          "MSTP process ID.";
      }
      leaf instance-id {
        type uint32;
        description
          "Multiple spanning tree instance (MSTI) ID.";
      }
    }
  }
  augment "/ncs:devices/ncs:device/ncs:notifications/ncs:received-notifications/ncs:notification/ncs:data" {
    container tc-flap-receive {
      presence "";
      config false;
      description
        "The local device received many TC BPDUs from neighbors.";
      leaf process-id {
        type uint32;
        description
          "Process ID.";
      }
      leaf instance-id {
        type uint32;
        description
          "MSTP instance ID.";
      }
      leaf if-index {
        type uint32;
        description
          "Interface index.";
      }
      leaf if-name {
        type pub-type:ncs_rpc_notif_if-name;
        description
          "Interface name.";
      }
      leaf pw-name {
        type string {
          length "1..15";
        }
        description
          "PW name.";
      }
      leaf src-mac {
        type pub-type:ncs_rpc_notif_mac-address;
        description
          "Source MAC address.";
      }
    }
  }
  augment "/ncs:devices/ncs:device/ncs:netconf-notifications/ncs:received-notifications/ncs:notification/ncs:data" {
    container tc-flap-resume {
      presence "";
      config false;
      description
        "The STP topology of the local device stopped flapping.";
      leaf process-id {
        type uint32;
        description
          "MSTP process ID.";
      }
      leaf instance-id {
        type uint32;
        description
          "Multiple spanning tree instance (MSTI) ID.";
      }
    }
  }
  augment "/ncs:devices/ncs:device/ncs:netconf-notifications/ncs:received-notifications/ncs:notification/ncs:data" {
    container tc-flap {
      presence "";
      config false;
      description
        "The local device proactively detected that its STP topology was flapping.";
      leaf process-id {
        type uint32;
        description
          "MSTP process ID.";
      }
      leaf instance-id {
        type uint32;
        description
          "Multiple spanning tree instance (MSTI) ID.";
      }
    }
  }
  augment "/ncs:devices/ncs:device/ncs:netconf-notifications/ncs:received-notifications/ncs:notification/ncs:data" {
    container tc-flap-receive {
      presence "";
      config false;
      description
        "The local device received many TC BPDUs from neighbors.";
      leaf process-id {
        type uint32;
        description
          "Process ID.";
      }
      leaf instance-id {
        type uint32;
        description
          "MSTP instance ID.";
      }
      leaf if-index {
        type uint32;
        description
          "Interface index.";
      }
      leaf if-name {
        type pub-type:ncs_rpc_notif_if-name;
        description
          "Interface name.";
      }
      leaf pw-name {
        type string {
          length "1..15";
        }
        description
          "PW name.";
      }
      leaf src-mac {
        type pub-type:ncs_rpc_notif_mac-address;
        description
          "Source MAC address.";
      }
    }
  }
}
