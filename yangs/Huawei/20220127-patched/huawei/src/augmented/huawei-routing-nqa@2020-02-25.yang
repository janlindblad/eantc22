module huawei-routing-nqa {
  // Generated by yanger -t ncs
  tailf:mount-id "huawei-nc-1.0:huawei-nc-1.0";
  tailf:ncs-device-type "netconf";

  yang-version 1;
  namespace "urn:huawei:yang:huawei-routing-nqa";
  prefix rt-nqa;

  import huawei-extension {
    prefix ext;
  }
  import huawei-network-instance {
    prefix ni;
  }
  import huawei-l3vpn {
    prefix l3vpn;
  }
  import huawei-routing {
    prefix rt;
  }
  import huawei-nqa {
    prefix nqa;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "The file defines the static route track NQA.";

  revision 2020-02-25 {
    description
      "Initial revision.";
    reference "Huawei private.";
  }
  ext:task-name "route-base";

  augment "/ncs:devices/ncs:template/ncs:ned-id/ncs:config/ni:network-instance/ni:instances/ni:instance/l3vpn:afs/l3vpn:af/rt:routing/rt:static-routing/rt:unicast-routes/rt:unicast-route/rt:track-setting" {
    description
      "Static route track NQA.";
    case nqa {
      description
        "Track NQA.";
      leaf admin-name {
        type string;
        // NCS drop must statement
        description
          "Name of an NQA administer instance.";
      }
      leaf test-name {
        type string;
        // NCS drop must statement
        description
          "Name of an NQA test instance.";
      }
    }
  }
  augment "/ncs:devices/ncs:device/ncs:live-status/ni:network-instance/ni:instances/ni:instance/l3vpn:afs/l3vpn:af/rt:routing/rt:static-routing/rt:unicast-routes/rt:unicast-route/rt:track-setting" {
    description
      "Static route track NQA.";
    case nqa {
      description
        "Track NQA.";
      leaf admin-name {
        type leafref {
          path "/ncs:devices/ncs:device/ncs:live-status/nqa:nqa/nqa:instances/nqa:instance/nqa:admin-name" {
            tailf:xpath-root 3;
          }
        }
        // NCS drop must statement
        description
          "Name of an NQA administer instance.";
      }
      leaf test-name {
        type leafref {
          path "/ncs:devices/ncs:device/ncs:live-status/nqa:nqa/nqa:instances/nqa:instance/nqa:test-name" {
            tailf:xpath-root 3;
          }
        }
        // NCS drop must statement
        description
          "Name of an NQA test instance.";
      }
    }
  }
  augment "/ncs:devices/ncs:device/ncs:config/ni:network-instance/ni:instances/ni:instance/l3vpn:afs/l3vpn:af/rt:routing/rt:static-routing/rt:unicast-routes/rt:unicast-route/rt:track-setting" {
    description
      "Static route track NQA.";
    case nqa {
      description
        "Track NQA.";
      leaf admin-name {
        type leafref {
          path "/ncs:devices/ncs:device/ncs:config/nqa:nqa/nqa:instances/nqa:instance/nqa:admin-name" {
            tailf:xpath-root 3;
          }
        }
        must "../rt:bfd-enable='false' and ../rt:inherit-cost='false' and ../rt:permanent='false' and ../rt:topology-name='base'" {
          tailf:xpath-root 3;
        }
        description
          "Name of an NQA administer instance.";
      }
      leaf test-name {
        type leafref {
          path "/ncs:devices/ncs:device/ncs:config/nqa:nqa/nqa:instances/nqa:instance/nqa:test-name" {
            tailf:xpath-root 3;
          }
        }
        must "../rt:bfd-enable='false' and ../rt:inherit-cost='false' and ../rt:permanent='false' and ../rt:topology-name='base'" {
          tailf:xpath-root 3;
        }
        description
          "Name of an NQA test instance.";
      }
    }
  }
  augment "/ncs:devices/ncs:template/ncs:ned-id/ncs:config/ni:network-instance/ni:instances/ni:instance/l3vpn:afs/l3vpn:af/rt:routing/rt:static-routing/rt:unicast-route2s/rt:unicast-route2/rt:nexthop-interfaces/rt:nexthop-interface/rt:track-setting" {
    description
      "Static route track NQA.";
    case nqa {
      description
        "Track NQA.";
      leaf nqa-admin-name {
        type string;
        // NCS drop must statement
        description
          "Name of an NQA administer instance.";
      }
      leaf nqa-test-name {
        type string;
        // NCS drop must statement
        description
          "Name of an NQA test instance.";
      }
    }
  }
  augment "/ncs:devices/ncs:device/ncs:live-status/ni:network-instance/ni:instances/ni:instance/l3vpn:afs/l3vpn:af/rt:routing/rt:static-routing/rt:unicast-route2s/rt:unicast-route2/rt:nexthop-interfaces/rt:nexthop-interface/rt:track-setting" {
    description
      "Static route track NQA.";
    case nqa {
      description
        "Track NQA.";
      leaf nqa-admin-name {
        type leafref {
          path "/ncs:devices/ncs:device/ncs:live-status/nqa:nqa/nqa:instances/nqa:instance/nqa:admin-name" {
            tailf:xpath-root 3;
          }
        }
        // NCS drop must statement
        description
          "Name of an NQA administer instance.";
      }
      leaf nqa-test-name {
        type leafref {
          path "/ncs:devices/ncs:device/ncs:live-status/nqa:nqa/nqa:instances/nqa:instance/nqa:test-name" {
            tailf:xpath-root 3;
          }
        }
        // NCS drop must statement
        description
          "Name of an NQA test instance.";
      }
    }
  }
  augment "/ncs:devices/ncs:device/ncs:config/ni:network-instance/ni:instances/ni:instance/l3vpn:afs/l3vpn:af/rt:routing/rt:static-routing/rt:unicast-route2s/rt:unicast-route2/rt:nexthop-interfaces/rt:nexthop-interface/rt:track-setting" {
    description
      "Static route track NQA.";
    case nqa {
      description
        "Track NQA.";
      leaf nqa-admin-name {
        type leafref {
          path "/ncs:devices/ncs:device/ncs:config/nqa:nqa/nqa:instances/nqa:instance/nqa:admin-name" {
            tailf:xpath-root 3;
          }
        }
        must "../rt:permanent='false' and ../../../rt:topology-name='base'" {
          tailf:xpath-root 3;
        }
        description
          "Name of an NQA administer instance.";
      }
      leaf nqa-test-name {
        type leafref {
          path "/ncs:devices/ncs:device/ncs:config/nqa:nqa/nqa:instances/nqa:instance/nqa:test-name" {
            tailf:xpath-root 3;
          }
        }
        must "../rt:permanent='false' and ../../../rt:topology-name='base'" {
          tailf:xpath-root 3;
        }
        description
          "Name of an NQA test instance.";
      }
    }
  }
  augment "/ncs:devices/ncs:template/ncs:ned-id/ncs:config/ni:network-instance/ni:instances/ni:instance/l3vpn:afs/l3vpn:af/rt:routing/rt:static-routing/rt:unicast-route2s/rt:unicast-route2/rt:nexthop-interface-addresses/rt:nexthop-interface-address/rt:track-setting" {
    description
      "Static route track NQA.";
    case nqa {
      description
        "Track NQA.";
      leaf nqa-admin-name {
        type string;
        // NCS drop must statement
        description
          "Name of an NQA administer instance.";
      }
      leaf nqa-test-name {
        type string;
        // NCS drop must statement
        description
          "Name of an NQA test instance.";
      }
    }
  }
  augment "/ncs:devices/ncs:device/ncs:live-status/ni:network-instance/ni:instances/ni:instance/l3vpn:afs/l3vpn:af/rt:routing/rt:static-routing/rt:unicast-route2s/rt:unicast-route2/rt:nexthop-interface-addresses/rt:nexthop-interface-address/rt:track-setting" {
    description
      "Static route track NQA.";
    case nqa {
      description
        "Track NQA.";
      leaf nqa-admin-name {
        type leafref {
          path "/ncs:devices/ncs:device/ncs:live-status/nqa:nqa/nqa:instances/nqa:instance/nqa:admin-name" {
            tailf:xpath-root 3;
          }
        }
        // NCS drop must statement
        description
          "Name of an NQA administer instance.";
      }
      leaf nqa-test-name {
        type leafref {
          path "/ncs:devices/ncs:device/ncs:live-status/nqa:nqa/nqa:instances/nqa:instance/nqa:test-name" {
            tailf:xpath-root 3;
          }
        }
        // NCS drop must statement
        description
          "Name of an NQA test instance.";
      }
    }
  }
  augment "/ncs:devices/ncs:device/ncs:config/ni:network-instance/ni:instances/ni:instance/l3vpn:afs/l3vpn:af/rt:routing/rt:static-routing/rt:unicast-route2s/rt:unicast-route2/rt:nexthop-interface-addresses/rt:nexthop-interface-address/rt:track-setting" {
    description
      "Static route track NQA.";
    case nqa {
      description
        "Track NQA.";
      leaf nqa-admin-name {
        type leafref {
          path "/ncs:devices/ncs:device/ncs:config/nqa:nqa/nqa:instances/nqa:instance/nqa:admin-name" {
            tailf:xpath-root 3;
          }
        }
        must "../rt:permanent='false' and ../../../rt:topology-name='base'" {
          tailf:xpath-root 3;
        }
        description
          "Name of an NQA administer instance.";
      }
      leaf nqa-test-name {
        type leafref {
          path "/ncs:devices/ncs:device/ncs:config/nqa:nqa/nqa:instances/nqa:instance/nqa:test-name" {
            tailf:xpath-root 3;
          }
        }
        must "../rt:permanent='false' and ../../../rt:topology-name='base'" {
          tailf:xpath-root 3;
        }
        description
          "Name of an NQA test instance.";
      }
    }
  }
  augment "/ncs:devices/ncs:template/ncs:ned-id/ncs:config/ni:network-instance/ni:instances/ni:instance/l3vpn:afs/l3vpn:af/rt:routing/rt:static-routing/rt:unicast-route2s/rt:unicast-route2/rt:nexthop-addresses/rt:nexthop-address/rt:track-setting" {
    description
      "Static route track NQA.";
    case nqa {
      description
        "Track NQA.";
      leaf nqa-admin-name {
        type string;
        // NCS drop must statement
        description
          "Name of an NQA administer instance.";
      }
      leaf nqa-test-name {
        type string;
        // NCS drop must statement
        description
          "Name of an NQA test instance.";
      }
    }
  }
  augment "/ncs:devices/ncs:device/ncs:live-status/ni:network-instance/ni:instances/ni:instance/l3vpn:afs/l3vpn:af/rt:routing/rt:static-routing/rt:unicast-route2s/rt:unicast-route2/rt:nexthop-addresses/rt:nexthop-address/rt:track-setting" {
    description
      "Static route track NQA.";
    case nqa {
      description
        "Track NQA.";
      leaf nqa-admin-name {
        type leafref {
          path "/ncs:devices/ncs:device/ncs:live-status/nqa:nqa/nqa:instances/nqa:instance/nqa:admin-name" {
            tailf:xpath-root 3;
          }
        }
        // NCS drop must statement
        description
          "Name of an NQA administer instance.";
      }
      leaf nqa-test-name {
        type leafref {
          path "/ncs:devices/ncs:device/ncs:live-status/nqa:nqa/nqa:instances/nqa:instance/nqa:test-name" {
            tailf:xpath-root 3;
          }
        }
        // NCS drop must statement
        description
          "Name of an NQA test instance.";
      }
    }
  }
  augment "/ncs:devices/ncs:device/ncs:config/ni:network-instance/ni:instances/ni:instance/l3vpn:afs/l3vpn:af/rt:routing/rt:static-routing/rt:unicast-route2s/rt:unicast-route2/rt:nexthop-addresses/rt:nexthop-address/rt:track-setting" {
    description
      "Static route track NQA.";
    case nqa {
      description
        "Track NQA.";
      leaf nqa-admin-name {
        type leafref {
          path "/ncs:devices/ncs:device/ncs:config/nqa:nqa/nqa:instances/nqa:instance/nqa:admin-name" {
            tailf:xpath-root 3;
          }
        }
        must "../rt:inherit-cost='false' and ../rt:permanent='false' and ../../../rt:topology-name='base'" {
          tailf:xpath-root 3;
        }
        description
          "Name of an NQA administer instance.";
      }
      leaf nqa-test-name {
        type leafref {
          path "/ncs:devices/ncs:device/ncs:config/nqa:nqa/nqa:instances/nqa:instance/nqa:test-name" {
            tailf:xpath-root 3;
          }
        }
        must "../rt:inherit-cost='false' and ../rt:permanent='false' and ../../../rt:topology-name='base'" {
          tailf:xpath-root 3;
        }
        description
          "Name of an NQA test instance.";
      }
    }
  }
  augment "/ncs:devices/ncs:template/ncs:ned-id/ncs:config/ni:network-instance/ni:instances/ni:instance/l3vpn:afs/l3vpn:af/rt:routing/rt:static-routing/rt:unicast-route2s/rt:unicast-route2/rt:nexthop-vrf-addresses/rt:nexthop-vrf-address/rt:track-setting" {
    description
      "Static route track NQA.";
    case nqa {
      description
        "Track NQA.";
      leaf nqa-admin-name {
        type string;
        // NCS drop must statement
        description
          "Name of an NQA administer instance.";
      }
      leaf nqa-test-name {
        type string;
        // NCS drop must statement
        description
          "Name of an NQA test instance.";
      }
    }
  }
  augment "/ncs:devices/ncs:device/ncs:live-status/ni:network-instance/ni:instances/ni:instance/l3vpn:afs/l3vpn:af/rt:routing/rt:static-routing/rt:unicast-route2s/rt:unicast-route2/rt:nexthop-vrf-addresses/rt:nexthop-vrf-address/rt:track-setting" {
    description
      "Static route track NQA.";
    case nqa {
      description
        "Track NQA.";
      leaf nqa-admin-name {
        type leafref {
          path "/ncs:devices/ncs:device/ncs:live-status/nqa:nqa/nqa:instances/nqa:instance/nqa:admin-name" {
            tailf:xpath-root 3;
          }
        }
        // NCS drop must statement
        description
          "Name of an NQA administer instance.";
      }
      leaf nqa-test-name {
        type leafref {
          path "/ncs:devices/ncs:device/ncs:live-status/nqa:nqa/nqa:instances/nqa:instance/nqa:test-name" {
            tailf:xpath-root 3;
          }
        }
        // NCS drop must statement
        description
          "Name of an NQA test instance.";
      }
    }
  }
  augment "/ncs:devices/ncs:device/ncs:config/ni:network-instance/ni:instances/ni:instance/l3vpn:afs/l3vpn:af/rt:routing/rt:static-routing/rt:unicast-route2s/rt:unicast-route2/rt:nexthop-vrf-addresses/rt:nexthop-vrf-address/rt:track-setting" {
    description
      "Static route track NQA.";
    case nqa {
      description
        "Track NQA.";
      leaf nqa-admin-name {
        type leafref {
          path "/ncs:devices/ncs:device/ncs:config/nqa:nqa/nqa:instances/nqa:instance/nqa:admin-name" {
            tailf:xpath-root 3;
          }
        }
        must "../rt:inherit-cost='false' and ../rt:permanent='false' and ../../../rt:topology-name='base'" {
          tailf:xpath-root 3;
        }
        description
          "Name of an NQA administer instance.";
      }
      leaf nqa-test-name {
        type leafref {
          path "/ncs:devices/ncs:device/ncs:config/nqa:nqa/nqa:instances/nqa:instance/nqa:test-name" {
            tailf:xpath-root 3;
          }
        }
        must "../rt:inherit-cost='false' and ../rt:permanent='false' and ../../../rt:topology-name='base'" {
          tailf:xpath-root 3;
        }
        description
          "Name of an NQA test instance.";
      }
    }
  }
  augment "/ncs:devices/ncs:device/ncs:live-status/ni:network-instance/ni:instances/ni:instance/l3vpn:afs/l3vpn:af/rt:routing/rt:static-routing/rt:ipv4-routes/rt:ipv4-route" {
    description
      "Static route track NQA.";
    leaf nqa-admin-name {
      tailf:ncs-device-type "netconf";
      tailf:display-when "not(../../../../../../../../../../../ncs:module) or ../../../../../../../../../../../ncs:module[ncs:name='huawei-routing-nqa'] or (../../../../../../../../../../../ncs:live-status-protocol[not(ncs:capability)]) or (../../../../../../../../../../../ncs:live-status-protocol/ncs:capability/ncs:module[.='huawei-routing-nqa'])";
      type leafref {
        path "/ncs:devices/ncs:device/ncs:live-status/nqa:nqa/nqa:instances/nqa:instance/nqa:admin-name" {
          tailf:xpath-root 3;
        }
      }
      description
        "Name of an NQA administer instance.";
    }
    leaf nqa-test-name {
      tailf:ncs-device-type "netconf";
      tailf:display-when "not(../../../../../../../../../../../ncs:module) or ../../../../../../../../../../../ncs:module[ncs:name='huawei-routing-nqa'] or (../../../../../../../../../../../ncs:live-status-protocol[not(ncs:capability)]) or (../../../../../../../../../../../ncs:live-status-protocol/ncs:capability/ncs:module[.='huawei-routing-nqa'])";
      type leafref {
        path "/ncs:devices/ncs:device/ncs:live-status/nqa:nqa/nqa:instances/nqa:instance/nqa:test-name" {
          tailf:xpath-root 3;
        }
      }
      description
        "Name of an NQA test instance.";
    }
  }
  augment "/ncs:devices/ncs:device/ncs:live-status/ni:network-instance/ni:instances/ni:instance/l3vpn:afs/l3vpn:af/rt:routing/rt:static-routing/rt:ipv6-routes/rt:ipv6-route" {
    description
      "Static route track NQA.";
    leaf nqa-admin-name {
      tailf:ncs-device-type "netconf";
      tailf:display-when "not(../../../../../../../../../../../ncs:module) or ../../../../../../../../../../../ncs:module[ncs:name='huawei-routing-nqa'] or (../../../../../../../../../../../ncs:live-status-protocol[not(ncs:capability)]) or (../../../../../../../../../../../ncs:live-status-protocol/ncs:capability/ncs:module[.='huawei-routing-nqa'])";
      type leafref {
        path "/ncs:devices/ncs:device/ncs:live-status/nqa:nqa/nqa:instances/nqa:instance/nqa:admin-name" {
          tailf:xpath-root 3;
        }
      }
      description
        "Name of an NQA administer instance.";
    }
    leaf nqa-test-name {
      tailf:ncs-device-type "netconf";
      tailf:display-when "not(../../../../../../../../../../../ncs:module) or ../../../../../../../../../../../ncs:module[ncs:name='huawei-routing-nqa'] or (../../../../../../../../../../../ncs:live-status-protocol[not(ncs:capability)]) or (../../../../../../../../../../../ncs:live-status-protocol/ncs:capability/ncs:module[.='huawei-routing-nqa'])";
      type leafref {
        path "/ncs:devices/ncs:device/ncs:live-status/nqa:nqa/nqa:instances/nqa:instance/nqa:test-name" {
          tailf:xpath-root 3;
        }
      }
      description
        "Name of an NQA test instance.";
    }
  }
}
