module huawei-multicore {
  // Generated by yanger -t ncs
  tailf:mount-id "huawei-nc-1.0:huawei-nc-1.0";
  tailf:ncs-device-type "netconf";

  yang-version 1;
  namespace "urn:huawei:yang:huawei-multicore";
  prefix multicore;

  import huawei-extension {
    prefix ext;
  }
  import huawei-devm {
    prefix devm;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Global Configuration.";

  revision 2020-04-08 {
    description
      "Initial revision.";
    reference "Huawei private.";
  }
  ext:task-name "forwarding";

  augment "/ncs:devices/ncs:template/ncs:ned-id/ncs:config/devm:devm" {
    description
      "Forward CPU alarm.";
    container forward-cpu-alarm {
      description
        "Configure forward alarm for the multi-core CPU average usage on a board.";
      leaf threshold {
        type string;
        units "%";
        // NCS drop default statement
        description
          "Specifies the alarm threshold for the multi-core CPU average usage on a board.";
      }
      leaf log-enable {
        type string;
        // NCS drop default statement
        description
          "Enable/disable log reporting when the multi-core CPU average usage reaches the threshold.";
      }
      leaf trap-enable {
        type string;
        // NCS drop default statement
        description
          "Enable/disable alarm reporting when the multi-core CPU average usage reaches the threshold.";
      }
    }
    container forward-vcpu-alarm {
      description
        "Configure forward alarm for the usage of the multi-core's single core.";
      leaf threshold {
        type string;
        units "%";
        // NCS drop default statement
        description
          "Specifies the alarm threshold for the usage of the multi-core's single core.";
      }
      leaf log-enable {
        type string;
        // NCS drop default statement
        description
          "Enable/disable log reporting when the CPU usage of the multi-core's single core reaches the threshold.";
      }
      leaf trap-enable {
        type string;
        // NCS drop default statement
        description
          "Enable/disable alarm reporting when the CPU usage of the multi-core's single core reaches the threshold.";
      }
    }
  }
  augment "/ncs:devices/ncs:device/ncs:live-status/devm:devm" {
    description
      "Forward CPU alarm.";
    container forward-cpu-alarm {
      tailf:ncs-device-type "netconf";
      tailf:display-when "not(../../../ncs:module) or ../../../ncs:module[ncs:name='huawei-multicore'] or (../../../ncs:live-status-protocol[not(ncs:capability)]) or (../../../ncs:live-status-protocol/ncs:capability/ncs:module[.='huawei-multicore'])";
      description
        "Configure forward alarm for the multi-core CPU average usage on a board.";
      leaf threshold {
        type uint8 {
          range "40..100";
        }
        units "%";
        // NCS drop default statement
        description
          "Specifies the alarm threshold for the multi-core CPU average usage on a board.";
      }
      leaf log-enable {
        type boolean;
        // NCS drop default statement
        description
          "Enable/disable log reporting when the multi-core CPU average usage reaches the threshold.";
      }
      leaf trap-enable {
        type boolean;
        // NCS drop default statement
        description
          "Enable/disable alarm reporting when the multi-core CPU average usage reaches the threshold.";
      }
    }
    container forward-vcpu-alarm {
      tailf:ncs-device-type "netconf";
      tailf:display-when "not(../../../ncs:module) or ../../../ncs:module[ncs:name='huawei-multicore'] or (../../../ncs:live-status-protocol[not(ncs:capability)]) or (../../../ncs:live-status-protocol/ncs:capability/ncs:module[.='huawei-multicore'])";
      description
        "Configure forward alarm for the usage of the multi-core's single core.";
      leaf threshold {
        type uint8 {
          range "40..100";
        }
        units "%";
        // NCS drop default statement
        description
          "Specifies the alarm threshold for the usage of the multi-core's single core.";
      }
      leaf log-enable {
        type boolean;
        // NCS drop default statement
        description
          "Enable/disable log reporting when the CPU usage of the multi-core's single core reaches the threshold.";
      }
      leaf trap-enable {
        type boolean;
        // NCS drop default statement
        description
          "Enable/disable alarm reporting when the CPU usage of the multi-core's single core reaches the threshold.";
      }
    }
  }
  augment "/ncs:devices/ncs:device/ncs:config/devm:devm" {
    description
      "Forward CPU alarm.";
    container forward-cpu-alarm {
      tailf:ncs-device-type "netconf";
      tailf:display-when "not(../../../ncs:module) or ../../../ncs:module[ncs:name='huawei-multicore']";
      description
        "Configure forward alarm for the multi-core CPU average usage on a board.";
      leaf threshold {
        type uint8 {
          range "40..100";
        }
        units "%";
        default "95";
        description
          "Specifies the alarm threshold for the multi-core CPU average usage on a board.";
      }
      leaf log-enable {
        type boolean;
        default "true";
        description
          "Enable/disable log reporting when the multi-core CPU average usage reaches the threshold.";
      }
      leaf trap-enable {
        type boolean;
        default "true";
        description
          "Enable/disable alarm reporting when the multi-core CPU average usage reaches the threshold.";
      }
    }
    container forward-vcpu-alarm {
      tailf:ncs-device-type "netconf";
      tailf:display-when "not(../../../ncs:module) or ../../../ncs:module[ncs:name='huawei-multicore']";
      description
        "Configure forward alarm for the usage of the multi-core's single core.";
      leaf threshold {
        type uint8 {
          range "40..100";
        }
        units "%";
        default "95";
        description
          "Specifies the alarm threshold for the usage of the multi-core's single core.";
      }
      leaf log-enable {
        type boolean;
        default "true";
        description
          "Enable/disable log reporting when the CPU usage of the multi-core's single core reaches the threshold.";
      }
      leaf trap-enable {
        type boolean;
        default "true";
        description
          "Enable/disable alarm reporting when the CPU usage of the multi-core's single core reaches the threshold.";
      }
    }
  }
}
