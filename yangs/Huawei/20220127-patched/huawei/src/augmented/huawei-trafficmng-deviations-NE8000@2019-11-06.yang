module huawei-trafficmng-deviations-NE8000 {
  // Generated by yanger -t ncs
  tailf:mount-id "huawei-nc-1.0:huawei-nc-1.0";
  tailf:ncs-device-type "netconf";

  namespace "urn:huawei:yang:huawei-trafficmng-deviations-NE8000";
  prefix trafficmng-devs-NE8000;

  import huawei-trafficmng {
    prefix trafficmng;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "This module defines deviation statements for huawei-trafficmng module.";

  revision 2019-11-06 {
    description
      "Initial revision.";
    reference "Huawei private.";
  }

  deviation "/ncs:devices/ncs:template/ncs:ned-id/ncs:config/trafficmng:trafficmng/trafficmng:board-alarm-sfu-thresholds" {
    deviate not-supported;
  }
  deviation "/ncs:devices/ncs:device/ncs:live-status/trafficmng:trafficmng/trafficmng:board-alarm-sfu-thresholds" {
    deviate not-supported;
  }
  deviation "/ncs:devices/ncs:device/ncs:config/trafficmng:trafficmng/trafficmng:board-alarm-sfu-thresholds" {
    deviate not-supported;
  }
  deviation "/ncs:devices/ncs:template/ncs:ned-id/ncs:config/trafficmng:trafficmng/trafficmng:board-alarm-lpu-thresholds" {
    deviate not-supported;
  }
  deviation "/ncs:devices/ncs:device/ncs:live-status/trafficmng:trafficmng/trafficmng:board-alarm-lpu-thresholds" {
    deviate not-supported;
  }
  deviation "/ncs:devices/ncs:device/ncs:config/trafficmng:trafficmng/trafficmng:board-alarm-lpu-thresholds" {
    deviate not-supported;
  }
  deviation "/ncs:devices/ncs:template/ncs:ned-id/ncs:config/trafficmng:trafficmng/trafficmng:packet-loss-alarms" {
    deviate not-supported;
  }
  deviation "/ncs:devices/ncs:device/ncs:live-status/trafficmng:trafficmng/trafficmng:packet-loss-alarms" {
    deviate not-supported;
  }
  deviation "/ncs:devices/ncs:device/ncs:config/trafficmng:trafficmng/trafficmng:packet-loss-alarms" {
    deviate not-supported;
  }
  deviation "/ncs:devices/ncs:template/ncs:ned-id/ncs:config/trafficmng:trafficmng/trafficmng:lpu-backpressure-switch" {
    deviate not-supported;
  }
  deviation "/ncs:devices/ncs:device/ncs:live-status/trafficmng:trafficmng/trafficmng:lpu-backpressure-switch" {
    deviate not-supported;
  }
  deviation "/ncs:devices/ncs:device/ncs:config/trafficmng:trafficmng/trafficmng:lpu-backpressure-switch" {
    deviate not-supported;
  }
}
