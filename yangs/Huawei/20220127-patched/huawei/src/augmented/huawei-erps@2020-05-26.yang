module huawei-erps {
  // Generated by yanger -t ncs
  tailf:mount-id "huawei-nc-1.0:huawei-nc-1.0";
  tailf:ncs-device-type "netconf";

  namespace "urn:huawei:yang:huawei-erps";
  prefix erps;

  import huawei-ifm {
    prefix ifm;
  }
  import huawei-ethernet {
    prefix ethernet;
  }
  import huawei-mstp {
    prefix mstp;
  }
  import huawei-y1731 {
    prefix y1731;
  }
  import huawei-vlan {
    prefix vlan;
  }
  import huawei-pub-type {
    prefix pub-type;
  }
  import huawei-extension {
    prefix ext;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Ethernet ring protection switching.";

  revision 2020-05-26 {
    description
      "Initial revision.";
    reference "Huawei private.";
  }
  ext:task-name "erps";

  typedef ncs_template_erps-version {
    type string;
    description
      "ERPS version.";
  }

  typedef ncs_template_erps-ring-mode {
    type string;
    description
      "ERPS ring mode.";
  }

  typedef ncs_template_erps-enable-state {
    type string;
    description
      "ERPS port state.";
  }

  typedef ncs_template_erps-port-role {
    type string;
    description
      "ERPS port role.";
  }

  typedef ncs_rpc_notif_erps-version {
    type enumeration {
      enum "v1" {
        value 1;
        description
          "ERPS ring version 1.";
      }
      enum "v2" {
        value 2;
        description
          "ERPS ring version 2.";
      }
    }
    description
      "ERPS version.";
  }

  typedef ncs_rpc_notif_erps-ring-mode {
    type enumeration {
      enum "major" {
        value 0;
        description
          "ERPS major ring.";
      }
      enum "sub" {
        value 1;
        description
          "ERPS sub-ring.";
      }
    }
    description
      "ERPS ring mode.";
  }

  typedef ncs_rpc_notif_erps-enable-state {
    type enumeration {
      enum "disable" {
        value 0;
        description
          "Disable.";
      }
      enum "enable" {
        value 1;
        description
          "Enable.";
      }
    }
    description
      "ERPS port state.";
  }

  typedef ncs_rpc_notif_erps-port-role {
    type enumeration {
      enum "common" {
        value 0;
        description
          "Common port.";
      }
      enum "neighbour" {
        value 1;
        description
          "RPL neighbour port.";
      }
      enum "owner" {
        value 2;
        description
          "RPL owner port.";
      }
    }
    description
      "ERPS port role.";
  }

  typedef live_ncs_erps-version {
    type enumeration {
      enum "v1" {
        value 1;
        description
          "ERPS ring version 1.";
      }
      enum "v2" {
        value 2;
        description
          "ERPS ring version 2.";
      }
    }
    description
      "ERPS version.";
  }

  typedef live_ncs_erps-ring-mode {
    type enumeration {
      enum "major" {
        value 0;
        description
          "ERPS major ring.";
      }
      enum "sub" {
        value 1;
        description
          "ERPS sub-ring.";
      }
    }
    description
      "ERPS ring mode.";
  }

  typedef live_ncs_erps-enable-state {
    type enumeration {
      enum "disable" {
        value 0;
        description
          "Disable.";
      }
      enum "enable" {
        value 1;
        description
          "Enable.";
      }
    }
    description
      "ERPS port state.";
  }

  typedef live_ncs_erps-port-role {
    type enumeration {
      enum "common" {
        value 0;
        description
          "Common port.";
      }
      enum "neighbour" {
        value 1;
        description
          "RPL neighbour port.";
      }
      enum "owner" {
        value 2;
        description
          "RPL owner port.";
      }
    }
    description
      "ERPS port role.";
  }

  typedef erps-version {
    type enumeration {
      enum "v1" {
        value 1;
        description
          "ERPS ring version 1.";
      }
      enum "v2" {
        value 2;
        description
          "ERPS ring version 2.";
      }
    }
    description
      "ERPS version.";
  }

  typedef erps-ring-mode {
    type enumeration {
      enum "major" {
        value 0;
        description
          "ERPS major ring.";
      }
      enum "sub" {
        value 1;
        description
          "ERPS sub-ring.";
      }
    }
    description
      "ERPS ring mode.";
  }

  typedef erps-enable-state {
    type enumeration {
      enum "disable" {
        value 0;
        description
          "Disable.";
      }
      enum "enable" {
        value 1;
        description
          "Enable.";
      }
    }
    description
      "ERPS port state.";
  }

  typedef erps-port-role {
    type enumeration {
      enum "common" {
        value 0;
        description
          "Common port.";
      }
      enum "neighbour" {
        value 1;
        description
          "RPL neighbour port.";
      }
      enum "owner" {
        value 2;
        description
          "RPL owner port.";
      }
    }
    description
      "ERPS port role.";
  }

  augment "/ncs:devices/ncs:device/ncs:config" {
    container erps {
      tailf:ncs-device-type "netconf";
      tailf:display-when "not(../../ncs:module) or ../../ncs:module[ncs:name='huawei-erps']";
      description
        "Ethernet ring protection switching.";
      container rings {
        description
          "List of ERPS rings.";
        list ring {
          key "id";
          unique "control-vlan";
          description
            "Configure ERPS ring management.";
          leaf id {
            type uint32 {
              range "1..255";
            }
            description
              "ERPS ring ID.";
          }
          leaf description {
            type string {
              length "1..80";
            }
            description
              "Description of an ERPS ring.";
          }
          leaf control-vlan {
            type uint16 {
              range "1..4094";
            }
            must "/vlan:vlan/vlan:vlans/vlan:vlan[vlan:id=current()]/vlan:mac-learning='disable'" {
              tailf:xpath-root 3;
            }
            description
              "Control VLAN ID.";
          }
          leaf protected-instance-list {
            type pub-type:id-range {
              ext:value-range "0..4094";
              pattern '((409[0-4]|40[0-8][0-9]|[1-3][0-9]{3}|[1-9][0-9]{1,2}|[0-9])?(-(409[0-4]|40[0-8][0-9]|[1-3][0-9]{3}|[1-9][0-9]{1,2}|[0-9]))?(,((409[0-4]|40[0-8][0-9]|[1-3][0-9]{3}|[1-9][0-9]{1,2}|[0-9])(-(409[0-4]|40[0-8][0-9]|[1-3][0-9]{3}|[1-9][0-9]{1,2}|[0-9]))?))*)|((([\\+|\\-](409[0-4]|40[0-8][0-9]|[1-3][0-9]{3}|[1-9][0-9]{1,2}|[0-9]))|([\\+|\\-]\\((409[0-4]|40[0-8][0-9]|[1-3][0-9]{3}|[1-9][0-9]{1,2}|[0-9])-(409[0-4]|40[0-8][0-9]|[1-3][0-9]{3}|[1-9][0-9]{1,2}|[0-9])\\)))?(,(([\\+|\\-](409[0-4]|40[0-8][0-9]|[1-3][0-9]{3}|[1-9][0-9]{1,2}|[0-9]))|([\\+|\\-]\\((409[0-4]|40[0-8][0-9]|[1-3][0-9]{3}|[1-9][0-9]{1,2}|[0-9])-(409[0-4]|40[0-8][0-9]|[1-3][0-9]{3}|[1-9][0-9]{1,2}|[0-9])\\))))*)';
            }
            description
              "Protect instance ID of an ERPS ring.";
          }
          leaf wait-restore-timer {
            type uint32 {
              range "1..12";
            }
            units "min";
            default "5";
            description
              "Wait-to-restore time.";
          }
          leaf guard-timer {
            type uint32 {
              range "1..200";
            }
            units "cs";
            default "200";
            description
              "Guard time for blocking received RAPS packets.";
          }
          leaf holdoff-timer {
            type uint32 {
              range "0..100";
            }
            units "ds";
            default "0";
            description
              "Holdoff time.";
          }
          leaf raps-mel {
            type uint32 {
              range "0..7";
            }
            default "7";
            description
              "Maintenance entity group level for ring automatic protection switching.";
          }
          leaf version {
            type erps-version;
            default "v1";
            description
              "Basic version of an ERPS ring.";
          }
          leaf revertive-enable {
            type boolean;
            default "true";
            description
              "Enable/disable revertive status of an ERPS ring.";
          }
          leaf tc-protection-interval {
            type uint16 {
              range "1..600";
            }
            units "s";
            default "2";
            description
              "Topology change notification interval.";
          }
          leaf tc-protection-threshold {
            type uint16 {
              range "1..255";
            }
            default "3";
            description
              "Topology change notification threshold.";
          }
          container version-v2 {
            when "../version='v2'" {
              tailf:xpath-root 3;
            }
            description
              "Configure the ERPS ring information of version 2.";
            leaf ring-role {
              type erps-ring-mode;
              default "major";
              description
                "Role information of an ERPS ring.";
            }
            leaf virtual-channel-enable {
              type boolean;
              default "false";
              description
                "Enable/disable status of a virtual channel.";
            }
            leaf tc-notify-ring {
              type pub-type:id-range {
                ext:value-range "1..255";
                pattern '((25[0-5]|2[0-4][0-9]|1[0-9]{2}|[1-9][0-9]{0,1})?(-(25[0-5]|2[0-4][0-9]|1[0-9]{2}|[1-9][0-9]{0,1}))?(,((25[0-5]|2[0-4][0-9]|1[0-9]{2}|[1-9][0-9]{0,1})(-(25[0-5]|2[0-4][0-9]|1[0-9]{2}|[1-9][0-9]{0,1}))?))*)|((([\\+|\\-](25[0-5]|2[0-4][0-9]|1[0-9]{2}|[1-9][0-9]{0,1}))|([\\+|\\-]\\((25[0-5]|2[0-4][0-9]|1[0-9]{2}|[1-9][0-9]{0,1})-(25[0-5]|2[0-4][0-9]|1[0-9]{2}|[1-9][0-9]{0,1})\\)))?(,(([\\+|\\-](25[0-5]|2[0-4][0-9]|1[0-9]{2}|[1-9][0-9]{0,1}))|([\\+|\\-]\\((25[0-5]|2[0-4][0-9]|1[0-9]{2}|[1-9][0-9]{0,1})-(25[0-5]|2[0-4][0-9]|1[0-9]{2}|[1-9][0-9]{0,1})\\))))*)';
              }
              description
                "Ring ID for TC notification.";
            }
          }
          container port-attributes {
            description
              "List of ERPS ring port.";
            list port-attribute {
              key "if-name";
              max-elements 2;
              description
                "Configure port information of an ERPS ring.";
              leaf if-name {
                type leafref {
                  path "/ncs:devices/ncs:device/ncs:config/ifm:ifm/ifm:interfaces/ifm:interface/ifm:name" {
                    tailf:xpath-root 3;
                  }
                }
                must "/ifm:ifm/ifm:interfaces/ifm:interface[ifm:name=current()]/ethernet:ethernet/ethernet:main-interface/ethernet:l2-attribute/mstp:mstp-attribute/mstp:enable='false'" {
                  tailf:xpath-root 3;
                }
                must '../../../control-vlan and ../../../protected-instance-list' {
                  tailf:xpath-root 3;
                }
                description
                  "Name of an ERPS ring port.";
              }
              leaf port-role {
                type erps-port-role;
                must "../port-role='common' or (/ifm:ifm/ifm:interfaces/ifm:interface[ifm:name=current()/../if-name]/ifm:admin-status='down' and (../port-role='owner' or ( ../../../version='v2')))" {
                  tailf:xpath-root 3;
                }
                default "common";
                description
                  "Role of an ERPS ring port.";
              }
              leaf md-name {
                type leafref {
                  path "/ncs:devices/ncs:device/ncs:config/y1731:y1731/y1731:global-enable/y1731:mds/y1731:md/y1731:name" {
                    tailf:xpath-root 3;
                  }
                }
                description
                  "Name of a maintenance domain.";
              }
              leaf ma-name {
                when '../md-name' {
                  tailf:xpath-root 3;
                }
                type leafref {
                  path "/ncs:devices/ncs:device/ncs:config/y1731:y1731/y1731:global-enable/y1731:mds/y1731:md/y1731:mas/y1731:ma/y1731:name" {
                    tailf:xpath-root 3;
                  }
                }
                mandatory true;
                description
                  "Name of a maintenance association.";
              }
              leaf mep-id {
                when '../ma-name' {
                  tailf:xpath-root 3;
                }
                type leafref {
                  path "/ncs:devices/ncs:device/ncs:config/y1731:y1731/y1731:global-enable/y1731:mds/y1731:md/y1731:mas/y1731:ma/y1731:meps/y1731:mep/y1731:id" {
                    tailf:xpath-root 3;
                  }
                }
                mandatory true;
                description
                  "ID of a MEP.";
              }
              leaf rmep-id {
                when '../mep-id' {
                  tailf:xpath-root 3;
                }
                type leafref {
                  path "/ncs:devices/ncs:device/ncs:config/y1731:y1731/y1731:global-enable/y1731:mds/y1731:md/y1731:mas/y1731:ma/y1731:rmeps/y1731:rmep/y1731:id" {
                    tailf:xpath-root 3;
                  }
                }
                mandatory true;
                description
                  "ID of a remote MEP.";
              }
              leaf vpls-enable {
                type erps-enable-state;
                default "disable";
                description
                  "Enable/disable VPLS status.";
              }
              leaf bd-enable {
                type erps-enable-state;
                default "disable";
                description
                  "Enable/disable BD status.";
              }
            }
          }
        }
      }
    }
  }
  augment "/ncs:devices/ncs:device/ncs:live-status" {
    container erps {
      tailf:ncs-device-type "netconf";
      tailf:display-when "not(../../ncs:module) or ../../ncs:module[ncs:name='huawei-erps'] or (../../ncs:live-status-protocol[not(ncs:capability)]) or (../../ncs:live-status-protocol/ncs:capability/ncs:module[.='huawei-erps'])";
      description
        "Ethernet ring protection switching.";
      container rings {
        description
          "List of ERPS rings.";
        list ring {
          key "id";
          unique "control-vlan";
          description
            "Configure ERPS ring management.";
          leaf id {
            type uint32 {
              range "1..255";
            }
            description
              "ERPS ring ID.";
          }
          leaf description {
            type string {
              length "1..80";
            }
            description
              "Description of an ERPS ring.";
          }
          leaf control-vlan {
            type uint16 {
              range "1..4094";
            }
            // NCS drop must statement
            description
              "Control VLAN ID.";
          }
          leaf protected-instance-list {
            type pub-type:live_ncs_id-range;
            description
              "Protect instance ID of an ERPS ring.";
          }
          leaf wait-restore-timer {
            type uint32 {
              range "1..12";
            }
            units "min";
            // NCS drop default statement
            description
              "Wait-to-restore time.";
          }
          leaf guard-timer {
            type uint32 {
              range "1..200";
            }
            units "cs";
            // NCS drop default statement
            description
              "Guard time for blocking received RAPS packets.";
          }
          leaf holdoff-timer {
            type uint32 {
              range "0..100";
            }
            units "ds";
            // NCS drop default statement
            description
              "Holdoff time.";
          }
          leaf raps-mel {
            type uint32 {
              range "0..7";
            }
            // NCS drop default statement
            description
              "Maintenance entity group level for ring automatic protection switching.";
          }
          leaf version {
            type live_ncs_erps-version;
            // NCS drop default statement
            description
              "Basic version of an ERPS ring.";
          }
          leaf revertive-enable {
            type boolean;
            // NCS drop default statement
            description
              "Enable/disable revertive status of an ERPS ring.";
          }
          leaf tc-protection-interval {
            type uint16 {
              range "1..600";
            }
            units "s";
            // NCS drop default statement
            description
              "Topology change notification interval.";
          }
          leaf tc-protection-threshold {
            type uint16 {
              range "1..255";
            }
            // NCS drop default statement
            description
              "Topology change notification threshold.";
          }
          container version-v2 {
            // NCS drop when statement
            description
              "Configure the ERPS ring information of version 2.";
            leaf ring-role {
              type live_ncs_erps-ring-mode;
              // NCS drop default statement
              description
                "Role information of an ERPS ring.";
            }
            leaf virtual-channel-enable {
              type boolean;
              // NCS drop default statement
              description
                "Enable/disable status of a virtual channel.";
            }
            leaf tc-notify-ring {
              type pub-type:live_ncs_id-range;
              description
                "Ring ID for TC notification.";
            }
          }
          container port-attributes {
            description
              "List of ERPS ring port.";
            list port-attribute {
              key "if-name";
              // NCS drop max-elements statement
              description
                "Configure port information of an ERPS ring.";
              leaf if-name {
                type leafref {
                  path "/ncs:devices/ncs:device/ncs:live-status/ifm:ifm/ifm:interfaces/ifm:interface/ifm:name" {
                    tailf:xpath-root 3;
                  }
                }
                // NCS drop must statement
                // NCS drop must statement
                description
                  "Name of an ERPS ring port.";
              }
              leaf port-role {
                type live_ncs_erps-port-role;
                // NCS drop must statement
                // NCS drop default statement
                description
                  "Role of an ERPS ring port.";
              }
              leaf md-name {
                type leafref {
                  path "/ncs:devices/ncs:device/ncs:live-status/y1731:y1731/y1731:global-enable/y1731:mds/y1731:md/y1731:name" {
                    tailf:xpath-root 3;
                  }
                }
                description
                  "Name of a maintenance domain.";
              }
              leaf ma-name {
                // NCS drop when statement
                type leafref {
                  path "/ncs:devices/ncs:device/ncs:live-status/y1731:y1731/y1731:global-enable/y1731:mds/y1731:md/y1731:mas/y1731:ma/y1731:name" {
                    tailf:xpath-root 3;
                  }
                }
                // NCS drop mandatory statement
                description
                  "Name of a maintenance association.";
              }
              leaf mep-id {
                // NCS drop when statement
                type leafref {
                  path "/ncs:devices/ncs:device/ncs:live-status/y1731:y1731/y1731:global-enable/y1731:mds/y1731:md/y1731:mas/y1731:ma/y1731:meps/y1731:mep/y1731:id" {
                    tailf:xpath-root 3;
                  }
                }
                // NCS drop mandatory statement
                description
                  "ID of a MEP.";
              }
              leaf rmep-id {
                // NCS drop when statement
                type leafref {
                  path "/ncs:devices/ncs:device/ncs:live-status/y1731:y1731/y1731:global-enable/y1731:mds/y1731:md/y1731:mas/y1731:ma/y1731:rmeps/y1731:rmep/y1731:id" {
                    tailf:xpath-root 3;
                  }
                }
                // NCS drop mandatory statement
                description
                  "ID of a remote MEP.";
              }
              leaf vpls-enable {
                type live_ncs_erps-enable-state;
                // NCS drop default statement
                description
                  "Enable/disable VPLS status.";
              }
              leaf bd-enable {
                type live_ncs_erps-enable-state;
                // NCS drop default statement
                description
                  "Enable/disable BD status.";
              }
            }
          }
        }
      }
    }
  }
  augment "/ncs:devices/ncs:template/ncs:ned-id/ncs:config" {
    container erps {
      description
        "Ethernet ring protection switching.";
      container rings {
        description
          "List of ERPS rings.";
        list ring {
          // NCS patched for predictable order
          ordered-by user;
          key "id";
          unique "control-vlan";
          description
            "Configure ERPS ring management.";
          leaf id {
            type string;
            description
              "ERPS ring ID.";
          }
          leaf description {
            type string;
            description
              "Description of an ERPS ring.";
          }
          leaf control-vlan {
            type string;
            // NCS drop must statement
            description
              "Control VLAN ID.";
          }
          leaf protected-instance-list {
            type pub-type:ncs_template_id-range;
            description
              "Protect instance ID of an ERPS ring.";
          }
          leaf wait-restore-timer {
            type string;
            units "min";
            // NCS drop default statement
            description
              "Wait-to-restore time.";
          }
          leaf guard-timer {
            type string;
            units "cs";
            // NCS drop default statement
            description
              "Guard time for blocking received RAPS packets.";
          }
          leaf holdoff-timer {
            type string;
            units "ds";
            // NCS drop default statement
            description
              "Holdoff time.";
          }
          leaf raps-mel {
            type string;
            // NCS drop default statement
            description
              "Maintenance entity group level for ring automatic protection switching.";
          }
          leaf version {
            type ncs_template_erps-version;
            // NCS drop default statement
            description
              "Basic version of an ERPS ring.";
          }
          leaf revertive-enable {
            type string;
            // NCS drop default statement
            description
              "Enable/disable revertive status of an ERPS ring.";
          }
          leaf tc-protection-interval {
            type string;
            units "s";
            // NCS drop default statement
            description
              "Topology change notification interval.";
          }
          leaf tc-protection-threshold {
            type string;
            // NCS drop default statement
            description
              "Topology change notification threshold.";
          }
          container version-v2 {
            // NCS drop when statement
            description
              "Configure the ERPS ring information of version 2.";
            leaf ring-role {
              type ncs_template_erps-ring-mode;
              // NCS drop default statement
              description
                "Role information of an ERPS ring.";
            }
            leaf virtual-channel-enable {
              type string;
              // NCS drop default statement
              description
                "Enable/disable status of a virtual channel.";
            }
            leaf tc-notify-ring {
              type pub-type:ncs_template_id-range;
              description
                "Ring ID for TC notification.";
            }
          }
          container port-attributes {
            description
              "List of ERPS ring port.";
            list port-attribute {
              // NCS patched for predictable order
              ordered-by user;
              key "if-name";
              // NCS drop max-elements statement
              description
                "Configure port information of an ERPS ring.";
              leaf if-name {
                type string;
                // NCS drop must statement
                // NCS drop must statement
                description
                  "Name of an ERPS ring port.";
              }
              leaf port-role {
                type ncs_template_erps-port-role;
                // NCS drop must statement
                // NCS drop default statement
                description
                  "Role of an ERPS ring port.";
              }
              leaf md-name {
                type string;
                description
                  "Name of a maintenance domain.";
              }
              leaf ma-name {
                // NCS drop when statement
                type string;
                // NCS drop mandatory statement
                description
                  "Name of a maintenance association.";
              }
              leaf mep-id {
                // NCS drop when statement
                type string;
                // NCS drop mandatory statement
                description
                  "ID of a MEP.";
              }
              leaf rmep-id {
                // NCS drop when statement
                type string;
                // NCS drop mandatory statement
                description
                  "ID of a remote MEP.";
              }
              leaf vpls-enable {
                type ncs_template_erps-enable-state;
                // NCS drop default statement
                description
                  "Enable/disable VPLS status.";
              }
              leaf bd-enable {
                type ncs_template_erps-enable-state;
                // NCS drop default statement
                description
                  "Enable/disable BD status.";
              }
            }
          }
        }
      }
    }
  }
}
