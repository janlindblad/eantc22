module huawei-bgp-vpnv4mcast {
  // Generated by yanger -t ncs
  tailf:mount-id "huawei-nc-1.0:huawei-nc-1.0";
  tailf:ncs-device-type "netconf";

  yang-version 1;
  namespace "urn:huawei:yang:huawei-bgp-vpnv4mcast";
  prefix bgp-vpnv4mcast;

  import huawei-extension {
    prefix ext;
  }
  import huawei-network-instance {
    prefix ni;
  }
  import huawei-bgp {
    prefix bgp;
  }
  import huawei-xpl {
    prefix xpl;
  }
  import huawei-routing-policy {
    prefix rtp;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Inter-AS routing protocol that exchanges Network Layer Reachability Information (NLRI) with other BGP systems.";

  revision 2020-02-25 {
    description
      "The YANG descriptions are modified according to new standards.";
    reference "Huawei private.";
  }
  revision 2019-03-22 {
    description
      "Initial revision.";
    reference "Huawei private.";
  }
  ext:task-name "bgp";

  augment "/ncs:devices/ncs:template/ncs:ned-id/ncs:config/ni:network-instance/ni:instances/ni:instance/bgp:bgp/bgp:base-process/bgp:afs/bgp:af" {
    description
      "BGP IPv4 vpnv4-multicast address family configuration.";
    container ipv4-vpn-multicast {
      // NCS drop when statement
      description
        "Configure IPv4 vpnv4-multicast address family.";
      container common {
        description
          "Configure BGP IPv4 vpnv4-multicast common options.";
        uses bgp:ncs_template_vpn-target-type;
        uses bgp:ncs_template_reflector-cluster-type;
        leaf reflect-between-client {
          type string;
          // NCS drop default statement
          description
            "Enable/disable route reflection between clients.";
        }
        leaf reflect-change-path {
          type string;
          // NCS drop default statement
          description
            "Enable/disable an RR to use an export policy to change route AS_Path. By default, this function is not enabled.";
        }
      }
      uses bgp:ncs_template_slow-peer-type;
    }
  }
  augment "/ncs:devices/ncs:device/ncs:live-status/ni:network-instance/ni:instances/ni:instance/bgp:bgp/bgp:base-process/bgp:afs/bgp:af" {
    description
      "BGP IPv4 vpnv4-multicast address family configuration.";
    container ipv4-vpn-multicast {
      tailf:ncs-device-type "netconf";
      tailf:display-when "not(../../../../../../../../../ncs:module) or ../../../../../../../../../ncs:module[ncs:name='huawei-bgp-vpnv4mcast'] or (../../../../../../../../../ncs:live-status-protocol[not(ncs:capability)]) or (../../../../../../../../../ncs:live-status-protocol/ncs:capability/ncs:module[.='huawei-bgp-vpnv4mcast'])";
      // NCS drop when statement
      description
        "Configure IPv4 vpnv4-multicast address family.";
      container common {
        description
          "Configure BGP IPv4 vpnv4-multicast common options.";
        uses bgp:live_ncs_vpn-target-type;
        uses bgp:live_ncs_reflector-cluster-type;
        leaf reflect-between-client {
          type boolean;
          // NCS drop default statement
          description
            "Enable/disable route reflection between clients.";
        }
        leaf reflect-change-path {
          type boolean;
          // NCS drop default statement
          description
            "Enable/disable an RR to use an export policy to change route AS_Path. By default, this function is not enabled.";
        }
      }
      uses bgp:live_ncs_slow-peer-type;
    }
  }
  augment "/ncs:devices/ncs:device/ncs:config/ni:network-instance/ni:instances/ni:instance/bgp:bgp/bgp:base-process/bgp:afs/bgp:af" {
    description
      "BGP IPv4 vpnv4-multicast address family configuration.";
    container ipv4-vpn-multicast {
      tailf:ncs-device-type "netconf";
      tailf:display-when "not(../../../../../../../../../ncs:module) or ../../../../../../../../../ncs:module[ncs:name='huawei-bgp-vpnv4mcast']";
      when "../bgp:type='ipv4vpnmcast'" {
        tailf:xpath-root 3;
      }
      description
        "Configure IPv4 vpnv4-multicast address family.";
      container common {
        description
          "Configure BGP IPv4 vpnv4-multicast common options.";
        uses bgp:vpn-target-type;
        uses bgp:reflector-cluster-type;
        leaf reflect-between-client {
          type boolean;
          default "true";
          description
            "Enable/disable route reflection between clients.";
        }
        leaf reflect-change-path {
          type boolean;
          default "false";
          description
            "Enable/disable an RR to use an export policy to change route AS_Path. By default, this function is not enabled.";
        }
      }
      uses bgp:slow-peer-type;
    }
  }
  augment "/ncs:devices/ncs:template/ncs:ned-id/ncs:config/ni:network-instance/ni:instances/ni:instance/bgp:bgp/bgp:base-process/bgp:peer-groups/bgp:peer-group/bgp:afs/bgp:af" {
    description
      "BGP IPv4 vpnv4-multicast address family configuration.";
    container ipv4-vpn-multicast {
      // NCS drop when statement
      description
        "Configure BGP IPv4 vpnv4-multicast options.";
      uses bgp:ncs_template_rt-update-interval-type;
      uses bgp:ncs_template_advertise-large-community-group-type;
      uses bgp:ncs_template_advertise-community-type;
      uses bgp:ncs_template_group-independent-peer-group-type;
      leaf reflect-client {
        // NCS drop when statement
        type string;
        // NCS drop default statement
        description
          "Enable/disable the local device as a route reflector (RR) and a peer or peer group as its client. This configuration is applicable between IBGP peers only. The configurations of RRs and its clients in an address family are valid only in this address family. Therefore, it is recommended to configure RRs and its clients in the specified address family that is required.";
      }
      choice import-policy-type {
        description
          "Set route policy or filter.";
        case rtp-ref {
          description
            "Route policy.";
          leaf import-policy {
            type string;
            description
              "Specify the filtering policy applied to the routes learned from a peer. By default, no such policy is specified.";
          }
        }
        case xpl-ref {
          description
            "Route filter.";
          container import-filter {
            description
              "Configure an import route-filter to filter the routes received from peers. By default, no route-filter is specified to filter the routes imported from peers.";
            leaf name {
              type string;
              description
                "Specify an import route-filter name.";
            }
            leaf parameter {
              // NCS drop when statement
              type xpl:ncs_template_filter-parameter-type;
              description
                "Specify an import route-filter parameter.";
            }
          }
        }
      }
      choice export-policy-type {
        description
          "Set route policy or filter.";
        case rtp-ref {
          description
            "Route policy.";
          leaf export-policy {
            type string;
            description
              "Specify the filtering policy applied to the routes to be advertised to a peer. By default, no such policy is specified.";
          }
        }
        case xpl-ref {
          description
            "Route filter.";
          container export-filter {
            description
              "Configure an export route-filter to filter the routes to be advertised to peers. By default, no route-filter is specified to filter the routes to be advertised to peers.";
            leaf name {
              type string;
              description
                "Specify an export route-filter name.";
            }
            leaf parameter {
              // NCS drop when statement
              type xpl:ncs_template_filter-parameter-type;
              description
                "Specify an export route-filter parameter.";
            }
          }
        }
      }
      leaf update-packet-standard-compatible {
        type string;
        // NCS drop default statement
        description
          "Enable/disable compatible standard update packet.";
      }
      uses bgp:ncs_template_route-limit-type;
    }
  }
  augment "/ncs:devices/ncs:device/ncs:live-status/ni:network-instance/ni:instances/ni:instance/bgp:bgp/bgp:base-process/bgp:peer-groups/bgp:peer-group/bgp:afs/bgp:af" {
    description
      "BGP IPv4 vpnv4-multicast address family configuration.";
    container ipv4-vpn-multicast {
      tailf:ncs-device-type "netconf";
      tailf:display-when "not(../../../../../../../../../../../ncs:module) or ../../../../../../../../../../../ncs:module[ncs:name='huawei-bgp-vpnv4mcast'] or (../../../../../../../../../../../ncs:live-status-protocol[not(ncs:capability)]) or (../../../../../../../../../../../ncs:live-status-protocol/ncs:capability/ncs:module[.='huawei-bgp-vpnv4mcast'])";
      // NCS drop when statement
      description
        "Configure BGP IPv4 vpnv4-multicast options.";
      uses bgp:live_ncs_rt-update-interval-type;
      uses bgp:live_ncs_advertise-large-community-group-type;
      uses bgp:live_ncs_advertise-community-type;
      uses bgp:live_ncs_group-independent-peer-group-type;
      leaf reflect-client {
        // NCS drop when statement
        type boolean;
        // NCS drop default statement
        description
          "Enable/disable the local device as a route reflector (RR) and a peer or peer group as its client. This configuration is applicable between IBGP peers only. The configurations of RRs and its clients in an address family are valid only in this address family. Therefore, it is recommended to configure RRs and its clients in the specified address family that is required.";
      }
      choice import-policy-type {
        description
          "Set route policy or filter.";
        case rtp-ref {
          description
            "Route policy.";
          leaf import-policy {
            type leafref {
              path "/ncs:devices/ncs:device/ncs:live-status/rtp:routing-policy/rtp:policy-definitions/rtp:policy-definition/rtp:name" {
                tailf:xpath-root 3;
              }
            }
            description
              "Specify the filtering policy applied to the routes learned from a peer. By default, no such policy is specified.";
          }
        }
        case xpl-ref {
          description
            "Route filter.";
          container import-filter {
            description
              "Configure an import route-filter to filter the routes received from peers. By default, no route-filter is specified to filter the routes imported from peers.";
            leaf name {
              type leafref {
                path "/ncs:devices/ncs:device/ncs:live-status/xpl:xpl/xpl:route-filters/xpl:route-filter/xpl:name" {
                  tailf:xpath-root 3;
                }
              }
              description
                "Specify an import route-filter name.";
            }
            leaf parameter {
              // NCS drop when statement
              type xpl:live_ncs_filter-parameter-type;
              description
                "Specify an import route-filter parameter.";
            }
          }
        }
      }
      choice export-policy-type {
        description
          "Set route policy or filter.";
        case rtp-ref {
          description
            "Route policy.";
          leaf export-policy {
            type leafref {
              path "/ncs:devices/ncs:device/ncs:live-status/rtp:routing-policy/rtp:policy-definitions/rtp:policy-definition/rtp:name" {
                tailf:xpath-root 3;
              }
            }
            description
              "Specify the filtering policy applied to the routes to be advertised to a peer. By default, no such policy is specified.";
          }
        }
        case xpl-ref {
          description
            "Route filter.";
          container export-filter {
            description
              "Configure an export route-filter to filter the routes to be advertised to peers. By default, no route-filter is specified to filter the routes to be advertised to peers.";
            leaf name {
              type leafref {
                path "/ncs:devices/ncs:device/ncs:live-status/xpl:xpl/xpl:route-filters/xpl:route-filter/xpl:name" {
                  tailf:xpath-root 3;
                }
              }
              description
                "Specify an export route-filter name.";
            }
            leaf parameter {
              // NCS drop when statement
              type xpl:live_ncs_filter-parameter-type;
              description
                "Specify an export route-filter parameter.";
            }
          }
        }
      }
      leaf update-packet-standard-compatible {
        type boolean;
        // NCS drop default statement
        description
          "Enable/disable compatible standard update packet.";
      }
      uses bgp:live_ncs_route-limit-type;
    }
  }
  augment "/ncs:devices/ncs:device/ncs:config/ni:network-instance/ni:instances/ni:instance/bgp:bgp/bgp:base-process/bgp:peer-groups/bgp:peer-group/bgp:afs/bgp:af" {
    description
      "BGP IPv4 vpnv4-multicast address family configuration.";
    container ipv4-vpn-multicast {
      tailf:ncs-device-type "netconf";
      tailf:display-when "not(../../../../../../../../../../../ncs:module) or ../../../../../../../../../../../ncs:module[ncs:name='huawei-bgp-vpnv4mcast']";
      when "../bgp:type='ipv4vpnmcast'" {
        tailf:xpath-root 3;
      }
      description
        "Configure BGP IPv4 vpnv4-multicast options.";
      uses bgp:rt-update-interval-type;
      uses bgp:advertise-large-community-group-type;
      uses bgp:advertise-community-type;
      uses bgp:group-independent-peer-group-type;
      leaf reflect-client {
        when "../../../../bgp:type='ibgp'" {
          tailf:xpath-root 3;
        }
        type boolean;
        default "false";
        description
          "Enable/disable the local device as a route reflector (RR) and a peer or peer group as its client. This configuration is applicable between IBGP peers only. The configurations of RRs and its clients in an address family are valid only in this address family. Therefore, it is recommended to configure RRs and its clients in the specified address family that is required.";
      }
      choice import-policy-type {
        description
          "Set route policy or filter.";
        case rtp-ref {
          description
            "Route policy.";
          leaf import-policy {
            type leafref {
              path "/ncs:devices/ncs:device/ncs:config/rtp:routing-policy/rtp:policy-definitions/rtp:policy-definition/rtp:name" {
                tailf:xpath-root 3;
              }
            }
            description
              "Specify the filtering policy applied to the routes learned from a peer. By default, no such policy is specified.";
          }
        }
        case xpl-ref {
          description
            "Route filter.";
          container import-filter {
            description
              "Configure an import route-filter to filter the routes received from peers. By default, no route-filter is specified to filter the routes imported from peers.";
            leaf name {
              type leafref {
                path "/ncs:devices/ncs:device/ncs:config/xpl:xpl/xpl:route-filters/xpl:route-filter/xpl:name" {
                  tailf:xpath-root 3;
                }
              }
              description
                "Specify an import route-filter name.";
            }
            leaf parameter {
              when '../name' {
                tailf:xpath-root 3;
              }
              type xpl:filter-parameter-type;
              description
                "Specify an import route-filter parameter.";
            }
          }
        }
      }
      choice export-policy-type {
        description
          "Set route policy or filter.";
        case rtp-ref {
          description
            "Route policy.";
          leaf export-policy {
            type leafref {
              path "/ncs:devices/ncs:device/ncs:config/rtp:routing-policy/rtp:policy-definitions/rtp:policy-definition/rtp:name" {
                tailf:xpath-root 3;
              }
            }
            description
              "Specify the filtering policy applied to the routes to be advertised to a peer. By default, no such policy is specified.";
          }
        }
        case xpl-ref {
          description
            "Route filter.";
          container export-filter {
            description
              "Configure an export route-filter to filter the routes to be advertised to peers. By default, no route-filter is specified to filter the routes to be advertised to peers.";
            leaf name {
              type leafref {
                path "/ncs:devices/ncs:device/ncs:config/xpl:xpl/xpl:route-filters/xpl:route-filter/xpl:name" {
                  tailf:xpath-root 3;
                }
              }
              description
                "Specify an export route-filter name.";
            }
            leaf parameter {
              when '../name' {
                tailf:xpath-root 3;
              }
              type xpl:filter-parameter-type;
              description
                "Specify an export route-filter parameter.";
            }
          }
        }
      }
      leaf update-packet-standard-compatible {
        type boolean;
        default "false";
        description
          "Enable/disable compatible standard update packet.";
      }
      uses bgp:route-limit-type;
    }
  }
  augment "/ncs:devices/ncs:template/ncs:ned-id/ncs:config/ni:network-instance/ni:instances/ni:instance/bgp:bgp/bgp:base-process/bgp:peers/bgp:peer/bgp:afs/bgp:af" {
    description
      "BGP IPv4 vpnv4-multicast address family configuration.";
    container ipv4-vpn-multicast {
      // NCS drop when statement
      description
        "Configure IPv4 vpnv4-multicast options.";
      leaf group-name {
        type string;
        // NCS drop must statement
        // NCS drop must statement
        description
          "Configure a name for a peer group. After a peer is deleted from the peer group, the peer is disabled from the address family. The object cannot be modified.";
        ext:operation-exclude "update" {
          description
            "The node cannot be modified, when the peer already belongs to a peer-group.";
        }
      }
      uses bgp:ncs_template_rt-update-interval-type;
      uses bgp:ncs_template_advertise-large-community-type;
      uses bgp:ncs_template_advertise-community-type;
      uses bgp:ncs_template_peer-independent-peer-group-type;
      leaf reflect-client {
        type string;
        // NCS drop default statement
        description
          "Enable/disable the local device as a route reflector (RR) and a peer or peer group as its client. This configuration is applicable between IBGP peers only. The configurations of RRs and its clients in an address family are valid only in this address family. Therefore, it is recommended to configure RRs and its clients in the specified address family that is required.";
      }
      choice import-policy-type {
        description
          "Set route policy or filter.";
        case rtp-ref {
          description
            "Route policy.";
          leaf import-policy {
            type string;
            description
              "Specify the filtering policy applied to the routes learned from a peer. By default, no such policy is specified.";
          }
        }
        case xpl-ref {
          description
            "Route filter.";
          container import-filter {
            description
              "Configure an import route-filter to filter the routes received from peers. By default, no route-filter is specified to filter the routes imported from peers.";
            leaf name {
              type string;
              description
                "Specify an import route-filter name.";
            }
            leaf parameter {
              // NCS drop when statement
              type xpl:ncs_template_filter-parameter-type;
              description
                "Specify an import route-filter parameter.";
            }
          }
        }
      }
      choice export-policy-type {
        description
          "Set route policy or filter.";
        case rtp-ref {
          description
            "Route policy.";
          leaf export-policy {
            type string;
            description
              "Specify the filtering policy applied to the routes to be advertised to a peer. By default, no such policy is specified.";
          }
        }
        case xpl-ref {
          description
            "Route filter.";
          container export-filter {
            description
              "Configure an export route-filter to filter the routes to be advertised to peers. By default, no route-filter is specified to filter the routes to be advertised to peers.";
            leaf name {
              type string;
              description
                "Specify an export route-filter name.";
            }
            leaf parameter {
              // NCS drop when statement
              type xpl:ncs_template_filter-parameter-type;
              description
                "Specify an export route-filter parameter.";
            }
          }
        }
      }
      leaf update-packet-standard-compatible {
        type string;
        // NCS drop default statement
        description
          "Enable/disable compatible standard update packet.";
      }
      uses bgp:ncs_template_route-limit-type;
      uses bgp:ncs_template_path-attr-map-type;
    }
  }
  augment "/ncs:devices/ncs:device/ncs:live-status/ni:network-instance/ni:instances/ni:instance/bgp:bgp/bgp:base-process/bgp:peers/bgp:peer/bgp:afs/bgp:af" {
    description
      "BGP IPv4 vpnv4-multicast address family configuration.";
    container ipv4-vpn-multicast {
      tailf:ncs-device-type "netconf";
      tailf:display-when "not(../../../../../../../../../../../ncs:module) or ../../../../../../../../../../../ncs:module[ncs:name='huawei-bgp-vpnv4mcast'] or (../../../../../../../../../../../ncs:live-status-protocol[not(ncs:capability)]) or (../../../../../../../../../../../ncs:live-status-protocol/ncs:capability/ncs:module[.='huawei-bgp-vpnv4mcast'])";
      // NCS drop when statement
      description
        "Configure IPv4 vpnv4-multicast options.";
      leaf group-name {
        type leafref {
          path "../../../../../../bgp:peer-groups/bgp:peer-group/bgp:name";
        }
        // NCS drop must statement
        // NCS drop must statement
        description
          "Configure a name for a peer group. After a peer is deleted from the peer group, the peer is disabled from the address family. The object cannot be modified.";
        ext:operation-exclude "update" {
          description
            "The node cannot be modified, when the peer already belongs to a peer-group.";
        }
      }
      uses bgp:live_ncs_rt-update-interval-type;
      uses bgp:live_ncs_advertise-large-community-type;
      uses bgp:live_ncs_advertise-community-type;
      uses bgp:live_ncs_peer-independent-peer-group-type;
      leaf reflect-client {
        type boolean;
        // NCS drop default statement
        description
          "Enable/disable the local device as a route reflector (RR) and a peer or peer group as its client. This configuration is applicable between IBGP peers only. The configurations of RRs and its clients in an address family are valid only in this address family. Therefore, it is recommended to configure RRs and its clients in the specified address family that is required.";
      }
      choice import-policy-type {
        description
          "Set route policy or filter.";
        case rtp-ref {
          description
            "Route policy.";
          leaf import-policy {
            type leafref {
              path "/ncs:devices/ncs:device/ncs:live-status/rtp:routing-policy/rtp:policy-definitions/rtp:policy-definition/rtp:name" {
                tailf:xpath-root 3;
              }
            }
            description
              "Specify the filtering policy applied to the routes learned from a peer. By default, no such policy is specified.";
          }
        }
        case xpl-ref {
          description
            "Route filter.";
          container import-filter {
            description
              "Configure an import route-filter to filter the routes received from peers. By default, no route-filter is specified to filter the routes imported from peers.";
            leaf name {
              type leafref {
                path "/ncs:devices/ncs:device/ncs:live-status/xpl:xpl/xpl:route-filters/xpl:route-filter/xpl:name" {
                  tailf:xpath-root 3;
                }
              }
              description
                "Specify an import route-filter name.";
            }
            leaf parameter {
              // NCS drop when statement
              type xpl:live_ncs_filter-parameter-type;
              description
                "Specify an import route-filter parameter.";
            }
          }
        }
      }
      choice export-policy-type {
        description
          "Set route policy or filter.";
        case rtp-ref {
          description
            "Route policy.";
          leaf export-policy {
            type leafref {
              path "/ncs:devices/ncs:device/ncs:live-status/rtp:routing-policy/rtp:policy-definitions/rtp:policy-definition/rtp:name" {
                tailf:xpath-root 3;
              }
            }
            description
              "Specify the filtering policy applied to the routes to be advertised to a peer. By default, no such policy is specified.";
          }
        }
        case xpl-ref {
          description
            "Route filter.";
          container export-filter {
            description
              "Configure an export route-filter to filter the routes to be advertised to peers. By default, no route-filter is specified to filter the routes to be advertised to peers.";
            leaf name {
              type leafref {
                path "/ncs:devices/ncs:device/ncs:live-status/xpl:xpl/xpl:route-filters/xpl:route-filter/xpl:name" {
                  tailf:xpath-root 3;
                }
              }
              description
                "Specify an export route-filter name.";
            }
            leaf parameter {
              // NCS drop when statement
              type xpl:live_ncs_filter-parameter-type;
              description
                "Specify an export route-filter parameter.";
            }
          }
        }
      }
      leaf update-packet-standard-compatible {
        type boolean;
        // NCS drop default statement
        description
          "Enable/disable compatible standard update packet.";
      }
      uses bgp:live_ncs_route-limit-type;
      uses bgp:live_ncs_path-attr-map-type;
    }
  }
  augment "/ncs:devices/ncs:device/ncs:config/ni:network-instance/ni:instances/ni:instance/bgp:bgp/bgp:base-process/bgp:peers/bgp:peer/bgp:afs/bgp:af" {
    description
      "BGP IPv4 vpnv4-multicast address family configuration.";
    container ipv4-vpn-multicast {
      tailf:ncs-device-type "netconf";
      tailf:display-when "not(../../../../../../../../../../../ncs:module) or ../../../../../../../../../../../ncs:module[ncs:name='huawei-bgp-vpnv4mcast']";
      when "../bgp:type = 'ipv4vpnmcast'" {
        tailf:xpath-root 3;
      }
      description
        "Configure IPv4 vpnv4-multicast options.";
      leaf group-name {
        type leafref {
          path "../../../../../../bgp:peer-groups/bgp:peer-group/bgp:name";
        }
        must "../../../../../../bgp:peer-groups/bgp:peer-group[bgp:name = current()]/bgp:afs/bgp:af[bgp:type='ipv4vpnmcast']" {
          tailf:xpath-root 3;
        }
        must "../../../../../../bgp:peer-groups/bgp:peer-group[bgp:name = current()]/bgp:peer-establish-mode = 'static'" {
          tailf:xpath-root 3;
        }
        description
          "Configure a name for a peer group. After a peer is deleted from the peer group, the peer is disabled from the address family. The object cannot be modified.";
        ext:operation-exclude "update" {
          description
            "The node cannot be modified, when the peer already belongs to a peer-group.";
        }
      }
      uses bgp:rt-update-interval-type;
      uses bgp:advertise-large-community-type;
      uses bgp:advertise-community-type;
      uses bgp:peer-independent-peer-group-type;
      leaf reflect-client {
        type boolean;
        default "false";
        description
          "Enable/disable the local device as a route reflector (RR) and a peer or peer group as its client. This configuration is applicable between IBGP peers only. The configurations of RRs and its clients in an address family are valid only in this address family. Therefore, it is recommended to configure RRs and its clients in the specified address family that is required.";
      }
      choice import-policy-type {
        description
          "Set route policy or filter.";
        case rtp-ref {
          description
            "Route policy.";
          leaf import-policy {
            type leafref {
              path "/ncs:devices/ncs:device/ncs:config/rtp:routing-policy/rtp:policy-definitions/rtp:policy-definition/rtp:name" {
                tailf:xpath-root 3;
              }
            }
            description
              "Specify the filtering policy applied to the routes learned from a peer. By default, no such policy is specified.";
          }
        }
        case xpl-ref {
          description
            "Route filter.";
          container import-filter {
            description
              "Configure an import route-filter to filter the routes received from peers. By default, no route-filter is specified to filter the routes imported from peers.";
            leaf name {
              type leafref {
                path "/ncs:devices/ncs:device/ncs:config/xpl:xpl/xpl:route-filters/xpl:route-filter/xpl:name" {
                  tailf:xpath-root 3;
                }
              }
              description
                "Specify an import route-filter name.";
            }
            leaf parameter {
              when '../name' {
                tailf:xpath-root 3;
              }
              type xpl:filter-parameter-type;
              description
                "Specify an import route-filter parameter.";
            }
          }
        }
      }
      choice export-policy-type {
        description
          "Set route policy or filter.";
        case rtp-ref {
          description
            "Route policy.";
          leaf export-policy {
            type leafref {
              path "/ncs:devices/ncs:device/ncs:config/rtp:routing-policy/rtp:policy-definitions/rtp:policy-definition/rtp:name" {
                tailf:xpath-root 3;
              }
            }
            description
              "Specify the filtering policy applied to the routes to be advertised to a peer. By default, no such policy is specified.";
          }
        }
        case xpl-ref {
          description
            "Route filter.";
          container export-filter {
            description
              "Configure an export route-filter to filter the routes to be advertised to peers. By default, no route-filter is specified to filter the routes to be advertised to peers.";
            leaf name {
              type leafref {
                path "/ncs:devices/ncs:device/ncs:config/xpl:xpl/xpl:route-filters/xpl:route-filter/xpl:name" {
                  tailf:xpath-root 3;
                }
              }
              description
                "Specify an export route-filter name.";
            }
            leaf parameter {
              when '../name' {
                tailf:xpath-root 3;
              }
              type xpl:filter-parameter-type;
              description
                "Specify an export route-filter parameter.";
            }
          }
        }
      }
      leaf update-packet-standard-compatible {
        type boolean;
        default "false";
        description
          "Enable/disable compatible standard update packet.";
      }
      uses bgp:route-limit-type;
      uses bgp:path-attr-map-type;
    }
  }
}
