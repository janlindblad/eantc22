module huawei-mstp {
  // Generated by yanger -t ncs
  tailf:mount-id "huawei-nc-1.0:huawei-nc-1.0";
  tailf:ncs-device-type "netconf";

  namespace "urn:huawei:yang:huawei-mstp";
  prefix mstp;

  import huawei-ifm {
    prefix ifm;
  }
  import huawei-vlan {
    prefix vlan;
  }
  import huawei-ethernet {
    prefix ethernet;
  }
  import huawei-l2vpn {
    prefix l2vpn;
  }
  import huawei-pub-type {
    prefix pub-type;
  }
  import ietf-yang-types {
    prefix yang;
  }
  import huawei-extension {
    prefix ext;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Multiple spanning tree protocol.";

  revision 2019-04-23 {
    description
      "Initial revision.";
    reference "Huawei private.";
  }
  ext:task-name "mstp";

  typedef ncs_template_bpdu-filter-type {
    type string;
    description
      "BPDU filter type.";
  }

  typedef ncs_template_compliance-type {
    type string;
    description
      "MSTP BPDU format type.";
  }

  typedef ncs_template_edge-port-type {
    type string;
    description
      "Edge port type.";
  }

  typedef ncs_template_stp-mode {
    type string;
    description
      "STP mode.";
  }

  typedef ncs_template_path-cost-standard-type {
    type string;
    description
      "Path Cost Standard.";
  }

  typedef ncs_template_point-to-point-type {
    type string;
    description
      "The link type of a port.";
  }

  typedef ncs_template_port-state-type {
    type string;
    description
      "The type of STP port state.";
  }

  typedef ncs_template_protection-type {
    type string;
    description
      "STP protection type.";
  }

  typedef ncs_template_port-role-type {
    type string;
    description
      "STP port role.";
  }

  typedef ncs_template_root-type {
    type string;
    description
      "STP root type.";
  }

  typedef ncs_template_converge-mode {
    type string;
    description
      "MSTP converge mode.";
  }

  typedef ncs_rpc_notif_bpdu-filter-type {
    type enumeration {
      enum "disable" {
        value 1;
        description
          "Disable the BPDU filter function.";
      }
      enum "enable" {
        value 2;
        description
          "Enable the BPDU filter function.";
      }
      enum "default" {
        value 3;
        description
          "The default BPDU filter function.";
      }
    }
    description
      "BPDU filter type.";
  }

  typedef ncs_rpc_notif_compliance-type {
    type enumeration {
      enum "auto" {
        value 1;
        description
          "Indicates that the MST BPDU format is self-adaptive.";
      }
      enum "dot1s" {
        value 2;
        description
          "Indicates that the MST BPDU format is standard IEEE 802.1s.";
      }
      enum "legacy" {
        value 3;
        description
          "Indicates that the MST BPDU format is proprietary.";
      }
    }
    description
      "MSTP BPDU format type.";
  }

  typedef ncs_rpc_notif_edge-port-type {
    type enumeration {
      enum "disable" {
        value 1;
        description
          "Set a port as a non-edge port.";
      }
      enum "enable" {
        value 2;
        description
          "Set a port as an edge port.";
      }
      enum "default" {
        value 3;
        description
          "Default port.";
      }
    }
    description
      "Edge port type.";
  }

  typedef ncs_rpc_notif_stp-mode {
    type enumeration {
      enum "stp" {
        value 0;
        description
          "Spanning tree protocol mode.";
      }
      enum "rstp" {
        value 2;
        description
          "Rapid spanning tree protocol mode.";
      }
      enum "mstp" {
        value 3;
        description
          "Multiple ppanning tree protocol mode.";
      }
      enum "vbst" {
        value 4;
        description
          "VLAN-Based spanning tree protocol mode.";
      }
    }
    description
      "STP mode.";
  }

  typedef ncs_rpc_notif_path-cost-standard-type {
    type enumeration {
      enum "dot1d-1998" {
        value 1;
        description
          "IEEE 802.1D standard used to calculate the path cost.";
      }
      enum "dot1t" {
        value 2;
        description
          "IEEE 802.1T standard used to calculate the path cost.";
      }
      enum "legacy" {
        value 3;
        description
          "Huawei legacy standard used to calculate the path cost.";
      }
    }
    description
      "Path Cost Standard.";
  }

  typedef ncs_rpc_notif_point-to-point-type {
    type enumeration {
      enum "force-true" {
        value 1;
        description
          "The link type is a point to point link.";
      }
      enum "force-false" {
        value 2;
        description
          "The link type is not a point to point link.";
      }
      enum "auto" {
        value 3;
        description
          "The spanning tree protocol detects automatically whether the port is connected to a point to point link.";
      }
    }
    description
      "The link type of a port.";
  }

  typedef ncs_rpc_notif_port-state-type {
    type enumeration {
      enum "down" {
        value 1;
        description
          "Down status.";
      }
      enum "disabled" {
        value 2;
        description
          "Disabled status.";
      }
      enum "forwarding" {
        value 3;
        description
          "Forwarding status.";
      }
      enum "learning" {
        value 4;
        description
          "Learning status.";
      }
      enum "discarding" {
        value 5;
        description
          "Discarding status.";
      }
      enum "inactive" {
        value 6;
        description
          "Inactive status.";
      }
    }
    description
      "The type of STP port state.";
  }

  typedef ncs_rpc_notif_protection-type {
    type enumeration {
      enum "none" {
        value 1;
        description
          "No protection.";
      }
      enum "loopback" {
        value 2;
        description
          "Loopback detection.";
      }
      enum "bpdu-root" {
        value 3;
        description
          "BPDU and root protection.";
      }
      enum "root" {
        value 4;
        description
          "Root protection.";
      }
      enum "bpdu" {
        value 5;
        description
          "BPDU protection.";
      }
      enum "loop" {
        value 6;
        description
          "Loop protection.";
      }
    }
    description
      "STP protection type.";
  }

  typedef ncs_rpc_notif_port-role-type {
    type enumeration {
      enum "disabled" {
        value 1;
        description
          "Inactive port.";
      }
      enum "alternate" {
        value 2;
        description
          "Alternate port.";
      }
      enum "backup" {
        value 3;
        description
          "Backup port.";
      }
      enum "root" {
        value 4;
        description
          "Root port.";
      }
      enum "designated" {
        value 5;
        description
          "Designated port.";
      }
      enum "master" {
        value 6;
        description
          "Master Port.";
      }
    }
    description
      "STP port role.";
  }

  typedef ncs_rpc_notif_root-type {
    type enumeration {
      enum "normal" {
        value 1;
        description
          "Configure a device as a normal root bridge of a spanning tree.";
      }
      enum "primary" {
        value 2;
        description
          "Configure a device as a primary root bridge of a spanning tree.";
      }
      enum "secondary" {
        value 3;
        description
          "Configure a device as a secondary root bridge of a spanning tree.";
      }
    }
    description
      "STP root type.";
  }

  typedef ncs_rpc_notif_converge-mode {
    type enumeration {
      enum "fast" {
        value 1;
        description
          "Set MSTP aging mode to fast.";
      }
      enum "normal" {
        value 2;
        description
          "Set MSTP aging mode to normal.";
      }
    }
    description
      "MSTP converge mode.";
  }

  typedef live_ncs_bpdu-filter-type {
    type enumeration {
      enum "disable" {
        value 1;
        description
          "Disable the BPDU filter function.";
      }
      enum "enable" {
        value 2;
        description
          "Enable the BPDU filter function.";
      }
      enum "default" {
        value 3;
        description
          "The default BPDU filter function.";
      }
    }
    description
      "BPDU filter type.";
  }

  typedef live_ncs_compliance-type {
    type enumeration {
      enum "auto" {
        value 1;
        description
          "Indicates that the MST BPDU format is self-adaptive.";
      }
      enum "dot1s" {
        value 2;
        description
          "Indicates that the MST BPDU format is standard IEEE 802.1s.";
      }
      enum "legacy" {
        value 3;
        description
          "Indicates that the MST BPDU format is proprietary.";
      }
    }
    description
      "MSTP BPDU format type.";
  }

  typedef live_ncs_edge-port-type {
    type enumeration {
      enum "disable" {
        value 1;
        description
          "Set a port as a non-edge port.";
      }
      enum "enable" {
        value 2;
        description
          "Set a port as an edge port.";
      }
      enum "default" {
        value 3;
        description
          "Default port.";
      }
    }
    description
      "Edge port type.";
  }

  typedef live_ncs_stp-mode {
    type enumeration {
      enum "stp" {
        value 0;
        description
          "Spanning tree protocol mode.";
      }
      enum "rstp" {
        value 2;
        description
          "Rapid spanning tree protocol mode.";
      }
      enum "mstp" {
        value 3;
        description
          "Multiple ppanning tree protocol mode.";
      }
      enum "vbst" {
        value 4;
        description
          "VLAN-Based spanning tree protocol mode.";
      }
    }
    description
      "STP mode.";
  }

  typedef live_ncs_path-cost-standard-type {
    type enumeration {
      enum "dot1d-1998" {
        value 1;
        description
          "IEEE 802.1D standard used to calculate the path cost.";
      }
      enum "dot1t" {
        value 2;
        description
          "IEEE 802.1T standard used to calculate the path cost.";
      }
      enum "legacy" {
        value 3;
        description
          "Huawei legacy standard used to calculate the path cost.";
      }
    }
    description
      "Path Cost Standard.";
  }

  typedef live_ncs_point-to-point-type {
    type enumeration {
      enum "force-true" {
        value 1;
        description
          "The link type is a point to point link.";
      }
      enum "force-false" {
        value 2;
        description
          "The link type is not a point to point link.";
      }
      enum "auto" {
        value 3;
        description
          "The spanning tree protocol detects automatically whether the port is connected to a point to point link.";
      }
    }
    description
      "The link type of a port.";
  }

  typedef live_ncs_port-state-type {
    type enumeration {
      enum "down" {
        value 1;
        description
          "Down status.";
      }
      enum "disabled" {
        value 2;
        description
          "Disabled status.";
      }
      enum "forwarding" {
        value 3;
        description
          "Forwarding status.";
      }
      enum "learning" {
        value 4;
        description
          "Learning status.";
      }
      enum "discarding" {
        value 5;
        description
          "Discarding status.";
      }
      enum "inactive" {
        value 6;
        description
          "Inactive status.";
      }
    }
    description
      "The type of STP port state.";
  }

  typedef live_ncs_protection-type {
    type enumeration {
      enum "none" {
        value 1;
        description
          "No protection.";
      }
      enum "loopback" {
        value 2;
        description
          "Loopback detection.";
      }
      enum "bpdu-root" {
        value 3;
        description
          "BPDU and root protection.";
      }
      enum "root" {
        value 4;
        description
          "Root protection.";
      }
      enum "bpdu" {
        value 5;
        description
          "BPDU protection.";
      }
      enum "loop" {
        value 6;
        description
          "Loop protection.";
      }
    }
    description
      "STP protection type.";
  }

  typedef live_ncs_port-role-type {
    type enumeration {
      enum "disabled" {
        value 1;
        description
          "Inactive port.";
      }
      enum "alternate" {
        value 2;
        description
          "Alternate port.";
      }
      enum "backup" {
        value 3;
        description
          "Backup port.";
      }
      enum "root" {
        value 4;
        description
          "Root port.";
      }
      enum "designated" {
        value 5;
        description
          "Designated port.";
      }
      enum "master" {
        value 6;
        description
          "Master Port.";
      }
    }
    description
      "STP port role.";
  }

  typedef live_ncs_root-type {
    type enumeration {
      enum "normal" {
        value 1;
        description
          "Configure a device as a normal root bridge of a spanning tree.";
      }
      enum "primary" {
        value 2;
        description
          "Configure a device as a primary root bridge of a spanning tree.";
      }
      enum "secondary" {
        value 3;
        description
          "Configure a device as a secondary root bridge of a spanning tree.";
      }
    }
    description
      "STP root type.";
  }

  typedef live_ncs_converge-mode {
    type enumeration {
      enum "fast" {
        value 1;
        description
          "Set MSTP aging mode to fast.";
      }
      enum "normal" {
        value 2;
        description
          "Set MSTP aging mode to normal.";
      }
    }
    description
      "MSTP converge mode.";
  }

  typedef bpdu-filter-type {
    type enumeration {
      enum "disable" {
        value 1;
        description
          "Disable the BPDU filter function.";
      }
      enum "enable" {
        value 2;
        description
          "Enable the BPDU filter function.";
      }
      enum "default" {
        value 3;
        description
          "The default BPDU filter function.";
      }
    }
    description
      "BPDU filter type.";
  }

  typedef compliance-type {
    type enumeration {
      enum "auto" {
        value 1;
        description
          "Indicates that the MST BPDU format is self-adaptive.";
      }
      enum "dot1s" {
        value 2;
        description
          "Indicates that the MST BPDU format is standard IEEE 802.1s.";
      }
      enum "legacy" {
        value 3;
        description
          "Indicates that the MST BPDU format is proprietary.";
      }
    }
    description
      "MSTP BPDU format type.";
  }

  typedef edge-port-type {
    type enumeration {
      enum "disable" {
        value 1;
        description
          "Set a port as a non-edge port.";
      }
      enum "enable" {
        value 2;
        description
          "Set a port as an edge port.";
      }
      enum "default" {
        value 3;
        description
          "Default port.";
      }
    }
    description
      "Edge port type.";
  }

  typedef stp-mode {
    type enumeration {
      enum "stp" {
        value 0;
        description
          "Spanning tree protocol mode.";
      }
      enum "rstp" {
        value 2;
        description
          "Rapid spanning tree protocol mode.";
      }
      enum "mstp" {
        value 3;
        description
          "Multiple ppanning tree protocol mode.";
      }
      enum "vbst" {
        value 4;
        description
          "VLAN-Based spanning tree protocol mode.";
      }
    }
    description
      "STP mode.";
  }

  typedef path-cost-standard-type {
    type enumeration {
      enum "dot1d-1998" {
        value 1;
        description
          "IEEE 802.1D standard used to calculate the path cost.";
      }
      enum "dot1t" {
        value 2;
        description
          "IEEE 802.1T standard used to calculate the path cost.";
      }
      enum "legacy" {
        value 3;
        description
          "Huawei legacy standard used to calculate the path cost.";
      }
    }
    description
      "Path Cost Standard.";
  }

  typedef point-to-point-type {
    type enumeration {
      enum "force-true" {
        value 1;
        description
          "The link type is a point to point link.";
      }
      enum "force-false" {
        value 2;
        description
          "The link type is not a point to point link.";
      }
      enum "auto" {
        value 3;
        description
          "The spanning tree protocol detects automatically whether the port is connected to a point to point link.";
      }
    }
    description
      "The link type of a port.";
  }

  typedef port-state-type {
    type enumeration {
      enum "down" {
        value 1;
        description
          "Down status.";
      }
      enum "disabled" {
        value 2;
        description
          "Disabled status.";
      }
      enum "forwarding" {
        value 3;
        description
          "Forwarding status.";
      }
      enum "learning" {
        value 4;
        description
          "Learning status.";
      }
      enum "discarding" {
        value 5;
        description
          "Discarding status.";
      }
      enum "inactive" {
        value 6;
        description
          "Inactive status.";
      }
    }
    description
      "The type of STP port state.";
  }

  typedef protection-type {
    type enumeration {
      enum "none" {
        value 1;
        description
          "No protection.";
      }
      enum "loopback" {
        value 2;
        description
          "Loopback detection.";
      }
      enum "bpdu-root" {
        value 3;
        description
          "BPDU and root protection.";
      }
      enum "root" {
        value 4;
        description
          "Root protection.";
      }
      enum "bpdu" {
        value 5;
        description
          "BPDU protection.";
      }
      enum "loop" {
        value 6;
        description
          "Loop protection.";
      }
    }
    description
      "STP protection type.";
  }

  typedef port-role-type {
    type enumeration {
      enum "disabled" {
        value 1;
        description
          "Inactive port.";
      }
      enum "alternate" {
        value 2;
        description
          "Alternate port.";
      }
      enum "backup" {
        value 3;
        description
          "Backup port.";
      }
      enum "root" {
        value 4;
        description
          "Root port.";
      }
      enum "designated" {
        value 5;
        description
          "Designated port.";
      }
      enum "master" {
        value 6;
        description
          "Master Port.";
      }
    }
    description
      "STP port role.";
  }

  typedef root-type {
    type enumeration {
      enum "normal" {
        value 1;
        description
          "Configure a device as a normal root bridge of a spanning tree.";
      }
      enum "primary" {
        value 2;
        description
          "Configure a device as a primary root bridge of a spanning tree.";
      }
      enum "secondary" {
        value 3;
        description
          "Configure a device as a secondary root bridge of a spanning tree.";
      }
    }
    description
      "STP root type.";
  }

  typedef converge-mode {
    type enumeration {
      enum "fast" {
        value 1;
        description
          "Set MSTP aging mode to fast.";
      }
      enum "normal" {
        value 2;
        description
          "Set MSTP aging mode to normal.";
      }
    }
    description
      "MSTP converge mode.";
  }

  grouping ncs_template_process-common {
    description
      "Common attributes of process.";
    leaf enable {
      type string;
      // NCS drop default statement
      description
        "Enable/disable STP/RSTP/MSTP on a device.";
    }
    leaf bpdu-protection {
      type string;
      // NCS drop default statement
      description
        "Enable/disable to configure BPDU protection on an edge port. This function prevents network flapping caused by attack packets.";
    }
    leaf flush-capability {
      type string;
      // NCS drop default statement
      description
        "Enable/disable to flush capability on a switch.";
    }
    leaf max-hops {
      type string;
      // NCS drop default statement
      description
        "Set the maximum hops of a spanning tree in an MST region.";
    }
    leaf mode {
      type ncs_template_stp-mode;
      // NCS drop default statement
      description
        "Set an operation mode for the current MSTP process.";
    }
    leaf path-cost-standard {
      type ncs_template_path-cost-standard-type;
      // NCS drop default statement
      description
        "Set a standard for calculating the path cost.";
    }
    leaf tc-protection {
      type string;
      // NCS drop default statement
      description
        "Enable/disable to configure the TC BPDU protection function for an MSTP process.";
    }
    leaf tc-protection-threshold {
      type string;
      // NCS drop default statement
      description
        "Set the maximum number of TC BPDUs that the MSTP can handle.";
    }
    leaf tc-protection-interval {
      type string;
      units "s";
      description
        "Set the time the MSTP device takes to handle the maximum number of TC BPDUs and immediately refresh forwarding entries.";
    }
    leaf timer-factor {
      type string;
      // NCS drop default statement
      description
        "Set a multiplier for the Hello timer. If a device does not receive BPDUs from an upstream device within the timeout period (timeout period = hello time x 3 x timer factor), the spanning tree is calculated again.";
    }
    leaf region-name {
      type string;
      ext:dynamic-default;
      description
        "Configure an MST region name for a device.";
    }
    leaf revision-level {
      type string;
      // NCS drop default statement
      description
        "Configure a revision level for an MST region.";
    }
    leaf forward-delay {
      type string;
      units "10 ms";
      // NCS drop must statement
      // NCS drop default statement
      description
        "Set the value of the forward delay. The step is 1000ms.";
    }
    leaf hello-time {
      type string;
      units "10 ms";
      // NCS drop must statement
      // NCS drop default statement
      description
        "Set the interval at which BPDUs are sent. The step is 1000ms.";
    }
    leaf max-age {
      type string;
      units "10 ms";
      // NCS drop must statement
      // NCS drop default statement
      description
        "Set the BPDU aging time on a port of a device. The step is 1000ms.";
    }
  }

  grouping ncs_template_instance-common {
    description
      "Common attributes of instance.";
    leaf priority {
      // NCS drop when statement
      type string;
      // NCS drop must statement
      // NCS drop default statement
      description
        "Set the priority of a device in a spanning tree instance. The default step is 4096, that is, the device can have 16 priorities configured, such as 0, 4096, and 8192. A smaller value indicates a higher priority.";
    }
    leaf root-type {
      type ncs_template_root-type;
      // NCS drop default statement
      description
        "Configure the current device as the root bridge of a spanning tree instance.";
    }
  }

  grouping ncs_template_process-instance {
    description
      "Configuration of instance.";
    container default-instance {
      description
        "Configure instance.";
      uses ncs_template_instance-common;
      // NCS drop config false leaf 'vlan-mapping'
    }
    container instances {
      description
        "List of configurations of process instance.";
      list instance {
        // NCS patched for predictable order
        ordered-by user;
        // NCS drop must statement
        key "id";
        description
          "Configure process instance.";
        leaf id {
          type string;
          description
            "Instance ID.";
        }
        uses ncs_template_instance-common;
        leaf vlan-mapping {
          type pub-type:ncs_template_vlan-range;
          description
            "VLAN mappings in instance.";
        }
      }
    }
  }

  grouping ncs_template_port-pw-common {
    description
      "Common attributes of port and PW.";
    leaf enable {
      type string;
      // NCS drop default statement
      description
        "Enable/disable STP/RSTP/MSTP on PW.";
    }
    leaf loop-protection {
      type string;
      // NCS drop default statement
      description
        "Enable/disable loop protection on the current port.";
    }
    leaf no-agreement-check {
      type string;
      // NCS drop default statement
      description
        "Enable/disable to configure the common fast transition mechanism on the current interface.";
    }
    leaf point-to-point {
      type ncs_template_point-to-point-type;
      // NCS drop default statement
      description
        "Set the link type of a port.";
    }
    leaf root-protection {
      type string;
      // NCS drop must statement
      // NCS drop default statement
      description
        "Enable/disable root protection on the current port.";
    }
    leaf transmit-limit {
      type string;
      description
        "Set the maximum number of BPDUs sent by the current port within each hello interval.";
    }
    leaf tc-restriction {
      type string;
      // NCS drop default statement
      description
        "Enable/disable to configure TC/TCN packet suppression.";
    }
  }

  grouping ncs_template_port-common {
    description
      "Common attributes of port.";
    uses ncs_template_port-pw-common;
    leaf bpdu-filter {
      type ncs_template_bpdu-filter-type;
      // NCS drop default statement
      description
        "Specify the current port as a BPDU filter port or a non-BPDU filter port.";
    }
    leaf edge-port {
      type ncs_template_edge-port-type;
      // NCS drop default statement
      description
        "Specify the current port as an edge port or a non-edge port.";
    }
    leaf vpls-sub-interface {
      type string;
      // NCS drop default statement
      description
        "Enable/disable to configure an interface to instruct its VPLS-bound sub-interfaces to update ARP and MAC entries after the interface receives TC BPDUs.";
    }
  }

  grouping ncs_rpc_notif_process-common {
    description
      "Common attributes of process.";
    leaf enable {
      type boolean;
      default "false";
      description
        "Enable/disable STP/RSTP/MSTP on a device.";
    }
    leaf bpdu-protection {
      type boolean;
      default "false";
      description
        "Enable/disable to configure BPDU protection on an edge port. This function prevents network flapping caused by attack packets.";
    }
    leaf flush-capability {
      type boolean;
      default "true";
      description
        "Enable/disable to flush capability on a switch.";
    }
    leaf max-hops {
      type uint16 {
        range "1..40";
      }
      default "20";
      description
        "Set the maximum hops of a spanning tree in an MST region.";
    }
    leaf mode {
      type ncs_rpc_notif_stp-mode;
      default "mstp";
      description
        "Set an operation mode for the current MSTP process.";
    }
    leaf path-cost-standard {
      type ncs_rpc_notif_path-cost-standard-type;
      default "dot1t";
      description
        "Set a standard for calculating the path cost.";
    }
    leaf tc-protection {
      type boolean;
      default "false";
      description
        "Enable/disable to configure the TC BPDU protection function for an MSTP process.";
    }
    leaf tc-protection-threshold {
      type uint32 {
        range "1..255";
      }
      default "1";
      description
        "Set the maximum number of TC BPDUs that the MSTP can handle.";
    }
    leaf tc-protection-interval {
      type uint16 {
        range "1..600";
      }
      units "s";
      description
        "Set the time the MSTP device takes to handle the maximum number of TC BPDUs and immediately refresh forwarding entries.";
    }
    leaf timer-factor {
      type uint8 {
        range "1..10";
      }
      default "3";
      description
        "Set a multiplier for the Hello timer. If a device does not receive BPDUs from an upstream device within the timeout period (timeout period = hello time x 3 x timer factor), the spanning tree is calculated again.";
    }
    leaf region-name {
      type string {
        length "1..32";
      }
      ext:dynamic-default;
      description
        "Configure an MST region name for a device.";
    }
    leaf revision-level {
      type uint16 {
        range "0..65535";
      }
      default "0";
      description
        "Configure a revision level for an MST region.";
    }
    leaf forward-delay {
      type uint16 {
        range "400..3000";
      }
      units "10 ms";
      must '(../forward-delay) mod 100 = 0' {
        tailf:xpath-root 3;
      }
      default "1500";
      description
        "Set the value of the forward delay. The step is 1000ms.";
    }
    leaf hello-time {
      type uint16 {
        range "100..1000";
      }
      units "10 ms";
      must '(../hello-time) mod 100 = 0' {
        tailf:xpath-root 3;
      }
      default "200";
      description
        "Set the interval at which BPDUs are sent. The step is 1000ms.";
    }
    leaf max-age {
      type uint16 {
        range "600..4000";
      }
      units "10 ms";
      must '(../max-age) mod 100 = 0' {
        tailf:xpath-root 3;
      }
      default "2000";
      description
        "Set the BPDU aging time on a port of a device. The step is 1000ms.";
    }
  }

  grouping ncs_rpc_notif_instance-common {
    description
      "Common attributes of instance.";
    leaf priority {
      when "../root-type='normal'" {
        tailf:xpath-root 3;
      }
      type uint32 {
        range "0..61440";
      }
      must '(../priority) mod 4096 = 0' {
        tailf:xpath-root 3;
      }
      default "32768";
      description
        "Set the priority of a device in a spanning tree instance. The default step is 4096, that is, the device can have 16 priorities configured, such as 0, 4096, and 8192. A smaller value indicates a higher priority.";
    }
    leaf root-type {
      type ncs_rpc_notif_root-type;
      default "normal";
      description
        "Configure the current device as the root bridge of a spanning tree instance.";
    }
  }

  grouping ncs_rpc_notif_process-instance {
    description
      "Configuration of instance.";
    container default-instance {
      description
        "Configure instance.";
      uses ncs_rpc_notif_instance-common;
      leaf vlan-mapping {
        type pub-type:ncs_rpc_notif_vlan-range;
        config false;
        description
          "VLAN mappings in instance 0.";
      }
    }
    container instances {
      description
        "List of configurations of process instance.";
      list instance {
        must "(priority and priority!=32768) or (root-type and root-type!='normal') or vlan-mapping" {
          tailf:xpath-root 3;
        }
        key "id";
        description
          "Configure process instance.";
        leaf id {
          type uint32 {
            range "1..4094";
          }
          description
            "Instance ID.";
        }
        uses ncs_rpc_notif_instance-common;
        leaf vlan-mapping {
          type pub-type:ncs_rpc_notif_vlan-range;
          description
            "VLAN mappings in instance.";
        }
      }
    }
  }

  grouping ncs_rpc_notif_port-pw-common {
    description
      "Common attributes of port and PW.";
    leaf enable {
      type boolean;
      default "false";
      description
        "Enable/disable STP/RSTP/MSTP on PW.";
    }
    leaf loop-protection {
      type boolean;
      default "false";
      description
        "Enable/disable loop protection on the current port.";
    }
    leaf no-agreement-check {
      type boolean;
      default "false";
      description
        "Enable/disable to configure the common fast transition mechanism on the current interface.";
    }
    leaf point-to-point {
      type ncs_rpc_notif_point-to-point-type;
      default "auto";
      description
        "Set the link type of a port.";
    }
    leaf root-protection {
      type boolean;
      must "../loop-protection='false' or ../root-protection='false'" {
        tailf:xpath-root 3;
      }
      default "false";
      description
        "Enable/disable root protection on the current port.";
    }
    leaf transmit-limit {
      type uint16 {
        range "1..255";
      }
      description
        "Set the maximum number of BPDUs sent by the current port within each hello interval.";
    }
    leaf tc-restriction {
      type boolean;
      default "false";
      description
        "Enable/disable to configure TC/TCN packet suppression.";
    }
  }

  grouping ncs_rpc_notif_port-common {
    description
      "Common attributes of port.";
    uses ncs_rpc_notif_port-pw-common;
    leaf bpdu-filter {
      type ncs_rpc_notif_bpdu-filter-type;
      default "default";
      description
        "Specify the current port as a BPDU filter port or a non-BPDU filter port.";
    }
    leaf edge-port {
      type ncs_rpc_notif_edge-port-type;
      default "default";
      description
        "Specify the current port as an edge port or a non-edge port.";
    }
    leaf vpls-sub-interface {
      type boolean;
      default "false";
      description
        "Enable/disable to configure an interface to instruct its VPLS-bound sub-interfaces to update ARP and MAC entries after the interface receives TC BPDUs.";
    }
  }

  grouping live_ncs_process-common {
    description
      "Common attributes of process.";
    leaf enable {
      type boolean;
      // NCS drop default statement
      description
        "Enable/disable STP/RSTP/MSTP on a device.";
    }
    leaf bpdu-protection {
      type boolean;
      // NCS drop default statement
      description
        "Enable/disable to configure BPDU protection on an edge port. This function prevents network flapping caused by attack packets.";
    }
    leaf flush-capability {
      type boolean;
      // NCS drop default statement
      description
        "Enable/disable to flush capability on a switch.";
    }
    leaf max-hops {
      type uint16 {
        range "1..40";
      }
      // NCS drop default statement
      description
        "Set the maximum hops of a spanning tree in an MST region.";
    }
    leaf mode {
      type live_ncs_stp-mode;
      // NCS drop default statement
      description
        "Set an operation mode for the current MSTP process.";
    }
    leaf path-cost-standard {
      type live_ncs_path-cost-standard-type;
      // NCS drop default statement
      description
        "Set a standard for calculating the path cost.";
    }
    leaf tc-protection {
      type boolean;
      // NCS drop default statement
      description
        "Enable/disable to configure the TC BPDU protection function for an MSTP process.";
    }
    leaf tc-protection-threshold {
      type uint32 {
        range "1..255";
      }
      // NCS drop default statement
      description
        "Set the maximum number of TC BPDUs that the MSTP can handle.";
    }
    leaf tc-protection-interval {
      type uint16 {
        range "1..600";
      }
      units "s";
      description
        "Set the time the MSTP device takes to handle the maximum number of TC BPDUs and immediately refresh forwarding entries.";
    }
    leaf timer-factor {
      type uint8 {
        range "1..10";
      }
      // NCS drop default statement
      description
        "Set a multiplier for the Hello timer. If a device does not receive BPDUs from an upstream device within the timeout period (timeout period = hello time x 3 x timer factor), the spanning tree is calculated again.";
    }
    leaf region-name {
      type string {
        length "1..32";
      }
      ext:dynamic-default;
      description
        "Configure an MST region name for a device.";
    }
    leaf revision-level {
      type uint16 {
        range "0..65535";
      }
      // NCS drop default statement
      description
        "Configure a revision level for an MST region.";
    }
    leaf forward-delay {
      type uint16 {
        range "400..3000";
      }
      units "10 ms";
      // NCS drop must statement
      // NCS drop default statement
      description
        "Set the value of the forward delay. The step is 1000ms.";
    }
    leaf hello-time {
      type uint16 {
        range "100..1000";
      }
      units "10 ms";
      // NCS drop must statement
      // NCS drop default statement
      description
        "Set the interval at which BPDUs are sent. The step is 1000ms.";
    }
    leaf max-age {
      type uint16 {
        range "600..4000";
      }
      units "10 ms";
      // NCS drop must statement
      // NCS drop default statement
      description
        "Set the BPDU aging time on a port of a device. The step is 1000ms.";
    }
  }

  grouping live_ncs_instance-common {
    description
      "Common attributes of instance.";
    leaf priority {
      // NCS drop when statement
      type uint32 {
        range "0..61440";
      }
      // NCS drop must statement
      // NCS drop default statement
      description
        "Set the priority of a device in a spanning tree instance. The default step is 4096, that is, the device can have 16 priorities configured, such as 0, 4096, and 8192. A smaller value indicates a higher priority.";
    }
    leaf root-type {
      type live_ncs_root-type;
      // NCS drop default statement
      description
        "Configure the current device as the root bridge of a spanning tree instance.";
    }
  }

  grouping live_ncs_process-instance {
    description
      "Configuration of instance.";
    container default-instance {
      description
        "Configure instance.";
      uses live_ncs_instance-common;
      leaf vlan-mapping {
        type pub-type:live_ncs_vlan-range;
        description
          "VLAN mappings in instance 0.";
      }
    }
    container instances {
      description
        "List of configurations of process instance.";
      list instance {
        // NCS drop must statement
        key "id";
        description
          "Configure process instance.";
        leaf id {
          type uint32 {
            range "1..4094";
          }
          description
            "Instance ID.";
        }
        uses live_ncs_instance-common;
        leaf vlan-mapping {
          type pub-type:live_ncs_vlan-range;
          description
            "VLAN mappings in instance.";
        }
      }
    }
  }

  grouping live_ncs_port-pw-common {
    description
      "Common attributes of port and PW.";
    leaf enable {
      type boolean;
      // NCS drop default statement
      description
        "Enable/disable STP/RSTP/MSTP on PW.";
    }
    leaf loop-protection {
      type boolean;
      // NCS drop default statement
      description
        "Enable/disable loop protection on the current port.";
    }
    leaf no-agreement-check {
      type boolean;
      // NCS drop default statement
      description
        "Enable/disable to configure the common fast transition mechanism on the current interface.";
    }
    leaf point-to-point {
      type live_ncs_point-to-point-type;
      // NCS drop default statement
      description
        "Set the link type of a port.";
    }
    leaf root-protection {
      type boolean;
      // NCS drop must statement
      // NCS drop default statement
      description
        "Enable/disable root protection on the current port.";
    }
    leaf transmit-limit {
      type uint16 {
        range "1..255";
      }
      description
        "Set the maximum number of BPDUs sent by the current port within each hello interval.";
    }
    leaf tc-restriction {
      type boolean;
      // NCS drop default statement
      description
        "Enable/disable to configure TC/TCN packet suppression.";
    }
  }

  grouping live_ncs_port-common {
    description
      "Common attributes of port.";
    uses live_ncs_port-pw-common;
    leaf bpdu-filter {
      type live_ncs_bpdu-filter-type;
      // NCS drop default statement
      description
        "Specify the current port as a BPDU filter port or a non-BPDU filter port.";
    }
    leaf edge-port {
      type live_ncs_edge-port-type;
      // NCS drop default statement
      description
        "Specify the current port as an edge port or a non-edge port.";
    }
    leaf vpls-sub-interface {
      type boolean;
      // NCS drop default statement
      description
        "Enable/disable to configure an interface to instruct its VPLS-bound sub-interfaces to update ARP and MAC entries after the interface receives TC BPDUs.";
    }
  }

  grouping process-common {
    description
      "Common attributes of process.";
    leaf enable {
      type boolean;
      default "false";
      description
        "Enable/disable STP/RSTP/MSTP on a device.";
    }
    leaf bpdu-protection {
      type boolean;
      default "false";
      description
        "Enable/disable to configure BPDU protection on an edge port. This function prevents network flapping caused by attack packets.";
    }
    leaf flush-capability {
      type boolean;
      default "true";
      description
        "Enable/disable to flush capability on a switch.";
    }
    leaf max-hops {
      type uint16 {
        range "1..40";
      }
      default "20";
      description
        "Set the maximum hops of a spanning tree in an MST region.";
    }
    leaf mode {
      type stp-mode;
      default "mstp";
      description
        "Set an operation mode for the current MSTP process.";
    }
    leaf path-cost-standard {
      type path-cost-standard-type;
      default "dot1t";
      description
        "Set a standard for calculating the path cost.";
    }
    leaf tc-protection {
      type boolean;
      default "false";
      description
        "Enable/disable to configure the TC BPDU protection function for an MSTP process.";
    }
    leaf tc-protection-threshold {
      type uint32 {
        range "1..255";
      }
      default "1";
      description
        "Set the maximum number of TC BPDUs that the MSTP can handle.";
    }
    leaf tc-protection-interval {
      type uint16 {
        range "1..600";
      }
      units "s";
      description
        "Set the time the MSTP device takes to handle the maximum number of TC BPDUs and immediately refresh forwarding entries.";
    }
    leaf timer-factor {
      type uint8 {
        range "1..10";
      }
      default "3";
      description
        "Set a multiplier for the Hello timer. If a device does not receive BPDUs from an upstream device within the timeout period (timeout period = hello time x 3 x timer factor), the spanning tree is calculated again.";
    }
    leaf region-name {
      type string {
        length "1..32";
      }
      ext:dynamic-default;
      description
        "Configure an MST region name for a device.";
    }
    leaf revision-level {
      type uint16 {
        range "0..65535";
      }
      default "0";
      description
        "Configure a revision level for an MST region.";
    }
    leaf forward-delay {
      type uint16 {
        range "400..3000";
      }
      units "10 ms";
      must '(../forward-delay) mod 100 = 0' {
        tailf:xpath-root 3;
      }
      default "1500";
      description
        "Set the value of the forward delay. The step is 1000ms.";
    }
    leaf hello-time {
      type uint16 {
        range "100..1000";
      }
      units "10 ms";
      must '(../hello-time) mod 100 = 0' {
        tailf:xpath-root 3;
      }
      default "200";
      description
        "Set the interval at which BPDUs are sent. The step is 1000ms.";
    }
    leaf max-age {
      type uint16 {
        range "600..4000";
      }
      units "10 ms";
      must '(../max-age) mod 100 = 0' {
        tailf:xpath-root 3;
      }
      default "2000";
      description
        "Set the BPDU aging time on a port of a device. The step is 1000ms.";
    }
  }

  grouping instance-common {
    description
      "Common attributes of instance.";
    leaf priority {
      when "../root-type='normal'" {
        tailf:xpath-root 3;
      }
      type uint32 {
        range "0..61440";
      }
      must '(../priority) mod 4096 = 0' {
        tailf:xpath-root 3;
      }
      default "32768";
      description
        "Set the priority of a device in a spanning tree instance. The default step is 4096, that is, the device can have 16 priorities configured, such as 0, 4096, and 8192. A smaller value indicates a higher priority.";
    }
    leaf root-type {
      type root-type;
      default "normal";
      description
        "Configure the current device as the root bridge of a spanning tree instance.";
    }
  }

  grouping process-instance {
    description
      "Configuration of instance.";
    container default-instance {
      description
        "Configure instance.";
      uses instance-common;
      // NCS drop config false leaf 'vlan-mapping'
    }
    container instances {
      description
        "List of configurations of process instance.";
      list instance {
        must "(priority and priority!=32768) or (root-type and root-type!='normal') or vlan-mapping" {
          tailf:xpath-root 3;
        }
        key "id";
        description
          "Configure process instance.";
        leaf id {
          type uint32 {
            range "1..4094";
          }
          description
            "Instance ID.";
        }
        uses instance-common;
        leaf vlan-mapping {
          type pub-type:vlan-range;
          description
            "VLAN mappings in instance.";
        }
      }
    }
  }

  grouping port-pw-common {
    description
      "Common attributes of port and PW.";
    leaf enable {
      type boolean;
      default "false";
      description
        "Enable/disable STP/RSTP/MSTP on PW.";
    }
    leaf loop-protection {
      type boolean;
      default "false";
      description
        "Enable/disable loop protection on the current port.";
    }
    leaf no-agreement-check {
      type boolean;
      default "false";
      description
        "Enable/disable to configure the common fast transition mechanism on the current interface.";
    }
    leaf point-to-point {
      type point-to-point-type;
      default "auto";
      description
        "Set the link type of a port.";
    }
    leaf root-protection {
      type boolean;
      must "../loop-protection='false' or ../root-protection='false'" {
        tailf:xpath-root 3;
      }
      default "false";
      description
        "Enable/disable root protection on the current port.";
    }
    leaf transmit-limit {
      type uint16 {
        range "1..255";
      }
      description
        "Set the maximum number of BPDUs sent by the current port within each hello interval.";
    }
    leaf tc-restriction {
      type boolean;
      default "false";
      description
        "Enable/disable to configure TC/TCN packet suppression.";
    }
  }

  grouping port-common {
    description
      "Common attributes of port.";
    uses port-pw-common;
    leaf bpdu-filter {
      type bpdu-filter-type;
      default "default";
      description
        "Specify the current port as a BPDU filter port or a non-BPDU filter port.";
    }
    leaf edge-port {
      type edge-port-type;
      default "default";
      description
        "Specify the current port as an edge port or a non-edge port.";
    }
    leaf vpls-sub-interface {
      type boolean;
      default "false";
      description
        "Enable/disable to configure an interface to instruct its VPLS-bound sub-interfaces to update ARP and MAC entries after the interface receives TC BPDUs.";
    }
  }

  augment "/ncs:devices/ncs:device/ncs:config" {
    container mstp {
      tailf:ncs-device-type "netconf";
      tailf:display-when "not(../../ncs:module) or ../../ncs:module[ncs:name='huawei-mstp']";
      description
        "Multiple spanning tree protocol.";
      container global {
        description
          "Configure MSTP global attributes.";
        leaf bpdu-filter {
          type boolean;
          default "false";
          description
            "Enable/disable to default configuration of the BPDU filter function.";
        }
        leaf edge-port {
          type boolean;
          default "false";
          description
            "Enable/disable default configuration of global edge port function.";
        }
        leaf bridge-address {
          type pub-type:mac-address {
            pattern '[0-9a-f][02468ace][0-9a-f]{2}(-[0-9a-f]{4}){2}';
          }
          description
            "Bridge MAC address.";
        }
        leaf transmit-limit {
          type uint16 {
            range "1..255";
          }
          default "6";
          description
            "Maximum number of BPDUs allowed to be sent globally within a hello interval.";
        }
        leaf vstp-enable {
          type boolean;
          default "false";
          description
            "Enable/disable V-STP function.";
        }
      }
      container default-process {
        description
          "Configure default MSTP process.";
        uses process-common;
        leaf converge-mode {
          type converge-mode;
          default "normal";
          description
            "MSTP convergence mode.";
        }
        // NCS expand uses statement
        container default-instance {
          description
            "Configure instance.";
          // NCS expand uses statement
          leaf priority {
            when "../root-type='normal'" {
              tailf:xpath-root 3;
            }
            type uint32 {
              range "0..61440";
            }
            must '(../priority) mod 4096 = 0' {
              tailf:xpath-root 3;
            }
            default "32768";
            description
              "Set the priority of a device in a spanning tree instance. The default step is 4096, that is, the device can have 16 priorities configured, such as 0, 4096, and 8192. A smaller value indicates a higher priority.";
          }
          leaf root-type {
            type root-type;
            default "normal";
            description
              "Configure the current device as the root bridge of a spanning tree instance.";
          }
          // NCS drop config false leaf 'vlan-mapping'
        }
        container instances {
          description
            "List of configurations of process instance.";
          list instance {
            must "(priority and priority!=32768) or (root-type and root-type!='normal') or vlan-mapping" {
              tailf:xpath-root 3;
            }
            key "id";
            description
              "Configure process instance.";
            leaf id {
              type uint32 {
                range "1..4094";
              }
              description
                "Instance ID.";
            }
            // NCS expand uses statement
            leaf priority {
              when "../root-type='normal'" {
                tailf:xpath-root 3;
              }
              type uint32 {
                range "0..61440";
              }
              must '(../priority) mod 4096 = 0' {
                tailf:xpath-root 3;
              }
              default "32768";
              description
                "Set the priority of a device in a spanning tree instance. The default step is 4096, that is, the device can have 16 priorities configured, such as 0, 4096, and 8192. A smaller value indicates a higher priority.";
            }
            leaf root-type {
              type root-type;
              default "normal";
              description
                "Configure the current device as the root bridge of a spanning tree instance.";
            }
            leaf vlan-mapping {
              type pub-type:vlan-range;
              description
                "VLAN mappings in instance.";
              must 'not(/vlan:vlan/vlan:instances/vlan:instance)' {
                tailf:xpath-root 3;
              }
            }
          }
        }
      }
      container processs {
        description
          "List of MSTP processes.";
        list process {
          key "id";
          description
            "Configure MSTP process.";
          leaf id {
            type uint32 {
              range "1..256";
            }
            description
              "MSTP process ID.";
          }
          uses process-common;
          leaf tc-notify {
            type boolean;
            default "false";
            description
              "Enable/disable the TC notification function on the current MSTP process.";
          }
          leaf link-share-protect {
            type boolean;
            default "false";
            description
              "Enable/disable to configure shared-link protection for an MSTP process.";
          }
          // NCS expand uses statement
          container default-instance {
            description
              "Configure instance.";
            // NCS expand uses statement
            leaf priority {
              when "../root-type='normal'" {
                tailf:xpath-root 3;
              }
              type uint32 {
                range "0..61440";
              }
              must '(../priority) mod 4096 = 0' {
                tailf:xpath-root 3;
              }
              default "32768";
              description
                "Set the priority of a device in a spanning tree instance. The default step is 4096, that is, the device can have 16 priorities configured, such as 0, 4096, and 8192. A smaller value indicates a higher priority.";
            }
            leaf root-type {
              type root-type;
              default "normal";
              description
                "Configure the current device as the root bridge of a spanning tree instance.";
            }
            // NCS drop config false leaf 'vlan-mapping'
          }
          container instances {
            description
              "List of configurations of process instance.";
            list instance {
              must "(priority and priority!=32768) or (root-type and root-type!='normal') or vlan-mapping" {
                tailf:xpath-root 3;
              }
              key "id";
              description
                "Configure process instance.";
              leaf id {
                type uint32 {
                  range "1..4094";
                }
                description
                  "Instance ID.";
              }
              // NCS expand uses statement
              leaf priority {
                when "../root-type='normal'" {
                  tailf:xpath-root 3;
                }
                type uint32 {
                  range "0..61440";
                }
                must '(../priority) mod 4096 = 0' {
                  tailf:xpath-root 3;
                }
                default "32768";
                description
                  "Set the priority of a device in a spanning tree instance. The default step is 4096, that is, the device can have 16 priorities configured, such as 0, 4096, and 8192. A smaller value indicates a higher priority.";
              }
              leaf root-type {
                type root-type;
                default "normal";
                description
                  "Configure the current device as the root bridge of a spanning tree instance.";
              }
              leaf vlan-mapping {
                type pub-type:vlan-range;
                description
                  "VLAN mappings in instance.";
                must 'not(/vlan:vlan/vlan:instances/vlan:instance)' {
                  tailf:xpath-root 3;
                }
              }
            }
          }
        }
      }
      // NCS drop config false container 'error-packet-statistic'
    }
  }
  augment "/ncs:devices/ncs:device/ncs:live-status" {
    container mstp {
      tailf:ncs-device-type "netconf";
      tailf:display-when "not(../../ncs:module) or ../../ncs:module[ncs:name='huawei-mstp'] or (../../ncs:live-status-protocol[not(ncs:capability)]) or (../../ncs:live-status-protocol/ncs:capability/ncs:module[.='huawei-mstp'])";
      description
        "Multiple spanning tree protocol.";
      container global {
        description
          "Configure MSTP global attributes.";
        leaf bpdu-filter {
          type boolean;
          // NCS drop default statement
          description
            "Enable/disable to default configuration of the BPDU filter function.";
        }
        leaf edge-port {
          type boolean;
          // NCS drop default statement
          description
            "Enable/disable default configuration of global edge port function.";
        }
        leaf bridge-address {
          type pub-type:live_ncs_mac-address;
          description
            "Bridge MAC address.";
        }
        leaf transmit-limit {
          type uint16 {
            range "1..255";
          }
          // NCS drop default statement
          description
            "Maximum number of BPDUs allowed to be sent globally within a hello interval.";
        }
        leaf vstp-enable {
          type boolean;
          // NCS drop default statement
          description
            "Enable/disable V-STP function.";
        }
      }
      container default-process {
        description
          "Configure default MSTP process.";
        uses live_ncs_process-common;
        leaf converge-mode {
          type live_ncs_converge-mode;
          // NCS drop default statement
          description
            "MSTP convergence mode.";
        }
        // NCS expand uses statement
        container default-instance {
          description
            "Configure instance.";
          // NCS expand uses statement
          leaf priority {
            // NCS drop when statement
            type uint32 {
              range "0..61440";
            }
            // NCS drop must statement
            // NCS drop default statement
            description
              "Set the priority of a device in a spanning tree instance. The default step is 4096, that is, the device can have 16 priorities configured, such as 0, 4096, and 8192. A smaller value indicates a higher priority.";
          }
          leaf root-type {
            type live_ncs_root-type;
            // NCS drop default statement
            description
              "Configure the current device as the root bridge of a spanning tree instance.";
          }
          leaf vlan-mapping {
            type pub-type:live_ncs_vlan-range;
            description
              "VLAN mappings in instance 0.";
          }
        }
        container instances {
          description
            "List of configurations of process instance.";
          list instance {
            // NCS drop must statement
            key "id";
            description
              "Configure process instance.";
            leaf id {
              type uint32 {
                range "1..4094";
              }
              description
                "Instance ID.";
            }
            // NCS expand uses statement
            leaf priority {
              // NCS drop when statement
              type uint32 {
                range "0..61440";
              }
              // NCS drop must statement
              // NCS drop default statement
              description
                "Set the priority of a device in a spanning tree instance. The default step is 4096, that is, the device can have 16 priorities configured, such as 0, 4096, and 8192. A smaller value indicates a higher priority.";
            }
            leaf root-type {
              type live_ncs_root-type;
              // NCS drop default statement
              description
                "Configure the current device as the root bridge of a spanning tree instance.";
            }
            leaf vlan-mapping {
              type pub-type:live_ncs_vlan-range;
              description
                "VLAN mappings in instance.";
              // NCS drop must statement
            }
          }
        }
      }
      container processs {
        description
          "List of MSTP processes.";
        list process {
          key "id";
          description
            "Configure MSTP process.";
          leaf id {
            type uint32 {
              range "1..256";
            }
            description
              "MSTP process ID.";
          }
          uses live_ncs_process-common;
          leaf tc-notify {
            type boolean;
            // NCS drop default statement
            description
              "Enable/disable the TC notification function on the current MSTP process.";
          }
          leaf link-share-protect {
            type boolean;
            // NCS drop default statement
            description
              "Enable/disable to configure shared-link protection for an MSTP process.";
          }
          // NCS expand uses statement
          container default-instance {
            description
              "Configure instance.";
            // NCS expand uses statement
            leaf priority {
              // NCS drop when statement
              type uint32 {
                range "0..61440";
              }
              // NCS drop must statement
              // NCS drop default statement
              description
                "Set the priority of a device in a spanning tree instance. The default step is 4096, that is, the device can have 16 priorities configured, such as 0, 4096, and 8192. A smaller value indicates a higher priority.";
            }
            leaf root-type {
              type live_ncs_root-type;
              // NCS drop default statement
              description
                "Configure the current device as the root bridge of a spanning tree instance.";
            }
            leaf vlan-mapping {
              type pub-type:live_ncs_vlan-range;
              description
                "VLAN mappings in instance 0.";
            }
          }
          container instances {
            description
              "List of configurations of process instance.";
            list instance {
              // NCS drop must statement
              key "id";
              description
                "Configure process instance.";
              leaf id {
                type uint32 {
                  range "1..4094";
                }
                description
                  "Instance ID.";
              }
              // NCS expand uses statement
              leaf priority {
                // NCS drop when statement
                type uint32 {
                  range "0..61440";
                }
                // NCS drop must statement
                // NCS drop default statement
                description
                  "Set the priority of a device in a spanning tree instance. The default step is 4096, that is, the device can have 16 priorities configured, such as 0, 4096, and 8192. A smaller value indicates a higher priority.";
              }
              leaf root-type {
                type live_ncs_root-type;
                // NCS drop default statement
                description
                  "Configure the current device as the root bridge of a spanning tree instance.";
              }
              leaf vlan-mapping {
                type pub-type:live_ncs_vlan-range;
                description
                  "VLAN mappings in instance.";
                // NCS drop must statement
              }
            }
          }
        }
      }
      container error-packet-statistic {
        description
          "Operational state of displaying error packet information, including error packet statistics, packet contents and receiving time.";
        leaf time {
          type yang:date-and-time;
          description
            "Display the last time when error packets were received.";
        }
        leaf count {
          type uint32;
          description
            "Display the statistics about error packets received by MSTP.";
        }
        leaf content {
          type string {
            length "0..4500";
          }
          description
            "Display the contents of received error packets.";
        }
      }
    }
  }
  augment "/ncs:devices/ncs:template/ncs:ned-id/ncs:config" {
    container mstp {
      description
        "Multiple spanning tree protocol.";
      container global {
        description
          "Configure MSTP global attributes.";
        leaf bpdu-filter {
          type string;
          // NCS drop default statement
          description
            "Enable/disable to default configuration of the BPDU filter function.";
        }
        leaf edge-port {
          type string;
          // NCS drop default statement
          description
            "Enable/disable default configuration of global edge port function.";
        }
        leaf bridge-address {
          type pub-type:ncs_template_mac-address;
          description
            "Bridge MAC address.";
        }
        leaf transmit-limit {
          type string;
          // NCS drop default statement
          description
            "Maximum number of BPDUs allowed to be sent globally within a hello interval.";
        }
        leaf vstp-enable {
          type string;
          // NCS drop default statement
          description
            "Enable/disable V-STP function.";
        }
      }
      container default-process {
        description
          "Configure default MSTP process.";
        uses ncs_template_process-common;
        leaf converge-mode {
          type ncs_template_converge-mode;
          // NCS drop default statement
          description
            "MSTP convergence mode.";
        }
        // NCS expand uses statement
        container default-instance {
          description
            "Configure instance.";
          // NCS expand uses statement
          leaf priority {
            // NCS drop when statement
            type string;
            // NCS drop must statement
            // NCS drop default statement
            description
              "Set the priority of a device in a spanning tree instance. The default step is 4096, that is, the device can have 16 priorities configured, such as 0, 4096, and 8192. A smaller value indicates a higher priority.";
          }
          leaf root-type {
            type ncs_template_root-type;
            // NCS drop default statement
            description
              "Configure the current device as the root bridge of a spanning tree instance.";
          }
          // NCS drop config false leaf 'vlan-mapping'
        }
        container instances {
          description
            "List of configurations of process instance.";
          list instance {
            // NCS patched for predictable order
            ordered-by user;
            // NCS drop must statement
            key "id";
            description
              "Configure process instance.";
            leaf id {
              type string;
              description
                "Instance ID.";
            }
            // NCS expand uses statement
            leaf priority {
              // NCS drop when statement
              type string;
              // NCS drop must statement
              // NCS drop default statement
              description
                "Set the priority of a device in a spanning tree instance. The default step is 4096, that is, the device can have 16 priorities configured, such as 0, 4096, and 8192. A smaller value indicates a higher priority.";
            }
            leaf root-type {
              type ncs_template_root-type;
              // NCS drop default statement
              description
                "Configure the current device as the root bridge of a spanning tree instance.";
            }
            leaf vlan-mapping {
              type pub-type:ncs_template_vlan-range;
              description
                "VLAN mappings in instance.";
              // NCS drop must statement
            }
          }
        }
      }
      container processs {
        description
          "List of MSTP processes.";
        list process {
          // NCS patched for predictable order
          ordered-by user;
          key "id";
          description
            "Configure MSTP process.";
          leaf id {
            type string;
            description
              "MSTP process ID.";
          }
          uses ncs_template_process-common;
          leaf tc-notify {
            type string;
            // NCS drop default statement
            description
              "Enable/disable the TC notification function on the current MSTP process.";
          }
          leaf link-share-protect {
            type string;
            // NCS drop default statement
            description
              "Enable/disable to configure shared-link protection for an MSTP process.";
          }
          // NCS expand uses statement
          container default-instance {
            description
              "Configure instance.";
            // NCS expand uses statement
            leaf priority {
              // NCS drop when statement
              type string;
              // NCS drop must statement
              // NCS drop default statement
              description
                "Set the priority of a device in a spanning tree instance. The default step is 4096, that is, the device can have 16 priorities configured, such as 0, 4096, and 8192. A smaller value indicates a higher priority.";
            }
            leaf root-type {
              type ncs_template_root-type;
              // NCS drop default statement
              description
                "Configure the current device as the root bridge of a spanning tree instance.";
            }
            // NCS drop config false leaf 'vlan-mapping'
          }
          container instances {
            description
              "List of configurations of process instance.";
            list instance {
              // NCS patched for predictable order
              ordered-by user;
              // NCS drop must statement
              key "id";
              description
                "Configure process instance.";
              leaf id {
                type string;
                description
                  "Instance ID.";
              }
              // NCS expand uses statement
              leaf priority {
                // NCS drop when statement
                type string;
                // NCS drop must statement
                // NCS drop default statement
                description
                  "Set the priority of a device in a spanning tree instance. The default step is 4096, that is, the device can have 16 priorities configured, such as 0, 4096, and 8192. A smaller value indicates a higher priority.";
              }
              leaf root-type {
                type ncs_template_root-type;
                // NCS drop default statement
                description
                  "Configure the current device as the root bridge of a spanning tree instance.";
              }
              leaf vlan-mapping {
                type pub-type:ncs_template_vlan-range;
                description
                  "VLAN mappings in instance.";
                // NCS drop must statement
              }
            }
          }
        }
      }
      // NCS drop config false container 'error-packet-statistic'
    }
  }
  augment "/ncs:devices/ncs:template/ncs:ned-id/ncs:config/ifm:ifm/ifm:interfaces/ifm:interface/ethernet:ethernet/ethernet:main-interface/ethernet:l2-attribute" {
    description
      "MSTP attribute on layer 2 port.";
    container mstp-attribute {
      description
        "Configure MSTP attribute on layer 2 port.";
      // NCS expand uses statement
      // NCS expand uses statement
      leaf enable {
        type string;
        // NCS drop default statement
        description
          "Enable/disable STP/RSTP/MSTP on layer 2 port.";
      }
      leaf loop-protection {
        type string;
        // NCS drop default statement
        description
          "Enable/disable loop protection on the current port.";
      }
      leaf no-agreement-check {
        type string;
        // NCS drop default statement
        description
          "Enable/disable to configure the common fast transition mechanism on the current interface.";
      }
      leaf point-to-point {
        type ncs_template_point-to-point-type;
        // NCS drop default statement
        description
          "Set the link type of a port.";
      }
      leaf root-protection {
        type string;
        // NCS drop must statement
        // NCS drop default statement
        description
          "Enable/disable root protection on the current port.";
      }
      leaf transmit-limit {
        type string;
        description
          "Set the maximum number of BPDUs sent by the current port within each hello interval.";
      }
      leaf tc-restriction {
        type string;
        // NCS drop default statement
        description
          "Enable/disable to configure TC/TCN packet suppression.";
      }
      leaf bpdu-filter {
        type ncs_template_bpdu-filter-type;
        // NCS drop default statement
        description
          "Specify the current port as a BPDU filter port or a non-BPDU filter port.";
      }
      leaf edge-port {
        type ncs_template_edge-port-type;
        // NCS drop default statement
        description
          "Specify the current port as an edge port or a non-edge port.";
      }
      leaf vpls-sub-interface {
        type string;
        // NCS drop default statement
        description
          "Enable/disable to configure an interface to instruct its VPLS-bound sub-interfaces to update ARP and MAC entries after the interface receives TC BPDUs.";
      }
    }
  }
  augment "/ncs:devices/ncs:device/ncs:live-status/ifm:ifm/ifm:interfaces/ifm:interface/ethernet:ethernet/ethernet:main-interface/ethernet:l2-attribute" {
    description
      "MSTP attribute on layer 2 port.";
    container mstp-attribute {
      tailf:ncs-device-type "netconf";
      tailf:display-when "not(../../../../../../../../ncs:module) or ../../../../../../../../ncs:module[ncs:name='huawei-mstp'] or (../../../../../../../../ncs:live-status-protocol[not(ncs:capability)]) or (../../../../../../../../ncs:live-status-protocol/ncs:capability/ncs:module[.='huawei-mstp'])";
      description
        "Configure MSTP attribute on layer 2 port.";
      // NCS expand uses statement
      // NCS expand uses statement
      leaf enable {
        type boolean;
        // NCS drop default statement
        description
          "Enable/disable STP/RSTP/MSTP on layer 2 port.";
      }
      leaf loop-protection {
        type boolean;
        // NCS drop default statement
        description
          "Enable/disable loop protection on the current port.";
      }
      leaf no-agreement-check {
        type boolean;
        // NCS drop default statement
        description
          "Enable/disable to configure the common fast transition mechanism on the current interface.";
      }
      leaf point-to-point {
        type live_ncs_point-to-point-type;
        // NCS drop default statement
        description
          "Set the link type of a port.";
      }
      leaf root-protection {
        type boolean;
        // NCS drop must statement
        // NCS drop default statement
        description
          "Enable/disable root protection on the current port.";
      }
      leaf transmit-limit {
        type uint16 {
          range "1..255";
        }
        description
          "Set the maximum number of BPDUs sent by the current port within each hello interval.";
      }
      leaf tc-restriction {
        type boolean;
        // NCS drop default statement
        description
          "Enable/disable to configure TC/TCN packet suppression.";
      }
      leaf bpdu-filter {
        type live_ncs_bpdu-filter-type;
        // NCS drop default statement
        description
          "Specify the current port as a BPDU filter port or a non-BPDU filter port.";
      }
      leaf edge-port {
        type live_ncs_edge-port-type;
        // NCS drop default statement
        description
          "Specify the current port as an edge port or a non-edge port.";
      }
      leaf vpls-sub-interface {
        type boolean;
        // NCS drop default statement
        description
          "Enable/disable to configure an interface to instruct its VPLS-bound sub-interfaces to update ARP and MAC entries after the interface receives TC BPDUs.";
      }
    }
  }
  augment "/ncs:devices/ncs:device/ncs:config/ifm:ifm/ifm:interfaces/ifm:interface/ethernet:ethernet/ethernet:main-interface/ethernet:l2-attribute" {
    description
      "MSTP attribute on layer 2 port.";
    container mstp-attribute {
      tailf:ncs-device-type "netconf";
      tailf:display-when "not(../../../../../../../../ncs:module) or ../../../../../../../../ncs:module[ncs:name='huawei-mstp']";
      description
        "Configure MSTP attribute on layer 2 port.";
      // NCS expand uses statement
      // NCS expand uses statement
      leaf enable {
        type boolean;
        default "true";
        description
          "Enable/disable STP/RSTP/MSTP on layer 2 port.";
      }
      leaf loop-protection {
        type boolean;
        default "false";
        description
          "Enable/disable loop protection on the current port.";
      }
      leaf no-agreement-check {
        type boolean;
        default "false";
        description
          "Enable/disable to configure the common fast transition mechanism on the current interface.";
      }
      leaf point-to-point {
        type point-to-point-type;
        default "auto";
        description
          "Set the link type of a port.";
      }
      leaf root-protection {
        type boolean;
        must "../loop-protection='false' or ../root-protection='false'" {
          tailf:xpath-root 3;
        }
        default "false";
        description
          "Enable/disable root protection on the current port.";
      }
      leaf transmit-limit {
        type uint16 {
          range "1..255";
        }
        description
          "Set the maximum number of BPDUs sent by the current port within each hello interval.";
      }
      leaf tc-restriction {
        type boolean;
        default "false";
        description
          "Enable/disable to configure TC/TCN packet suppression.";
      }
      leaf bpdu-filter {
        type bpdu-filter-type;
        default "default";
        description
          "Specify the current port as a BPDU filter port or a non-BPDU filter port.";
      }
      leaf edge-port {
        type edge-port-type;
        default "default";
        description
          "Specify the current port as an edge port or a non-edge port.";
      }
      leaf vpls-sub-interface {
        type boolean;
        default "false";
        description
          "Enable/disable to configure an interface to instruct its VPLS-bound sub-interfaces to update ARP and MAC entries after the interface receives TC BPDUs.";
      }
    }
  }
  augment "/ncs:devices/ncs:template/ncs:ned-id/ncs:config/ifm:ifm/ifm:interfaces/ifm:interface/ethernet:ethernet/ethernet:main-interface" {
    // NCS drop when statement
    description
      "MSTP attribute on layer 3 port.";
    container mstp-attribute {
      presence "MSTP attribute";
      description
        "Configure MSTP attribute on layer 3 port. The container must have non-default attributes. If you want to change all attributes to the default attributes, delete the container.";
      // NCS expand uses statement
      // NCS expand uses statement
      leaf enable {
        type string;
        // NCS drop default statement
        description
          "Enable/disable STP/RSTP/MSTP on layer 3 port.";
      }
      leaf loop-protection {
        type string;
        // NCS drop default statement
        description
          "Enable/disable loop protection on the current port.";
      }
      leaf no-agreement-check {
        type string;
        // NCS drop default statement
        description
          "Enable/disable to configure the common fast transition mechanism on the current interface.";
      }
      leaf point-to-point {
        type ncs_template_point-to-point-type;
        // NCS drop default statement
        description
          "Set the link type of a port.";
      }
      leaf root-protection {
        type string;
        // NCS drop must statement
        // NCS drop default statement
        description
          "Enable/disable root protection on the current port.";
      }
      leaf transmit-limit {
        type string;
        description
          "Set the maximum number of BPDUs sent by the current port within each hello interval.";
      }
      leaf tc-restriction {
        type string;
        // NCS drop default statement
        description
          "Enable/disable to configure TC/TCN packet suppression.";
      }
      leaf bpdu-filter {
        type ncs_template_bpdu-filter-type;
        // NCS drop default statement
        description
          "Specify the current port as a BPDU filter port or a non-BPDU filter port.";
      }
      leaf edge-port {
        type ncs_template_edge-port-type;
        // NCS drop default statement
        description
          "Specify the current port as an edge port or a non-edge port.";
      }
      leaf vpls-sub-interface {
        type string;
        // NCS drop default statement
        description
          "Enable/disable to configure an interface to instruct its VPLS-bound sub-interfaces to update ARP and MAC entries after the interface receives TC BPDUs.";
      }
    }
  }
  augment "/ncs:devices/ncs:device/ncs:live-status/ifm:ifm/ifm:interfaces/ifm:interface/ethernet:ethernet/ethernet:main-interface" {
    // NCS drop when statement
    description
      "MSTP attribute on layer 3 port.";
    container mstp-attribute {
      tailf:ncs-device-type "netconf";
      tailf:display-when "not(../../../../../../../ncs:module) or ../../../../../../../ncs:module[ncs:name='huawei-mstp'] or (../../../../../../../ncs:live-status-protocol[not(ncs:capability)]) or (../../../../../../../ncs:live-status-protocol/ncs:capability/ncs:module[.='huawei-mstp'])";
      presence "MSTP attribute";
      description
        "Configure MSTP attribute on layer 3 port. The container must have non-default attributes. If you want to change all attributes to the default attributes, delete the container.";
      // NCS expand uses statement
      // NCS expand uses statement
      leaf enable {
        type boolean;
        // NCS drop default statement
        description
          "Enable/disable STP/RSTP/MSTP on layer 3 port.";
      }
      leaf loop-protection {
        type boolean;
        // NCS drop default statement
        description
          "Enable/disable loop protection on the current port.";
      }
      leaf no-agreement-check {
        type boolean;
        // NCS drop default statement
        description
          "Enable/disable to configure the common fast transition mechanism on the current interface.";
      }
      leaf point-to-point {
        type live_ncs_point-to-point-type;
        // NCS drop default statement
        description
          "Set the link type of a port.";
      }
      leaf root-protection {
        type boolean;
        // NCS drop must statement
        // NCS drop default statement
        description
          "Enable/disable root protection on the current port.";
      }
      leaf transmit-limit {
        type uint16 {
          range "1..255";
        }
        description
          "Set the maximum number of BPDUs sent by the current port within each hello interval.";
      }
      leaf tc-restriction {
        type boolean;
        // NCS drop default statement
        description
          "Enable/disable to configure TC/TCN packet suppression.";
      }
      leaf bpdu-filter {
        type live_ncs_bpdu-filter-type;
        // NCS drop default statement
        description
          "Specify the current port as a BPDU filter port or a non-BPDU filter port.";
      }
      leaf edge-port {
        type live_ncs_edge-port-type;
        // NCS drop default statement
        description
          "Specify the current port as an edge port or a non-edge port.";
      }
      leaf vpls-sub-interface {
        type boolean;
        // NCS drop default statement
        description
          "Enable/disable to configure an interface to instruct its VPLS-bound sub-interfaces to update ARP and MAC entries after the interface receives TC BPDUs.";
      }
    }
  }
  augment "/ncs:devices/ncs:device/ncs:config/ifm:ifm/ifm:interfaces/ifm:interface/ethernet:ethernet/ethernet:main-interface" {
    when 'not(ethernet:l2-attribute)' {
      tailf:xpath-root 3;
    }
    description
      "MSTP attribute on layer 3 port.";
    container mstp-attribute {
      tailf:ncs-device-type "netconf";
      tailf:display-when "not(../../../../../../../ncs:module) or ../../../../../../../ncs:module[ncs:name='huawei-mstp']";
      presence "MSTP attribute";
      description
        "Configure MSTP attribute on layer 3 port. The container must have non-default attributes. If you want to change all attributes to the default attributes, delete the container.";
      // NCS expand uses statement
      // NCS expand uses statement
      leaf enable {
        type boolean;
        default "false";
        description
          "Enable/disable STP/RSTP/MSTP on layer 3 port.";
      }
      leaf loop-protection {
        type boolean;
        default "false";
        description
          "Enable/disable loop protection on the current port.";
      }
      leaf no-agreement-check {
        type boolean;
        default "false";
        description
          "Enable/disable to configure the common fast transition mechanism on the current interface.";
      }
      leaf point-to-point {
        type point-to-point-type;
        default "auto";
        description
          "Set the link type of a port.";
      }
      leaf root-protection {
        type boolean;
        must "../loop-protection='false' or ../root-protection='false'" {
          tailf:xpath-root 3;
        }
        default "false";
        description
          "Enable/disable root protection on the current port.";
      }
      leaf transmit-limit {
        type uint16 {
          range "1..255";
        }
        description
          "Set the maximum number of BPDUs sent by the current port within each hello interval.";
      }
      leaf tc-restriction {
        type boolean;
        default "false";
        description
          "Enable/disable to configure TC/TCN packet suppression.";
      }
      leaf bpdu-filter {
        type bpdu-filter-type;
        default "default";
        description
          "Specify the current port as a BPDU filter port or a non-BPDU filter port.";
      }
      leaf edge-port {
        type edge-port-type;
        default "default";
        description
          "Specify the current port as an edge port or a non-edge port.";
      }
      leaf vpls-sub-interface {
        type boolean;
        default "false";
        description
          "Enable/disable to configure an interface to instruct its VPLS-bound sub-interfaces to update ARP and MAC entries after the interface receives TC BPDUs.";
      }
    }
  }
  augment "/ncs:devices/ncs:template/ncs:ned-id/ncs:config/l2vpn:l2vpn/l2vpn:instances/l2vpn:instance/l2vpn:vpls/l2vpn:ldp-signaling/l2vpn:pws/l2vpn:pw" {
    description
      "MSTP attribute on PW.";
    container mstp-attribute {
      // NCS drop when statement
      description
        "Configure MSTP attribute on PW.";
      uses ncs_template_port-pw-common;
    }
  }
  augment "/ncs:devices/ncs:device/ncs:live-status/l2vpn:l2vpn/l2vpn:instances/l2vpn:instance/l2vpn:vpls/l2vpn:ldp-signaling/l2vpn:pws/l2vpn:pw" {
    description
      "MSTP attribute on PW.";
    container mstp-attribute {
      tailf:ncs-device-type "netconf";
      tailf:display-when "not(../../../../../../../../../ncs:module) or ../../../../../../../../../ncs:module[ncs:name='huawei-mstp'] or (../../../../../../../../../ncs:live-status-protocol[not(ncs:capability)]) or (../../../../../../../../../ncs:live-status-protocol/ncs:capability/ncs:module[.='huawei-mstp'])";
      // NCS drop when statement
      description
        "Configure MSTP attribute on PW.";
      uses live_ncs_port-pw-common;
    }
  }
  augment "/ncs:devices/ncs:device/ncs:config/l2vpn:l2vpn/l2vpn:instances/l2vpn:instance/l2vpn:vpls/l2vpn:ldp-signaling/l2vpn:pws/l2vpn:pw" {
    description
      "MSTP attribute on PW.";
    container mstp-attribute {
      tailf:ncs-device-type "netconf";
      tailf:display-when "not(../../../../../../../../../ncs:module) or ../../../../../../../../../ncs:module[ncs:name='huawei-mstp']";
      when "../l2vpn:name and ../../../../l2vpn:work-mode='normal'" {
        tailf:xpath-root 3;
      }
      description
        "Configure MSTP attribute on PW.";
      uses port-pw-common;
    }
  }
}
