module huawei-ip-cga {
  // Generated by yanger -t ncs
  tailf:mount-id "huawei-nc-1.0:huawei-nc-1.0";
  tailf:ncs-device-type "netconf";

  namespace "urn:huawei:yang:huawei-ip-cga";
  prefix ip-cga;

  import ietf-inet-types {
    prefix inet;
  }
  import huawei-ifm {
    prefix ifm;
  }
  import huawei-ip {
    prefix ip;
  }
  import huawei-rsa {
    prefix rsa;
  }
  import huawei-extension {
    prefix ext;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "This module contains a collection of YANG definitions for
     configuring IP implementations.
     Copyright (C) 2019 Huawei Technologies Co., Ltd. All rights reserved.";

  revision 2020-02-14 {
    description
      "Modify the description of nodes.";
    reference "Huawei private.";
  }
  revision 2019-08-30 {
    description
      "Initial revision.";
    reference "Huawei private.";
  }
  ext:task-name "interface-mgr";

  augment "/ncs:devices/ncs:template/ncs:ned-id/ncs:config/ifm:ifm/ifm:interfaces/ifm:interface/ip:ipv6" {
    description
      "Cryptographically generated adresses.";
    container cgas {
      description
        "List of CGA information.";
      list cga {
        // NCS patched for predictable order
        ordered-by user;
        key "rsakey-pair";
        // NCS drop max-elements statement
        description
          "Configure CGA information.";
        leaf rsakey-pair {
          type string;
          description
            "RSA key.";
        }
        leaf sec-level {
          type string;
          description
            "Security level.";
        }
        leaf modifier {
          type string;
          // NCS drop must statement
          // NCS drop default statement
          description
            "CGA address modifier.";
        }
      }
    }
  }
  augment "/ncs:devices/ncs:device/ncs:live-status/ifm:ifm/ifm:interfaces/ifm:interface/ip:ipv6" {
    description
      "Cryptographically generated adresses.";
    container cgas {
      tailf:ncs-device-type "netconf";
      tailf:display-when "not(../../../../../../ncs:module) or ../../../../../../ncs:module[ncs:name='huawei-ip-cga'] or (../../../../../../ncs:live-status-protocol[not(ncs:capability)]) or (../../../../../../ncs:live-status-protocol/ncs:capability/ncs:module[.='huawei-ip-cga'])";
      description
        "List of CGA information.";
      list cga {
        key "rsakey-pair";
        // NCS drop max-elements statement
        description
          "Configure CGA information.";
        leaf rsakey-pair {
          type leafref {
            path "/ncs:devices/ncs:device/ncs:live-status/rsa:rsa/rsa:key-pairs/rsa:key-pair/rsa:key-pair-label" {
              tailf:xpath-root 3;
            }
          }
          description
            "RSA key.";
        }
        leaf sec-level {
          type uint8 {
            range "0..1";
          }
          description
            "Security level.";
        }
        leaf modifier {
          type inet:ipv6-address-no-zone;
          // NCS drop must statement
          // NCS drop default statement
          description
            "CGA address modifier.";
        }
      }
    }
  }
  augment "/ncs:devices/ncs:device/ncs:config/ifm:ifm/ifm:interfaces/ifm:interface/ip:ipv6" {
    description
      "Cryptographically generated adresses.";
    container cgas {
      tailf:ncs-device-type "netconf";
      tailf:display-when "not(../../../../../../ncs:module) or ../../../../../../ncs:module[ncs:name='huawei-ip-cga']";
      description
        "List of CGA information.";
      list cga {
        key "rsakey-pair";
        max-elements 1;
        description
          "Configure CGA information.";
        leaf rsakey-pair {
          type leafref {
            path "/ncs:devices/ncs:device/ncs:config/rsa:rsa/rsa:key-pairs/rsa:key-pair/rsa:key-pair-label" {
              tailf:xpath-root 3;
            }
          }
          description
            "RSA key.";
        }
        leaf sec-level {
          type uint8 {
            range "0..1";
          }
          description
            "Security level.";
        }
        leaf modifier {
          type inet:ipv6-address-no-zone;
          must "not (../sec-level=1 and ../modifier!='::')" {
            tailf:xpath-root 3;
          }
          default "::";
          description
            "CGA address modifier.";
        }
      }
    }
  }
}
