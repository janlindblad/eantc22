module huawei-fwd-engine {
  // Generated by yanger -t ncs
  tailf:mount-id "huawei-nc-1.0:huawei-nc-1.0";
  tailf:ncs-device-type "netconf";

  yang-version 1;
  namespace "urn:huawei:yang:huawei-fwd-engine";
  prefix fwd-engine;

  import huawei-extension {
    prefix ext;
  }
  import huawei-devm {
    prefix devm;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Global Configuration.";

  revision 2021-04-20 {
    description
      "Added frame-padding-fix.";
    reference "Huawei private.";
  }
  revision 2020-03-09 {
    description
      "Initial revision.";
    reference "Huawei private.";
  }
  ext:task-name "device-mgr";

  augment "/ncs:devices/ncs:template/ncs:ned-id/ncs:config/devm:devm" {
    description
      "Forward engine configuration.";
    container fwd-performance-alarms {
      description
        "List of forwarding performance alarm.";
      list fwd-performance-alarm {
        // NCS patched for predictable order
        ordered-by user;
        key "slot-id";
        description
          "Configure the alarm reporting and alarm clearance thresholds for forwarding performance.";
        ext:generated-by "system";
        ext:operation-exclude "create|delete";
        leaf slot-id {
          type string;
          description
            "Slot ID.";
        }
        leaf report-threshold {
          type string;
          units "%";
          // NCS drop must statement
          // NCS drop default statement
          description
            "Specifies the alarm reporting threshold.";
        }
        leaf clear-threshold {
          type string;
          units "%";
          // NCS drop must statement
          // NCS drop default statement
          description
            "Specifies the alarm clearance threshold.";
        }
      }
    }
    container fwd-services-alarms {
      description
        "List of value-added services alarm.";
      list fwd-services-alarm {
        // NCS patched for predictable order
        ordered-by user;
        key "slot-id";
        description
          "Configure the alarm reporting and alarm clearance thresholds for value-added services.";
        ext:generated-by "system";
        ext:operation-exclude "create|delete";
        leaf slot-id {
          type string;
          description
            "Slot ID.";
        }
        leaf report-threshold {
          type string;
          units "%";
          // NCS drop must statement
          // NCS drop default statement
          description
            "Specifies the alarm reporting threshold.";
        }
        leaf clear-threshold {
          type string;
          units "%";
          // NCS drop must statement
          // NCS drop default statement
          description
            "Specifies the alarm clearance threshold.";
        }
      }
    }
    container fwd-reassembly-alarms {
      description
        "List of packet reassembly alarm.";
      list fwd-reassembly-alarm {
        // NCS patched for predictable order
        ordered-by user;
        key "slot-id";
        description
          "Configure the alarm reporting and alarm clearance thresholds for packet reassembly.";
        ext:generated-by "system";
        ext:operation-exclude "create|delete";
        leaf slot-id {
          type string;
          description
            "Slot ID.";
        }
        leaf report-threshold {
          type string;
          units "%";
          // NCS drop must statement
          // NCS drop default statement
          description
            "Specifies the alarm reporting threshold.";
        }
        leaf clear-threshold {
          type string;
          units "%";
          // NCS drop must statement
          // NCS drop default statement
          description
            "Specifies the alarm clearance threshold.";
        }
      }
    }
    container fwd-board-flow-alarms {
      description
        "List of traffic alarm on a board.";
      list fwd-board-flow-alarm {
        // NCS patched for predictable order
        ordered-by user;
        key "slot-id";
        description
          "Configure the alarm reporting and alarm clearance thresholds for traffic on a board.";
        ext:generated-by "system";
        ext:operation-exclude "create|delete";
        leaf slot-id {
          type string;
          description
            "Slot ID.";
        }
        leaf input-report-threshold {
          type string;
          units "%";
          // NCS drop must statement
          // NCS drop default statement
          description
            "Specifies the input bandwidth alarm reporting threshold.";
        }
        leaf input-clear-threshold {
          type string;
          units "%";
          // NCS drop must statement
          // NCS drop default statement
          description
            "Specifies the input bandwidth alarm clearance threshold.";
        }
        leaf output-report-threshold {
          type string;
          units "%";
          // NCS drop must statement
          // NCS drop default statement
          description
            "Specifies the output bandwidth alarm reporting threshold.";
        }
        leaf output-clear-threshold {
          type string;
          units "%";
          // NCS drop must statement
          // NCS drop default statement
          description
            "Specifies the output bandwidth alarm clearance threshold.";
        }
      }
    }
  }
  augment "/ncs:devices/ncs:device/ncs:live-status/devm:devm" {
    description
      "Forward engine configuration.";
    container fwd-performance-alarms {
      tailf:ncs-device-type "netconf";
      tailf:display-when "not(../../../ncs:module) or ../../../ncs:module[ncs:name='huawei-fwd-engine'] or (../../../ncs:live-status-protocol[not(ncs:capability)]) or (../../../ncs:live-status-protocol/ncs:capability/ncs:module[.='huawei-fwd-engine'])";
      description
        "List of forwarding performance alarm.";
      list fwd-performance-alarm {
        key "slot-id";
        description
          "Configure the alarm reporting and alarm clearance thresholds for forwarding performance.";
        ext:generated-by "system";
        ext:operation-exclude "create|delete";
        leaf slot-id {
          type string {
            length "1..15";
          }
          description
            "Slot ID.";
        }
        leaf report-threshold {
          type uint32 {
            range "0..100";
          }
          units "%";
          // NCS drop must statement
          // NCS drop default statement
          description
            "Specifies the alarm reporting threshold.";
        }
        leaf clear-threshold {
          type uint32 {
            range "0..100";
          }
          units "%";
          // NCS drop must statement
          // NCS drop default statement
          description
            "Specifies the alarm clearance threshold.";
        }
      }
    }
    container fwd-services-alarms {
      tailf:ncs-device-type "netconf";
      tailf:display-when "not(../../../ncs:module) or ../../../ncs:module[ncs:name='huawei-fwd-engine'] or (../../../ncs:live-status-protocol[not(ncs:capability)]) or (../../../ncs:live-status-protocol/ncs:capability/ncs:module[.='huawei-fwd-engine'])";
      description
        "List of value-added services alarm.";
      list fwd-services-alarm {
        key "slot-id";
        description
          "Configure the alarm reporting and alarm clearance thresholds for value-added services.";
        ext:generated-by "system";
        ext:operation-exclude "create|delete";
        leaf slot-id {
          type string {
            length "1..15";
          }
          description
            "Slot ID.";
        }
        leaf report-threshold {
          type uint32 {
            range "0..100";
          }
          units "%";
          // NCS drop must statement
          // NCS drop default statement
          description
            "Specifies the alarm reporting threshold.";
        }
        leaf clear-threshold {
          type uint32 {
            range "0..100";
          }
          units "%";
          // NCS drop must statement
          // NCS drop default statement
          description
            "Specifies the alarm clearance threshold.";
        }
      }
    }
    container fwd-reassembly-alarms {
      tailf:ncs-device-type "netconf";
      tailf:display-when "not(../../../ncs:module) or ../../../ncs:module[ncs:name='huawei-fwd-engine'] or (../../../ncs:live-status-protocol[not(ncs:capability)]) or (../../../ncs:live-status-protocol/ncs:capability/ncs:module[.='huawei-fwd-engine'])";
      description
        "List of packet reassembly alarm.";
      list fwd-reassembly-alarm {
        key "slot-id";
        description
          "Configure the alarm reporting and alarm clearance thresholds for packet reassembly.";
        ext:generated-by "system";
        ext:operation-exclude "create|delete";
        leaf slot-id {
          type string {
            length "1..15";
          }
          description
            "Slot ID.";
        }
        leaf report-threshold {
          type uint32 {
            range "0..100";
          }
          units "%";
          // NCS drop must statement
          // NCS drop default statement
          description
            "Specifies the alarm reporting threshold.";
        }
        leaf clear-threshold {
          type uint32 {
            range "0..100";
          }
          units "%";
          // NCS drop must statement
          // NCS drop default statement
          description
            "Specifies the alarm clearance threshold.";
        }
      }
    }
    container fwd-board-flow-alarms {
      tailf:ncs-device-type "netconf";
      tailf:display-when "not(../../../ncs:module) or ../../../ncs:module[ncs:name='huawei-fwd-engine'] or (../../../ncs:live-status-protocol[not(ncs:capability)]) or (../../../ncs:live-status-protocol/ncs:capability/ncs:module[.='huawei-fwd-engine'])";
      description
        "List of traffic alarm on a board.";
      list fwd-board-flow-alarm {
        key "slot-id";
        description
          "Configure the alarm reporting and alarm clearance thresholds for traffic on a board.";
        ext:generated-by "system";
        ext:operation-exclude "create|delete";
        leaf slot-id {
          type string {
            length "1..15";
          }
          description
            "Slot ID.";
        }
        leaf input-report-threshold {
          type uint32 {
            range "0..100";
          }
          units "%";
          // NCS drop must statement
          // NCS drop default statement
          description
            "Specifies the input bandwidth alarm reporting threshold.";
        }
        leaf input-clear-threshold {
          type uint32 {
            range "0..100";
          }
          units "%";
          // NCS drop must statement
          // NCS drop default statement
          description
            "Specifies the input bandwidth alarm clearance threshold.";
        }
        leaf output-report-threshold {
          type uint32 {
            range "0..100";
          }
          units "%";
          // NCS drop must statement
          // NCS drop default statement
          description
            "Specifies the output bandwidth alarm reporting threshold.";
        }
        leaf output-clear-threshold {
          type uint32 {
            range "0..100";
          }
          units "%";
          // NCS drop must statement
          // NCS drop default statement
          description
            "Specifies the output bandwidth alarm clearance threshold.";
        }
      }
    }
  }
  augment "/ncs:devices/ncs:device/ncs:config/devm:devm" {
    description
      "Forward engine configuration.";
    container fwd-performance-alarms {
      tailf:ncs-device-type "netconf";
      tailf:display-when "not(../../../ncs:module) or ../../../ncs:module[ncs:name='huawei-fwd-engine']";
      description
        "List of forwarding performance alarm.";
      list fwd-performance-alarm {
        key "slot-id";
        description
          "Configure the alarm reporting and alarm clearance thresholds for forwarding performance.";
        ext:generated-by "system";
        ext:operation-exclude "create|delete";
        leaf slot-id {
          type string {
            length "1..15";
          }
          description
            "Slot ID.";
        }
        leaf report-threshold {
          type uint32 {
            range "0..100";
          }
          units "%";
          must '(../report-threshold>../clear-threshold)' {
            tailf:xpath-root 3;
          }
          default "80";
          description
            "Specifies the alarm reporting threshold.";
        }
        leaf clear-threshold {
          type uint32 {
            range "0..100";
          }
          units "%";
          must '(../report-threshold>../clear-threshold)' {
            tailf:xpath-root 3;
          }
          default "75";
          description
            "Specifies the alarm clearance threshold.";
        }
      }
    }
    container fwd-services-alarms {
      tailf:ncs-device-type "netconf";
      tailf:display-when "not(../../../ncs:module) or ../../../ncs:module[ncs:name='huawei-fwd-engine']";
      description
        "List of value-added services alarm.";
      list fwd-services-alarm {
        key "slot-id";
        description
          "Configure the alarm reporting and alarm clearance thresholds for value-added services.";
        ext:generated-by "system";
        ext:operation-exclude "create|delete";
        leaf slot-id {
          type string {
            length "1..15";
          }
          description
            "Slot ID.";
        }
        leaf report-threshold {
          type uint32 {
            range "0..100";
          }
          units "%";
          must '(../report-threshold>../clear-threshold)' {
            tailf:xpath-root 3;
          }
          default "80";
          description
            "Specifies the alarm reporting threshold.";
        }
        leaf clear-threshold {
          type uint32 {
            range "0..100";
          }
          units "%";
          must '(../report-threshold>../clear-threshold)' {
            tailf:xpath-root 3;
          }
          default "75";
          description
            "Specifies the alarm clearance threshold.";
        }
      }
    }
    container fwd-reassembly-alarms {
      tailf:ncs-device-type "netconf";
      tailf:display-when "not(../../../ncs:module) or ../../../ncs:module[ncs:name='huawei-fwd-engine']";
      description
        "List of packet reassembly alarm.";
      list fwd-reassembly-alarm {
        key "slot-id";
        description
          "Configure the alarm reporting and alarm clearance thresholds for packet reassembly.";
        ext:generated-by "system";
        ext:operation-exclude "create|delete";
        leaf slot-id {
          type string {
            length "1..15";
          }
          description
            "Slot ID.";
        }
        leaf report-threshold {
          type uint32 {
            range "0..100";
          }
          units "%";
          must '(../report-threshold>../clear-threshold)' {
            tailf:xpath-root 3;
          }
          default "80";
          description
            "Specifies the alarm reporting threshold.";
        }
        leaf clear-threshold {
          type uint32 {
            range "0..100";
          }
          units "%";
          must '(../report-threshold>../clear-threshold)' {
            tailf:xpath-root 3;
          }
          default "75";
          description
            "Specifies the alarm clearance threshold.";
        }
      }
    }
    container fwd-board-flow-alarms {
      tailf:ncs-device-type "netconf";
      tailf:display-when "not(../../../ncs:module) or ../../../ncs:module[ncs:name='huawei-fwd-engine']";
      description
        "List of traffic alarm on a board.";
      list fwd-board-flow-alarm {
        key "slot-id";
        description
          "Configure the alarm reporting and alarm clearance thresholds for traffic on a board.";
        ext:generated-by "system";
        ext:operation-exclude "create|delete";
        leaf slot-id {
          type string {
            length "1..15";
          }
          description
            "Slot ID.";
        }
        leaf input-report-threshold {
          type uint32 {
            range "0..100";
          }
          units "%";
          must '(../input-report-threshold>../input-clear-threshold)' {
            tailf:xpath-root 3;
          }
          default "80";
          description
            "Specifies the input bandwidth alarm reporting threshold.";
        }
        leaf input-clear-threshold {
          type uint32 {
            range "0..100";
          }
          units "%";
          must '(../input-report-threshold>../input-clear-threshold)' {
            tailf:xpath-root 3;
          }
          default "75";
          description
            "Specifies the input bandwidth alarm clearance threshold.";
        }
        leaf output-report-threshold {
          type uint32 {
            range "0..100";
          }
          units "%";
          must '(../output-report-threshold>../output-clear-threshold)' {
            tailf:xpath-root 3;
          }
          default "80";
          description
            "Specifies the output bandwidth alarm reporting threshold.";
        }
        leaf output-clear-threshold {
          type uint32 {
            range "0..100";
          }
          units "%";
          must '(../output-report-threshold>../output-clear-threshold)' {
            tailf:xpath-root 3;
          }
          default "75";
          description
            "Specifies the output bandwidth alarm clearance threshold.";
        }
      }
    }
  }
  augment "/ncs:devices/ncs:template/ncs:ned-id/ncs:config/devm:devm/devm:lpu-boards/devm:lpu-board" {
    description
      "Padding fix configuration.";
    container frame-padding-fix {
      presence "create frame-padding-fix";
      description
        "Enable/disable a board to reserve the padding fields in upstream Ethernet packets.";
    }
  }
  augment "/ncs:devices/ncs:device/ncs:live-status/devm:devm/devm:lpu-boards/devm:lpu-board" {
    description
      "Padding fix configuration.";
    container frame-padding-fix {
      tailf:ncs-device-type "netconf";
      tailf:display-when "not(../../../../../ncs:module) or ../../../../../ncs:module[ncs:name='huawei-fwd-engine'] or (../../../../../ncs:live-status-protocol[not(ncs:capability)]) or (../../../../../ncs:live-status-protocol/ncs:capability/ncs:module[.='huawei-fwd-engine'])";
      presence "create frame-padding-fix";
      description
        "Enable/disable a board to reserve the padding fields in upstream Ethernet packets.";
    }
  }
  augment "/ncs:devices/ncs:device/ncs:config/devm:devm/devm:lpu-boards/devm:lpu-board" {
    description
      "Padding fix configuration.";
    container frame-padding-fix {
      tailf:ncs-device-type "netconf";
      tailf:display-when "not(../../../../../ncs:module) or ../../../../../ncs:module[ncs:name='huawei-fwd-engine']";
      presence "create frame-padding-fix";
      description
        "Enable/disable a board to reserve the padding fields in upstream Ethernet packets.";
    }
  }
  augment "/ncs:devices/ncs:template/ncs:ned-id/ncs:config/devm:devm/devm:mpu-boards/devm:mpu-board" {
    description
      "Padding fix configuration.";
    container frame-padding-fix {
      presence "create frame-padding-fix";
      description
        "Enable/disable a board to reserve the padding fields in upstream Ethernet packets.";
    }
  }
  augment "/ncs:devices/ncs:device/ncs:live-status/devm:devm/devm:mpu-boards/devm:mpu-board" {
    description
      "Padding fix configuration.";
    container frame-padding-fix {
      tailf:ncs-device-type "netconf";
      tailf:display-when "not(../../../../../ncs:module) or ../../../../../ncs:module[ncs:name='huawei-fwd-engine'] or (../../../../../ncs:live-status-protocol[not(ncs:capability)]) or (../../../../../ncs:live-status-protocol/ncs:capability/ncs:module[.='huawei-fwd-engine'])";
      presence "create frame-padding-fix";
      description
        "Enable/disable a board to reserve the padding fields in upstream Ethernet packets.";
    }
  }
  augment "/ncs:devices/ncs:device/ncs:config/devm:devm/devm:mpu-boards/devm:mpu-board" {
    description
      "Padding fix configuration.";
    container frame-padding-fix {
      tailf:ncs-device-type "netconf";
      tailf:display-when "not(../../../../../ncs:module) or ../../../../../ncs:module[ncs:name='huawei-fwd-engine']";
      presence "create frame-padding-fix";
      description
        "Enable/disable a board to reserve the padding fields in upstream Ethernet packets.";
    }
  }
}
