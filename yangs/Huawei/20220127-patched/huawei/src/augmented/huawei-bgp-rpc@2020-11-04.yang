module huawei-bgp-rpc {
  // Generated by yanger -t ncs
  tailf:mount-id "huawei-nc-1.0:huawei-nc-1.0";
  tailf:ncs-device-type "netconf";

  yang-version 1;
  namespace "urn:huawei:yang:huawei-bgp-rpc";
  prefix bgp-rpc;

  import huawei-network-instance {
    prefix ni;
  }
  import huawei-extension {
    prefix ext;
  }
  import huawei-bgp {
    prefix bgp;
  }
  import ietf-inet-types {
    prefix inet;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "BGP rpc configuration.";

  revision 2020-11-04 {
    description
      "Initial revision.";
    reference "Huawei private.";
  }
  ext:task-name "bgp";

  augment "/ncs:devices/ncs:device/ncs:rpc" {
    container rpc-refresh-base-process-bgp-group-af {
      tailf:ncs-device-type "netconf";
      tailf:display-when "not(../../ncs:module) or ../../ncs:module[ncs:name='huawei-bgp-rpc']";
      tailf:action refresh-base-process-bgp-group-af {
        tailf:actionpoint ncsproxy {
          tailf:internal;
        }
        ext:node-ref "/ni:network-instance/ni:instances/ni:instance/bgp:bgp/bgp:base-process/bgp:peer-groups/bgp:peer-group/bgp:afs/bgp:af";
        description
          "Soft reset a peer group with a specified group name.";
        input {
          leaf vrf-name {
            type string;
            mandatory true;
            description
              "VPN name of a BGP instance.";
          }
          leaf address-family {
            type bgp:ncs_rpc_notif_group-af-type;
            mandatory true;
            description
              "Address family type of a BGP instance.";
          }
          leaf group-name {
            type string;
            mandatory true;
            description
              "Specify the name of a peer group.";
          }
          leaf direction {
            type bgp:ncs_rpc_notif_direction-type;
            mandatory true;
            description
              "Soft reset BGP connections in the inbound/outbound direction.";
          }
        }
      }
    }
  }
  augment "/ncs:devices/ncs:device-group/ncs:ned-id/ncs:rpc" {
    container rpc-refresh-base-process-bgp-group-af {
      tailf:ncs-device-type "netconf";
      tailf:display-when "/ncs:devices/ncs:device[ncs:name=current()/../../../ncs:member]/ncs:module[ncs:name='huawei-bgp-rpc']";
      tailf:action refresh-base-process-bgp-group-af {
        tailf:actionpoint ncsproxy {
          tailf:internal;
        }
        ext:node-ref "/ni:network-instance/ni:instances/ni:instance/bgp:bgp/bgp:base-process/bgp:peer-groups/bgp:peer-group/bgp:afs/bgp:af";
        description
          "Soft reset a peer group with a specified group name.";
        input {
          leaf vrf-name {
            type string;
            mandatory true;
            description
              "VPN name of a BGP instance.";
          }
          leaf address-family {
            type bgp:ncs_rpc_notif_group-af-type;
            mandatory true;
            description
              "Address family type of a BGP instance.";
          }
          leaf group-name {
            type string;
            mandatory true;
            description
              "Specify the name of a peer group.";
          }
          leaf direction {
            type bgp:ncs_rpc_notif_direction-type;
            mandatory true;
            description
              "Soft reset BGP connections in the inbound/outbound direction.";
          }
        }
      }
    }
  }
  augment "/ncs:devices/ncs:device/ncs:rpc" {
    container rpc-refresh-base-process-bgp-peer-type-direction {
      tailf:ncs-device-type "netconf";
      tailf:display-when "not(../../ncs:module) or ../../ncs:module[ncs:name='huawei-bgp-rpc']";
      tailf:action refresh-base-process-bgp-peer-type-direction {
        tailf:actionpoint ncsproxy {
          tailf:internal;
        }
        ext:node-ref "/ni:network-instance/ni:instances/ni:instance/bgp:bgp/bgp:base-process/bgp:peers/bgp:peer/bgp:afs/bgp:af";
        description
          "Soft reset peers with a specified peer type.";
        input {
          leaf vrf-name {
            type string;
            mandatory true;
            description
              "VPN name of a BGP instance.";
          }
          leaf address-family {
            type bgp:ncs_rpc_notif_af-type;
            mandatory true;
            description
              "Address family type of a BGP instance.";
          }
          leaf peer-type {
            type bgp:ncs_rpc_notif_peer-type-info;
            mandatory true;
            description
              "Peer type.";
          }
          leaf direction {
            type bgp:ncs_rpc_notif_direction-type;
            mandatory true;
            description
              "Soft reset BGP connections in the inbound/outbound direction.";
          }
        }
      }
    }
  }
  augment "/ncs:devices/ncs:device-group/ncs:ned-id/ncs:rpc" {
    container rpc-refresh-base-process-bgp-peer-type-direction {
      tailf:ncs-device-type "netconf";
      tailf:display-when "/ncs:devices/ncs:device[ncs:name=current()/../../../ncs:member]/ncs:module[ncs:name='huawei-bgp-rpc']";
      tailf:action refresh-base-process-bgp-peer-type-direction {
        tailf:actionpoint ncsproxy {
          tailf:internal;
        }
        ext:node-ref "/ni:network-instance/ni:instances/ni:instance/bgp:bgp/bgp:base-process/bgp:peers/bgp:peer/bgp:afs/bgp:af";
        description
          "Soft reset peers with a specified peer type.";
        input {
          leaf vrf-name {
            type string;
            mandatory true;
            description
              "VPN name of a BGP instance.";
          }
          leaf address-family {
            type bgp:ncs_rpc_notif_af-type;
            mandatory true;
            description
              "Address family type of a BGP instance.";
          }
          leaf peer-type {
            type bgp:ncs_rpc_notif_peer-type-info;
            mandatory true;
            description
              "Peer type.";
          }
          leaf direction {
            type bgp:ncs_rpc_notif_direction-type;
            mandatory true;
            description
              "Soft reset BGP connections in the inbound/outbound direction.";
          }
        }
      }
    }
  }
  augment "/ncs:devices/ncs:device/ncs:rpc" {
    container rpc-refresh-base-process-bgp-peer-af-direction {
      tailf:ncs-device-type "netconf";
      tailf:display-when "not(../../ncs:module) or ../../ncs:module[ncs:name='huawei-bgp-rpc']";
      tailf:action refresh-base-process-bgp-peer-af-direction {
        tailf:actionpoint ncsproxy {
          tailf:internal;
        }
        ext:node-ref "/ni:network-instance/ni:instances/ni:instance/bgp:bgp/bgp:base-process/bgp:peers/bgp:peer/bgp:afs/bgp:af";
        description
          "Soft reset a peer with a specified peer address.";
        input {
          leaf vrf-name {
            type string;
            mandatory true;
            description
              "VPN name of a BGP instance.";
          }
          leaf address-family {
            type bgp:ncs_rpc_notif_af-type;
            mandatory true;
            description
              "Address family type of a BGP instance.";
          }
          leaf remote-address {
            type inet:ip-address-no-zone;
            mandatory true;
            description
              "Peer address.";
          }
          leaf direction {
            type bgp:ncs_rpc_notif_direction-type;
            mandatory true;
            description
              "Soft reset BGP connections in the inbound/outbound direction.";
          }
        }
      }
    }
  }
  augment "/ncs:devices/ncs:device-group/ncs:ned-id/ncs:rpc" {
    container rpc-refresh-base-process-bgp-peer-af-direction {
      tailf:ncs-device-type "netconf";
      tailf:display-when "/ncs:devices/ncs:device[ncs:name=current()/../../../ncs:member]/ncs:module[ncs:name='huawei-bgp-rpc']";
      tailf:action refresh-base-process-bgp-peer-af-direction {
        tailf:actionpoint ncsproxy {
          tailf:internal;
        }
        ext:node-ref "/ni:network-instance/ni:instances/ni:instance/bgp:bgp/bgp:base-process/bgp:peers/bgp:peer/bgp:afs/bgp:af";
        description
          "Soft reset a peer with a specified peer address.";
        input {
          leaf vrf-name {
            type string;
            mandatory true;
            description
              "VPN name of a BGP instance.";
          }
          leaf address-family {
            type bgp:ncs_rpc_notif_af-type;
            mandatory true;
            description
              "Address family type of a BGP instance.";
          }
          leaf remote-address {
            type inet:ip-address-no-zone;
            mandatory true;
            description
              "Peer address.";
          }
          leaf direction {
            type bgp:ncs_rpc_notif_direction-type;
            mandatory true;
            description
              "Soft reset BGP connections in the inbound/outbound direction.";
          }
        }
      }
    }
  }
  augment "/ncs:devices/ncs:device/ncs:rpc" {
    container rpc-refresh-base-process-bgp-af-direction {
      tailf:ncs-device-type "netconf";
      tailf:display-when "not(../../ncs:module) or ../../ncs:module[ncs:name='huawei-bgp-rpc']";
      tailf:action refresh-base-process-bgp-af-direction {
        tailf:actionpoint ncsproxy {
          tailf:internal;
        }
        ext:node-ref "/ni:network-instance/ni:instances/ni:instance/bgp:bgp/bgp:base-process/bgp:afs/bgp:af";
        description
          "Soft reset BGP connections.";
        input {
          leaf vrf-name {
            type string;
            mandatory true;
            description
              "VPN name of a BGP instance.";
          }
          leaf address-family {
            type bgp:ncs_rpc_notif_af-type;
            mandatory true;
            description
              "Address family type of a BGP instance.";
          }
          leaf direction {
            type bgp:ncs_rpc_notif_direction-type;
            mandatory true;
            description
              "Soft reset BGP connections in the inbound/outbound direction.";
          }
        }
      }
    }
  }
  augment "/ncs:devices/ncs:device-group/ncs:ned-id/ncs:rpc" {
    container rpc-refresh-base-process-bgp-af-direction {
      tailf:ncs-device-type "netconf";
      tailf:display-when "/ncs:devices/ncs:device[ncs:name=current()/../../../ncs:member]/ncs:module[ncs:name='huawei-bgp-rpc']";
      tailf:action refresh-base-process-bgp-af-direction {
        tailf:actionpoint ncsproxy {
          tailf:internal;
        }
        ext:node-ref "/ni:network-instance/ni:instances/ni:instance/bgp:bgp/bgp:base-process/bgp:afs/bgp:af";
        description
          "Soft reset BGP connections.";
        input {
          leaf vrf-name {
            type string;
            mandatory true;
            description
              "VPN name of a BGP instance.";
          }
          leaf address-family {
            type bgp:ncs_rpc_notif_af-type;
            mandatory true;
            description
              "Address family type of a BGP instance.";
          }
          leaf direction {
            type bgp:ncs_rpc_notif_direction-type;
            mandatory true;
            description
              "Soft reset BGP connections in the inbound/outbound direction.";
          }
        }
      }
    }
  }
  augment "/ncs:devices/ncs:device/ncs:rpc" {
    container rpc-reset-base-process-bgp-group-af {
      tailf:ncs-device-type "netconf";
      tailf:display-when "not(../../ncs:module) or ../../ncs:module[ncs:name='huawei-bgp-rpc']";
      tailf:action reset-base-process-bgp-group-af {
        tailf:actionpoint ncsproxy {
          tailf:internal;
        }
        ext:node-ref "/ni:network-instance/ni:instances/ni:instance/bgp:bgp/bgp:base-process/bgp:peer-groups/bgp:peer-group/bgp:afs/bgp:af";
        description
          "Reset the BGP group operation.";
        input {
          leaf vrf-name {
            type string;
            mandatory true;
            description
              "VPN name of a BGP instance.";
          }
          leaf address-family {
            type bgp:ncs_rpc_notif_group-af-type;
            mandatory true;
            description
              "Address family type of a BGP instance.";
          }
          leaf group-name {
            type string;
            mandatory true;
            description
              "Specify the name of a peer group.";
          }
        }
      }
    }
  }
  augment "/ncs:devices/ncs:device-group/ncs:ned-id/ncs:rpc" {
    container rpc-reset-base-process-bgp-group-af {
      tailf:ncs-device-type "netconf";
      tailf:display-when "/ncs:devices/ncs:device[ncs:name=current()/../../../ncs:member]/ncs:module[ncs:name='huawei-bgp-rpc']";
      tailf:action reset-base-process-bgp-group-af {
        tailf:actionpoint ncsproxy {
          tailf:internal;
        }
        ext:node-ref "/ni:network-instance/ni:instances/ni:instance/bgp:bgp/bgp:base-process/bgp:peer-groups/bgp:peer-group/bgp:afs/bgp:af";
        description
          "Reset the BGP group operation.";
        input {
          leaf vrf-name {
            type string;
            mandatory true;
            description
              "VPN name of a BGP instance.";
          }
          leaf address-family {
            type bgp:ncs_rpc_notif_group-af-type;
            mandatory true;
            description
              "Address family type of a BGP instance.";
          }
          leaf group-name {
            type string;
            mandatory true;
            description
              "Specify the name of a peer group.";
          }
        }
      }
    }
  }
  augment "/ncs:devices/ncs:device/ncs:rpc" {
    container rpc-reset-base-process-bgp-peer-type {
      tailf:ncs-device-type "netconf";
      tailf:display-when "not(../../ncs:module) or ../../ncs:module[ncs:name='huawei-bgp-rpc']";
      tailf:action reset-base-process-bgp-peer-type {
        tailf:actionpoint ncsproxy {
          tailf:internal;
        }
        ext:node-ref "/ni:network-instance/ni:instances/ni:instance/bgp:bgp/bgp:base-process/bgp:peers/bgp:peer";
        description
          "Reset the BGP peer operation.";
        input {
          leaf vrf-name {
            type string;
            mandatory true;
            description
              "VPN name of a BGP instance.";
          }
          leaf address-family {
            type bgp:ncs_rpc_notif_af-type;
            mandatory true;
            description
              "Address family type of a BGP instance.";
          }
          leaf peer-type {
            type bgp:ncs_rpc_notif_peer-type-info;
            mandatory true;
            description
              "Peer type.";
          }
        }
      }
    }
  }
  augment "/ncs:devices/ncs:device-group/ncs:ned-id/ncs:rpc" {
    container rpc-reset-base-process-bgp-peer-type {
      tailf:ncs-device-type "netconf";
      tailf:display-when "/ncs:devices/ncs:device[ncs:name=current()/../../../ncs:member]/ncs:module[ncs:name='huawei-bgp-rpc']";
      tailf:action reset-base-process-bgp-peer-type {
        tailf:actionpoint ncsproxy {
          tailf:internal;
        }
        ext:node-ref "/ni:network-instance/ni:instances/ni:instance/bgp:bgp/bgp:base-process/bgp:peers/bgp:peer";
        description
          "Reset the BGP peer operation.";
        input {
          leaf vrf-name {
            type string;
            mandatory true;
            description
              "VPN name of a BGP instance.";
          }
          leaf address-family {
            type bgp:ncs_rpc_notif_af-type;
            mandatory true;
            description
              "Address family type of a BGP instance.";
          }
          leaf peer-type {
            type bgp:ncs_rpc_notif_peer-type-info;
            mandatory true;
            description
              "Peer type.";
          }
        }
      }
    }
  }
  augment "/ncs:devices/ncs:device/ncs:rpc" {
    container rpc-reset-base-process-bgp-peer-as {
      tailf:ncs-device-type "netconf";
      tailf:display-when "not(../../ncs:module) or ../../ncs:module[ncs:name='huawei-bgp-rpc']";
      tailf:action reset-base-process-bgp-peer-as {
        tailf:actionpoint ncsproxy {
          tailf:internal;
        }
        ext:node-ref "/ni:network-instance/ni:instances/ni:instance/bgp:bgp/bgp:base-process/bgp:peers/bgp:peer/bgp:afs/bgp:af";
        description
          "Reset the BGP AS number.";
        input {
          leaf vrf-name {
            type string;
            mandatory true;
            description
              "VPN name of a BGP instance.";
          }
          leaf address-family {
            type bgp:ncs_rpc_notif_af-type;
            mandatory true;
            description
              "Address family type of a BGP instance.";
          }
          leaf remote-as {
            type bgp:ncs_rpc_notif_as-number-validate;
            mandatory true;
            description
              "AS number of a peer.";
          }
        }
      }
    }
  }
  augment "/ncs:devices/ncs:device-group/ncs:ned-id/ncs:rpc" {
    container rpc-reset-base-process-bgp-peer-as {
      tailf:ncs-device-type "netconf";
      tailf:display-when "/ncs:devices/ncs:device[ncs:name=current()/../../../ncs:member]/ncs:module[ncs:name='huawei-bgp-rpc']";
      tailf:action reset-base-process-bgp-peer-as {
        tailf:actionpoint ncsproxy {
          tailf:internal;
        }
        ext:node-ref "/ni:network-instance/ni:instances/ni:instance/bgp:bgp/bgp:base-process/bgp:peers/bgp:peer/bgp:afs/bgp:af";
        description
          "Reset the BGP AS number.";
        input {
          leaf vrf-name {
            type string;
            mandatory true;
            description
              "VPN name of a BGP instance.";
          }
          leaf address-family {
            type bgp:ncs_rpc_notif_af-type;
            mandatory true;
            description
              "Address family type of a BGP instance.";
          }
          leaf remote-as {
            type bgp:ncs_rpc_notif_as-number-validate;
            mandatory true;
            description
              "AS number of a peer.";
          }
        }
      }
    }
  }
  augment "/ncs:devices/ncs:device/ncs:rpc" {
    container rpc-reset-base-process-bgp-peer-af {
      tailf:ncs-device-type "netconf";
      tailf:display-when "not(../../ncs:module) or ../../ncs:module[ncs:name='huawei-bgp-rpc']";
      tailf:action reset-base-process-bgp-peer-af {
        tailf:actionpoint ncsproxy {
          tailf:internal;
        }
        ext:node-ref "/ni:network-instance/ni:instances/ni:instance/bgp:bgp/bgp:base-process/bgp:peers/bgp:peer/bgp:afs/bgp:af";
        description
          "Reset the BGP peer operation.";
        input {
          leaf vrf-name {
            type string;
            mandatory true;
            description
              "VPN name of a BGP instance.";
          }
          leaf address-family {
            type bgp:ncs_rpc_notif_af-type;
            mandatory true;
            description
              "Address family type of a BGP instance.";
          }
          leaf remote-address {
            type inet:ip-address-no-zone;
            mandatory true;
            description
              "Peer address.";
          }
        }
      }
    }
  }
  augment "/ncs:devices/ncs:device-group/ncs:ned-id/ncs:rpc" {
    container rpc-reset-base-process-bgp-peer-af {
      tailf:ncs-device-type "netconf";
      tailf:display-when "/ncs:devices/ncs:device[ncs:name=current()/../../../ncs:member]/ncs:module[ncs:name='huawei-bgp-rpc']";
      tailf:action reset-base-process-bgp-peer-af {
        tailf:actionpoint ncsproxy {
          tailf:internal;
        }
        ext:node-ref "/ni:network-instance/ni:instances/ni:instance/bgp:bgp/bgp:base-process/bgp:peers/bgp:peer/bgp:afs/bgp:af";
        description
          "Reset the BGP peer operation.";
        input {
          leaf vrf-name {
            type string;
            mandatory true;
            description
              "VPN name of a BGP instance.";
          }
          leaf address-family {
            type bgp:ncs_rpc_notif_af-type;
            mandatory true;
            description
              "Address family type of a BGP instance.";
          }
          leaf remote-address {
            type inet:ip-address-no-zone;
            mandatory true;
            description
              "Peer address.";
          }
        }
      }
    }
  }
  augment "/ncs:devices/ncs:device/ncs:rpc" {
    container rpc-reset-base-process-bgp-all {
      tailf:ncs-device-type "netconf";
      tailf:display-when "not(../../ncs:module) or ../../ncs:module[ncs:name='huawei-bgp-rpc']";
      tailf:action reset-base-process-bgp-all {
        tailf:actionpoint ncsproxy {
          tailf:internal;
        }
        ext:node-ref "/ni:network-instance/ni:instances/ni:instance/bgp:bgp/bgp:base-process";
        description
          "Reset BGP operation.";
      }
    }
  }
  augment "/ncs:devices/ncs:device-group/ncs:ned-id/ncs:rpc" {
    container rpc-reset-base-process-bgp-all {
      tailf:ncs-device-type "netconf";
      tailf:display-when "/ncs:devices/ncs:device[ncs:name=current()/../../../ncs:member]/ncs:module[ncs:name='huawei-bgp-rpc']";
      tailf:action reset-base-process-bgp-all {
        tailf:actionpoint ncsproxy {
          tailf:internal;
        }
        ext:node-ref "/ni:network-instance/ni:instances/ni:instance/bgp:bgp/bgp:base-process";
        description
          "Reset BGP operation.";
      }
    }
  }
  augment "/ncs:devices/ncs:device/ncs:rpc" {
    container rpc-reset-base-process-bgp-af {
      tailf:ncs-device-type "netconf";
      tailf:display-when "not(../../ncs:module) or ../../ncs:module[ncs:name='huawei-bgp-rpc']";
      tailf:action reset-base-process-bgp-af {
        tailf:actionpoint ncsproxy {
          tailf:internal;
        }
        ext:node-ref "/ni:network-instance/ni:instances/ni:instance/bgp:bgp/bgp:base-process/bgp:afs/bgp:af";
        description
          "Reset BGP address family operation.";
        input {
          leaf vrf-name {
            type string;
            mandatory true;
            description
              "VPN name of a BGP instance.";
          }
          leaf address-family {
            type bgp:ncs_rpc_notif_af-type;
            mandatory true;
            description
              "Address family type of a BGP instance.";
          }
        }
      }
    }
  }
  augment "/ncs:devices/ncs:device-group/ncs:ned-id/ncs:rpc" {
    container rpc-reset-base-process-bgp-af {
      tailf:ncs-device-type "netconf";
      tailf:display-when "/ncs:devices/ncs:device[ncs:name=current()/../../../ncs:member]/ncs:module[ncs:name='huawei-bgp-rpc']";
      tailf:action reset-base-process-bgp-af {
        tailf:actionpoint ncsproxy {
          tailf:internal;
        }
        ext:node-ref "/ni:network-instance/ni:instances/ni:instance/bgp:bgp/bgp:base-process/bgp:afs/bgp:af";
        description
          "Reset BGP address family operation.";
        input {
          leaf vrf-name {
            type string;
            mandatory true;
            description
              "VPN name of a BGP instance.";
          }
          leaf address-family {
            type bgp:ncs_rpc_notif_af-type;
            mandatory true;
            description
              "Address family type of a BGP instance.";
          }
        }
      }
    }
  }
}
