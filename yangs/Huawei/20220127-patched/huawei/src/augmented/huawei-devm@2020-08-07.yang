module huawei-devm {
  // Generated by yanger -t ncs
  tailf:mount-id "huawei-nc-1.0:huawei-nc-1.0";
  tailf:ncs-device-type "netconf";

  namespace "urn:huawei:yang:huawei-devm";
  prefix devm;

  import huawei-pub-type {
    prefix pub-type;
  }
  import ietf-yang-types {
    prefix yang;
  }
  import huawei-extension {
    prefix ext;
  }
  include huawei-devm-action;
  include huawei-devm-type;
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Global configuration.";

  revision 2020-08-07 {
    description
      "Add container active-hardware-alarm-infos and history-hardware-alarm-infos.";
    reference "Huawei private.";
  }
  revision 2020-06-04 {
    description
      "Add units of up-to-last-clean, alarm-exist-days, enable-transmission-delay and physical-bandwidth.
       Modify operation-exclude for list chassis, mpu-board, lpu-board, card and port.
       Delete leaf current-id, next-id, current-run-mode and next-run-mode.
       Modify the description of port position.";
    reference "Huawei private.";
  }
  revision 2020-05-07 {
    description
      "Modify spelling errors.";
    reference "Huawei private.";
  }
  revision 2020-04-10 {
    description
      "Modify description warnings.";
    reference "Huawei private.";
  }
  revision 2020-03-17 {
    description
      "Modify description warnings and delete the countiner optical-info.";
    reference "Huawei private.";
  }
  revision 2020-03-11 {
    description
      "Add a new countiner optical-info which mainly describes the information of the optical transceiver.";
    reference "Huawei private.";
  }
  revision 2020-02-29 {
    description
      "Modify syntax errors.";
    reference "Huawei private.";
  }
  revision 2020-02-14 {
    description
      "Add operation-exclude for list chassis, mpu-board, lpu-board, card and port. Modify the units of dust-clean-cycle from days to d.";
    reference "Huawei private.";
  }
  revision 2019-09-09 {
    description
      "Add new leafs.";
    reference "Huawei private.";
  }
  revision 2019-04-05 {
    description
      "Initial revision.";
    reference "Huawei private.";
  }
  ext:task-name "device-mgr";

  augment "/ncs:devices/ncs:device/ncs:config" {
    container devm {
      tailf:ncs-device-type "netconf";
      tailf:display-when "not(../../ncs:module) or ../../ncs:module[ncs:name='huawei-devm']";
      description
        "Global configuration.";
      // NCS drop config false container 'physical-entitys'
      container logic-entitys {
        description
          "List of information about logical entity.";
        list logic-entity {
          key "class position serial-number";
          description
            "Configure information about a logical entity.";
          leaf class {
            type entity-class-type;
            description
              "Entity class.";
          }
          leaf position {
            type pub-type:position;
            description
              "Entity position.";
          }
          leaf serial-number {
            type string {
              length "0..32";
            }
            description
              "Entity number.";
          }
          leaf vendor-type {
            type hardware-type;
            default "unknown";
            description
              "Type of a hardware entity.";
          }
          // NCS drop config false leaf name
          // NCS drop config false leaf 'entity-description'
          // NCS drop config false leaf index
          // NCS drop config false leaf 'oper-state'
          // NCS drop config false leaf 'parent-index'
          // NCS drop config false leaf 'parent-relative-position'
          leaf memo {
            type string {
              length "0..256";
            }
            description
              "Chassis Description.";
          }
        }
      }
      container chassiss {
        ext:operation-exclude "create";
        description
          "List of chassis.";
        list chassis {
          key "position";
          ext:operation-exclude "create";
          description
            "Specify chassis.";
          ext:generated-by "system";
          leaf position {
            type string {
              length "1..32";
            }
            description
              "Chassis position.";
          }
          // NCS drop config false leaf index
          // NCS drop config false leaf type
          // NCS drop config false leaf 'service-type'
          // NCS drop config false leaf 'slot-num'
          // NCS drop config false leaf 'board-num'
          // NCS drop config false leaf 'fan-num'
          // NCS drop config false leaf 'power-num'
          // NCS drop config false leaf 'up-time'
          // NCS drop config false leaf 'status-last-change'
          // NCS drop config false leaf 'entity-last-change'
          leaf dust-clean-cycle {
            type uint32 {
              range "0..65535";
            }
            units "d";
            default "90";
            description
              "Interval at which air filter dust is cleaned.";
          }
          // NCS drop config false leaf 'last-clean-date'
          // NCS drop config false leaf 'up-to-last-clean'
          // NCS drop config false leaf 'alarm-exist-days'
          // NCS drop config false container 'monitor-board-changes'
        }
      }
      // NCS drop config false container 'logic-containers'
      // NCS drop config false container containers
      container mpu-boards {
        ext:operation-exclude "create";
        description
          "List of MPU.";
        list mpu-board {
          key "position";
          ext:operation-exclude "create";
          description
            "Specify MPU.";
          ext:generated-by "system";
          leaf position {
            type string {
              length "1..32";
            }
            description
              "MPU position.";
          }
          // NCS drop config false leaf index
          // NCS drop config false leaf 'board-type'
          // NCS drop config false leaf 'up-time'
          // NCS drop config false leaf 'sdram-size'
          // NCS drop config false leaf 'nvram-size'
          // NCS drop config false leaf 'flash-size'
          // NCS drop config false leaf 'ls-role'
          // NCS drop config false leaf 'last-reset-time'
          // NCS drop config false leaf 'last-reset-reason'
          // NCS drop config false leaf 'register-time'
          // NCS drop config false leaf 'is-register'
          // NCS drop config false leaf 'cfcard-size'
          // NCS drop config false leaf 'cfcard2-size'
        }
      }
      container lpu-boards {
        ext:operation-exclude "create";
        description
          "List of LPU.";
        list lpu-board {
          key "position";
          ext:operation-exclude "create";
          description
            "Specify LPU.";
          ext:generated-by "system";
          leaf position {
            type string {
              length "1..32";
            }
            description
              "LPU position.";
          }
          // NCS drop config false leaf index
          // NCS drop config false leaf 'board-type'
          // NCS drop config false leaf 'sdram-size'
          // NCS drop config false leaf 'flash-size'
          // NCS drop config false leaf 'up-time'
          // NCS drop config false leaf 'np-rdram-size'
          // NCS drop config false leaf 'np-sram-size'
          // NCS drop config false leaf 'service-type'
          // NCS drop config false leaf 'next-service-type'
          // NCS drop config false leaf 'pic-num'
          // NCS drop config false leaf 'sub-slot-num'
          leaf clock-8k-port {
            type string {
              length "0..32";
            }
            description
              "8K clock port.";
          }
          // NCS drop config false leaf 'current-l3-clk'
          // NCS drop config false leaf 'register-time'
          // NCS drop config false leaf 'is-register'
        }
      }
      // NCS drop config false container 'sfu-boards'
      container cards {
        ext:operation-exclude "create";
        description
          "List of card.";
        list card {
          key "position index";
          ext:operation-exclude "create";
          description
            "Specify card.";
          ext:generated-by "system";
          leaf position {
            type string {
              length "1..32";
            }
            description
              "Card position.";
          }
          leaf index {
            type uint32;
            description
              "Card index.";
          }
          // NCS drop config false leaf type
          // NCS drop config false leaf 'hard-type'
          // NCS drop config false leaf 'port-num'
          // NCS drop config false leaf 'init-status'
          // NCS drop config false leaf 'register-status'
          // NCS drop config false container pic
        }
      }
      // NCS drop config false container 'cf-cards'
      container ports {
        ext:operation-exclude "create";
        description
          "List of port.";
        list port {
          key "position";
          ext:operation-exclude "create";
          description
            "Specify port.";
          ext:generated-by "system";
          leaf position {
            type string {
              length "1..32";
            }
            description
              "Port position. The position is expressed in the format of slotID/cardID/portID. For example, 1/0/1. Here 1/0/1 is an example. The value may vary with devices.";
          }
          // NCS drop config false leaf index
          leaf admin-state {
            type entity-admin-state;
            must "((../admin-state='active' or ../admin-state='inactive') )" {
              tailf:xpath-root 3;
            }
            default "active";
            description
              "Port administration state.";
          }
          // NCS drop config false leaf type
          // NCS drop config false leaf 'hard-type'
          leaf loopback-mode {
            type loopback-state-type;
            default "noLoopback";
            description
              "Port loopback mode.";
          }
          leaf enable-transmission-delay {
            type uint32 {
              range "0..86400000";
            }
            units "ms";
            default "0";
            description
              "Enable port transmission delay (ms).";
          }
          // NCS drop config false leaf 'last-up-time'
          // NCS drop config false leaf 'last-down-time'
          // NCS drop config false leaf 'medium-type'
          // NCS drop config false leaf 'optical-equipped'
          // NCS drop config false leaf 'physical-bandwidth'
        }
      }
      container logic-ports {
        description
          "List of logic port.";
        list logic-port {
          key "position serial-number port-type";
          description
            "Configure logic port.";
          leaf position {
            type pub-type:position;
            description
              "Port position. The position is expressed in the format of slotID/cardID/portID. For example, 1/0/1. Here 1/0/1 is an example. The value may vary with devices.";
          }
          leaf serial-number {
            type string {
              length "0..32";
            }
            description
              "Port number.";
          }
          leaf port-type {
            type port-class-type;
            description
              "Port type, such as ETH, POS, or OTN.";
          }
          // NCS drop config false leaf index
          // NCS drop config false leaf 'admin-state'
          leaf hard-type {
            type port-hardware-type;
            mandatory true;
            description
              "Hardware type of a port.";
          }
          // NCS drop config false leaf 'enable-transmission-delay'
          leaf level {
            type port-level-type;
            mandatory true;
            description
              "Port speed level.";
          }
        }
      }
      // NCS drop config false container 'entity-classes'
      // NCS drop config false container 'inconsistent-entitys'
      // NCS drop config false container offlines
      // NCS drop config false container 'schedule-reboot'
      // NCS drop config false container 'active-hardware-alarm-infos'
      // NCS drop config false container 'history-hardware-alarm-infos'
    }
  }
  augment "/ncs:devices/ncs:device/ncs:live-status" {
    container devm {
      tailf:ncs-device-type "netconf";
      tailf:display-when "not(../../ncs:module) or ../../ncs:module[ncs:name='huawei-devm'] or (../../ncs:live-status-protocol[not(ncs:capability)]) or (../../ncs:live-status-protocol/ncs:capability/ncs:module[.='huawei-devm'])";
      description
        "Global configuration.";
      container physical-entitys {
        status deprecated;
        description
          "List of physical entities.";
        list physical-entity {
          key "class position serial-number";
          status deprecated;
          description
            "Operational data of physical entities.";
          leaf class {
            type live_ncs_entity-class-type;
            status deprecated;
            description
              "Entity class.";
          }
          leaf position {
            type string {
              length "1..32";
            }
            status deprecated;
            description
              "Entity position.";
          }
          leaf serial-number {
            type string {
              length "0..32";
            }
            status deprecated;
            description
              "Entity number.";
          }
          leaf index {
            type uint32;
            status deprecated;
            description
              "Entity index.";
          }
          leaf chassis-index {
            type uint32;
            status deprecated;
            description
              "Chassis index.";
          }
          leaf board-index {
            type uint32;
            status deprecated;
            description
              "Board index.";
          }
          leaf name {
            type string {
              length "0..128";
            }
            status deprecated;
            description
              "Entity name.";
          }
          leaf entity-description {
            type string {
              length "0..256";
            }
            status deprecated;
            description
              "Entity description.";
          }
          leaf alias {
            type string {
              length "0..128";
            }
            status deprecated;
            description
              "Entity alias.";
          }
          leaf vendor-type {
            type string {
              length "0..30";
            }
            status deprecated;
            description
              "Type of a hardware entity.";
          }
          leaf contained-index {
            type uint32;
            status deprecated;
            description
              "Information about the parent index of an entity.";
          }
          leaf parent-relative-position {
            type uint32;
            status deprecated;
            description
              "Position of an entity relative to its parent entity.";
          }
          leaf hardware-version {
            type string {
              length "0..128";
            }
            status deprecated;
            description
              "Hardware version.";
          }
          leaf firmware-version {
            type string {
              length "0..128";
            }
            status deprecated;
            description
              "Firmware version.";
          }
          leaf software-version {
            type string {
              length "0..128";
            }
            status deprecated;
            description
              "Software version.";
          }
          leaf module-name {
            type string {
              length "0..128";
            }
            status deprecated;
            description
              "Module name.";
          }
          leaf is-fru {
            type boolean;
            status deprecated;
            description
              "Whether the entity a replaceable unit.";
          }
          leaf admin-state {
            type live_ncs_entity-admin-state;
            status deprecated;
            description
              "Administration state (read-only).";
          }
          leaf running-state {
            type live_ncs_entity-oper-state-type;
            status deprecated;
            description
              "Running state of an entity (read-only).";
          }
          leaf standby-state {
            type live_ncs_entity-standby-state;
            status deprecated;
            description
              "Active/standby state.";
          }
          leaf system-oid {
            type string {
              length "1..128";
            }
            status deprecated;
            description
              "Entity OID.";
          }
          leaf ls-name {
            type string {
              length "1..32";
            }
            status deprecated;
            description
              "The LS name of the entity.";
          }
        }
      }
      container logic-entitys {
        description
          "List of information about logical entity.";
        list logic-entity {
          key "class position serial-number";
          description
            "Configure information about a logical entity.";
          leaf class {
            type live_ncs_entity-class-type;
            description
              "Entity class.";
          }
          leaf position {
            type pub-type:live_ncs_position;
            description
              "Entity position.";
          }
          leaf serial-number {
            type string {
              length "0..32";
            }
            description
              "Entity number.";
          }
          leaf vendor-type {
            type live_ncs_hardware-type;
            // NCS drop default statement
            description
              "Type of a hardware entity.";
          }
          leaf name {
            type string {
              length "0..128";
            }
            description
              "Entity name.";
          }
          leaf entity-description {
            type string {
              length "0..256";
            }
            description
              "Entity description.";
          }
          leaf index {
            type uint32;
            description
              "Entity index.";
          }
          leaf oper-state {
            type live_ncs_entity-oper-state-type;
            description
              "Operation state of an entity (read-only).";
          }
          leaf parent-index {
            type uint32;
            description
              "Information about the parent index of an entity.";
          }
          leaf parent-relative-position {
            type uint32;
            description
              "Position of an entity relative to its parent entity.";
          }
          leaf memo {
            type string {
              length "0..256";
            }
            description
              "Chassis Description.";
          }
        }
      }
      container chassiss {
        ext:operation-exclude "create";
        description
          "List of chassis.";
        list chassis {
          key "position";
          ext:operation-exclude "create";
          description
            "Specify chassis.";
          ext:generated-by "system";
          leaf position {
            type string {
              length "1..32";
            }
            description
              "Chassis position.";
          }
          leaf index {
            type uint32;
            description
              "Chassis index.";
          }
          leaf type {
            type string {
              length "0..30";
            }
            description
              "Chassis type.";
          }
          leaf service-type {
            type string {
              length "0..30";
            }
            description
              "Chassis service type.";
          }
          leaf slot-num {
            type uint32;
            description
              "Number of slots on a chassis.";
          }
          leaf board-num {
            type uint32;
            description
              "Number of boards on a chassis.";
          }
          leaf fan-num {
            type uint32;
            description
              "Number of fans on a chassis.";
          }
          leaf power-num {
            type uint32;
            description
              "Number of power modules for a chassis.";
          }
          leaf up-time {
            type pub-type:live_ncs_time-tick;
            description
              "Running time of a chassis.";
          }
          leaf status-last-change {
            type pub-type:live_ncs_time-tick;
            description
              "Time when the entity running status last changed.";
          }
          leaf entity-last-change {
            type pub-type:live_ncs_time-tick;
            description
              "Time when the entity on chassis last changed.";
          }
          leaf dust-clean-cycle {
            type uint32 {
              range "0..65535";
            }
            units "d";
            // NCS drop default statement
            description
              "Interval at which air filter dust is cleaned.";
          }
          leaf last-clean-date {
            type string {
              length "1..128";
            }
            description
              "Date when dust was last cleaned.";
          }
          leaf up-to-last-clean {
            type uint32 {
              range "0..4294967295";
            }
            units "d";
            // NCS drop default statement
            description
              "Time past since dust was last cleaned.";
          }
          leaf alarm-exist-days {
            type uint32 {
              range "0..4294967295";
            }
            units "d";
            // NCS drop default statement
            description
              "Alarm existence days.";
          }
          container monitor-board-changes {
            description
              "List of time when board status changes.";
            list monitor-board-change {
              key "board-index";
              description
                "Operational data of time when the status of a board changes.";
              leaf board-index {
                type uint32;
                description
                  "Board index.";
              }
              leaf status-last-change {
                type pub-type:live_ncs_time-tick;
                description
                  "Time when the board running status changes.";
              }
              leaf entity-last-change {
                type pub-type:live_ncs_time-tick;
                description
                  "Time when the board entity changes.";
              }
            }
          }
        }
      }
      container logic-containers {
        description
          "List of logic slot.";
        list logic-container {
          key "position";
          description
            "Operational data of logic slot.";
          leaf position {
            type string {
              length "0..32";
            }
            description
              "Slot position.";
          }
          leaf index {
            type uint32;
            description
              "Slot index.";
          }
          leaf container-type {
            type live_ncs_container-class-type;
            description
              "Slot type.";
          }
          leaf equiped-entity-type {
            type live_ncs_hardware-type;
            description
              "Type of an installed entity.";
          }
          container supported-entity-types {
            description
              "List of supported entity types.";
            list supported-entity-type {
              key "entity-type";
              description
                "Statistics of supported entity types.";
              leaf entity-type {
                type live_ncs_hardware-type;
                description
                  "Type of an equipped entity.";
              }
            }
          }
        }
      }
      container containers {
        description
          "List of slot.";
        list container {
          key "position";
          description
            "Operational data of slot.";
          leaf position {
            type string {
              length "1..32";
            }
            description
              "Slot position.";
          }
          leaf index {
            type uint32;
            description
              "Slot index.";
          }
          leaf type {
            type string {
              length "0..30";
            }
            description
              "Slot type.";
          }
          leaf equiped-entity-type {
            type string {
              length "0..30";
            }
            description
              "Type of an equipped entity.";
          }
          container supported-entity-types {
            description
              "List of supported entity types.";
            list supported-entity-type {
              key "entity-type";
              description
                "Statistics of supported entity types.";
              leaf entity-type {
                type string {
                  length "0..30";
                }
                description
                  "Type of an equipped entity.";
              }
            }
          }
        }
      }
      container mpu-boards {
        ext:operation-exclude "create";
        description
          "List of MPU.";
        list mpu-board {
          key "position";
          ext:operation-exclude "create";
          description
            "Specify MPU.";
          ext:generated-by "system";
          leaf position {
            type string {
              length "1..32";
            }
            description
              "MPU position.";
          }
          leaf index {
            type uint32;
            description
              "MPU index.";
          }
          leaf board-type {
            type string {
              length "0..30";
            }
            description
              "MPU type.";
          }
          leaf up-time {
            type pub-type:live_ncs_time-tick;
            description
              "MPU running time, expressed in the number of timeticks.";
          }
          leaf sdram-size {
            type uint32;
            units "MByte";
            description
              "SDRAM size.";
          }
          leaf nvram-size {
            type uint32;
            units "MByte";
            description
              "NVRAM size.";
          }
          leaf flash-size {
            type uint32;
            units "MByte";
            description
              "Flash size.";
          }
          leaf ls-role {
            type live_ncs_board-role-type;
            description
              "MPU role.";
          }
          leaf last-reset-time {
            type yang:date-and-time;
            description
              "Last reset time.";
          }
          leaf last-reset-reason {
            type string {
              length "0..256";
            }
            description
              "Last reset reason.";
          }
          leaf register-time {
            type yang:date-and-time;
            description
              "Time when a board goes Up.";
          }
          leaf is-register {
            type boolean;
            description
              "Whether the board is register.";
          }
          leaf cfcard-size {
            type uint32;
            units "MB";
            description
              "Cfcard memory size.";
          }
          leaf cfcard2-size {
            type uint32;
            units "MB";
            description
              "Cfcard2 memory size.";
          }
        }
      }
      container lpu-boards {
        ext:operation-exclude "create";
        description
          "List of LPU.";
        list lpu-board {
          key "position";
          ext:operation-exclude "create";
          description
            "Specify LPU.";
          ext:generated-by "system";
          leaf position {
            type string {
              length "1..32";
            }
            description
              "LPU position.";
          }
          leaf index {
            type uint32;
            description
              "LPU index.";
          }
          leaf board-type {
            type string {
              length "0..30";
            }
            description
              "LPU type.";
          }
          leaf sdram-size {
            type uint32;
            units "MByte";
            description
              "SDRAM size.";
          }
          leaf flash-size {
            type uint32;
            units "MByte";
            description
              "Flash size.";
          }
          leaf up-time {
            type pub-type:live_ncs_time-tick;
            description
              "LPU running time, expressed in the number of timeticks.";
          }
          leaf np-rdram-size {
            type uint32;
            units "MByte";
            description
              "NP RDRAM size.";
          }
          leaf np-sram-size {
            type uint32;
            units "MByte";
            description
              "NP SRAM size.";
          }
          leaf service-type {
            type live_ncs_lpu-service-type;
            description
              "Service type.";
          }
          leaf next-service-type {
            type live_ncs_lpu-service-type;
            description
              "Type of next started service board.";
          }
          leaf pic-num {
            type uint32;
            description
              "Number of PICs on an LPU.";
          }
          leaf sub-slot-num {
            type uint32;
            description
              "Number of slots on a subcard.";
          }
          leaf clock-8k-port {
            type string {
              length "0..32";
            }
            description
              "8K clock port.";
          }
          leaf current-l3-clk {
            type uint32;
            description
              "L3 clock source being used.";
          }
          leaf register-time {
            type yang:date-and-time;
            description
              "Time when a board goes Up.";
          }
          leaf is-register {
            type boolean;
            description
              "Whether the board is register.";
          }
        }
      }
      container sfu-boards {
        description
          "List of SFU.";
        list sfu-board {
          key "position";
          description
            "Operational data of SFU.";
          leaf position {
            type string {
              length "1..32";
            }
            description
              "SFU position.";
          }
          leaf index {
            type uint32;
            description
              "SFU index.";
          }
          leaf board-type {
            type string {
              length "0..30";
            }
            description
              "SFU type.";
          }
          leaf sdram-size {
            type uint32;
            units "MByte";
            description
              "SDRAM size.";
          }
          leaf flash-size {
            type uint32;
            units "MByte";
            description
              "Flash size.";
          }
          leaf up-time {
            type pub-type:live_ncs_time-tick;
            description
              "SFU running time, expressed in the number of timeticks.";
          }
          leaf register-time {
            type yang:date-and-time;
            description
              "Time when a board goes Up.";
          }
          leaf is-register {
            type boolean;
            description
              "Whether the board is register.";
          }
        }
      }
      container cards {
        ext:operation-exclude "create";
        description
          "List of card.";
        list card {
          key "position index";
          ext:operation-exclude "create";
          description
            "Specify card.";
          ext:generated-by "system";
          leaf position {
            type string {
              length "1..32";
            }
            description
              "Card position.";
          }
          leaf index {
            type uint32;
            description
              "Card index.";
          }
          leaf type {
            type string {
              length "0..30";
            }
            description
              "Elabel type of a card.";
          }
          leaf hard-type {
            type string {
              length "0..30";
            }
            description
              "Hardware type of a card.";
          }
          leaf port-num {
            type uint32;
            description
              "Number of ports on a card.";
          }
          leaf init-status {
            type live_ncs_init-status-type;
            description
              "Initialized status of a card.";
          }
          leaf register-status {
            type live_ncs_register-status-type;
            description
              "Registered status of a card.";
          }
          container pic {
            description
              "Operational data of physical interface card.";
            leaf logic-status {
              type live_ncs_logic-status-type;
              description
                "Logic loading status.";
            }
            leaf up-time {
              type yang:date-and-time;
              description
                "Time when a card goes Up.";
            }
          }
        }
      }
      container cf-cards {
        description
          "List of CF card.";
        list cf-card {
          key "position serial-number";
          description
            "Operational data of CF card.";
          leaf position {
            type string {
              length "1..32";
            }
            description
              "CF card position.";
          }
          leaf serial-number {
            type string {
              length "1..32";
            }
            description
              "Number of a CF card.";
          }
          leaf index {
            type uint32;
            description
              "CF card index.";
          }
          leaf card-type {
            type string {
              length "0..30";
            }
            description
              "CF card type.";
          }
          leaf memory-size {
            type uint32;
            units "kB";
            description
              "Memory size of a CF card.";
          }
          leaf memory-used {
            type uint32;
            units "kB";
            description
              "Used memory of a CF card.";
          }
          leaf memory-free {
            type uint32;
            units "kB";
            description
              "Available memory of a CF card.";
          }
        }
      }
      container ports {
        ext:operation-exclude "create";
        description
          "List of port.";
        list port {
          key "position";
          ext:operation-exclude "create";
          description
            "Specify port.";
          ext:generated-by "system";
          leaf position {
            type string {
              length "1..32";
            }
            description
              "Port position. The position is expressed in the format of slotID/cardID/portID. For example, 1/0/1. Here 1/0/1 is an example. The value may vary with devices.";
          }
          leaf index {
            type uint32 {
              range "1..4294967295";
            }
            // NCS drop default statement
            ext:support-filter "true";
            description
              "Port index.";
          }
          leaf admin-state {
            type live_ncs_entity-admin-state;
            // NCS drop must statement
            // NCS drop default statement
            description
              "Port administration state.";
          }
          leaf type {
            type live_ncs_port-class-type;
            ext:support-filter "true";
            description
              "Port type, such as ETH, POS, or OTN.";
          }
          leaf hard-type {
            type live_ncs_port-hardware-type;
            description
              "Hardware type of a port.";
          }
          leaf loopback-mode {
            type live_ncs_loopback-state-type;
            // NCS drop default statement
            description
              "Port loopback mode.";
          }
          leaf enable-transmission-delay {
            type uint32 {
              range "0..86400000";
            }
            units "ms";
            // NCS drop default statement
            description
              "Enable port transmission delay (ms).";
          }
          leaf last-up-time {
            type yang:date-and-time;
            description
              "Time when a port last went Up.";
          }
          leaf last-down-time {
            type yang:date-and-time;
            description
              "Time when a port last went Down.";
          }
          leaf medium-type {
            type live_ncs_port-medium-type;
            ext:support-filter "true";
            description
              "Port medium type.";
          }
          leaf optical-equipped {
            type boolean;
            description
              "Flag indicating whether an optical transceiver is equipped.";
          }
          leaf physical-bandwidth {
            type uint64 {
              range "0..10000000000000";
            }
            units "bit/s";
            // NCS drop default statement
            description
              "Port physical bandwidth.";
          }
        }
      }
      container logic-ports {
        description
          "List of logic port.";
        list logic-port {
          key "position serial-number port-type";
          description
            "Configure logic port.";
          leaf position {
            type pub-type:live_ncs_position;
            description
              "Port position. The position is expressed in the format of slotID/cardID/portID. For example, 1/0/1. Here 1/0/1 is an example. The value may vary with devices.";
          }
          leaf serial-number {
            type string {
              length "0..32";
            }
            description
              "Port number.";
          }
          leaf port-type {
            type live_ncs_port-class-type;
            description
              "Port type, such as ETH, POS, or OTN.";
          }
          leaf index {
            type uint32 {
              range "1..4294967295";
            }
            // NCS drop default statement
            description
              "Port index.";
          }
          leaf admin-state {
            type live_ncs_entity-admin-state;
            description
              "Port administration state.";
          }
          leaf hard-type {
            type live_ncs_port-hardware-type;
            // NCS drop mandatory statement
            description
              "Hardware type of a port.";
          }
          leaf enable-transmission-delay {
            type uint32 {
              range "0..86400000";
            }
            // NCS drop default statement
            description
              "Enable port transmission delay (ms).";
          }
          leaf level {
            type live_ncs_port-level-type;
            // NCS drop mandatory statement
            description
              "Port speed level.";
          }
        }
      }
      container entity-classes {
        description
          "List of entity capability.";
        list entity-class {
          key "class-name";
          description
            "Statistics of entity capability.";
          leaf class-name {
            type live_ncs_entity-class-type;
            description
              "Entity type.";
          }
          leaf is-resetable {
            type boolean;
            description
              "Flag indicating whether the entity can be reset.";
          }
          leaf is-switchoverable {
            type boolean;
            description
              "Flag indicating whether a switchover can be performed on the entity.";
          }
        }
      }
      container inconsistent-entitys {
        description
          "List of incompatible entity.";
        list inconsistent-entity {
          key "class position serial-number";
          description
            "Operational data of incompatible entity.";
          leaf class {
            type live_ncs_entity-class-type;
            description
              "Entity class.";
          }
          leaf position {
            type pub-type:live_ncs_position;
            description
              "Position.";
          }
          leaf serial-number {
            type string {
              length "0..32";
            }
            description
              "Number.";
          }
          leaf logical-type {
            type live_ncs_hardware-type;
            description
              "Logical type.";
          }
          leaf physical-type {
            type live_ncs_hardware-type;
            description
              "Physical type.";
          }
          leaf oper-state {
            type live_ncs_entity-oper-state-type;
            description
              "Running status.";
          }
        }
      }
      container offlines {
        description
          "List of offline configuration.";
        list offline {
          key "class position";
          description
            "Operational data of offline configuration.";
          leaf class {
            type live_ncs_offline-class-type;
            description
              "Class.";
          }
          leaf position {
            type string {
              length "1..32";
            }
            description
              "Position.";
          }
        }
      }
      container schedule-reboot {
        description
          "Statistics of schedule reboot date time.";
        leaf datetime {
          type yang:date-and-time;
          description
            "At Time.";
        }
        leaf delay-time {
          type string {
            length "1..49";
          }
          description
            "Delay time.";
        }
      }
      container active-hardware-alarm-infos {
        description
          "List of active hardware alarms.";
        list active-hardware-alarm-info {
          key "sequence";
          description
            "Statistics of information about an active hardware alarm.";
          leaf sequence {
            type uint32 {
              range "1..4294967295";
            }
            description
              "Sequence number of an active alarm.";
          }
          leaf position {
            type string {
              length "1..32";
            }
            ext:support-filter "true";
            description
              "Hardware entity position.";
          }
          leaf alarm-id {
            type uint32 {
              range "1..4294967295";
            }
            description
              "ID of an active alarm.";
          }
          leaf level {
            type string {
              length "1..24";
            }
            description
              "Severity of an active alarm.";
          }
          leaf generated-time {
            type yang:date-and-time;
            description
              "Time when an active alarm is generated.";
          }
          leaf info {
            type string {
              length "1..256";
            }
            description
              "Alarm information.";
          }
        }
      }
      container history-hardware-alarm-infos {
        description
          "List of historical hardware alarms.";
        list history-hardware-alarm-info {
          key "sequence";
          description
            "Statistics of information about a historical hardware alarm.";
          leaf sequence {
            type uint32 {
              range "1..4294967295";
            }
            description
              "Sequence number of a historical alarm.";
          }
          leaf position {
            type string {
              length "1..32";
            }
            ext:support-filter "true";
            description
              "Hardware entity position.";
          }
          leaf alarm-id {
            type uint32 {
              range "1..4294967295";
            }
            description
              "ID of a historical alarm.";
          }
          leaf level {
            type string {
              length "1..24";
            }
            description
              "Severity of a historical alarm.";
          }
          leaf generated-time {
            type yang:date-and-time;
            description
              "Time when a historical alarm is generated.";
          }
          leaf info {
            type string {
              length "1..256";
            }
            description
              "Alarm information.";
          }
        }
      }
    }
  }
  augment "/ncs:devices/ncs:template/ncs:ned-id/ncs:config" {
    container devm {
      description
        "Global configuration.";
      // NCS drop config false container 'physical-entitys'
      container logic-entitys {
        description
          "List of information about logical entity.";
        list logic-entity {
          // NCS patched for predictable order
          ordered-by user;
          key "class position serial-number";
          description
            "Configure information about a logical entity.";
          leaf class {
            type ncs_template_entity-class-type;
            description
              "Entity class.";
          }
          leaf position {
            type pub-type:ncs_template_position;
            description
              "Entity position.";
          }
          leaf serial-number {
            type string;
            description
              "Entity number.";
          }
          leaf vendor-type {
            type ncs_template_hardware-type;
            // NCS drop default statement
            description
              "Type of a hardware entity.";
          }
          // NCS drop config false leaf name
          // NCS drop config false leaf 'entity-description'
          // NCS drop config false leaf index
          // NCS drop config false leaf 'oper-state'
          // NCS drop config false leaf 'parent-index'
          // NCS drop config false leaf 'parent-relative-position'
          leaf memo {
            type string;
            description
              "Chassis Description.";
          }
        }
      }
      container chassiss {
        ext:operation-exclude "create";
        description
          "List of chassis.";
        list chassis {
          // NCS patched for predictable order
          ordered-by user;
          key "position";
          ext:operation-exclude "create";
          description
            "Specify chassis.";
          ext:generated-by "system";
          leaf position {
            type string;
            description
              "Chassis position.";
          }
          // NCS drop config false leaf index
          // NCS drop config false leaf type
          // NCS drop config false leaf 'service-type'
          // NCS drop config false leaf 'slot-num'
          // NCS drop config false leaf 'board-num'
          // NCS drop config false leaf 'fan-num'
          // NCS drop config false leaf 'power-num'
          // NCS drop config false leaf 'up-time'
          // NCS drop config false leaf 'status-last-change'
          // NCS drop config false leaf 'entity-last-change'
          leaf dust-clean-cycle {
            type string;
            units "d";
            // NCS drop default statement
            description
              "Interval at which air filter dust is cleaned.";
          }
          // NCS drop config false leaf 'last-clean-date'
          // NCS drop config false leaf 'up-to-last-clean'
          // NCS drop config false leaf 'alarm-exist-days'
          // NCS drop config false container 'monitor-board-changes'
        }
      }
      // NCS drop config false container 'logic-containers'
      // NCS drop config false container containers
      container mpu-boards {
        ext:operation-exclude "create";
        description
          "List of MPU.";
        list mpu-board {
          // NCS patched for predictable order
          ordered-by user;
          key "position";
          ext:operation-exclude "create";
          description
            "Specify MPU.";
          ext:generated-by "system";
          leaf position {
            type string;
            description
              "MPU position.";
          }
          // NCS drop config false leaf index
          // NCS drop config false leaf 'board-type'
          // NCS drop config false leaf 'up-time'
          // NCS drop config false leaf 'sdram-size'
          // NCS drop config false leaf 'nvram-size'
          // NCS drop config false leaf 'flash-size'
          // NCS drop config false leaf 'ls-role'
          // NCS drop config false leaf 'last-reset-time'
          // NCS drop config false leaf 'last-reset-reason'
          // NCS drop config false leaf 'register-time'
          // NCS drop config false leaf 'is-register'
          // NCS drop config false leaf 'cfcard-size'
          // NCS drop config false leaf 'cfcard2-size'
        }
      }
      container lpu-boards {
        ext:operation-exclude "create";
        description
          "List of LPU.";
        list lpu-board {
          // NCS patched for predictable order
          ordered-by user;
          key "position";
          ext:operation-exclude "create";
          description
            "Specify LPU.";
          ext:generated-by "system";
          leaf position {
            type string;
            description
              "LPU position.";
          }
          // NCS drop config false leaf index
          // NCS drop config false leaf 'board-type'
          // NCS drop config false leaf 'sdram-size'
          // NCS drop config false leaf 'flash-size'
          // NCS drop config false leaf 'up-time'
          // NCS drop config false leaf 'np-rdram-size'
          // NCS drop config false leaf 'np-sram-size'
          // NCS drop config false leaf 'service-type'
          // NCS drop config false leaf 'next-service-type'
          // NCS drop config false leaf 'pic-num'
          // NCS drop config false leaf 'sub-slot-num'
          leaf clock-8k-port {
            type string;
            description
              "8K clock port.";
          }
          // NCS drop config false leaf 'current-l3-clk'
          // NCS drop config false leaf 'register-time'
          // NCS drop config false leaf 'is-register'
        }
      }
      // NCS drop config false container 'sfu-boards'
      container cards {
        ext:operation-exclude "create";
        description
          "List of card.";
        list card {
          // NCS patched for predictable order
          ordered-by user;
          key "position index";
          ext:operation-exclude "create";
          description
            "Specify card.";
          ext:generated-by "system";
          leaf position {
            type string;
            description
              "Card position.";
          }
          leaf index {
            type string;
            description
              "Card index.";
          }
          // NCS drop config false leaf type
          // NCS drop config false leaf 'hard-type'
          // NCS drop config false leaf 'port-num'
          // NCS drop config false leaf 'init-status'
          // NCS drop config false leaf 'register-status'
          // NCS drop config false container pic
        }
      }
      // NCS drop config false container 'cf-cards'
      container ports {
        ext:operation-exclude "create";
        description
          "List of port.";
        list port {
          // NCS patched for predictable order
          ordered-by user;
          key "position";
          ext:operation-exclude "create";
          description
            "Specify port.";
          ext:generated-by "system";
          leaf position {
            type string;
            description
              "Port position. The position is expressed in the format of slotID/cardID/portID. For example, 1/0/1. Here 1/0/1 is an example. The value may vary with devices.";
          }
          // NCS drop config false leaf index
          leaf admin-state {
            type ncs_template_entity-admin-state;
            // NCS drop must statement
            // NCS drop default statement
            description
              "Port administration state.";
          }
          // NCS drop config false leaf type
          // NCS drop config false leaf 'hard-type'
          leaf loopback-mode {
            type ncs_template_loopback-state-type;
            // NCS drop default statement
            description
              "Port loopback mode.";
          }
          leaf enable-transmission-delay {
            type string;
            units "ms";
            // NCS drop default statement
            description
              "Enable port transmission delay (ms).";
          }
          // NCS drop config false leaf 'last-up-time'
          // NCS drop config false leaf 'last-down-time'
          // NCS drop config false leaf 'medium-type'
          // NCS drop config false leaf 'optical-equipped'
          // NCS drop config false leaf 'physical-bandwidth'
        }
      }
      container logic-ports {
        description
          "List of logic port.";
        list logic-port {
          // NCS patched for predictable order
          ordered-by user;
          key "position serial-number port-type";
          description
            "Configure logic port.";
          leaf position {
            type pub-type:ncs_template_position;
            description
              "Port position. The position is expressed in the format of slotID/cardID/portID. For example, 1/0/1. Here 1/0/1 is an example. The value may vary with devices.";
          }
          leaf serial-number {
            type string;
            description
              "Port number.";
          }
          leaf port-type {
            type ncs_template_port-class-type;
            description
              "Port type, such as ETH, POS, or OTN.";
          }
          // NCS drop config false leaf index
          // NCS drop config false leaf 'admin-state'
          leaf hard-type {
            type ncs_template_port-hardware-type;
            // NCS drop mandatory statement
            description
              "Hardware type of a port.";
          }
          // NCS drop config false leaf 'enable-transmission-delay'
          leaf level {
            type ncs_template_port-level-type;
            // NCS drop mandatory statement
            description
              "Port speed level.";
          }
        }
      }
      // NCS drop config false container 'entity-classes'
      // NCS drop config false container 'inconsistent-entitys'
      // NCS drop config false container offlines
      // NCS drop config false container 'schedule-reboot'
      // NCS drop config false container 'active-hardware-alarm-infos'
      // NCS drop config false container 'history-hardware-alarm-infos'
    }
  }
}
