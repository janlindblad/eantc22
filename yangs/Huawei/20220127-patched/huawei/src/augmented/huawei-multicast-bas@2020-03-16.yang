module huawei-multicast-bas {
  // Generated by yanger -t ncs
  tailf:mount-id "huawei-nc-1.0:huawei-nc-1.0";
  tailf:ncs-device-type "netconf";

  namespace "urn:huawei:yang:huawei-multicast-bas";
  prefix mcbas;

  import huawei-ifm {
    prefix ifm;
  }
  import huawei-extension {
    prefix ext;
  }
  import huawei-bras-basic-access {
    prefix bras-basic-access;
  }
  import huawei-network-instance {
    prefix ni;
  }
  import huawei-l3vpn {
    prefix l3vpn;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Multicast for BRAS access.";

  revision 2020-03-16 {
    description
      "Modify addr-family-type enumeration name.";
    reference "Huawei private.";
  }
  revision 2019-03-30 {
    description
      "Init revision.";
    reference "Huawei private.";
  }
  ext:task-name "mcast-base";

  typedef ncs_template_addr-family-type {
    type string;
    description
      "Address family.";
  }

  typedef ncs_rpc_notif_addr-family-type {
    type enumeration {
      enum "ipv4-unicast" {
        value 1;
        description
          "IPv4 unicast.";
      }
      enum "ipv6-unicast" {
        value 2;
        description
          "IPv6 unicast.";
      }
    }
    description
      "Address family.";
  }

  typedef live_ncs_addr-family-type {
    type enumeration {
      enum "ipv4-unicast" {
        value 1;
        description
          "IPv4 unicast.";
      }
      enum "ipv6-unicast" {
        value 2;
        description
          "IPv6 unicast.";
      }
    }
    description
      "Address family.";
  }

  typedef addr-family-type {
    type enumeration {
      enum "ipv4-unicast" {
        value 1;
        description
          "IPv4 unicast.";
      }
      enum "ipv6-unicast" {
        value 2;
        description
          "IPv6 unicast.";
      }
    }
    description
      "Address family.";
  }

  augment "/ncs:devices/ncs:template/ncs:ned-id/ncs:config/ifm:ifm/ifm:interfaces/ifm:interface" {
    description
      "Add multicast BAS configuration to the ifm module.";
    container multicast-bas {
      // NCS drop must statement
      description
        "Configure multicast BAS.";
      choice vlan-type {
        description
          "Specify the VLAN-type of multicast BAS user-aggregation.";
        case qinq {
          description
            "QinQ type.";
          leaf user-aggregation-pevlan {
            type string;
            description
              "QINQ PE ID in an outer VLAN tag.";
          }
          leaf user-aggregation-cevlan {
            type string;
            description
              "QINQ CE ID in an inner VLAN tag.";
          }
        }
        case vlan {
          description
            "VLAN type.";
          leaf user-aggregation-vlan {
            type string;
            description
              "VLAN ID in an outer VLAN tag.";
          }
        }
      }
      leaf copy-by-session-enable {
        // NCS drop when statement
        type string;
        // NCS drop default statement
        description
          "Enable/disable multicast copy by-session.";
      }
      leaf copy-by-vlan-enable {
        // NCS drop when statement
        type string;
        // NCS drop default statement
        description
          "Enable/disable multicast copy by-VLAN.";
      }
      leaf authorization-enable {
        type string;
        // NCS drop default statement
        description
          "Enable/disable authorization.";
      }
      leaf igmp-query-auto-send-enable {
        // NCS drop when statement
        type string;
        // NCS drop default statement
        description
          "Enable/disable IGMP to send query message automatically.";
      }
      container binding-vpn-instances {
        description
          "List of multicast binding vpn-instance configurations.";
        list binding-vpn-instance {
          // NCS patched for predictable order
          ordered-by user;
          key "name address-family";
          description
            "Configure multicast binding vpn-instance.";
          leaf name {
            type string;
            // NCS drop must statement
            description
              "VPN instance.";
          }
          leaf address-family {
            type ncs_template_addr-family-type;
            // NCS drop must statement
            // NCS drop must statement
            description
              "Address family, which determines whether an address belongs to IPv4 or IPv6.";
          }
        }
      }
    }
  }
  augment "/ncs:devices/ncs:device/ncs:live-status/ifm:ifm/ifm:interfaces/ifm:interface" {
    description
      "Add multicast BAS configuration to the ifm module.";
    container multicast-bas {
      tailf:ncs-device-type "netconf";
      tailf:display-when "not(../../../../../ncs:module) or ../../../../../ncs:module[ncs:name='huawei-multicast-bas'] or (../../../../../ncs:live-status-protocol[not(ncs:capability)]) or (../../../../../ncs:live-status-protocol/ncs:capability/ncs:module[.='huawei-multicast-bas'])";
      // NCS drop must statement
      description
        "Configure multicast BAS.";
      choice vlan-type {
        description
          "Specify the VLAN-type of multicast BAS user-aggregation.";
        case qinq {
          description
            "QinQ type.";
          leaf user-aggregation-pevlan {
            type uint32 {
              range "1..4094";
            }
            description
              "QINQ PE ID in an outer VLAN tag.";
          }
          leaf user-aggregation-cevlan {
            type uint32 {
              range "1..4094";
            }
            description
              "QINQ CE ID in an inner VLAN tag.";
          }
        }
        case vlan {
          description
            "VLAN type.";
          leaf user-aggregation-vlan {
            type uint32 {
              range "1..4094";
            }
            description
              "VLAN ID in an outer VLAN tag.";
          }
        }
      }
      leaf copy-by-session-enable {
        // NCS drop when statement
        type boolean;
        // NCS drop default statement
        description
          "Enable/disable multicast copy by-session.";
      }
      leaf copy-by-vlan-enable {
        // NCS drop when statement
        type boolean;
        // NCS drop default statement
        description
          "Enable/disable multicast copy by-VLAN.";
      }
      leaf authorization-enable {
        type boolean;
        // NCS drop default statement
        description
          "Enable/disable authorization.";
      }
      leaf igmp-query-auto-send-enable {
        // NCS drop when statement
        type boolean;
        // NCS drop default statement
        description
          "Enable/disable IGMP to send query message automatically.";
      }
      container binding-vpn-instances {
        description
          "List of multicast binding vpn-instance configurations.";
        list binding-vpn-instance {
          key "name address-family";
          description
            "Configure multicast binding vpn-instance.";
          leaf name {
            type leafref {
              path "/ncs:devices/ncs:device/ncs:live-status/ni:network-instance/ni:instances/ni:instance/ni:name" {
                tailf:xpath-root 3;
              }
            }
            // NCS drop must statement
            description
              "VPN instance.";
          }
          leaf address-family {
            type live_ncs_addr-family-type;
            // NCS drop must statement
            // NCS drop must statement
            description
              "Address family, which determines whether an address belongs to IPv4 or IPv6.";
          }
        }
      }
    }
  }
  augment "/ncs:devices/ncs:device/ncs:config/ifm:ifm/ifm:interfaces/ifm:interface" {
    description
      "Add multicast BAS configuration to the ifm module.";
    container multicast-bas {
      tailf:ncs-device-type "netconf";
      tailf:display-when "not(../../../../../ncs:module) or ../../../../../ncs:module[ncs:name='huawei-multicast-bas']";
      must '(./mcbas:user-aggregation-pevlan and ./mcbas:user-aggregation-cevlan) or (not(./mcbas:user-aggregation-pevlan) and not(./mcbas:user-aggregation-cevlan))' {
        tailf:xpath-root 3;
      }
      description
        "Configure multicast BAS.";
      choice vlan-type {
        description
          "Specify the VLAN-type of multicast BAS user-aggregation.";
        case qinq {
          description
            "QinQ type.";
          leaf user-aggregation-pevlan {
            type uint32 {
              range "1..4094";
            }
            description
              "QINQ PE ID in an outer VLAN tag.";
          }
          leaf user-aggregation-cevlan {
            type uint32 {
              range "1..4094";
            }
            description
              "QINQ CE ID in an inner VLAN tag.";
          }
        }
        case vlan {
          description
            "VLAN type.";
          leaf user-aggregation-vlan {
            type uint32 {
              range "1..4094";
            }
            description
              "VLAN ID in an outer VLAN tag.";
          }
        }
      }
      leaf copy-by-session-enable {
        when '../../bras-basic-access:bas/bras-basic-access:layer2-subscriber' {
          tailf:xpath-root 3;
        }
        type boolean;
        default "false";
        description
          "Enable/disable multicast copy by-session.";
      }
      leaf copy-by-vlan-enable {
        when '../../bras-basic-access:bas/bras-basic-access:layer2-subscriber' {
          tailf:xpath-root 3;
        }
        type boolean;
        default "false";
        description
          "Enable/disable multicast copy by-VLAN.";
      }
      leaf authorization-enable {
        type boolean;
        default "false";
        description
          "Enable/disable authorization.";
      }
      leaf igmp-query-auto-send-enable {
        when '../../bras-basic-access:bas/bras-basic-access:layer2-subscriber' {
          tailf:xpath-root 3;
        }
        type boolean;
        default "false";
        description
          "Enable/disable IGMP to send query message automatically.";
      }
      container binding-vpn-instances {
        description
          "List of multicast binding vpn-instance configurations.";
        list binding-vpn-instance {
          key "name address-family";
          description
            "Configure multicast binding vpn-instance.";
          leaf name {
            type leafref {
              path "/ncs:devices/ncs:device/ncs:config/ni:network-instance/ni:instances/ni:instance/ni:name" {
                tailf:xpath-root 3;
              }
            }
            must "../name!='_public_'" {
              tailf:xpath-root 3;
            }
            description
              "VPN instance.";
          }
          leaf address-family {
            type addr-family-type;
            must "../address-family='ipv4-unicast' or ../../../../ifm:type='Virtual-Template'" {
              tailf:xpath-root 3;
            }
            must '/ni:network-instance/ni:instances/ni:instance[ni:name = current()/../name]/l3vpn:afs/l3vpn:af[l3vpn:type=current()]' {
              tailf:xpath-root 3;
            }
            description
              "Address family, which determines whether an address belongs to IPv4 or IPv6.";
          }
        }
      }
    }
  }
}
