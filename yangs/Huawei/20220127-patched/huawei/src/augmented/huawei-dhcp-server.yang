submodule huawei-dhcp-server {
  // Generated by yanger -t ncs
  tailf:mount-id "huawei-nc-1.0:huawei-nc-1.0";

  yang-version 1;
  belongs-to huawei-dhcp {
    prefix dhcp;
  }

  import huawei-network-instance {
    prefix ni;
  }
  import ietf-inet-types {
    prefix inet;
  }
  import huawei-l3vpn {
    prefix l3vpn;
  }
  import huawei-extension {
    prefix ext;
  }
  import huawei-pub-type {
    prefix pub-type;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "This module contains a collection of YANG definitions for managing DHCP server.";

  revision 2020-03-13 {
    description
      "Modify description.";
    reference "Huawei private.";
  }
  revision 2020-03-03 {
    description
      "Initial revision.";
    reference "Huawei private.";
  }

  typedef ncs_template_network-bios-type {
    type string;
    description
      "The type of network BIOS.";
  }

  typedef ncs_template_reply-type {
    type string;
    description
      "DHCP reply type.";
  }

  typedef ncs_template_sip-mode {
    type string;
    description
      "The type of SIP mode.";
  }

  typedef ncs_template_address-status {
    type string;
    description
      "The type of address status.";
  }

  typedef ncs_rpc_notif_network-bios-type {
    type enumeration {
      enum "b-node" {
        value 1;
        description
          "B-node.";
      }
      enum "h-node" {
        value 2;
        description
          "H-node.";
      }
      enum "m-node" {
        value 3;
        description
          "M-node.";
      }
      enum "p-node" {
        value 4;
        description
          "P-node.";
      }
    }
    description
      "The type of network BIOS.";
  }

  typedef ncs_rpc_notif_reply-type {
    type enumeration {
      enum "broadcast-always" {
        value 1;
        description
          "Always broadcast the reply.";
      }
      enum "unicast-always" {
        value 2;
        description
          "Always unicast the reply.";
      }
    }
    description
      "DHCP reply type.";
  }

  typedef ncs_rpc_notif_sip-mode {
    type enumeration {
      enum "ip-mode" {
        value 1;
        description
          "SIP server IP mode.";
      }
      enum "list-mode" {
        value 2;
        description
          "SIP server string mode.";
      }
    }
    description
      "The type of SIP mode.";
  }

  typedef ncs_rpc_notif_address-status {
    type enumeration {
      enum "static-bind-used" {
        value 0;
        description
          "Static bind used status.";
      }
      enum "static-bind" {
        value 1;
        description
          "Static bind status.";
      }
      enum "used" {
        value 2;
        description
          "Used status.";
      }
      enum "expired" {
        value 3;
        description
          "Expired status.";
      }
      enum "conflict" {
        value 4;
        description
          "Conflict status.";
      }
      enum "disable" {
        value 5;
        description
          "Disable status.";
      }
      enum "idle" {
        value 6;
        description
          "Idle status.";
      }
      enum "error" {
        value 7;
        description
          "Error.";
      }
    }
    description
      "The type of address status.";
  }

  typedef live_ncs_network-bios-type {
    type enumeration {
      enum "b-node" {
        value 1;
        description
          "B-node.";
      }
      enum "h-node" {
        value 2;
        description
          "H-node.";
      }
      enum "m-node" {
        value 3;
        description
          "M-node.";
      }
      enum "p-node" {
        value 4;
        description
          "P-node.";
      }
    }
    description
      "The type of network BIOS.";
  }

  typedef live_ncs_reply-type {
    type enumeration {
      enum "broadcast-always" {
        value 1;
        description
          "Always broadcast the reply.";
      }
      enum "unicast-always" {
        value 2;
        description
          "Always unicast the reply.";
      }
    }
    description
      "DHCP reply type.";
  }

  typedef live_ncs_sip-mode {
    type enumeration {
      enum "ip-mode" {
        value 1;
        description
          "SIP server IP mode.";
      }
      enum "list-mode" {
        value 2;
        description
          "SIP server string mode.";
      }
    }
    description
      "The type of SIP mode.";
  }

  typedef live_ncs_address-status {
    type enumeration {
      enum "static-bind-used" {
        value 0;
        description
          "Static bind used status.";
      }
      enum "static-bind" {
        value 1;
        description
          "Static bind status.";
      }
      enum "used" {
        value 2;
        description
          "Used status.";
      }
      enum "expired" {
        value 3;
        description
          "Expired status.";
      }
      enum "conflict" {
        value 4;
        description
          "Conflict status.";
      }
      enum "disable" {
        value 5;
        description
          "Disable status.";
      }
      enum "idle" {
        value 6;
        description
          "Idle status.";
      }
      enum "error" {
        value 7;
        description
          "Error.";
      }
    }
    description
      "The type of address status.";
  }

  typedef network-bios-type {
    type enumeration {
      enum "b-node" {
        value 1;
        description
          "B-node.";
      }
      enum "h-node" {
        value 2;
        description
          "H-node.";
      }
      enum "m-node" {
        value 3;
        description
          "M-node.";
      }
      enum "p-node" {
        value 4;
        description
          "P-node.";
      }
    }
    description
      "The type of network BIOS.";
  }

  typedef reply-type {
    type enumeration {
      enum "broadcast-always" {
        value 1;
        description
          "Always broadcast the reply.";
      }
      enum "unicast-always" {
        value 2;
        description
          "Always unicast the reply.";
      }
    }
    description
      "DHCP reply type.";
  }

  typedef sip-mode {
    type enumeration {
      enum "ip-mode" {
        value 1;
        description
          "SIP server IP mode.";
      }
      enum "list-mode" {
        value 2;
        description
          "SIP server string mode.";
      }
    }
    description
      "The type of SIP mode.";
  }

  typedef address-status {
    type enumeration {
      enum "static-bind-used" {
        value 0;
        description
          "Static bind used status.";
      }
      enum "static-bind" {
        value 1;
        description
          "Static bind status.";
      }
      enum "used" {
        value 2;
        description
          "Used status.";
      }
      enum "expired" {
        value 3;
        description
          "Expired status.";
      }
      enum "conflict" {
        value 4;
        description
          "Conflict status.";
      }
      enum "disable" {
        value 5;
        description
          "Disable status.";
      }
      enum "idle" {
        value 6;
        description
          "Idle status.";
      }
      enum "error" {
        value 7;
        description
          "Error.";
      }
    }
    description
      "The type of address status.";
  }

  grouping ncs_template_dhcp-server-type {
    description
      "Configure DHCP server attributes.";
    container common {
      description
        "Configure DHCP server common attributes.";
      leaf ping-packet-nub {
        type string;
        units "pps";
        // NCS drop default statement
        description
          "Number of ping packets.";
      }
      leaf ping-packet-timeout {
        type string;
        units "ms";
        // NCS drop default statement
        description
          "Timeout interval of ping reply.";
      }
      leaf trust-option82 {
        type string;
        // NCS drop default statement
        description
          "Enable/disable the system to trust option82.";
      }
      leaf bootp-enable {
        type string;
        // NCS drop default statement
        description
          "Enable/disable BOOTP.";
      }
      leaf bootp-auto-enable {
        type string;
        // NCS drop default statement
        description
          "Enable/disable BOOTP automatic IP address assignment.";
      }
      leaf database-enable {
        type string;
        // NCS drop default statement
        description
          "Enable/disable database.";
      }
      leaf database-recover {
        type string;
        // NCS drop default statement
        description
          "Enable/disable database recover.";
      }
      leaf write-delay-interval {
        type string;
        units "s";
        // NCS drop default statement
        description
          "Write delay interval, in the range of 300 to 86400, in seconds.";
      }
      leaf option60-enable {
        type string;
        // NCS drop default statement
        description
          "Enable/disable to allocate IP address by option60.";
      }
      leaf dest-ip-enable {
        type string;
        // NCS drop default statement
        description
          "Enable/disable to use destination IP address of the request packet as server identifier option.";
      }
      // NCS drop config false leaf 'lease-items-path'
      // NCS drop config false leaf 'conflict-items-path'
      leaf link-selection-enable {
        type string;
        // NCS drop default statement
        description
          "Enable/disable DHCP server to assign IP addresses based on the link-selection value in option82.";
      }
      leaf server-id-override-enable {
        type string;
        // NCS drop default statement
        description
          "Enable/disable DHCP server to encapsulate option54 into packet based on the server-id-override value in option82.";
      }
      leaf request-packet-all-interface-enable {
        type string;
        // NCS drop default statement
        description
          "Enable/disable the function of DHCP server on all interfaces.";
      }
    }
    container global-ip-pools {
      description
        "List of global ip pools.";
      list global-ip-pool {
        // NCS patched for predictable order
        ordered-by user;
        key "ip-pool-name";
        description
          "Configure a global ip pool.";
        leaf ip-pool-name {
          type string;
          ext:case-sensitivity "upper2lower";
          description
            "Pool name.";
        }
        leaf vpn-instance {
          type string;
          // NCS drop must statement
          // NCS drop default statement
          description
            "VPN instance.";
        }
        leaf locked-flag {
          type string;
          // NCS drop default statement
          description
            "Enable/disable to lock.";
        }
        leaf option-router-disable {
          type string;
          // NCS drop default statement
          description
            "Enable/disable reply router option.";
        }
        leaf client-option60-string {
          type string;
          description
            "The value of client option60 in the pool.";
        }
        leaf warning-exhaust-enable {
          type string;
          // NCS drop default statement
          description
            "Enable/disable the warning-exhaust of the pool.";
        }
        leaf warning-threshold {
          type string;
          // NCS drop default statement
          description
            "The warning threshold of the pool.";
        }
        leaf domain-name {
          type string;
          description
            "Configure a DNS domain name assigned to a DHCP client.";
        }
        leaf network-bios-type {
          type ncs_template_network-bios-type;
          description
            "NetBIOS type.";
        }
        leaf reply-packet-policy {
          type ncs_template_reply-type;
          description
            "Reply packets policy.";
        }
        leaf identifier-ip {
          type string;
          description
            "Server identify IP.";
        }
        container gateway {
          // NCS drop must statement
          // NCS drop must statement
          description
            "Configure the gateway information of the pool.";
          leaf ip-address {
            type string;
            description
              "The gateway address of the pool.";
          }
          leaf mask {
            type string;
            description
              "The gateway mask of the pool.";
          }
        }
        container conflict-recycle {
          description
            "Configure the conflict address auto recycle.";
          leaf auto-recycle-enable {
            type string;
            // NCS drop default statement
            description
              "Enable/disable auto recycle of the conflict address.";
          }
          leaf conflict-recycle-interval {
            // NCS drop when statement
            type string;
            units "min";
            // NCS drop default statement
            description
              "The interval of the conflict address auto recycle.";
          }
        }
        container lease-time {
          // NCS drop must statement
          description
            "Configure lease time.";
          leaf day {
            type string;
            units "d";
            // NCS drop default statement
            description
              "The lease time day.";
          }
          leaf hour {
            type string;
            units "h";
            // NCS drop default statement
            description
              "The lease time hour.";
          }
          leaf minute {
            type string;
            units "min";
            // NCS drop default statement
            description
              "The lease time minute.";
          }
          leaf unlimited {
            type string;
            // NCS drop default statement
            description
              "Enable/disable to unlimit lease time.";
          }
        }
        container rebind-time {
          // NCS drop must statement
          // NCS drop must statement
          description
            "Configure the rebind time of the pool.";
          leaf day {
            type string;
            units "d";
            // NCS drop default statement
            description
              "The rebinding time day.";
          }
          leaf hour {
            type string;
            units "h";
            // NCS drop default statement
            description
              "The rebinding time hour.";
          }
          leaf minute {
            type string;
            units "min";
            // NCS drop default statement
            description
              "The rebinding time minute.";
          }
        }
        container renew-time {
          // NCS drop must statement
          description
            "Configure the renew time of the pool.";
          leaf day {
            type string;
            units "d";
            // NCS drop default statement
            description
              "The renew time day.";
          }
          leaf hour {
            type string;
            units "h";
            // NCS drop default statement
            description
              "The renew time hour.";
          }
          leaf minute {
            type string;
            units "min";
            // NCS drop default statement
            description
              "The renew time minute.";
          }
        }
        container option125 {
          description
            "Configure an option125 of the pool.";
          leaf enterprise-code {
            // NCS drop when statement
            type string;
            // NCS drop default statement
            description
              "The enterprise information option code.";
          }
          leaf option-string {
            type string;
            description
              "The enterprise information option value.";
          }
        }
        container sip-server {
          description
            "Configure the SIP server of the pool.";
          leaf sip-server-mode {
            type ncs_template_sip-mode;
            // NCS drop must statement
            description
              "The mode of SIP server.";
          }
          choice sip-server-format {
            description
              "The format of SIP server.";
            case ip-format {
              description
                "The IP of SIP server.";
              leaf sip-server-ip1 {
                // NCS drop when statement
                type string;
                // NCS drop mandatory statement
                description
                  "The first IP of SIP server.";
              }
              leaf sip-server-ip2 {
                // NCS drop when statement
                type string;
                description
                  "The second IP of SIP server.";
              }
            }
            case string-format {
              description
                "The name of SIP server.";
              leaf sip-server-name1 {
                // NCS drop when statement
                type string;
                // NCS drop mandatory statement
                description
                  "The first name of SIP server.";
              }
              leaf sip-server-name2 {
                // NCS drop when statement
                type string;
                description
                  "The second name of SIP server.";
              }
            }
          }
        }
        container sections {
          description
            "List of the sections of the pool.";
          list section {
            // NCS patched for predictable order
            ordered-by user;
            // NCS drop must statement
            key "section-index";
            // NCS drop max-elements statement
            description
              "Configure the section of the pool.";
            leaf section-index {
              type string;
              description
                "The section index.";
            }
            leaf start-ip {
              type string;
              // NCS drop mandatory statement
              description
                "The start IP address of the section.";
            }
            leaf end-ip {
              type string;
              // NCS drop mandatory statement
              description
                "The end IP address of the section.";
            }
          }
        }
        container dns-lists {
          description
            "List of DNS IPs.";
          list dns-list {
            // NCS patched for predictable order
            ordered-by user;
            key "dns-ip";
            // NCS drop max-elements statement
            description
              "Configure a DNS IP instance.";
            leaf dns-ip {
              type string;
              description
                "DNS IP.";
            }
          }
        }
        container network-bios-ip-addresses {
          description
            "List of NetBIOS IPs.";
          list network-bios-ip-address {
            // NCS patched for predictable order
            ordered-by user;
            key "network-bios-ip";
            // NCS drop max-elements statement
            description
              "Configure a NetBIOS IP instance.";
            leaf network-bios-ip {
              type string;
              description
                "NetBIOS IP address.";
            }
          }
        }
        container excluded-ip-addresses {
          description
            "List of excluded IP addresses.";
          list excluded-ip-address {
            // NCS patched for predictable order
            ordered-by user;
            key "start-ip-address end-ip-address";
            description
              "Configure an excluded IP instance.";
            leaf start-ip-address {
              type string;
              description
                "Excluded start IP address.";
            }
            leaf end-ip-address {
              type string;
              description
                "Excluded end IP address.";
            }
          }
        }
        container static-binds {
          description
            "List of static bind IPs.";
          list static-bind {
            // NCS patched for predictable order
            ordered-by user;
            key "static-bind-ip";
            unique "static-bind-mac";
            // NCS drop max-elements statement
            description
              "Configure a static bind IP instance.";
            leaf static-bind-ip {
              type string;
              description
                "Specify the IP address to be bound.";
            }
            leaf static-bind-mac {
              type pub-type:ncs_template_mac-address;
              // NCS drop mandatory statement
              description
                "Specify the user MAC address.";
            }
          }
        }
        container option121s {
          description
            "List of the option121 attributes.";
          list option121 {
            // NCS patched for predictable order
            ordered-by user;
            key "destination-ip mask gateway";
            // NCS drop max-elements statement
            description
              "Configure the option121 attributes.";
            leaf destination-ip {
              type string;
              description
                "Destination IP address.";
            }
            leaf mask {
              type string;
              description
                "IP mask.";
            }
            leaf gateway {
              type string;
              description
                "Gateway address.";
            }
          }
        }
        container option33s {
          description
            "List of the option33 attributes.";
          list option33 {
            // NCS patched for predictable order
            ordered-by user;
            key "destination-ip gateway";
            // NCS drop max-elements statement
            description
              "Configure the option33 attributes.";
            leaf destination-ip {
              type string;
              description
                "Destionnation IP address.";
            }
            leaf gateway {
              type string;
              description
                "Gateway IP address.";
            }
          }
        }
        container domain-lists {
          description
            "List of the domain lists of the pool.";
          list domain-list {
            // NCS patched for predictable order
            ordered-by user;
            key "domain-name";
            // NCS drop max-elements statement
            description
              "Configure the domain list of the pool.";
            leaf domain-name {
              type string;
              description
                "Domain name.";
            }
          }
        }
        container user-options {
          description
            "List of configuring the user define options of the pool.";
          list user-option {
            // NCS patched for predictable order
            ordered-by user;
            key "option-code";
            // NCS drop max-elements statement
            description
              "Configure a user define option of the pool.";
            leaf option-code {
              type string;
              description
                "The user define option code.";
            }
            choice option-format {
              // NCS drop mandatory statement
              description
                "The format of server option.";
              case ascii-format {
                description
                  "ASCII string format.";
                leaf ascii-string {
                  type string;
                  description
                    "The ASCII string of the option.";
                }
              }
            }
          }
        }
        container option-force-replys {
          description
            "List of the force reply options of the pool.";
          list option-force-reply {
            // NCS patched for predictable order
            ordered-by user;
            key "option-code";
            // NCS drop max-elements statement
            description
              "Configure the force reply option of the pool.";
            leaf option-code {
              type string;
              description
                "The force reply option code.";
            }
          }
        }
      }
    }
  }

  grouping ncs_rpc_notif_dhcp-server-type {
    description
      "Configure DHCP server attributes.";
    container common {
      description
        "Configure DHCP server common attributes.";
      leaf ping-packet-nub {
        type uint32 {
          range "0..10";
        }
        units "pps";
        default "2";
        description
          "Number of ping packets.";
      }
      leaf ping-packet-timeout {
        type uint32 {
          range "0..10000";
        }
        units "ms";
        default "500";
        description
          "Timeout interval of ping reply.";
      }
      leaf trust-option82 {
        type boolean;
        default "true";
        description
          "Enable/disable the system to trust option82.";
      }
      leaf bootp-enable {
        type boolean;
        default "false";
        description
          "Enable/disable BOOTP.";
      }
      leaf bootp-auto-enable {
        type boolean;
        default "false";
        description
          "Enable/disable BOOTP automatic IP address assignment.";
      }
      leaf database-enable {
        type boolean;
        default "false";
        description
          "Enable/disable database.";
      }
      leaf database-recover {
        type boolean;
        default "false";
        description
          "Enable/disable database recover.";
      }
      leaf write-delay-interval {
        type uint32 {
          range "300..86400";
        }
        units "s";
        default "300";
        description
          "Write delay interval, in the range of 300 to 86400, in seconds.";
      }
      leaf option60-enable {
        type boolean;
        default "false";
        description
          "Enable/disable to allocate IP address by option60.";
      }
      leaf dest-ip-enable {
        type boolean;
        default "false";
        description
          "Enable/disable to use destination IP address of the request packet as server identifier option.";
      }
      leaf lease-items-path {
        type string {
          length "1..64";
        }
        config false;
        description
          "Lease items path.";
      }
      leaf conflict-items-path {
        type string {
          length "1..64";
        }
        config false;
        description
          "Conflict items path.";
      }
      leaf link-selection-enable {
        type boolean;
        default "false";
        description
          "Enable/disable DHCP server to assign IP addresses based on the link-selection value in option82.";
      }
      leaf server-id-override-enable {
        type boolean;
        default "false";
        description
          "Enable/disable DHCP server to encapsulate option54 into packet based on the server-id-override value in option82.";
      }
      leaf request-packet-all-interface-enable {
        type boolean;
        default "false";
        description
          "Enable/disable the function of DHCP server on all interfaces.";
      }
    }
    container global-ip-pools {
      description
        "List of global ip pools.";
      list global-ip-pool {
        key "ip-pool-name";
        description
          "Configure a global ip pool.";
        leaf ip-pool-name {
          type string {
            length "1..128";
          }
          ext:case-sensitivity "upper2lower";
          description
            "Pool name.";
        }
        leaf vpn-instance {
          type string;
          must "/ni:network-instance/ni:instances/ni:instance[ni:name=current()]/l3vpn:afs/l3vpn:af[l3vpn:type='ipv4-unicast']" {
            tailf:xpath-root 3;
          }
          default "_public_";
          description
            "VPN instance.";
        }
        leaf locked-flag {
          type boolean;
          default "false";
          description
            "Enable/disable to lock.";
        }
        leaf option-router-disable {
          type boolean;
          default "false";
          description
            "Enable/disable reply router option.";
        }
        leaf client-option60-string {
          type string {
            length "1..255";
          }
          description
            "The value of client option60 in the pool.";
        }
        leaf warning-exhaust-enable {
          type boolean;
          default "false";
          description
            "Enable/disable the warning-exhaust of the pool.";
        }
        leaf warning-threshold {
          type uint8 {
            range "0..100";
          }
          default "80";
          description
            "The warning threshold of the pool.";
        }
        leaf domain-name {
          type string {
            length "1..63";
          }
          description
            "Configure a DNS domain name assigned to a DHCP client.";
        }
        leaf network-bios-type {
          type ncs_rpc_notif_network-bios-type;
          description
            "NetBIOS type.";
        }
        leaf reply-packet-policy {
          type ncs_rpc_notif_reply-type;
          description
            "Reply packets policy.";
        }
        leaf identifier-ip {
          type inet:ipv4-address-no-zone;
          description
            "Server identify IP.";
        }
        container gateway {
          must '../gateway or (not(../gateway) and not(../sections))' {
            tailf:xpath-root 3;
          }
          must '(../gateway/ip-address and ../gateway/mask) or (not(../gateway/ip-address) and not(../gateway/mask))' {
            tailf:xpath-root 3;
          }
          description
            "Configure the gateway information of the pool.";
          leaf ip-address {
            type inet:ipv4-address-no-zone;
            description
              "The gateway address of the pool.";
          }
          leaf mask {
            type inet:ipv4-address-no-zone;
            description
              "The gateway mask of the pool.";
          }
        }
        container conflict-recycle {
          description
            "Configure the conflict address auto recycle.";
          leaf auto-recycle-enable {
            type boolean;
            default "true";
            description
              "Enable/disable auto recycle of the conflict address.";
          }
          leaf conflict-recycle-interval {
            when "../auto-recycle-enable='true'" {
              tailf:xpath-root 3;
            }
            type uint16 {
              range "30..1440";
            }
            units "min";
            default "30";
            description
              "The interval of the conflict address auto recycle.";
          }
        }
        container lease-time {
          must '(day=0 and hour=0 and minute=0 and ../rebind-time/day=0 and ../rebind-time/hour=0 and ../rebind-time/minute=0) or (day>../rebind-time/day) or (day=../rebind-time/day and hour>../rebind-time/hour) or (day=../rebind-time/day and hour=../rebind-time/hour and minute>../rebind-time/minute)' {
            tailf:xpath-root 3;
          }
          description
            "Configure lease time.";
          leaf day {
            type uint16 {
              range "0..999";
            }
            units "d";
            default "3";
            description
              "The lease time day.";
          }
          leaf hour {
            type uint16 {
              range "0..23";
            }
            units "h";
            default "0";
            description
              "The lease time hour.";
          }
          leaf minute {
            type uint16 {
              range "0..59";
            }
            units "min";
            default "0";
            description
              "The lease time minute.";
          }
          leaf unlimited {
            type boolean;
            default "false";
            description
              "Enable/disable to unlimit lease time.";
          }
        }
        container rebind-time {
          must '(day=0 and hour=0 and minute=0 and ../renew-time/day=0 and ../renew-time/hour=0 and ../renew-time/minute=0) or (day>../renew-time/day) or (day=../renew-time/day and hour>../renew-time/hour) or (day=../renew-time/day and hour=../renew-time/hour and minute>../renew-time/minute)' {
            tailf:xpath-root 3;
          }
          must '(day=0 and hour=0 and minute=0 and ../lease-time/day=0 and ../lease-time/hour=0 and ../lease-time/minute=0) or (day<../lease-time/day) or (day=../lease-time/day and hour<../lease-time/hour) or (day=../lease-time/day and hour=../lease-time/hour and minute<../lease-time/minute)' {
            tailf:xpath-root 3;
          }
          description
            "Configure the rebind time of the pool.";
          leaf day {
            type uint16 {
              range "0..999";
            }
            units "d";
            default "0";
            description
              "The rebinding time day.";
          }
          leaf hour {
            type uint8 {
              range "0..23";
            }
            units "h";
            default "0";
            description
              "The rebinding time hour.";
          }
          leaf minute {
            type uint8 {
              range "0..59";
            }
            units "min";
            default "0";
            description
              "The rebinding time minute.";
          }
        }
        container renew-time {
          must '(day = 0 and hour = 0 and minute = 0 and ../rebind-time/day = 0 and ../rebind-time/hour = 0 and ../rebind-time/minute = 0) or
(day < ../rebind-time/day) or
(day = ../rebind-time/day and hour < ../rebind-time/hour) or
(day = ../rebind-time/day and hour = ../rebind-time/hour and minute < ../rebind-time/minute)' {
            tailf:xpath-root 3;
          }
          description
            "Configure the renew time of the pool.";
          leaf day {
            type uint16 {
              range "0..999";
            }
            units "d";
            default "0";
            description
              "The renew time day.";
          }
          leaf hour {
            type uint8 {
              range "0..23";
            }
            units "h";
            default "0";
            description
              "The renew time hour.";
          }
          leaf minute {
            type uint8 {
              range "0..59";
            }
            units "min";
            default "0";
            description
              "The renew time minute.";
          }
        }
        container option125 {
          description
            "Configure an option125 of the pool.";
          leaf enterprise-code {
            when '../option-string' {
              tailf:xpath-root 3;
            }
            type uint32 {
              range "0..4294967295";
            }
            default "2011";
            description
              "The enterprise information option code.";
          }
          leaf option-string {
            type string {
              length "1..32";
            }
            description
              "The enterprise information option value.";
          }
        }
        container sip-server {
          description
            "Configure the SIP server of the pool.";
          leaf sip-server-mode {
            type ncs_rpc_notif_sip-mode;
            must "((../sip-server-mode = 'ip-mode') and (../sip-server-ip1)) or
((../sip-server-mode = 'list-mode') and (../sip-server-name1)) or
(not(../sip-server-mode))" {
              tailf:xpath-root 3;
            }
            description
              "The mode of SIP server.";
          }
          choice sip-server-format {
            description
              "The format of SIP server.";
            case ip-format {
              description
                "The IP of SIP server.";
              leaf sip-server-ip1 {
                when "../sip-server-mode='ip-mode'" {
                  tailf:xpath-root 3;
                }
                type inet:ipv4-address-no-zone;
                mandatory true;
                description
                  "The first IP of SIP server.";
              }
              leaf sip-server-ip2 {
                when "../sip-server-mode='ip-mode'" {
                  tailf:xpath-root 3;
                }
                type inet:ipv4-address-no-zone;
                description
                  "The second IP of SIP server.";
              }
            }
            case string-format {
              description
                "The name of SIP server.";
              leaf sip-server-name1 {
                when "../sip-server-mode='list-mode'" {
                  tailf:xpath-root 3;
                }
                type string {
                  length "1..63";
                }
                mandatory true;
                description
                  "The first name of SIP server.";
              }
              leaf sip-server-name2 {
                when "../sip-server-mode='list-mode'" {
                  tailf:xpath-root 3;
                }
                type string {
                  length "1..63";
                }
                description
                  "The second name of SIP server.";
              }
            }
          }
        }
        container sections {
          description
            "List of the sections of the pool.";
          list section {
            must '(../../gateway and ../section) or (not(../section))' {
              tailf:xpath-root 3;
            }
            key "section-index";
            max-elements 256;
            description
              "Configure the section of the pool.";
            leaf section-index {
              type uint32 {
                range "0..255";
              }
              description
                "The section index.";
            }
            leaf start-ip {
              type inet:ipv4-address-no-zone;
              mandatory true;
              description
                "The start IP address of the section.";
            }
            leaf end-ip {
              type inet:ipv4-address-no-zone;
              mandatory true;
              description
                "The end IP address of the section.";
            }
          }
        }
        container dns-lists {
          description
            "List of DNS IPs.";
          list dns-list {
            key "dns-ip";
            max-elements 8;
            description
              "Configure a DNS IP instance.";
            leaf dns-ip {
              type inet:ipv4-address-no-zone;
              description
                "DNS IP.";
            }
          }
        }
        container network-bios-ip-addresses {
          description
            "List of NetBIOS IPs.";
          list network-bios-ip-address {
            key "network-bios-ip";
            max-elements 8;
            description
              "Configure a NetBIOS IP instance.";
            leaf network-bios-ip {
              type inet:ipv4-address-no-zone;
              description
                "NetBIOS IP address.";
            }
          }
        }
        container excluded-ip-addresses {
          description
            "List of excluded IP addresses.";
          list excluded-ip-address {
            key "start-ip-address end-ip-address";
            description
              "Configure an excluded IP instance.";
            leaf start-ip-address {
              type inet:ipv4-address-no-zone;
              description
                "Excluded start IP address.";
            }
            leaf end-ip-address {
              type inet:ipv4-address-no-zone;
              description
                "Excluded end IP address.";
            }
          }
        }
        container static-binds {
          description
            "List of static bind IPs.";
          list static-bind {
            key "static-bind-ip";
            unique "static-bind-mac";
            max-elements 4096;
            description
              "Configure a static bind IP instance.";
            leaf static-bind-ip {
              type inet:ipv4-address-no-zone;
              description
                "Specify the IP address to be bound.";
            }
            leaf static-bind-mac {
              type pub-type:ncs_rpc_notif_mac-address;
              mandatory true;
              description
                "Specify the user MAC address.";
            }
          }
        }
        container option121s {
          description
            "List of the option121 attributes.";
          list option121 {
            key "destination-ip mask gateway";
            max-elements 8;
            description
              "Configure the option121 attributes.";
            leaf destination-ip {
              type inet:ipv4-address-no-zone;
              description
                "Destination IP address.";
            }
            leaf mask {
              type uint32 {
                range "0..32";
              }
              description
                "IP mask.";
            }
            leaf gateway {
              type inet:ipv4-address-no-zone;
              description
                "Gateway address.";
            }
          }
        }
        container option33s {
          description
            "List of the option33 attributes.";
          list option33 {
            key "destination-ip gateway";
            max-elements 8;
            description
              "Configure the option33 attributes.";
            leaf destination-ip {
              type inet:ipv4-address-no-zone;
              description
                "Destionnation IP address.";
            }
            leaf gateway {
              type inet:ipv4-address-no-zone;
              description
                "Gateway IP address.";
            }
          }
        }
        container domain-lists {
          description
            "List of the domain lists of the pool.";
          list domain-list {
            key "domain-name";
            max-elements 4;
            description
              "Configure the domain list of the pool.";
            leaf domain-name {
              type string {
                length "1..32";
              }
              description
                "Domain name.";
            }
          }
        }
        container user-options {
          description
            "List of configuring the user define options of the pool.";
          list user-option {
            key "option-code";
            max-elements 16;
            description
              "Configure a user define option of the pool.";
            leaf option-code {
              type uint32 {
                range "1..254";
              }
              description
                "The user define option code.";
            }
            choice option-format {
              mandatory true;
              description
                "The format of server option.";
              case ascii-format {
                description
                  "ASCII string format.";
                leaf ascii-string {
                  type string {
                    length "1..255";
                  }
                  description
                    "The ASCII string of the option.";
                }
              }
            }
          }
        }
        container option-force-replys {
          description
            "List of the force reply options of the pool.";
          list option-force-reply {
            key "option-code";
            max-elements 16;
            description
              "Configure the force reply option of the pool.";
            leaf option-code {
              type uint8 {
                range "2..254";
              }
              description
                "The force reply option code.";
            }
          }
        }
      }
    }
  }

  grouping live_ncs_dhcp-server-type {
    description
      "Configure DHCP server attributes.";
    container common {
      description
        "Configure DHCP server common attributes.";
      leaf ping-packet-nub {
        type uint32 {
          range "0..10";
        }
        units "pps";
        // NCS drop default statement
        description
          "Number of ping packets.";
      }
      leaf ping-packet-timeout {
        type uint32 {
          range "0..10000";
        }
        units "ms";
        // NCS drop default statement
        description
          "Timeout interval of ping reply.";
      }
      leaf trust-option82 {
        type boolean;
        // NCS drop default statement
        description
          "Enable/disable the system to trust option82.";
      }
      leaf bootp-enable {
        type boolean;
        // NCS drop default statement
        description
          "Enable/disable BOOTP.";
      }
      leaf bootp-auto-enable {
        type boolean;
        // NCS drop default statement
        description
          "Enable/disable BOOTP automatic IP address assignment.";
      }
      leaf database-enable {
        type boolean;
        // NCS drop default statement
        description
          "Enable/disable database.";
      }
      leaf database-recover {
        type boolean;
        // NCS drop default statement
        description
          "Enable/disable database recover.";
      }
      leaf write-delay-interval {
        type uint32 {
          range "300..86400";
        }
        units "s";
        // NCS drop default statement
        description
          "Write delay interval, in the range of 300 to 86400, in seconds.";
      }
      leaf option60-enable {
        type boolean;
        // NCS drop default statement
        description
          "Enable/disable to allocate IP address by option60.";
      }
      leaf dest-ip-enable {
        type boolean;
        // NCS drop default statement
        description
          "Enable/disable to use destination IP address of the request packet as server identifier option.";
      }
      leaf lease-items-path {
        type string {
          length "1..64";
        }
        description
          "Lease items path.";
      }
      leaf conflict-items-path {
        type string {
          length "1..64";
        }
        description
          "Conflict items path.";
      }
      leaf link-selection-enable {
        type boolean;
        // NCS drop default statement
        description
          "Enable/disable DHCP server to assign IP addresses based on the link-selection value in option82.";
      }
      leaf server-id-override-enable {
        type boolean;
        // NCS drop default statement
        description
          "Enable/disable DHCP server to encapsulate option54 into packet based on the server-id-override value in option82.";
      }
      leaf request-packet-all-interface-enable {
        type boolean;
        // NCS drop default statement
        description
          "Enable/disable the function of DHCP server on all interfaces.";
      }
    }
    container global-ip-pools {
      description
        "List of global ip pools.";
      list global-ip-pool {
        key "ip-pool-name";
        description
          "Configure a global ip pool.";
        leaf ip-pool-name {
          type string {
            length "1..128";
          }
          ext:case-sensitivity "upper2lower";
          description
            "Pool name.";
        }
        leaf vpn-instance {
          type leafref {
            path "/ncs:devices/ncs:device/ncs:live-status/ni:network-instance/ni:instances/ni:instance/ni:name" {
              tailf:xpath-root 3;
            }
          }
          // NCS drop must statement
          // NCS drop default statement
          description
            "VPN instance.";
        }
        leaf locked-flag {
          type boolean;
          // NCS drop default statement
          description
            "Enable/disable to lock.";
        }
        leaf option-router-disable {
          type boolean;
          // NCS drop default statement
          description
            "Enable/disable reply router option.";
        }
        leaf client-option60-string {
          type string {
            length "1..255";
          }
          description
            "The value of client option60 in the pool.";
        }
        leaf warning-exhaust-enable {
          type boolean;
          // NCS drop default statement
          description
            "Enable/disable the warning-exhaust of the pool.";
        }
        leaf warning-threshold {
          type uint8 {
            range "0..100";
          }
          // NCS drop default statement
          description
            "The warning threshold of the pool.";
        }
        leaf domain-name {
          type string {
            length "1..63";
          }
          description
            "Configure a DNS domain name assigned to a DHCP client.";
        }
        leaf network-bios-type {
          type live_ncs_network-bios-type;
          description
            "NetBIOS type.";
        }
        leaf reply-packet-policy {
          type live_ncs_reply-type;
          description
            "Reply packets policy.";
        }
        leaf identifier-ip {
          type inet:ipv4-address-no-zone;
          description
            "Server identify IP.";
        }
        container gateway {
          // NCS drop must statement
          // NCS drop must statement
          description
            "Configure the gateway information of the pool.";
          leaf ip-address {
            type inet:ipv4-address-no-zone;
            description
              "The gateway address of the pool.";
          }
          leaf mask {
            type inet:ipv4-address-no-zone;
            description
              "The gateway mask of the pool.";
          }
        }
        container conflict-recycle {
          description
            "Configure the conflict address auto recycle.";
          leaf auto-recycle-enable {
            type boolean;
            // NCS drop default statement
            description
              "Enable/disable auto recycle of the conflict address.";
          }
          leaf conflict-recycle-interval {
            // NCS drop when statement
            type uint16 {
              range "30..1440";
            }
            units "min";
            // NCS drop default statement
            description
              "The interval of the conflict address auto recycle.";
          }
        }
        container lease-time {
          // NCS drop must statement
          description
            "Configure lease time.";
          leaf day {
            type uint16 {
              range "0..999";
            }
            units "d";
            // NCS drop default statement
            description
              "The lease time day.";
          }
          leaf hour {
            type uint16 {
              range "0..23";
            }
            units "h";
            // NCS drop default statement
            description
              "The lease time hour.";
          }
          leaf minute {
            type uint16 {
              range "0..59";
            }
            units "min";
            // NCS drop default statement
            description
              "The lease time minute.";
          }
          leaf unlimited {
            type boolean;
            // NCS drop default statement
            description
              "Enable/disable to unlimit lease time.";
          }
        }
        container rebind-time {
          // NCS drop must statement
          // NCS drop must statement
          description
            "Configure the rebind time of the pool.";
          leaf day {
            type uint16 {
              range "0..999";
            }
            units "d";
            // NCS drop default statement
            description
              "The rebinding time day.";
          }
          leaf hour {
            type uint8 {
              range "0..23";
            }
            units "h";
            // NCS drop default statement
            description
              "The rebinding time hour.";
          }
          leaf minute {
            type uint8 {
              range "0..59";
            }
            units "min";
            // NCS drop default statement
            description
              "The rebinding time minute.";
          }
        }
        container renew-time {
          // NCS drop must statement
          description
            "Configure the renew time of the pool.";
          leaf day {
            type uint16 {
              range "0..999";
            }
            units "d";
            // NCS drop default statement
            description
              "The renew time day.";
          }
          leaf hour {
            type uint8 {
              range "0..23";
            }
            units "h";
            // NCS drop default statement
            description
              "The renew time hour.";
          }
          leaf minute {
            type uint8 {
              range "0..59";
            }
            units "min";
            // NCS drop default statement
            description
              "The renew time minute.";
          }
        }
        container option125 {
          description
            "Configure an option125 of the pool.";
          leaf enterprise-code {
            // NCS drop when statement
            type uint32 {
              range "0..4294967295";
            }
            // NCS drop default statement
            description
              "The enterprise information option code.";
          }
          leaf option-string {
            type string {
              length "1..32";
            }
            description
              "The enterprise information option value.";
          }
        }
        container sip-server {
          description
            "Configure the SIP server of the pool.";
          leaf sip-server-mode {
            type live_ncs_sip-mode;
            // NCS drop must statement
            description
              "The mode of SIP server.";
          }
          choice sip-server-format {
            description
              "The format of SIP server.";
            case ip-format {
              description
                "The IP of SIP server.";
              leaf sip-server-ip1 {
                // NCS drop when statement
                type inet:ipv4-address-no-zone;
                // NCS drop mandatory statement
                description
                  "The first IP of SIP server.";
              }
              leaf sip-server-ip2 {
                // NCS drop when statement
                type inet:ipv4-address-no-zone;
                description
                  "The second IP of SIP server.";
              }
            }
            case string-format {
              description
                "The name of SIP server.";
              leaf sip-server-name1 {
                // NCS drop when statement
                type string {
                  length "1..63";
                }
                // NCS drop mandatory statement
                description
                  "The first name of SIP server.";
              }
              leaf sip-server-name2 {
                // NCS drop when statement
                type string {
                  length "1..63";
                }
                description
                  "The second name of SIP server.";
              }
            }
          }
        }
        container sections {
          description
            "List of the sections of the pool.";
          list section {
            // NCS drop must statement
            key "section-index";
            // NCS drop max-elements statement
            description
              "Configure the section of the pool.";
            leaf section-index {
              type uint32 {
                range "0..255";
              }
              description
                "The section index.";
            }
            leaf start-ip {
              type inet:ipv4-address-no-zone;
              // NCS drop mandatory statement
              description
                "The start IP address of the section.";
            }
            leaf end-ip {
              type inet:ipv4-address-no-zone;
              // NCS drop mandatory statement
              description
                "The end IP address of the section.";
            }
          }
        }
        container dns-lists {
          description
            "List of DNS IPs.";
          list dns-list {
            key "dns-ip";
            // NCS drop max-elements statement
            description
              "Configure a DNS IP instance.";
            leaf dns-ip {
              type inet:ipv4-address-no-zone;
              description
                "DNS IP.";
            }
          }
        }
        container network-bios-ip-addresses {
          description
            "List of NetBIOS IPs.";
          list network-bios-ip-address {
            key "network-bios-ip";
            // NCS drop max-elements statement
            description
              "Configure a NetBIOS IP instance.";
            leaf network-bios-ip {
              type inet:ipv4-address-no-zone;
              description
                "NetBIOS IP address.";
            }
          }
        }
        container excluded-ip-addresses {
          description
            "List of excluded IP addresses.";
          list excluded-ip-address {
            key "start-ip-address end-ip-address";
            description
              "Configure an excluded IP instance.";
            leaf start-ip-address {
              type inet:ipv4-address-no-zone;
              description
                "Excluded start IP address.";
            }
            leaf end-ip-address {
              type inet:ipv4-address-no-zone;
              description
                "Excluded end IP address.";
            }
          }
        }
        container static-binds {
          description
            "List of static bind IPs.";
          list static-bind {
            key "static-bind-ip";
            unique "static-bind-mac";
            // NCS drop max-elements statement
            description
              "Configure a static bind IP instance.";
            leaf static-bind-ip {
              type inet:ipv4-address-no-zone;
              description
                "Specify the IP address to be bound.";
            }
            leaf static-bind-mac {
              type pub-type:live_ncs_mac-address;
              // NCS drop mandatory statement
              description
                "Specify the user MAC address.";
            }
          }
        }
        container option121s {
          description
            "List of the option121 attributes.";
          list option121 {
            key "destination-ip mask gateway";
            // NCS drop max-elements statement
            description
              "Configure the option121 attributes.";
            leaf destination-ip {
              type inet:ipv4-address-no-zone;
              description
                "Destination IP address.";
            }
            leaf mask {
              type uint32 {
                range "0..32";
              }
              description
                "IP mask.";
            }
            leaf gateway {
              type inet:ipv4-address-no-zone;
              description
                "Gateway address.";
            }
          }
        }
        container option33s {
          description
            "List of the option33 attributes.";
          list option33 {
            key "destination-ip gateway";
            // NCS drop max-elements statement
            description
              "Configure the option33 attributes.";
            leaf destination-ip {
              type inet:ipv4-address-no-zone;
              description
                "Destionnation IP address.";
            }
            leaf gateway {
              type inet:ipv4-address-no-zone;
              description
                "Gateway IP address.";
            }
          }
        }
        container domain-lists {
          description
            "List of the domain lists of the pool.";
          list domain-list {
            key "domain-name";
            // NCS drop max-elements statement
            description
              "Configure the domain list of the pool.";
            leaf domain-name {
              type string {
                length "1..32";
              }
              description
                "Domain name.";
            }
          }
        }
        container user-options {
          description
            "List of configuring the user define options of the pool.";
          list user-option {
            key "option-code";
            // NCS drop max-elements statement
            description
              "Configure a user define option of the pool.";
            leaf option-code {
              type uint32 {
                range "1..254";
              }
              description
                "The user define option code.";
            }
            choice option-format {
              // NCS drop mandatory statement
              description
                "The format of server option.";
              case ascii-format {
                description
                  "ASCII string format.";
                leaf ascii-string {
                  type string {
                    length "1..255";
                  }
                  description
                    "The ASCII string of the option.";
                }
              }
            }
          }
        }
        container option-force-replys {
          description
            "List of the force reply options of the pool.";
          list option-force-reply {
            key "option-code";
            // NCS drop max-elements statement
            description
              "Configure the force reply option of the pool.";
            leaf option-code {
              type uint8 {
                range "2..254";
              }
              description
                "The force reply option code.";
            }
          }
        }
      }
    }
  }

  grouping dhcp-server-type {
    description
      "Configure DHCP server attributes.";
    container common {
      description
        "Configure DHCP server common attributes.";
      leaf ping-packet-nub {
        type uint32 {
          range "0..10";
        }
        units "pps";
        default "2";
        description
          "Number of ping packets.";
      }
      leaf ping-packet-timeout {
        type uint32 {
          range "0..10000";
        }
        units "ms";
        default "500";
        description
          "Timeout interval of ping reply.";
      }
      leaf trust-option82 {
        type boolean;
        default "true";
        description
          "Enable/disable the system to trust option82.";
      }
      leaf bootp-enable {
        type boolean;
        default "false";
        description
          "Enable/disable BOOTP.";
      }
      leaf bootp-auto-enable {
        type boolean;
        default "false";
        description
          "Enable/disable BOOTP automatic IP address assignment.";
      }
      leaf database-enable {
        type boolean;
        default "false";
        description
          "Enable/disable database.";
      }
      leaf database-recover {
        type boolean;
        default "false";
        description
          "Enable/disable database recover.";
      }
      leaf write-delay-interval {
        type uint32 {
          range "300..86400";
        }
        units "s";
        default "300";
        description
          "Write delay interval, in the range of 300 to 86400, in seconds.";
      }
      leaf option60-enable {
        type boolean;
        default "false";
        description
          "Enable/disable to allocate IP address by option60.";
      }
      leaf dest-ip-enable {
        type boolean;
        default "false";
        description
          "Enable/disable to use destination IP address of the request packet as server identifier option.";
      }
      // NCS drop config false leaf 'lease-items-path'
      // NCS drop config false leaf 'conflict-items-path'
      leaf link-selection-enable {
        type boolean;
        default "false";
        description
          "Enable/disable DHCP server to assign IP addresses based on the link-selection value in option82.";
      }
      leaf server-id-override-enable {
        type boolean;
        default "false";
        description
          "Enable/disable DHCP server to encapsulate option54 into packet based on the server-id-override value in option82.";
      }
      leaf request-packet-all-interface-enable {
        type boolean;
        default "false";
        description
          "Enable/disable the function of DHCP server on all interfaces.";
      }
    }
    container global-ip-pools {
      description
        "List of global ip pools.";
      list global-ip-pool {
        key "ip-pool-name";
        description
          "Configure a global ip pool.";
        leaf ip-pool-name {
          type string {
            length "1..128";
          }
          ext:case-sensitivity "upper2lower";
          description
            "Pool name.";
        }
        leaf vpn-instance {
          type leafref {
            path "/ncs:devices/ncs:device/ncs:config/ni:network-instance/ni:instances/ni:instance/ni:name" {
              tailf:xpath-root 3;
            }
          }
          must "/ni:network-instance/ni:instances/ni:instance[ni:name=current()]/l3vpn:afs/l3vpn:af[l3vpn:type='ipv4-unicast']" {
            tailf:xpath-root 3;
          }
          default "_public_";
          description
            "VPN instance.";
        }
        leaf locked-flag {
          type boolean;
          default "false";
          description
            "Enable/disable to lock.";
        }
        leaf option-router-disable {
          type boolean;
          default "false";
          description
            "Enable/disable reply router option.";
        }
        leaf client-option60-string {
          type string {
            length "1..255";
          }
          description
            "The value of client option60 in the pool.";
        }
        leaf warning-exhaust-enable {
          type boolean;
          default "false";
          description
            "Enable/disable the warning-exhaust of the pool.";
        }
        leaf warning-threshold {
          type uint8 {
            range "0..100";
          }
          default "80";
          description
            "The warning threshold of the pool.";
        }
        leaf domain-name {
          type string {
            length "1..63";
          }
          description
            "Configure a DNS domain name assigned to a DHCP client.";
        }
        leaf network-bios-type {
          type network-bios-type;
          description
            "NetBIOS type.";
        }
        leaf reply-packet-policy {
          type reply-type;
          description
            "Reply packets policy.";
        }
        leaf identifier-ip {
          type inet:ipv4-address-no-zone;
          description
            "Server identify IP.";
        }
        container gateway {
          must '../gateway or (not(../gateway) and not(../sections))' {
            tailf:xpath-root 3;
          }
          must '(../gateway/ip-address and ../gateway/mask) or (not(../gateway/ip-address) and not(../gateway/mask))' {
            tailf:xpath-root 3;
          }
          description
            "Configure the gateway information of the pool.";
          leaf ip-address {
            type inet:ipv4-address-no-zone;
            description
              "The gateway address of the pool.";
          }
          leaf mask {
            type inet:ipv4-address-no-zone;
            description
              "The gateway mask of the pool.";
          }
        }
        container conflict-recycle {
          description
            "Configure the conflict address auto recycle.";
          leaf auto-recycle-enable {
            type boolean;
            default "true";
            description
              "Enable/disable auto recycle of the conflict address.";
          }
          leaf conflict-recycle-interval {
            when "../auto-recycle-enable='true'" {
              tailf:xpath-root 3;
            }
            type uint16 {
              range "30..1440";
            }
            units "min";
            default "30";
            description
              "The interval of the conflict address auto recycle.";
          }
        }
        container lease-time {
          must '(day=0 and hour=0 and minute=0 and ../rebind-time/day=0 and ../rebind-time/hour=0 and ../rebind-time/minute=0) or (day>../rebind-time/day) or (day=../rebind-time/day and hour>../rebind-time/hour) or (day=../rebind-time/day and hour=../rebind-time/hour and minute>../rebind-time/minute)' {
            tailf:xpath-root 3;
          }
          description
            "Configure lease time.";
          leaf day {
            type uint16 {
              range "0..999";
            }
            units "d";
            default "3";
            description
              "The lease time day.";
          }
          leaf hour {
            type uint16 {
              range "0..23";
            }
            units "h";
            default "0";
            description
              "The lease time hour.";
          }
          leaf minute {
            type uint16 {
              range "0..59";
            }
            units "min";
            default "0";
            description
              "The lease time minute.";
          }
          leaf unlimited {
            type boolean;
            default "false";
            description
              "Enable/disable to unlimit lease time.";
          }
        }
        container rebind-time {
          must '(day=0 and hour=0 and minute=0 and ../renew-time/day=0 and ../renew-time/hour=0 and ../renew-time/minute=0) or (day>../renew-time/day) or (day=../renew-time/day and hour>../renew-time/hour) or (day=../renew-time/day and hour=../renew-time/hour and minute>../renew-time/minute)' {
            tailf:xpath-root 3;
          }
          must '(day=0 and hour=0 and minute=0 and ../lease-time/day=0 and ../lease-time/hour=0 and ../lease-time/minute=0) or (day<../lease-time/day) or (day=../lease-time/day and hour<../lease-time/hour) or (day=../lease-time/day and hour=../lease-time/hour and minute<../lease-time/minute)' {
            tailf:xpath-root 3;
          }
          description
            "Configure the rebind time of the pool.";
          leaf day {
            type uint16 {
              range "0..999";
            }
            units "d";
            default "0";
            description
              "The rebinding time day.";
          }
          leaf hour {
            type uint8 {
              range "0..23";
            }
            units "h";
            default "0";
            description
              "The rebinding time hour.";
          }
          leaf minute {
            type uint8 {
              range "0..59";
            }
            units "min";
            default "0";
            description
              "The rebinding time minute.";
          }
        }
        container renew-time {
          must '(day = 0 and hour = 0 and minute = 0 and ../rebind-time/day = 0 and ../rebind-time/hour = 0 and ../rebind-time/minute = 0) or
(day < ../rebind-time/day) or
(day = ../rebind-time/day and hour < ../rebind-time/hour) or
(day = ../rebind-time/day and hour = ../rebind-time/hour and minute < ../rebind-time/minute)' {
            tailf:xpath-root 3;
          }
          description
            "Configure the renew time of the pool.";
          leaf day {
            type uint16 {
              range "0..999";
            }
            units "d";
            default "0";
            description
              "The renew time day.";
          }
          leaf hour {
            type uint8 {
              range "0..23";
            }
            units "h";
            default "0";
            description
              "The renew time hour.";
          }
          leaf minute {
            type uint8 {
              range "0..59";
            }
            units "min";
            default "0";
            description
              "The renew time minute.";
          }
        }
        container option125 {
          description
            "Configure an option125 of the pool.";
          leaf enterprise-code {
            when '../option-string' {
              tailf:xpath-root 3;
            }
            type uint32 {
              range "0..4294967295";
            }
            default "2011";
            description
              "The enterprise information option code.";
          }
          leaf option-string {
            type string {
              length "1..32";
            }
            description
              "The enterprise information option value.";
          }
        }
        container sip-server {
          description
            "Configure the SIP server of the pool.";
          leaf sip-server-mode {
            type sip-mode;
            must "((../sip-server-mode = 'ip-mode') and (../sip-server-ip1)) or
((../sip-server-mode = 'list-mode') and (../sip-server-name1)) or
(not(../sip-server-mode))" {
              tailf:xpath-root 3;
            }
            description
              "The mode of SIP server.";
          }
          choice sip-server-format {
            description
              "The format of SIP server.";
            case ip-format {
              description
                "The IP of SIP server.";
              leaf sip-server-ip1 {
                when "../sip-server-mode='ip-mode'" {
                  tailf:xpath-root 3;
                }
                type inet:ipv4-address-no-zone;
                mandatory true;
                description
                  "The first IP of SIP server.";
              }
              leaf sip-server-ip2 {
                when "../sip-server-mode='ip-mode'" {
                  tailf:xpath-root 3;
                }
                type inet:ipv4-address-no-zone;
                description
                  "The second IP of SIP server.";
              }
            }
            case string-format {
              description
                "The name of SIP server.";
              leaf sip-server-name1 {
                when "../sip-server-mode='list-mode'" {
                  tailf:xpath-root 3;
                }
                type string {
                  length "1..63";
                }
                mandatory true;
                description
                  "The first name of SIP server.";
              }
              leaf sip-server-name2 {
                when "../sip-server-mode='list-mode'" {
                  tailf:xpath-root 3;
                }
                type string {
                  length "1..63";
                }
                description
                  "The second name of SIP server.";
              }
            }
          }
        }
        container sections {
          description
            "List of the sections of the pool.";
          list section {
            must '(../../gateway and ../section) or (not(../section))' {
              tailf:xpath-root 3;
            }
            key "section-index";
            max-elements 256;
            description
              "Configure the section of the pool.";
            leaf section-index {
              type uint32 {
                range "0..255";
              }
              description
                "The section index.";
            }
            leaf start-ip {
              type inet:ipv4-address-no-zone;
              mandatory true;
              description
                "The start IP address of the section.";
            }
            leaf end-ip {
              type inet:ipv4-address-no-zone;
              mandatory true;
              description
                "The end IP address of the section.";
            }
          }
        }
        container dns-lists {
          description
            "List of DNS IPs.";
          list dns-list {
            key "dns-ip";
            max-elements 8;
            description
              "Configure a DNS IP instance.";
            leaf dns-ip {
              type inet:ipv4-address-no-zone;
              description
                "DNS IP.";
            }
          }
        }
        container network-bios-ip-addresses {
          description
            "List of NetBIOS IPs.";
          list network-bios-ip-address {
            key "network-bios-ip";
            max-elements 8;
            description
              "Configure a NetBIOS IP instance.";
            leaf network-bios-ip {
              type inet:ipv4-address-no-zone;
              description
                "NetBIOS IP address.";
            }
          }
        }
        container excluded-ip-addresses {
          description
            "List of excluded IP addresses.";
          list excluded-ip-address {
            key "start-ip-address end-ip-address";
            description
              "Configure an excluded IP instance.";
            leaf start-ip-address {
              type inet:ipv4-address-no-zone;
              description
                "Excluded start IP address.";
            }
            leaf end-ip-address {
              type inet:ipv4-address-no-zone;
              description
                "Excluded end IP address.";
            }
          }
        }
        container static-binds {
          description
            "List of static bind IPs.";
          list static-bind {
            key "static-bind-ip";
            unique "static-bind-mac";
            max-elements 4096;
            description
              "Configure a static bind IP instance.";
            leaf static-bind-ip {
              type inet:ipv4-address-no-zone;
              description
                "Specify the IP address to be bound.";
            }
            leaf static-bind-mac {
              type pub-type:mac-address {
                length "0..255";
              }
              mandatory true;
              description
                "Specify the user MAC address.";
            }
          }
        }
        container option121s {
          description
            "List of the option121 attributes.";
          list option121 {
            key "destination-ip mask gateway";
            max-elements 8;
            description
              "Configure the option121 attributes.";
            leaf destination-ip {
              type inet:ipv4-address-no-zone;
              description
                "Destination IP address.";
            }
            leaf mask {
              type uint32 {
                range "0..32";
              }
              description
                "IP mask.";
            }
            leaf gateway {
              type inet:ipv4-address-no-zone;
              description
                "Gateway address.";
            }
          }
        }
        container option33s {
          description
            "List of the option33 attributes.";
          list option33 {
            key "destination-ip gateway";
            max-elements 8;
            description
              "Configure the option33 attributes.";
            leaf destination-ip {
              type inet:ipv4-address-no-zone;
              description
                "Destionnation IP address.";
            }
            leaf gateway {
              type inet:ipv4-address-no-zone;
              description
                "Gateway IP address.";
            }
          }
        }
        container domain-lists {
          description
            "List of the domain lists of the pool.";
          list domain-list {
            key "domain-name";
            max-elements 4;
            description
              "Configure the domain list of the pool.";
            leaf domain-name {
              type string {
                length "1..32";
              }
              description
                "Domain name.";
            }
          }
        }
        container user-options {
          description
            "List of configuring the user define options of the pool.";
          list user-option {
            key "option-code";
            max-elements 16;
            description
              "Configure a user define option of the pool.";
            leaf option-code {
              type uint32 {
                range "1..254";
              }
              description
                "The user define option code.";
            }
            choice option-format {
              mandatory true;
              description
                "The format of server option.";
              case ascii-format {
                description
                  "ASCII string format.";
                leaf ascii-string {
                  type string {
                    length "1..255";
                  }
                  description
                    "The ASCII string of the option.";
                }
              }
            }
          }
        }
        container option-force-replys {
          description
            "List of the force reply options of the pool.";
          list option-force-reply {
            key "option-code";
            max-elements 16;
            description
              "Configure the force reply option of the pool.";
            leaf option-code {
              type uint8 {
                range "2..254";
              }
              description
                "The force reply option code.";
            }
          }
        }
      }
    }
  }
}
