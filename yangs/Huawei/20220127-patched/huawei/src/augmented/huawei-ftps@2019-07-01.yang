module huawei-ftps {
  // Generated by yanger -t ncs
  tailf:mount-id "huawei-nc-1.0:huawei-nc-1.0";
  tailf:ncs-device-type "netconf";

  namespace "urn:huawei:yang:huawei-ftps";
  prefix ftps;

  import huawei-pub-type {
    prefix pub-type;
  }
  import huawei-network-instance {
    prefix ni;
  }
  import ietf-inet-types {
    prefix inet;
  }
  import huawei-extension {
    prefix ext;
  }
  import huawei-acl {
    prefix acl;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "FTP server component.";

  revision 2019-07-01 {
    description
      "Initial revision.";
    reference "Huawei private.";
  }
  ext:task-name "ftp-server";

  typedef ncs_template_ftps-bool-type {
    type string;
    description
      "FTP server bool datatype for ftps server.";
  }

  typedef ncs_rpc_notif_ftps-bool-type {
    type enumeration {
      enum "disable" {
        value 0;
        description
          "Disable the FTP server service.";
      }
      enum "enable" {
        value 1;
        description
          "Enable the FTP server service.";
      }
    }
    description
      "FTP server bool datatype for ftps server.";
  }

  typedef live_ncs_ftps-bool-type {
    type enumeration {
      enum "disable" {
        value 0;
        description
          "Disable the FTP server service.";
      }
      enum "enable" {
        value 1;
        description
          "Enable the FTP server service.";
      }
    }
    description
      "FTP server bool datatype for ftps server.";
  }

  typedef ftps-bool-type {
    type enumeration {
      enum "disable" {
        value 0;
        description
          "Disable the FTP server service.";
      }
      enum "enable" {
        value 1;
        description
          "Enable the FTP server service.";
      }
    }
    description
      "FTP server bool datatype for ftps server.";
  }

  augment "/ncs:devices/ncs:device/ncs:rpc" {
    container rpc-activate-ip {
      tailf:ncs-device-type "netconf";
      tailf:display-when "not(../../ncs:module) or ../../ncs:module[ncs:name='huawei-ftps']";
      tailf:action activate-ip {
        tailf:actionpoint ncsproxy {
          tailf:internal;
        }
        description
          "Activate IP.";
        input {
          leaf ip-address {
            type inet:ip-address-no-zone;
            mandatory true;
            description
              "IP address.";
          }
          leaf vpn-name {
            type string;
            description
              "VPN name.";
          }
        }
      }
    }
  }
  augment "/ncs:devices/ncs:device-group/ncs:ned-id/ncs:rpc" {
    container rpc-activate-ip {
      tailf:ncs-device-type "netconf";
      tailf:display-when "/ncs:devices/ncs:device[ncs:name=current()/../../../ncs:member]/ncs:module[ncs:name='huawei-ftps']";
      tailf:action activate-ip {
        tailf:actionpoint ncsproxy {
          tailf:internal;
        }
        description
          "Activate IP.";
        input {
          leaf ip-address {
            type inet:ip-address-no-zone;
            mandatory true;
            description
              "IP address.";
          }
          leaf vpn-name {
            type string;
            description
              "VPN name.";
          }
        }
      }
    }
  }
  augment "/ncs:devices/ncs:device/ncs:config" {
    container ftps {
      tailf:ncs-device-type "netconf";
      tailf:display-when "not(../../ncs:module) or ../../ncs:module[ncs:name='huawei-ftps']";
      description
        "FTP server component.";
      container server {
        description
          "Configure FTP server statistics.";
        leaf server-enable {
          type ftps-bool-type;
          default "disable";
          description
            "Whether to enable the FTP server service.";
        }
        leaf ipv6-server-enable {
          type ftps-bool-type;
          default "disable";
          description
            "Whether to enable the IPv6 FTP server service.";
        }
        leaf listen-port-number {
          type uint32 {
            range "21..65535";
          }
          default "21";
          description
            "Listening port of the FTP server.";
        }
        leaf ipv6-listen-port-number {
          type uint32 {
            range "21..65535";
          }
          default "21";
          description
            "Listening port of the IPv6 FTP server.";
        }
        leaf idle-timeout {
          type uint32 {
            range "1..35791";
          }
          units "min";
          default "10";
          description
            "Users can set the timeout period for an idle client to connect to the FTP server.";
        }
        leaf ipv6-idle-timeout {
          type uint32 {
            range "1..35791";
          }
          units "min";
          default "10";
          description
            "Users can set the timeout period for an idle client to connect to the IPv6 FTP server.";
        }
        leaf default-dir {
          type string {
            length "1..255";
          }
          description
            "When no root directory is configured for RADIUS/TACACS users, they can log in to the FTP server using the default root directory.";
        }
        leaf acl4-name-or-number {
          type leafref {
            path "/ncs:devices/ncs:device/ncs:config/acl:acl/acl:groups/acl:group/acl:identity" {
              tailf:xpath-root 3;
            }
          }
          must "/acl:acl/acl:groups/acl:group[acl:identity=current()]/acl:type='basic' or /acl:acl/acl:groups/acl:group[acl:identity=current()]/acl:type='advance'" {
            tailf:xpath-root 3;
          }
          description
            "Server ACL name or number for IPv4 connections.";
        }
        leaf acl6-name-or-number {
          type leafref {
            path "/ncs:devices/ncs:device/ncs:config/acl:acl/acl:group6s/acl:group6/acl:identity" {
              tailf:xpath-root 3;
            }
          }
          must "/acl:acl/acl:group6s/acl:group6[acl:identity=current()]/acl:type='basic' or /acl:acl/acl:group6s/acl:group6[acl:identity=current()]/acl:type='advance'" {
            tailf:xpath-root 3;
          }
          description
            "Server ACL name or number for IPv6 connections.";
        }
        leaf server-max-sessions {
          type uint32 {
            range "0..15";
          }
          default "15";
          description
            "User can configure maximum number of clients can be connected to server at any point of time for FTP service.";
        }
      }
      // NCS drop config false container 'users-status'
      container ip-block {
        description
          "Configure FTP IP block.";
        leaf ip-block-enable {
          type ftps-bool-type;
          default "enable";
          description
            "Whether to enable IP block function.";
        }
        leaf ip-block-failed-times {
          type uint32 {
            range "1..10";
          }
          default "6";
          description
            "IP block continuous authentication failures.";
        }
        leaf ip-block-period {
          type uint32 {
            range "1..120";
          }
          units "min";
          default "5";
          description
            "IP block continuous authentication failure time period.";
        }
        leaf ip-block-react-period {
          type uint32 {
            range "1..1000";
          }
          units "min";
          default "5";
          description
            "IP block automatically unlock time.";
        }
      }
      container login-fail-alarm {
        description
          "Configure login failed frequently.";
        leaf upper-limit {
          type uint32 {
            range "0..100";
          }
          must '../upper-limit >= ../lower-limit' {
            tailf:xpath-root 3;
          }
          default "30";
          description
            "Login failed alarm report times.";
        }
        leaf lower-limit {
          type uint32 {
            range "0..45";
          }
          default "20";
          description
            "Login failed alarm resume times.";
        }
        leaf period {
          type uint32 {
            range "1..120";
          }
          units "min";
          default "5";
          description
            "Login failed alarm period.";
        }
      }
      container ipv4-addr-sources {
        description
          "List of FTP IPv4 server source address.";
        list ipv4-addr-source {
          key "source-ipv4-address";
          max-elements 5;
          description
            "Configure FTP IPv4 server source address.";
          leaf source-ipv4-address {
            type inet:ipv4-address-no-zone;
            description
              "FTP IPv4 server source address.";
          }
        }
      }
      container ipv4-source-interfaces {
        description
          "List of specify the source interface.";
        list ipv4-source-interface {
          key "src-interface";
          max-elements 5;
          description
            "Configure specify the source interface.";
          leaf src-interface {
            type pub-type:if-name;
            description
              "Specify the source interface name. The specified source interface must exist and an IP address must be configured on the interface.";
          }
        }
      }
      container ipv4-isolate-server-sources {
        description
          "List of the isolate source interface and source address.";
        list ipv4-isolate-server-source {
          key "src-interface src-ipv4-addr";
          max-elements 5;
          description
            "Configure the isolate source interface and source address.";
          leaf src-interface {
            type pub-type:if-name;
            must 'count(/ftps/ipv4-source-interfaces/ipv4-source-interface[src-interface = current()]) = 0' {
              tailf:xpath-root 3;
            }
            description
              "Specify the source interface name.";
          }
          leaf src-ipv4-addr {
            type inet:ipv4-address-no-zone;
            description
              "Specify the source IPv4 address.";
          }
        }
      }
      container ipv6-server-sources {
        description
          "List of FTP IPv6 server source address.";
        list ipv6-server-source {
          key "src-ipv6-addr";
          max-elements 5;
          description
            "Configure FTP IPv6 server source address.";
          leaf src-ipv6-addr {
            type inet:ipv6-address-no-zone;
            description
              "FTP IPv6 server source IP address.";
          }
          leaf src-ipv6-vpn-name {
            type string {
              length "1..31";
            }
            description
              "Specify the source VPN instance. The specified VPN instance must exist and IPv6-family must be enabled in the VPN instance.";
            ext:support-filter "true";
          }
        }
      }
      container ipv6-isolate-server-sources {
        description
          "List of the isolate source interface and source IPv6 address.";
        list ipv6-isolate-server-source {
          key "src-interface src-ipv6-addr";
          max-elements 5;
          description
            "Configure the isolate source interface and source IPv6 address.";
          leaf src-interface {
            type pub-type:if-name;
            description
              "Specify the source interface name.";
          }
          leaf src-ipv6-addr {
            type inet:ipv6-address-no-zone;
            must 'count(/ftps/ipv6-server-sources/ipv6-server-source[src-ipv6-addr = current()]) = 0' {
              tailf:xpath-root 3;
            }
            description
              "Specify the source IPv6 address.";
          }
        }
      }
      container all-server-source {
        description
          "Configure specify all interfaces.";
        leaf all-ipv4-interface {
          type boolean;
          default "false";
          description
            "Enable/disable specify all IPv4 interfaces.";
        }
        leaf all-ipv6-interface {
          type boolean;
          default "false";
          description
            "Enable/disable specify all IPv6 interfaces.";
        }
      }
      container session-car {
        must 'cir-interval<=pir-interval' {
          tailf:xpath-root 3;
        }
        must 'cbs-interval<=pbs-interval' {
          tailf:xpath-root 3;
        }
        description
          "Configure FTP server session CAR.";
        leaf enable {
          type boolean;
          default "true";
          description
            "Enable/disable session CAR.";
        }
        leaf cir-interval {
          type uint32 {
            range "1..1000000";
          }
          units "kbit/s";
          default "100";
          description
            "Specify the session CAR CIR interval.";
        }
        leaf cbs-interval {
          type uint32 {
            range "1..10000000";
          }
          units "bit/s";
          default "3000000";
          description
            "Specify the session CAR CBS interval.";
        }
        leaf pir-interval {
          type uint32 {
            range "1..1000000";
          }
          units "kbit/s";
          default "4000";
          description
            "Specify the session CAR PIR interval.";
        }
        leaf pbs-interval {
          type uint32 {
            range "1..10000000";
          }
          units "bit/s";
          default "9000000";
          description
            "Specify the session CAR PBS interval.";
        }
      }
    }
  }
  augment "/ncs:devices/ncs:device/ncs:live-status" {
    container ftps {
      tailf:ncs-device-type "netconf";
      tailf:display-when "not(../../ncs:module) or ../../ncs:module[ncs:name='huawei-ftps'] or (../../ncs:live-status-protocol[not(ncs:capability)]) or (../../ncs:live-status-protocol/ncs:capability/ncs:module[.='huawei-ftps'])";
      description
        "FTP server component.";
      container server {
        description
          "Configure FTP server statistics.";
        leaf server-enable {
          type live_ncs_ftps-bool-type;
          // NCS drop default statement
          description
            "Whether to enable the FTP server service.";
        }
        leaf ipv6-server-enable {
          type live_ncs_ftps-bool-type;
          // NCS drop default statement
          description
            "Whether to enable the IPv6 FTP server service.";
        }
        leaf listen-port-number {
          type uint32 {
            range "21..65535";
          }
          // NCS drop default statement
          description
            "Listening port of the FTP server.";
        }
        leaf ipv6-listen-port-number {
          type uint32 {
            range "21..65535";
          }
          // NCS drop default statement
          description
            "Listening port of the IPv6 FTP server.";
        }
        leaf idle-timeout {
          type uint32 {
            range "1..35791";
          }
          units "min";
          // NCS drop default statement
          description
            "Users can set the timeout period for an idle client to connect to the FTP server.";
        }
        leaf ipv6-idle-timeout {
          type uint32 {
            range "1..35791";
          }
          units "min";
          // NCS drop default statement
          description
            "Users can set the timeout period for an idle client to connect to the IPv6 FTP server.";
        }
        leaf default-dir {
          type string {
            length "1..255";
          }
          description
            "When no root directory is configured for RADIUS/TACACS users, they can log in to the FTP server using the default root directory.";
        }
        leaf acl4-name-or-number {
          type leafref {
            path "/ncs:devices/ncs:device/ncs:live-status/acl:acl/acl:groups/acl:group/acl:identity" {
              tailf:xpath-root 3;
            }
          }
          // NCS drop must statement
          description
            "Server ACL name or number for IPv4 connections.";
        }
        leaf acl6-name-or-number {
          type leafref {
            path "/ncs:devices/ncs:device/ncs:live-status/acl:acl/acl:group6s/acl:group6/acl:identity" {
              tailf:xpath-root 3;
            }
          }
          // NCS drop must statement
          description
            "Server ACL name or number for IPv6 connections.";
        }
        leaf server-max-sessions {
          type uint32 {
            range "0..15";
          }
          // NCS drop default statement
          description
            "User can configure maximum number of clients can be connected to server at any point of time for FTP service.";
        }
      }
      container users-status {
        description
          "FTP server configuration statistics.";
        leaf current-number-of-users {
          type uint32;
          description
            "Number of FTP clients connected.";
        }
        leaf max-number-of-users {
          type uint32;
          description
            "Maximum number of FTP clients.";
        }
      }
      container ip-block {
        description
          "Configure FTP IP block.";
        leaf ip-block-enable {
          type live_ncs_ftps-bool-type;
          // NCS drop default statement
          description
            "Whether to enable IP block function.";
        }
        leaf ip-block-failed-times {
          type uint32 {
            range "1..10";
          }
          // NCS drop default statement
          description
            "IP block continuous authentication failures.";
        }
        leaf ip-block-period {
          type uint32 {
            range "1..120";
          }
          units "min";
          // NCS drop default statement
          description
            "IP block continuous authentication failure time period.";
        }
        leaf ip-block-react-period {
          type uint32 {
            range "1..1000";
          }
          units "min";
          // NCS drop default statement
          description
            "IP block automatically unlock time.";
        }
      }
      container login-fail-alarm {
        description
          "Configure login failed frequently.";
        leaf upper-limit {
          type uint32 {
            range "0..100";
          }
          // NCS drop must statement
          // NCS drop default statement
          description
            "Login failed alarm report times.";
        }
        leaf lower-limit {
          type uint32 {
            range "0..45";
          }
          // NCS drop default statement
          description
            "Login failed alarm resume times.";
        }
        leaf period {
          type uint32 {
            range "1..120";
          }
          units "min";
          // NCS drop default statement
          description
            "Login failed alarm period.";
        }
      }
      container ipv4-addr-sources {
        description
          "List of FTP IPv4 server source address.";
        list ipv4-addr-source {
          key "source-ipv4-address";
          // NCS drop max-elements statement
          description
            "Configure FTP IPv4 server source address.";
          leaf source-ipv4-address {
            type inet:ipv4-address-no-zone;
            description
              "FTP IPv4 server source address.";
          }
        }
      }
      container ipv4-source-interfaces {
        description
          "List of specify the source interface.";
        list ipv4-source-interface {
          key "src-interface";
          // NCS drop max-elements statement
          description
            "Configure specify the source interface.";
          leaf src-interface {
            type pub-type:live_ncs_if-name;
            description
              "Specify the source interface name. The specified source interface must exist and an IP address must be configured on the interface.";
          }
        }
      }
      container ipv4-isolate-server-sources {
        description
          "List of the isolate source interface and source address.";
        list ipv4-isolate-server-source {
          key "src-interface src-ipv4-addr";
          // NCS drop max-elements statement
          description
            "Configure the isolate source interface and source address.";
          leaf src-interface {
            type pub-type:live_ncs_if-name;
            // NCS drop must statement
            description
              "Specify the source interface name.";
          }
          leaf src-ipv4-addr {
            type inet:ipv4-address-no-zone;
            description
              "Specify the source IPv4 address.";
          }
        }
      }
      container ipv6-server-sources {
        description
          "List of FTP IPv6 server source address.";
        list ipv6-server-source {
          key "src-ipv6-addr";
          // NCS drop max-elements statement
          description
            "Configure FTP IPv6 server source address.";
          leaf src-ipv6-addr {
            type inet:ipv6-address-no-zone;
            description
              "FTP IPv6 server source IP address.";
          }
          leaf src-ipv6-vpn-name {
            type string {
              length "1..31";
            }
            description
              "Specify the source VPN instance. The specified VPN instance must exist and IPv6-family must be enabled in the VPN instance.";
            ext:support-filter "true";
          }
        }
      }
      container ipv6-isolate-server-sources {
        description
          "List of the isolate source interface and source IPv6 address.";
        list ipv6-isolate-server-source {
          key "src-interface src-ipv6-addr";
          // NCS drop max-elements statement
          description
            "Configure the isolate source interface and source IPv6 address.";
          leaf src-interface {
            type pub-type:live_ncs_if-name;
            description
              "Specify the source interface name.";
          }
          leaf src-ipv6-addr {
            type inet:ipv6-address-no-zone;
            // NCS drop must statement
            description
              "Specify the source IPv6 address.";
          }
        }
      }
      container all-server-source {
        description
          "Configure specify all interfaces.";
        leaf all-ipv4-interface {
          type boolean;
          // NCS drop default statement
          description
            "Enable/disable specify all IPv4 interfaces.";
        }
        leaf all-ipv6-interface {
          type boolean;
          // NCS drop default statement
          description
            "Enable/disable specify all IPv6 interfaces.";
        }
      }
      container session-car {
        // NCS drop must statement
        // NCS drop must statement
        description
          "Configure FTP server session CAR.";
        leaf enable {
          type boolean;
          // NCS drop default statement
          description
            "Enable/disable session CAR.";
        }
        leaf cir-interval {
          type uint32 {
            range "1..1000000";
          }
          units "kbit/s";
          // NCS drop default statement
          description
            "Specify the session CAR CIR interval.";
        }
        leaf cbs-interval {
          type uint32 {
            range "1..10000000";
          }
          units "bit/s";
          // NCS drop default statement
          description
            "Specify the session CAR CBS interval.";
        }
        leaf pir-interval {
          type uint32 {
            range "1..1000000";
          }
          units "kbit/s";
          // NCS drop default statement
          description
            "Specify the session CAR PIR interval.";
        }
        leaf pbs-interval {
          type uint32 {
            range "1..10000000";
          }
          units "bit/s";
          // NCS drop default statement
          description
            "Specify the session CAR PBS interval.";
        }
      }
    }
  }
  augment "/ncs:devices/ncs:template/ncs:ned-id/ncs:config" {
    container ftps {
      description
        "FTP server component.";
      container server {
        description
          "Configure FTP server statistics.";
        leaf server-enable {
          type ncs_template_ftps-bool-type;
          // NCS drop default statement
          description
            "Whether to enable the FTP server service.";
        }
        leaf ipv6-server-enable {
          type ncs_template_ftps-bool-type;
          // NCS drop default statement
          description
            "Whether to enable the IPv6 FTP server service.";
        }
        leaf listen-port-number {
          type string;
          // NCS drop default statement
          description
            "Listening port of the FTP server.";
        }
        leaf ipv6-listen-port-number {
          type string;
          // NCS drop default statement
          description
            "Listening port of the IPv6 FTP server.";
        }
        leaf idle-timeout {
          type string;
          units "min";
          // NCS drop default statement
          description
            "Users can set the timeout period for an idle client to connect to the FTP server.";
        }
        leaf ipv6-idle-timeout {
          type string;
          units "min";
          // NCS drop default statement
          description
            "Users can set the timeout period for an idle client to connect to the IPv6 FTP server.";
        }
        leaf default-dir {
          type string;
          description
            "When no root directory is configured for RADIUS/TACACS users, they can log in to the FTP server using the default root directory.";
        }
        leaf acl4-name-or-number {
          type string;
          // NCS drop must statement
          description
            "Server ACL name or number for IPv4 connections.";
        }
        leaf acl6-name-or-number {
          type string;
          // NCS drop must statement
          description
            "Server ACL name or number for IPv6 connections.";
        }
        leaf server-max-sessions {
          type string;
          // NCS drop default statement
          description
            "User can configure maximum number of clients can be connected to server at any point of time for FTP service.";
        }
      }
      // NCS drop config false container 'users-status'
      container ip-block {
        description
          "Configure FTP IP block.";
        leaf ip-block-enable {
          type ncs_template_ftps-bool-type;
          // NCS drop default statement
          description
            "Whether to enable IP block function.";
        }
        leaf ip-block-failed-times {
          type string;
          // NCS drop default statement
          description
            "IP block continuous authentication failures.";
        }
        leaf ip-block-period {
          type string;
          units "min";
          // NCS drop default statement
          description
            "IP block continuous authentication failure time period.";
        }
        leaf ip-block-react-period {
          type string;
          units "min";
          // NCS drop default statement
          description
            "IP block automatically unlock time.";
        }
      }
      container login-fail-alarm {
        description
          "Configure login failed frequently.";
        leaf upper-limit {
          type string;
          // NCS drop must statement
          // NCS drop default statement
          description
            "Login failed alarm report times.";
        }
        leaf lower-limit {
          type string;
          // NCS drop default statement
          description
            "Login failed alarm resume times.";
        }
        leaf period {
          type string;
          units "min";
          // NCS drop default statement
          description
            "Login failed alarm period.";
        }
      }
      container ipv4-addr-sources {
        description
          "List of FTP IPv4 server source address.";
        list ipv4-addr-source {
          // NCS patched for predictable order
          ordered-by user;
          key "source-ipv4-address";
          // NCS drop max-elements statement
          description
            "Configure FTP IPv4 server source address.";
          leaf source-ipv4-address {
            type string;
            description
              "FTP IPv4 server source address.";
          }
        }
      }
      container ipv4-source-interfaces {
        description
          "List of specify the source interface.";
        list ipv4-source-interface {
          // NCS patched for predictable order
          ordered-by user;
          key "src-interface";
          // NCS drop max-elements statement
          description
            "Configure specify the source interface.";
          leaf src-interface {
            type pub-type:ncs_template_if-name;
            description
              "Specify the source interface name. The specified source interface must exist and an IP address must be configured on the interface.";
          }
        }
      }
      container ipv4-isolate-server-sources {
        description
          "List of the isolate source interface and source address.";
        list ipv4-isolate-server-source {
          // NCS patched for predictable order
          ordered-by user;
          key "src-interface src-ipv4-addr";
          // NCS drop max-elements statement
          description
            "Configure the isolate source interface and source address.";
          leaf src-interface {
            type pub-type:ncs_template_if-name;
            // NCS drop must statement
            description
              "Specify the source interface name.";
          }
          leaf src-ipv4-addr {
            type string;
            description
              "Specify the source IPv4 address.";
          }
        }
      }
      container ipv6-server-sources {
        description
          "List of FTP IPv6 server source address.";
        list ipv6-server-source {
          // NCS patched for predictable order
          ordered-by user;
          key "src-ipv6-addr";
          // NCS drop max-elements statement
          description
            "Configure FTP IPv6 server source address.";
          leaf src-ipv6-addr {
            type string;
            description
              "FTP IPv6 server source IP address.";
          }
          leaf src-ipv6-vpn-name {
            type string;
            description
              "Specify the source VPN instance. The specified VPN instance must exist and IPv6-family must be enabled in the VPN instance.";
            ext:support-filter "true";
          }
        }
      }
      container ipv6-isolate-server-sources {
        description
          "List of the isolate source interface and source IPv6 address.";
        list ipv6-isolate-server-source {
          // NCS patched for predictable order
          ordered-by user;
          key "src-interface src-ipv6-addr";
          // NCS drop max-elements statement
          description
            "Configure the isolate source interface and source IPv6 address.";
          leaf src-interface {
            type pub-type:ncs_template_if-name;
            description
              "Specify the source interface name.";
          }
          leaf src-ipv6-addr {
            type string;
            // NCS drop must statement
            description
              "Specify the source IPv6 address.";
          }
        }
      }
      container all-server-source {
        description
          "Configure specify all interfaces.";
        leaf all-ipv4-interface {
          type string;
          // NCS drop default statement
          description
            "Enable/disable specify all IPv4 interfaces.";
        }
        leaf all-ipv6-interface {
          type string;
          // NCS drop default statement
          description
            "Enable/disable specify all IPv6 interfaces.";
        }
      }
      container session-car {
        // NCS drop must statement
        // NCS drop must statement
        description
          "Configure FTP server session CAR.";
        leaf enable {
          type string;
          // NCS drop default statement
          description
            "Enable/disable session CAR.";
        }
        leaf cir-interval {
          type string;
          units "kbit/s";
          // NCS drop default statement
          description
            "Specify the session CAR CIR interval.";
        }
        leaf cbs-interval {
          type string;
          units "bit/s";
          // NCS drop default statement
          description
            "Specify the session CAR CBS interval.";
        }
        leaf pir-interval {
          type string;
          units "kbit/s";
          // NCS drop default statement
          description
            "Specify the session CAR PIR interval.";
        }
        leaf pbs-interval {
          type string;
          units "bit/s";
          // NCS drop default statement
          description
            "Specify the session CAR PBS interval.";
        }
      }
    }
  }
}
