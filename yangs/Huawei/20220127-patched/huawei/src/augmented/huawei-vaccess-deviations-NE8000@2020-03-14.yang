module huawei-vaccess-deviations-NE8000 {
  // Generated by yanger -t ncs
  tailf:mount-id "huawei-nc-1.0:huawei-nc-1.0";
  tailf:ncs-device-type "netconf";

  namespace "urn:huawei:yang:huawei-vaccess-deviations-NE8000";
  prefix vaccess-devs-NE8000;

  import huawei-vaccess {
    prefix vaccess;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Specifies the virtual access model.";

  revision 2020-03-14 {
    description
      "Init revision.";
    reference "Huawei private.";
  }

  deviation "/ncs:devices/ncs:template/ncs:ned-id/ncs:config/vaccess:vaccess/vaccess:ap" {
    deviate not-supported;
  }
  deviation "/ncs:devices/ncs:device/ncs:live-status/vaccess:vaccess/vaccess:ap" {
    deviate not-supported;
  }
  deviation "/ncs:devices/ncs:device/ncs:config/vaccess:vaccess/vaccess:ap" {
    deviate not-supported;
  }
}
