module huawei-ospfv2-sr {
  // Generated by yanger -t ncs
  tailf:mount-id "huawei-nc-1.0:huawei-nc-1.0";
  tailf:ncs-device-type "netconf";

  namespace "urn:huawei:yang:huawei-ospfv2-sr";
  prefix ospfv2-sr;

  import huawei-ifm {
    prefix ifm;
  }
  import huawei-network-instance {
    prefix ni;
  }
  import huawei-ospfv2 {
    prefix ospfv2;
  }
  import huawei-routing-policy {
    prefix rtp;
  }
  import huawei-segment-routing {
    prefix sr;
  }
  import huawei-extension {
    prefix ext;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "OSPF segment routing management.";

  revision 2020-03-03 {
    description
      "Modify the description.";
    reference "Huawei private.";
  }
  revision 2020-02-04 {
    description
      "Modify the description.";
    reference "Huawei private.";
  }
  revision 2019-04-04 {
    description
      "Initial revision.";
    reference "Huawei private.";
  }
  ext:task-name "ospf";

  typedef ncs_template_lsp-trigger-type {
    type string;
    description
      "Segment routing lsp trigger type.";
  }

  typedef ncs_template_prefix-sid-type {
    type string;
    description
      "Prefix SID type.";
  }

  typedef ncs_rpc_notif_lsp-trigger-type {
    type enumeration {
      enum "ip-prefix" {
        value 0;
        description
          "Trigger IP prefix list for segment routing.";
      }
      enum "none" {
        value 1;
        description
          "Do not trigger FECs for segment routing.";
      }
      enum "host" {
        value 2;
        description
          "Trigger host FECs for segment routing.";
      }
    }
    description
      "Segment routing lsp trigger type.";
  }

  typedef ncs_rpc_notif_prefix-sid-type {
    type enumeration {
      enum "absolute" {
        value 1;
        description
          "Absolute value.";
      }
      enum "index" {
        value 2;
        description
          "Index.";
      }
    }
    description
      "Prefix SID type.";
  }

  typedef live_ncs_lsp-trigger-type {
    type enumeration {
      enum "ip-prefix" {
        value 0;
        description
          "Trigger IP prefix list for segment routing.";
      }
      enum "none" {
        value 1;
        description
          "Do not trigger FECs for segment routing.";
      }
      enum "host" {
        value 2;
        description
          "Trigger host FECs for segment routing.";
      }
    }
    description
      "Segment routing lsp trigger type.";
  }

  typedef live_ncs_prefix-sid-type {
    type enumeration {
      enum "absolute" {
        value 1;
        description
          "Absolute value.";
      }
      enum "index" {
        value 2;
        description
          "Index.";
      }
    }
    description
      "Prefix SID type.";
  }

  typedef lsp-trigger-type {
    type enumeration {
      enum "ip-prefix" {
        value 0;
        description
          "Trigger IP prefix list for segment routing.";
      }
      enum "none" {
        value 1;
        description
          "Do not trigger FECs for segment routing.";
      }
      enum "host" {
        value 2;
        description
          "Trigger host FECs for segment routing.";
      }
    }
    description
      "Segment routing lsp trigger type.";
  }

  typedef prefix-sid-type {
    type enumeration {
      enum "absolute" {
        value 1;
        description
          "Absolute value.";
      }
      enum "index" {
        value 2;
        description
          "Index.";
      }
    }
    description
      "Prefix SID type.";
  }

  augment "/ncs:devices/ncs:template/ncs:ned-id/ncs:config/ni:network-instance/ni:instances/ni:instance/ospfv2:ospfv2/ospfv2:sites/ospfv2:site" {
    description
      "OSPFv2 segment routing augment to OSPFv2.";
    container segment-routing {
      description
        "Configure segment routing.";
      leaf enable {
        type string;
        // NCS drop must statement
        // NCS drop default statement
        description
          "Enable/disable MPLS on the segment routing forwarding plane.";
      }
      container binding {
        // NCS drop when statement
        description
          "Configure segment routing prefix and SID mapping information.";
        leaf receive {
          type string;
          // NCS drop default statement
          description
            "Enable/disable segment routing prefix and SID mapping information receiving function.";
        }
        leaf advertise {
          type string;
          // NCS drop default statement
          description
            "Enable/disable segment routing prefix and SID mapping information sending function.";
        }
      }
      container lsp-trigger {
        // NCS drop when statement
        description
          "Configure LSP trigger policy.";
        leaf type {
          type ncs_template_lsp-trigger-type;
          // NCS drop must statement
          // NCS drop default statement
          description
            "LSP trigger type.";
        }
        leaf ip-prefix {
          // NCS drop when statement
          type string;
          description
            "IP prefix name.";
        }
      }
    }
    container srgbs {
      // NCS drop when statement
      description
        "List of segment routing global block (SRGB).";
      list srgb {
        // NCS patched for predictable order
        ordered-by user;
        key "lower-bound upper-bound";
        // NCS drop max-elements statement
        description
          "Configure segment routing global block (SRGB).";
        leaf lower-bound {
          type string;
          description
            "Start value of a segment routing global block (SRGB).";
        }
        leaf upper-bound {
          type string;
          description
            "End value of a segment routing global block (SRGB).";
        }
      }
    }
    container sr-avoid-micro-loop {
      // NCS drop when statement
      description
        "Configure OSPF SR avoid microloop.";
      leaf enable {
        type string;
        // NCS drop default statement
        description
          "Enable/disable SR avoid microloop.";
      }
      leaf rib-update-delay {
        type string;
        units "ms";
        // NCS drop default statement
        description
          "Set the route delivery delay for SR avoid microloop.";
      }
    }
  }
  augment "/ncs:devices/ncs:device/ncs:live-status/ni:network-instance/ni:instances/ni:instance/ospfv2:ospfv2/ospfv2:sites/ospfv2:site" {
    description
      "OSPFv2 segment routing augment to OSPFv2.";
    container segment-routing {
      tailf:ncs-device-type "netconf";
      tailf:display-when "not(../../../../../../../../ncs:module) or ../../../../../../../../ncs:module[ncs:name='huawei-ospfv2-sr'] or (../../../../../../../../ncs:live-status-protocol[not(ncs:capability)]) or (../../../../../../../../ncs:live-status-protocol/ncs:capability/ncs:module[.='huawei-ospfv2-sr'])";
      description
        "Configure segment routing.";
      leaf enable {
        type boolean;
        // NCS drop must statement
        // NCS drop default statement
        description
          "Enable/disable MPLS on the segment routing forwarding plane.";
      }
      container binding {
        // NCS drop when statement
        description
          "Configure segment routing prefix and SID mapping information.";
        leaf receive {
          type boolean;
          // NCS drop default statement
          description
            "Enable/disable segment routing prefix and SID mapping information receiving function.";
        }
        leaf advertise {
          type boolean;
          // NCS drop default statement
          description
            "Enable/disable segment routing prefix and SID mapping information sending function.";
        }
      }
      container lsp-trigger {
        // NCS drop when statement
        description
          "Configure LSP trigger policy.";
        leaf type {
          type live_ncs_lsp-trigger-type;
          // NCS drop must statement
          // NCS drop default statement
          description
            "LSP trigger type.";
        }
        leaf ip-prefix {
          // NCS drop when statement
          type leafref {
            path "/ncs:devices/ncs:device/ncs:live-status/rtp:routing-policy/rtp:ipv4-prefix-filters/rtp:ipv4-prefix-filter/rtp:name" {
              tailf:xpath-root 3;
            }
          }
          description
            "IP prefix name.";
        }
      }
    }
    container srgbs {
      tailf:ncs-device-type "netconf";
      tailf:display-when "not(../../../../../../../../ncs:module) or ../../../../../../../../ncs:module[ncs:name='huawei-ospfv2-sr'] or (../../../../../../../../ncs:live-status-protocol[not(ncs:capability)]) or (../../../../../../../../ncs:live-status-protocol/ncs:capability/ncs:module[.='huawei-ospfv2-sr'])";
      // NCS drop when statement
      description
        "List of segment routing global block (SRGB).";
      list srgb {
        key "lower-bound upper-bound";
        // NCS drop max-elements statement
        description
          "Configure segment routing global block (SRGB).";
        leaf lower-bound {
          type uint32 {
            range "16..1048575";
          }
          description
            "Start value of a segment routing global block (SRGB).";
        }
        leaf upper-bound {
          type uint32 {
            range "16..1048575";
          }
          description
            "End value of a segment routing global block (SRGB).";
        }
      }
    }
    container sr-avoid-micro-loop {
      tailf:ncs-device-type "netconf";
      tailf:display-when "not(../../../../../../../../ncs:module) or ../../../../../../../../ncs:module[ncs:name='huawei-ospfv2-sr'] or (../../../../../../../../ncs:live-status-protocol[not(ncs:capability)]) or (../../../../../../../../ncs:live-status-protocol/ncs:capability/ncs:module[.='huawei-ospfv2-sr'])";
      // NCS drop when statement
      description
        "Configure OSPF SR avoid microloop.";
      leaf enable {
        type boolean;
        // NCS drop default statement
        description
          "Enable/disable SR avoid microloop.";
      }
      leaf rib-update-delay {
        type uint32 {
          range "1000..60000";
        }
        units "ms";
        // NCS drop default statement
        description
          "Set the route delivery delay for SR avoid microloop.";
      }
    }
  }
  augment "/ncs:devices/ncs:device/ncs:config/ni:network-instance/ni:instances/ni:instance/ospfv2:ospfv2/ospfv2:sites/ospfv2:site" {
    description
      "OSPFv2 segment routing augment to OSPFv2.";
    container segment-routing {
      tailf:ncs-device-type "netconf";
      tailf:display-when "not(../../../../../../../../ncs:module) or ../../../../../../../../ncs:module[ncs:name='huawei-ospfv2-sr']";
      description
        "Configure segment routing.";
      leaf enable {
        type boolean;
        must "../enable='false' or (../../../../../sr:segment-routing/sr:enable='true' and ../../../../../ni:name='_public_' and ../../ospfv2:opaque='true')" {
          tailf:xpath-root 3;
        }
        default "false";
        description
          "Enable/disable MPLS on the segment routing forwarding plane.";
      }
      container binding {
        when "../enable='true'" {
          tailf:xpath-root 3;
        }
        description
          "Configure segment routing prefix and SID mapping information.";
        leaf receive {
          type boolean;
          default "true";
          description
            "Enable/disable segment routing prefix and SID mapping information receiving function.";
        }
        leaf advertise {
          type boolean;
          default "false";
          description
            "Enable/disable segment routing prefix and SID mapping information sending function.";
        }
      }
      container lsp-trigger {
        when "../enable='true'" {
          tailf:xpath-root 3;
        }
        description
          "Configure LSP trigger policy.";
        leaf type {
          type lsp-trigger-type;
          must "../type='ip-prefix' and ../ip-prefix or ../type!='ip-prefix'" {
            tailf:xpath-root 3;
          }
          default "host";
          description
            "LSP trigger type.";
        }
        leaf ip-prefix {
          when "../type='ip-prefix'" {
            tailf:xpath-root 3;
          }
          type leafref {
            path "/ncs:devices/ncs:device/ncs:config/rtp:routing-policy/rtp:ipv4-prefix-filters/rtp:ipv4-prefix-filter/rtp:name" {
              tailf:xpath-root 3;
            }
          }
          description
            "IP prefix name.";
        }
      }
    }
    container srgbs {
      tailf:ncs-device-type "netconf";
      tailf:display-when "not(../../../../../../../../ncs:module) or ../../../../../../../../ncs:module[ncs:name='huawei-ospfv2-sr']";
      when "(../../../../sr:segment-routing/sr:enable='true' and ../../../../ni:name='_public_' and ../ospfv2:opaque='true')" {
        tailf:xpath-root 3;
      }
      description
        "List of segment routing global block (SRGB).";
      list srgb {
        key "lower-bound upper-bound";
        max-elements 1;
        description
          "Configure segment routing global block (SRGB).";
        leaf lower-bound {
          type uint32 {
            range "16..1048575";
          }
          description
            "Start value of a segment routing global block (SRGB).";
        }
        leaf upper-bound {
          type uint32 {
            range "16..1048575";
          }
          description
            "End value of a segment routing global block (SRGB).";
        }
      }
    }
    container sr-avoid-micro-loop {
      tailf:ncs-device-type "netconf";
      tailf:display-when "not(../../../../../../../../ncs:module) or ../../../../../../../../ncs:module[ncs:name='huawei-ospfv2-sr']";
      when "../ospfv2-sr:segment-routing/ospfv2-sr:enable='true'" {
        tailf:xpath-root 3;
      }
      description
        "Configure OSPF SR avoid microloop.";
      leaf enable {
        type boolean;
        default "false";
        description
          "Enable/disable SR avoid microloop.";
      }
      leaf rib-update-delay {
        type uint32 {
          range "1000..60000";
        }
        units "ms";
        default "5000";
        description
          "Set the route delivery delay for SR avoid microloop.";
      }
    }
  }
  augment "/ncs:devices/ncs:template/ncs:ned-id/ncs:config/ni:network-instance/ni:instances/ni:instance/ospfv2:ospfv2/ospfv2:sites/ospfv2:site/ospfv2:areas/ospfv2:area/ospfv2:interfaces/ospfv2:interface" {
    description
      "Prefix SID augment to OSPF.";
    container prefix-sids {
      // NCS drop when statement
      description
        "List of prefix segment ID.";
      list prefix-sid {
        // NCS patched for predictable order
        ordered-by user;
        key "algorithm";
        description
          "Configure prefix segment ID.";
        leaf algorithm {
          type string;
          description
            "Prefix SID algorithm.";
        }
        leaf type {
          type ncs_template_prefix-sid-type;
          // NCS drop mandatory statement
          description
            "Prefix segment ID type on the Loopback interface.";
        }
        leaf label {
          type string;
          // NCS drop mandatory statement
          description
            "Prefix segment ID label on the Loopback interface.";
        }
        leaf node-flag {
          type string;
          // NCS drop default statement
          description
            "Enable/disable the N flag on the Loopback interface.";
        }
      }
    }
  }
  augment "/ncs:devices/ncs:device/ncs:live-status/ni:network-instance/ni:instances/ni:instance/ospfv2:ospfv2/ospfv2:sites/ospfv2:site/ospfv2:areas/ospfv2:area/ospfv2:interfaces/ospfv2:interface" {
    description
      "Prefix SID augment to OSPF.";
    container prefix-sids {
      tailf:ncs-device-type "netconf";
      tailf:display-when "not(../../../../../../../../../../../../ncs:module) or ../../../../../../../../../../../../ncs:module[ncs:name='huawei-ospfv2-sr'] or (../../../../../../../../../../../../ncs:live-status-protocol[not(ncs:capability)]) or (../../../../../../../../../../../../ncs:live-status-protocol/ncs:capability/ncs:module[.='huawei-ospfv2-sr'])";
      // NCS drop when statement
      description
        "List of prefix segment ID.";
      list prefix-sid {
        key "algorithm";
        description
          "Configure prefix segment ID.";
        leaf algorithm {
          type uint32 {
            range "0";
          }
          description
            "Prefix SID algorithm.";
        }
        leaf type {
          type live_ncs_prefix-sid-type;
          // NCS drop mandatory statement
          description
            "Prefix segment ID type on the Loopback interface.";
        }
        leaf label {
          type uint32 {
            range "0..1048575";
          }
          // NCS drop mandatory statement
          description
            "Prefix segment ID label on the Loopback interface.";
        }
        leaf node-flag {
          type boolean;
          // NCS drop default statement
          description
            "Enable/disable the N flag on the Loopback interface.";
        }
      }
    }
  }
  augment "/ncs:devices/ncs:device/ncs:config/ni:network-instance/ni:instances/ni:instance/ospfv2:ospfv2/ospfv2:sites/ospfv2:site/ospfv2:areas/ospfv2:area/ospfv2:interfaces/ospfv2:interface" {
    description
      "Prefix SID augment to OSPF.";
    container prefix-sids {
      tailf:ncs-device-type "netconf";
      tailf:display-when "not(../../../../../../../../../../../../ncs:module) or ../../../../../../../../../../../../ncs:module[ncs:name='huawei-ospfv2-sr']";
      when "../../../../../ospfv2-sr:segment-routing/ospfv2-sr:enable='true' and /ifm:ifm/ifm:interfaces/ifm:interface[ifm:name=current()/../ospfv2:name]/ifm:type='LoopBack'" {
        tailf:xpath-root 3;
      }
      description
        "List of prefix segment ID.";
      list prefix-sid {
        key "algorithm";
        description
          "Configure prefix segment ID.";
        leaf algorithm {
          type uint32 {
            range "0";
          }
          description
            "Prefix SID algorithm.";
        }
        leaf type {
          type prefix-sid-type;
          mandatory true;
          description
            "Prefix segment ID type on the Loopback interface.";
        }
        leaf label {
          type uint32 {
            range "0..1048575";
          }
          mandatory true;
          description
            "Prefix segment ID label on the Loopback interface.";
        }
        leaf node-flag {
          type boolean;
          default "true";
          description
            "Enable/disable the N flag on the Loopback interface.";
        }
      }
    }
  }
}
