module huawei-efm {
  // Generated by yanger -t ncs
  tailf:mount-id "huawei-nc-1.0:huawei-nc-1.0";
  tailf:ncs-device-type "netconf";

  namespace "urn:huawei:yang:huawei-efm";
  prefix efm;

  import huawei-extension {
    prefix ext;
  }
  import huawei-ifm {
    prefix ifm;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Ethernet in the First Mile, which is used for fault and performance detection.";

  revision 2019-04-28 {
    description
      "Initial revision.";
    reference "Huawei private.";
  }
  ext:task-name "efm";

  typedef ncs_template_enable-state {
    type string;
    description
      "Enable-state.";
  }

  typedef ncs_template_work-mode {
    type string;
    description
      "Work-mode.";
  }

  typedef ncs_template_session-state {
    type string;
    description
      "Session-state.";
  }

  typedef ncs_template_parser-action {
    type string;
    description
      "Parser-action.";
  }

  typedef ncs_template_multiplexer-action {
    type string;
    description
      "Multiplexer-action.";
  }

  typedef ncs_template_test-packet-status {
    type string;
    description
      "The type of efm test packet status.";
  }

  typedef ncs_template_discovery-state {
    type string;
    description
      "The type of efm discovery state.";
  }

  typedef ncs_template_error-frame-period-unit {
    type string;
    description
      "EFM error frame period unit.";
  }

  typedef ncs_template_loopback-state {
    type string;
    description
      "The type of EFM loopback state.";
  }

  typedef ncs_template_extended-info-transmit-type {
    type string;
    description
      "The type of EFM extended information transmit.";
  }

  typedef ncs_rpc_notif_enable-state {
    type enumeration {
      enum "disable" {
        value 0;
        description
          "Indicates that EFM is disabled.";
      }
      enum "enable" {
        value 1;
        description
          "Indicates that EFM is enabled.";
      }
    }
    description
      "Enable-state.";
  }

  typedef ncs_rpc_notif_work-mode {
    type enumeration {
      enum "active" {
        value 1;
        description
          "Indicates that EFM works in active mode.";
      }
      enum "passive" {
        value 0;
        description
          "Indicates that EFM works in passive mode.";
      }
    }
    description
      "Work-mode.";
  }

  typedef ncs_rpc_notif_session-state {
    type enumeration {
      enum "discovery" {
        value 2;
        description
          "Indicates that the EFM session is in the discovery state.";
      }
      enum "detect" {
        value 1;
        description
          "Indicates that the EFM session is in the detect state.";
      }
      enum "loopback-be-controlled" {
        value 5;
        description
          "Indicates that the EFM session is in the loopback state on the end that receives the session connection request.";
      }
      enum "loopback-control" {
        value 3;
        description
          "Indicates that the EFM session is in the loopback state on the end that initiates the session connection request.";
      }
      enum "loopback-control-forward" {
        value 4;
        description
          "The EFM session is in the Loopback state (control, forward).";
      }
    }
    description
      "Session-state.";
  }

  typedef ncs_rpc_notif_parser-action {
    type enumeration {
      enum "forward" {
        value 0;
        description
          "The EFM parser action is forward.";
      }
      enum "loopback" {
        value 1;
        description
          "The EFM parser action is loopback.";
      }
      enum "discard" {
        value 2;
        description
          "The EFM parser action is discard.";
      }
      enum "reserve" {
        value 3;
        description
          "The EFM parser action is reserve.";
      }
    }
    description
      "Parser-action.";
  }

  typedef ncs_rpc_notif_multiplexer-action {
    type enumeration {
      enum "forward" {
        value 0;
        description
          "The EFM multiplexer action is forward.";
      }
      enum "discard" {
        value 1;
        description
          "The EFM multiplexer action is discard.";
      }
    }
    description
      "Multiplexer-action.";
  }

  typedef ncs_rpc_notif_test-packet-status {
    type enumeration {
      enum "working" {
        value 0;
        description
          "The EFM test packet is working.";
      }
      enum "finished" {
        value 1;
        description
          "The EFM test packet is finished.";
      }
    }
    description
      "The type of efm test packet status.";
  }

  typedef ncs_rpc_notif_discovery-state {
    type enumeration {
      enum "FAULT" {
        value 0;
        description
          "FAULT state.";
      }
      enum "ACTIVE-SEND-LOCAL" {
        value 1;
        description
          "ACTIVE_SEND_LOCAL state.";
      }
      enum "PASSIVE-WAIT" {
        value 2;
        description
          "PASSIVE_WAIT state.";
      }
      enum "SEND-LOCAL-REMOTE" {
        value 3;
        description
          "SEND_LOCAL_REMOTE state.";
      }
      enum "SEND-LOCAL-REMOTE-OK" {
        value 4;
        description
          "SEND_LOCAL_REMOTE_OK state.";
      }
      enum "SEND-ANY" {
        value 5;
        description
          "SEND_ANY state.";
      }
    }
    description
      "The type of efm discovery state.";
  }

  typedef ncs_rpc_notif_error-frame-period-unit {
    type enumeration {
      enum "second" {
        value 0;
        description
          "Error frame period unit: seconds.";
      }
      enum "millisecond" {
        value 1;
        description
          "Error frame period unit: milliseconds.";
      }
    }
    description
      "EFM error frame period unit.";
  }

  typedef ncs_rpc_notif_loopback-state {
    type enumeration {
      enum "none" {
        value 0;
        description
          "Indicates that the EFM session is in the Loopback state (none).";
      }
      enum "loopback-be-controlled" {
        value 1;
        description
          "Indicates that the EFM session is in the Loopback state on the end that receives the session connection request.";
      }
      enum "loopback-control" {
        value 2;
        description
          "Indicates that the EFM session is in the Loopback state on the end that initiates the session connection request.";
      }
    }
    description
      "The type of EFM loopback state.";
  }

  typedef ncs_rpc_notif_extended-info-transmit-type {
    type enumeration {
      enum "receive" {
        value 0;
        description
          "EFM receives extended information.";
      }
      enum "send" {
        value 1;
        description
          "EFM sends extended information.";
      }
      enum "send-and-receive" {
        value 2;
        description
          "EFM sends and receives extended information.";
      }
    }
    description
      "The type of EFM extended information transmit.";
  }

  typedef live_ncs_enable-state {
    type enumeration {
      enum "disable" {
        value 0;
        description
          "Indicates that EFM is disabled.";
      }
      enum "enable" {
        value 1;
        description
          "Indicates that EFM is enabled.";
      }
    }
    description
      "Enable-state.";
  }

  typedef live_ncs_work-mode {
    type enumeration {
      enum "active" {
        value 1;
        description
          "Indicates that EFM works in active mode.";
      }
      enum "passive" {
        value 0;
        description
          "Indicates that EFM works in passive mode.";
      }
    }
    description
      "Work-mode.";
  }

  typedef live_ncs_session-state {
    type enumeration {
      enum "discovery" {
        value 2;
        description
          "Indicates that the EFM session is in the discovery state.";
      }
      enum "detect" {
        value 1;
        description
          "Indicates that the EFM session is in the detect state.";
      }
      enum "loopback-be-controlled" {
        value 5;
        description
          "Indicates that the EFM session is in the loopback state on the end that receives the session connection request.";
      }
      enum "loopback-control" {
        value 3;
        description
          "Indicates that the EFM session is in the loopback state on the end that initiates the session connection request.";
      }
      enum "loopback-control-forward" {
        value 4;
        description
          "The EFM session is in the Loopback state (control, forward).";
      }
    }
    description
      "Session-state.";
  }

  typedef live_ncs_parser-action {
    type enumeration {
      enum "forward" {
        value 0;
        description
          "The EFM parser action is forward.";
      }
      enum "loopback" {
        value 1;
        description
          "The EFM parser action is loopback.";
      }
      enum "discard" {
        value 2;
        description
          "The EFM parser action is discard.";
      }
      enum "reserve" {
        value 3;
        description
          "The EFM parser action is reserve.";
      }
    }
    description
      "Parser-action.";
  }

  typedef live_ncs_multiplexer-action {
    type enumeration {
      enum "forward" {
        value 0;
        description
          "The EFM multiplexer action is forward.";
      }
      enum "discard" {
        value 1;
        description
          "The EFM multiplexer action is discard.";
      }
    }
    description
      "Multiplexer-action.";
  }

  typedef live_ncs_test-packet-status {
    type enumeration {
      enum "working" {
        value 0;
        description
          "The EFM test packet is working.";
      }
      enum "finished" {
        value 1;
        description
          "The EFM test packet is finished.";
      }
    }
    description
      "The type of efm test packet status.";
  }

  typedef live_ncs_discovery-state {
    type enumeration {
      enum "FAULT" {
        value 0;
        description
          "FAULT state.";
      }
      enum "ACTIVE-SEND-LOCAL" {
        value 1;
        description
          "ACTIVE_SEND_LOCAL state.";
      }
      enum "PASSIVE-WAIT" {
        value 2;
        description
          "PASSIVE_WAIT state.";
      }
      enum "SEND-LOCAL-REMOTE" {
        value 3;
        description
          "SEND_LOCAL_REMOTE state.";
      }
      enum "SEND-LOCAL-REMOTE-OK" {
        value 4;
        description
          "SEND_LOCAL_REMOTE_OK state.";
      }
      enum "SEND-ANY" {
        value 5;
        description
          "SEND_ANY state.";
      }
    }
    description
      "The type of efm discovery state.";
  }

  typedef live_ncs_error-frame-period-unit {
    type enumeration {
      enum "second" {
        value 0;
        description
          "Error frame period unit: seconds.";
      }
      enum "millisecond" {
        value 1;
        description
          "Error frame period unit: milliseconds.";
      }
    }
    description
      "EFM error frame period unit.";
  }

  typedef live_ncs_loopback-state {
    type enumeration {
      enum "none" {
        value 0;
        description
          "Indicates that the EFM session is in the Loopback state (none).";
      }
      enum "loopback-be-controlled" {
        value 1;
        description
          "Indicates that the EFM session is in the Loopback state on the end that receives the session connection request.";
      }
      enum "loopback-control" {
        value 2;
        description
          "Indicates that the EFM session is in the Loopback state on the end that initiates the session connection request.";
      }
    }
    description
      "The type of EFM loopback state.";
  }

  typedef live_ncs_extended-info-transmit-type {
    type enumeration {
      enum "receive" {
        value 0;
        description
          "EFM receives extended information.";
      }
      enum "send" {
        value 1;
        description
          "EFM sends extended information.";
      }
      enum "send-and-receive" {
        value 2;
        description
          "EFM sends and receives extended information.";
      }
    }
    description
      "The type of EFM extended information transmit.";
  }

  typedef enable-state {
    type enumeration {
      enum "disable" {
        value 0;
        description
          "Indicates that EFM is disabled.";
      }
      enum "enable" {
        value 1;
        description
          "Indicates that EFM is enabled.";
      }
    }
    description
      "Enable-state.";
  }

  typedef work-mode {
    type enumeration {
      enum "active" {
        value 1;
        description
          "Indicates that EFM works in active mode.";
      }
      enum "passive" {
        value 0;
        description
          "Indicates that EFM works in passive mode.";
      }
    }
    description
      "Work-mode.";
  }

  typedef session-state {
    type enumeration {
      enum "discovery" {
        value 2;
        description
          "Indicates that the EFM session is in the discovery state.";
      }
      enum "detect" {
        value 1;
        description
          "Indicates that the EFM session is in the detect state.";
      }
      enum "loopback-be-controlled" {
        value 5;
        description
          "Indicates that the EFM session is in the loopback state on the end that receives the session connection request.";
      }
      enum "loopback-control" {
        value 3;
        description
          "Indicates that the EFM session is in the loopback state on the end that initiates the session connection request.";
      }
      enum "loopback-control-forward" {
        value 4;
        description
          "The EFM session is in the Loopback state (control, forward).";
      }
    }
    description
      "Session-state.";
  }

  typedef parser-action {
    type enumeration {
      enum "forward" {
        value 0;
        description
          "The EFM parser action is forward.";
      }
      enum "loopback" {
        value 1;
        description
          "The EFM parser action is loopback.";
      }
      enum "discard" {
        value 2;
        description
          "The EFM parser action is discard.";
      }
      enum "reserve" {
        value 3;
        description
          "The EFM parser action is reserve.";
      }
    }
    description
      "Parser-action.";
  }

  typedef multiplexer-action {
    type enumeration {
      enum "forward" {
        value 0;
        description
          "The EFM multiplexer action is forward.";
      }
      enum "discard" {
        value 1;
        description
          "The EFM multiplexer action is discard.";
      }
    }
    description
      "Multiplexer-action.";
  }

  typedef test-packet-status {
    type enumeration {
      enum "working" {
        value 0;
        description
          "The EFM test packet is working.";
      }
      enum "finished" {
        value 1;
        description
          "The EFM test packet is finished.";
      }
    }
    description
      "The type of efm test packet status.";
  }

  typedef discovery-state {
    type enumeration {
      enum "FAULT" {
        value 0;
        description
          "FAULT state.";
      }
      enum "ACTIVE-SEND-LOCAL" {
        value 1;
        description
          "ACTIVE_SEND_LOCAL state.";
      }
      enum "PASSIVE-WAIT" {
        value 2;
        description
          "PASSIVE_WAIT state.";
      }
      enum "SEND-LOCAL-REMOTE" {
        value 3;
        description
          "SEND_LOCAL_REMOTE state.";
      }
      enum "SEND-LOCAL-REMOTE-OK" {
        value 4;
        description
          "SEND_LOCAL_REMOTE_OK state.";
      }
      enum "SEND-ANY" {
        value 5;
        description
          "SEND_ANY state.";
      }
    }
    description
      "The type of efm discovery state.";
  }

  typedef error-frame-period-unit {
    type enumeration {
      enum "second" {
        value 0;
        description
          "Error frame period unit: seconds.";
      }
      enum "millisecond" {
        value 1;
        description
          "Error frame period unit: milliseconds.";
      }
    }
    description
      "EFM error frame period unit.";
  }

  typedef loopback-state {
    type enumeration {
      enum "none" {
        value 0;
        description
          "Indicates that the EFM session is in the Loopback state (none).";
      }
      enum "loopback-be-controlled" {
        value 1;
        description
          "Indicates that the EFM session is in the Loopback state on the end that receives the session connection request.";
      }
      enum "loopback-control" {
        value 2;
        description
          "Indicates that the EFM session is in the Loopback state on the end that initiates the session connection request.";
      }
    }
    description
      "The type of EFM loopback state.";
  }

  typedef extended-info-transmit-type {
    type enumeration {
      enum "receive" {
        value 0;
        description
          "EFM receives extended information.";
      }
      enum "send" {
        value 1;
        description
          "EFM sends extended information.";
      }
      enum "send-and-receive" {
        value 2;
        description
          "EFM sends and receives extended information.";
      }
    }
    description
      "The type of EFM extended information transmit.";
  }

  augment "/ncs:devices/ncs:device/ncs:config" {
    container efm {
      tailf:ncs-device-type "netconf";
      tailf:display-when "not(../../ncs:module) or ../../ncs:module[ncs:name='huawei-efm']";
      presence "Enables EFM";
      description
        "Ethernet in the First Mile, which is used for fault and performance detection.";
    }
  }
  augment "/ncs:devices/ncs:device/ncs:live-status" {
    container efm {
      tailf:ncs-device-type "netconf";
      tailf:display-when "not(../../ncs:module) or ../../ncs:module[ncs:name='huawei-efm'] or (../../ncs:live-status-protocol[not(ncs:capability)]) or (../../ncs:live-status-protocol/ncs:capability/ncs:module[.='huawei-efm'])";
      presence "Enables EFM";
      description
        "Ethernet in the First Mile, which is used for fault and performance detection.";
    }
  }
  augment "/ncs:devices/ncs:template/ncs:ned-id/ncs:config" {
    container efm {
      presence "Enables EFM";
      description
        "Ethernet in the First Mile, which is used for fault and performance detection.";
    }
  }
  augment "/ncs:devices/ncs:template/ncs:ned-id/ncs:config/ifm:ifm/ifm:interfaces/ifm:interface" {
    // NCS drop when statement
    description
      "EFM configuration in interface.";
    container efm {
      description
        "Configure EFM on the interface.";
      container session {
        description
          "Configure EFM on the local interface.";
        leaf state {
          type ncs_template_enable-state;
          // NCS drop default statement
          description
            "Indicates whether EFM is enabled on an interface.";
        }
        leaf mode {
          type ncs_template_work-mode;
          // NCS drop default statement
          description
            "Specify the working mode of an EFM-enabled interface.";
        }
        leaf packet-max-size {
          type string;
          units "Byte";
          // NCS drop default statement
          description
            "Specify the maximum size of an EFM packet.";
        }
        leaf interval {
          type string;
          units "ms";
          // NCS drop must statement
          // NCS drop default statement
          description
            "Specify the interval at which EFM packets are sent.";
        }
        leaf timeout {
          type string;
          units "ms";
          // NCS drop must statement
          // NCS drop default statement
          description
            "Specify the timeout period for receiving EFM packets.";
        }
        leaf ignore-loopback-request {
          type ncs_template_enable-state;
          // NCS drop must statement
          // NCS drop default statement
          description
            "Indicates that this interface will ignore the loopback request from the peer.";
        }
        leaf trigger-if-down {
          type ncs_template_enable-state;
          // NCS drop must statement
          // NCS drop default statement
          description
            "Indicates that EFM blocks an interface after detecting a fault.";
        }
        leaf hold-up-time {
          type string;
          units "s";
          // NCS drop default statement
          description
            "Specify the time waiting for an interface blocked by EFM to go up.";
        }
        leaf trigger-mac-renew {
          type string;
          // NCS drop must statement
          // NCS drop default statement
          description
            "Enable/disable that EFM clears the MAC address of an interface after detecting a fault.";
        }
        container error-frame {
          description
            "Configure the error frame function.";
          leaf notification {
            type ncs_template_enable-state;
            // NCS drop default statement
            description
              "Indicates whether notification of error frames is enabled.";
          }
          leaf period {
            type string;
            units "s";
            // NCS drop default statement
            description
              "Specify the interval at which error frames are detected.";
          }
          leaf threshold {
            type string;
            // NCS drop default statement
            description
              "Specify the threshold for error frames.";
          }
          // NCS drop config false leaf 'period-unit'
        }
        container error-frame-second {
          description
            "Configure the error frames second function.";
          leaf notification {
            type ncs_template_enable-state;
            // NCS drop default statement
            description
              "Indicates whether notification of error frame seconds is enabled.";
          }
          leaf period {
            type string;
            units "s";
            // NCS drop default statement
            description
              "Specify the interval at which error frame seconds are detected.";
          }
          leaf threshold {
            type string;
            units "s";
            // NCS drop must statement
            // NCS drop default statement
            description
              "Specify the threshold for error frame seconds.";
          }
        }
        container error-code {
          description
            "Configure the error code function.";
          leaf notification {
            type ncs_template_enable-state;
            // NCS drop default statement
            description
              "Indicates whether notification of error codes is enabled.";
          }
          leaf period {
            type string;
            units "s";
            // NCS drop default statement
            description
              "Specify the interval at which error codes are detected.";
          }
          leaf threshold {
            type string;
            // NCS drop default statement
            description
              "Specify the threshold for error codes.";
          }
        }
        container error-frame-period {
          description
            "Configure the error frame period function.";
          leaf notification {
            type ncs_template_enable-state;
            // NCS drop default statement
            description
              "Indicates whether notification of error frame periods is enabled.";
          }
          leaf period {
            type string;
            // NCS drop default statement
            description
              "Specify the interval at which error frame periods are detected.";
          }
          leaf threshold {
            type string;
            // NCS drop must statement
            // NCS drop default statement
            description
              "Specify the threshold for error frame periods.";
          }
        }
      }
    }
  }
  augment "/ncs:devices/ncs:device/ncs:live-status/ifm:ifm/ifm:interfaces/ifm:interface" {
    // NCS drop when statement
    description
      "EFM configuration in interface.";
    container efm {
      tailf:ncs-device-type "netconf";
      tailf:display-when "not(../../../../../ncs:module) or ../../../../../ncs:module[ncs:name='huawei-efm'] or (../../../../../ncs:live-status-protocol[not(ncs:capability)]) or (../../../../../ncs:live-status-protocol/ncs:capability/ncs:module[.='huawei-efm'])";
      description
        "Configure EFM on the interface.";
      container session {
        description
          "Configure EFM on the local interface.";
        leaf state {
          type live_ncs_enable-state;
          // NCS drop default statement
          description
            "Indicates whether EFM is enabled on an interface.";
        }
        leaf mode {
          type live_ncs_work-mode;
          // NCS drop default statement
          description
            "Specify the working mode of an EFM-enabled interface.";
        }
        leaf packet-max-size {
          type uint16 {
            range "64..1518";
          }
          units "Byte";
          // NCS drop default statement
          description
            "Specify the maximum size of an EFM packet.";
        }
        leaf interval {
          type uint16 {
            range "100..1000";
          }
          units "ms";
          // NCS drop must statement
          // NCS drop default statement
          description
            "Specify the interval at which EFM packets are sent.";
        }
        leaf timeout {
          type uint16 {
            range "300..30000";
          }
          units "ms";
          // NCS drop must statement
          // NCS drop default statement
          description
            "Specify the timeout period for receiving EFM packets.";
        }
        leaf ignore-loopback-request {
          type live_ncs_enable-state;
          // NCS drop must statement
          // NCS drop default statement
          description
            "Indicates that this interface will ignore the loopback request from the peer.";
        }
        leaf trigger-if-down {
          type live_ncs_enable-state;
          // NCS drop must statement
          // NCS drop default statement
          description
            "Indicates that EFM blocks an interface after detecting a fault.";
        }
        leaf hold-up-time {
          type uint16 {
            range "0..50";
          }
          units "s";
          // NCS drop default statement
          description
            "Specify the time waiting for an interface blocked by EFM to go up.";
        }
        leaf trigger-mac-renew {
          type boolean;
          // NCS drop must statement
          // NCS drop default statement
          description
            "Enable/disable that EFM clears the MAC address of an interface after detecting a fault.";
        }
        container error-frame {
          description
            "Configure the error frame function.";
          leaf notification {
            type live_ncs_enable-state;
            // NCS drop default statement
            description
              "Indicates whether notification of error frames is enabled.";
          }
          leaf period {
            type uint32 {
              range "1..60";
            }
            units "s";
            // NCS drop default statement
            description
              "Specify the interval at which error frames are detected.";
          }
          leaf threshold {
            type uint32 {
              range "0..65535";
            }
            // NCS drop default statement
            description
              "Specify the threshold for error frames.";
          }
          leaf period-unit {
            type live_ncs_error-frame-period-unit;
            // NCS drop default statement
            description
              "Period unit of an error frame event.";
          }
        }
        container error-frame-second {
          description
            "Configure the error frames second function.";
          leaf notification {
            type live_ncs_enable-state;
            // NCS drop default statement
            description
              "Indicates whether notification of error frame seconds is enabled.";
          }
          leaf period {
            type uint32 {
              range "10..900";
            }
            units "s";
            // NCS drop default statement
            description
              "Specify the interval at which error frame seconds are detected.";
          }
          leaf threshold {
            type uint32 {
              range "0..900";
            }
            units "s";
            // NCS drop must statement
            // NCS drop default statement
            description
              "Specify the threshold for error frame seconds.";
          }
        }
        container error-code {
          description
            "Configure the error code function.";
          leaf notification {
            type live_ncs_enable-state;
            // NCS drop default statement
            description
              "Indicates whether notification of error codes is enabled.";
          }
          leaf period {
            type uint32 {
              range "1..60";
            }
            units "s";
            // NCS drop default statement
            description
              "Specify the interval at which error codes are detected.";
          }
          leaf threshold {
            type uint32 {
              range "0..65535";
            }
            // NCS drop default statement
            description
              "Specify the threshold for error codes.";
          }
        }
        container error-frame-period {
          description
            "Configure the error frame period function.";
          leaf notification {
            type live_ncs_enable-state;
            // NCS drop default statement
            description
              "Indicates whether notification of error frame periods is enabled.";
          }
          leaf period {
            type uint32 {
              range "20000..4294967295";
            }
            // NCS drop default statement
            description
              "Specify the interval at which error frame periods are detected.";
          }
          leaf threshold {
            type uint32 {
              range "0..4294967295";
            }
            // NCS drop must statement
            // NCS drop default statement
            description
              "Specify the threshold for error frame periods.";
          }
        }
      }
    }
  }
  augment "/ncs:devices/ncs:device/ncs:config/ifm:ifm/ifm:interfaces/ifm:interface" {
    when '/efm:efm' {
      tailf:xpath-root 3;
    }
    description
      "EFM configuration in interface.";
    container efm {
      tailf:ncs-device-type "netconf";
      tailf:display-when "not(../../../../../ncs:module) or ../../../../../ncs:module[ncs:name='huawei-efm']";
      description
        "Configure EFM on the interface.";
      container session {
        description
          "Configure EFM on the local interface.";
        leaf state {
          type enable-state;
          default "disable";
          description
            "Indicates whether EFM is enabled on an interface.";
        }
        leaf mode {
          type work-mode;
          default "active";
          description
            "Specify the working mode of an EFM-enabled interface.";
        }
        leaf packet-max-size {
          type uint16 {
            range "64..1518";
          }
          units "Byte";
          default "128";
          description
            "Specify the maximum size of an EFM packet.";
        }
        leaf interval {
          type uint16 {
            range "100..1000";
          }
          units "ms";
          must '(../interval) mod 100 = 0' {
            tailf:xpath-root 3;
          }
          default "1000";
          description
            "Specify the interval at which EFM packets are sent.";
        }
        leaf timeout {
          type uint16 {
            range "300..30000";
          }
          units "ms";
          must '(../timeout) mod 100 = 0' {
            tailf:xpath-root 3;
          }
          default "5000";
          description
            "Specify the timeout period for receiving EFM packets.";
        }
        leaf ignore-loopback-request {
          type enable-state;
          must "(../state='disable' and ../ignore-loopback-request='disable') or (../state='enable')" {
            tailf:xpath-root 3;
          }
          default "disable";
          description
            "Indicates that this interface will ignore the loopback request from the peer.";
        }
        leaf trigger-if-down {
          type enable-state;
          must "(../state='disable' and ../trigger-if-down='disable') or (../state='enable')" {
            tailf:xpath-root 3;
          }
          default "disable";
          description
            "Indicates that EFM blocks an interface after detecting a fault.";
        }
        leaf hold-up-time {
          type uint16 {
            range "0..50";
          }
          units "s";
          default "0";
          description
            "Specify the time waiting for an interface blocked by EFM to go up.";
        }
        leaf trigger-mac-renew {
          type boolean;
          must "(../state='disable' and ../trigger-mac-renew='false') or (../state='enable')" {
            tailf:xpath-root 3;
          }
          default "false";
          description
            "Enable/disable that EFM clears the MAC address of an interface after detecting a fault.";
        }
        container error-frame {
          description
            "Configure the error frame function.";
          leaf notification {
            type enable-state;
            default "disable";
            description
              "Indicates whether notification of error frames is enabled.";
          }
          leaf period {
            type uint32 {
              range "1..60";
            }
            units "s";
            default "1";
            description
              "Specify the interval at which error frames are detected.";
          }
          leaf threshold {
            type uint32 {
              range "0..65535";
            }
            default "1";
            description
              "Specify the threshold for error frames.";
          }
          // NCS drop config false leaf 'period-unit'
        }
        container error-frame-second {
          description
            "Configure the error frames second function.";
          leaf notification {
            type enable-state;
            default "disable";
            description
              "Indicates whether notification of error frame seconds is enabled.";
          }
          leaf period {
            type uint32 {
              range "10..900";
            }
            units "s";
            default "60";
            description
              "Specify the interval at which error frame seconds are detected.";
          }
          leaf threshold {
            type uint32 {
              range "0..900";
            }
            units "s";
            must '(../threshold<=../period)' {
              tailf:xpath-root 3;
            }
            default "1";
            description
              "Specify the threshold for error frame seconds.";
          }
        }
        container error-code {
          description
            "Configure the error code function.";
          leaf notification {
            type enable-state;
            default "disable";
            description
              "Indicates whether notification of error codes is enabled.";
          }
          leaf period {
            type uint32 {
              range "1..60";
            }
            units "s";
            default "1";
            description
              "Specify the interval at which error codes are detected.";
          }
          leaf threshold {
            type uint32 {
              range "0..65535";
            }
            default "1";
            description
              "Specify the threshold for error codes.";
          }
        }
        container error-frame-period {
          description
            "Configure the error frame period function.";
          leaf notification {
            type enable-state;
            default "disable";
            description
              "Indicates whether notification of error frame periods is enabled.";
          }
          leaf period {
            type uint32 {
              range "20000..4294967295";
            }
            default "200000";
            description
              "Specify the interval at which error frame periods are detected.";
          }
          leaf threshold {
            type uint32 {
              range "0..4294967295";
            }
            must '(../threshold<=../period)' {
              tailf:xpath-root 3;
            }
            default "1";
            description
              "Specify the threshold for error frame periods.";
          }
        }
      }
    }
  }
}
