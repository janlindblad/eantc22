module huawei-y1731-statistics-deviations-NE8000 {
  // Generated by yanger -t ncs
  tailf:mount-id "huawei-nc-1.0:huawei-nc-1.0";
  tailf:ncs-device-type "netconf";

  namespace "urn:huawei:yang:huawei-y1731-statistics-deviations-NE8000";
  prefix y1731-statistics-devs-NE8000;

  import huawei-y1731-statistics {
    prefix y1731-statistics;
  }
  import huawei-devm {
    prefix devm;
  }
  import huawei-y1731 {
    prefix y1731;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "This module defines deviation statements for huawei-y1731-statistics module.";

  revision 2019-11-06 {
    description
      "Initial revision.";
    reference "Huawei private.";
  }

  deviation "/ncs:devices/ncs:template/ncs:ned-id/ncs:config/y1731:y1731/y1731-statistics:inner-priority" {
    deviate not-supported;
  }
  deviation "/ncs:devices/ncs:device/ncs:live-status/y1731:y1731/y1731-statistics:inner-priority" {
    deviate not-supported;
  }
  deviation "/ncs:devices/ncs:device/ncs:config/y1731:y1731/y1731-statistics:inner-priority" {
    deviate not-supported;
  }
  deviation "/ncs:devices/ncs:template/ncs:ned-id/ncs:config/y1731:y1731/y1731-statistics:cfm-level-check" {
    deviate not-supported;
  }
  deviation "/ncs:devices/ncs:device/ncs:live-status/y1731:y1731/y1731-statistics:cfm-level-check" {
    deviate not-supported;
  }
  deviation "/ncs:devices/ncs:device/ncs:config/y1731:y1731/y1731-statistics:cfm-level-check" {
    deviate not-supported;
  }
  deviation "/ncs:devices/ncs:template/ncs:ned-id/ncs:config/devm:devm/devm:mpu-boards/devm:mpu-board/y1731-statistics:cfm-mac-level-enable-mpu" {
    deviate not-supported;
  }
  deviation "/ncs:devices/ncs:device/ncs:live-status/devm:devm/devm:mpu-boards/devm:mpu-board/y1731-statistics:cfm-mac-level-enable-mpu" {
    deviate not-supported;
  }
  deviation "/ncs:devices/ncs:device/ncs:config/devm:devm/devm:mpu-boards/devm:mpu-board/y1731-statistics:cfm-mac-level-enable-mpu" {
    deviate not-supported;
  }
}
