module huawei-file-operation-deviations-NE8000 {
  // Generated by yanger -t ncs
  tailf:mount-id "huawei-nc-1.0:huawei-nc-1.0";
  tailf:ncs-device-type "netconf";

  namespace "urn:huawei:yang:huawei-file-operation-deviations-NE8000";
  prefix file-operation-devs-NE8000;

  import huawei-file-operation {
    prefix file-operation;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "This module defines deviation statements for huawei-file-operation module.";

  revision 2019-11-06 {
    description
      "Initial revision.";
    reference "Huawei private.";
  }

  deviation "/ncs:devices/ncs:device/ncs:live-status/file-operation:file-operation/file-operation:disk-usages" {
    deviate not-supported;
  }
  deviation "/ncs:devices/ncs:device/ncs:rpc/file-operation:rpc-reset-recycle-bin/file-operation:reset-recycle-bin" {
    deviate not-supported;
  }
  deviation "/ncs:devices/ncs:device/ncs:rpc/file-operation:rpc-copy-file/file-operation:copy-file/file-operation:input/file-operation:all" {
    deviate not-supported;
  }
  deviation "/ncs:devices/ncs:device/ncs:rpc/file-operation:rpc-delete-file/file-operation:delete-file/file-operation:input/file-operation:all" {
    deviate not-supported;
  }
}
