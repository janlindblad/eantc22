module huawei-oam-efm-bfd {
  // Generated by yanger -t ncs
  tailf:mount-id "huawei-nc-1.0:huawei-nc-1.0";
  tailf:ncs-device-type "netconf";

  namespace "urn:huawei:yang:huawei-oam-efm-bfd";
  prefix oam-efm-bfd;

  import huawei-extension {
    prefix ext;
  }
  import huawei-oammgr {
    prefix oammgr;
  }
  import huawei-bfd {
    prefix bfd;
  }
  import huawei-ifm {
    prefix ifm;
  }
  import huawei-efm {
    prefix efm;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Configure the operation, administration and maintenance (OAM) association function.";

  revision 2020-09-18 {
    description
      "Initial revision.";
    reference "Huawei private.";
  }
  ext:task-name "oammgr";

  typedef ncs_template_efm-bind-bfd-type {
    type string;
    description
      "Binding type.";
  }

  typedef ncs_rpc_notif_efm-bind-bfd-type {
    type enumeration {
      enum "EFM-BFD" {
        value 1;
        description
          "Type that EFM transfers fault information to BFD.";
      }
      enum "BFD-EFM" {
        value 2;
        description
          "Type that BFD transfers fault information to EFM.";
      }
    }
    description
      "Binding type.";
  }

  typedef live_ncs_efm-bind-bfd-type {
    type enumeration {
      enum "EFM-BFD" {
        value 1;
        description
          "Type that EFM transfers fault information to BFD.";
      }
      enum "BFD-EFM" {
        value 2;
        description
          "Type that BFD transfers fault information to EFM.";
      }
    }
    description
      "Binding type.";
  }

  typedef efm-bind-bfd-type {
    type enumeration {
      enum "EFM-BFD" {
        value 1;
        description
          "Type that EFM transfers fault information to BFD.";
      }
      enum "BFD-EFM" {
        value 2;
        description
          "Type that BFD transfers fault information to EFM.";
      }
    }
    description
      "Binding type.";
  }

  augment "/ncs:devices/ncs:template/ncs:ned-id/ncs:config/oammgr:oammgr" {
    description
      "Configure the operation, administration and maintenance (OAM) association function.";
    container efm-bind-bfds {
      description
        "List of associations between EFM and BFD.";
      list efm-bind-bfd {
        // NCS patched for predictable order
        ordered-by user;
        key "if-name bfd-session-id bind-type";
        unique "if-name bind-type";
        unique "bfd-session-id bind-type";
        description
          "Configure an instance of an association between EFM and BFD.";
        leaf if-name {
          type string;
          // NCS drop must statement
          description
            "Configure the name of interface which the EFM instance bound.";
        }
        leaf bfd-session-id {
          type string;
          // NCS drop must statement
          description
            "Configure the local discriminator of a BFD session.";
        }
        leaf bind-type {
          type ncs_template_efm-bind-bfd-type;
          description
            "Configure a binding type.";
        }
      }
    }
  }
  augment "/ncs:devices/ncs:device/ncs:live-status/oammgr:oammgr" {
    description
      "Configure the operation, administration and maintenance (OAM) association function.";
    container efm-bind-bfds {
      tailf:ncs-device-type "netconf";
      tailf:display-when "not(../../../ncs:module) or ../../../ncs:module[ncs:name='huawei-oam-efm-bfd'] or (../../../ncs:live-status-protocol[not(ncs:capability)]) or (../../../ncs:live-status-protocol/ncs:capability/ncs:module[.='huawei-oam-efm-bfd'])";
      description
        "List of associations between EFM and BFD.";
      list efm-bind-bfd {
        key "if-name bfd-session-id bind-type";
        unique "if-name bind-type";
        unique "bfd-session-id bind-type";
        description
          "Configure an instance of an association between EFM and BFD.";
        leaf if-name {
          type leafref {
            path "/ncs:devices/ncs:device/ncs:live-status/ifm:ifm/ifm:interfaces/ifm:interface/ifm:name" {
              tailf:xpath-root 3;
            }
          }
          // NCS drop must statement
          description
            "Configure the name of interface which the EFM instance bound.";
        }
        leaf bfd-session-id {
          type uint32 {
            range "1..16384";
          }
          // NCS drop must statement
          description
            "Configure the local discriminator of a BFD session.";
        }
        leaf bind-type {
          type live_ncs_efm-bind-bfd-type;
          description
            "Configure a binding type.";
        }
      }
    }
  }
  augment "/ncs:devices/ncs:device/ncs:config/oammgr:oammgr" {
    description
      "Configure the operation, administration and maintenance (OAM) association function.";
    container efm-bind-bfds {
      tailf:ncs-device-type "netconf";
      tailf:display-when "not(../../../ncs:module) or ../../../ncs:module[ncs:name='huawei-oam-efm-bfd']";
      description
        "List of associations between EFM and BFD.";
      list efm-bind-bfd {
        key "if-name bfd-session-id bind-type";
        unique "if-name bind-type";
        unique "bfd-session-id bind-type";
        description
          "Configure an instance of an association between EFM and BFD.";
        leaf if-name {
          type leafref {
            path "/ncs:devices/ncs:device/ncs:config/ifm:ifm/ifm:interfaces/ifm:interface/ifm:name" {
              tailf:xpath-root 3;
            }
          }
          must "/ifm:ifm/ifm:interfaces/ifm:interface[ifm:name=current()]/efm:efm/efm:session/efm:state='enable'" {
            tailf:xpath-root 3;
          }
          description
            "Configure the name of interface which the EFM instance bound.";
        }
        leaf bfd-session-id {
          type uint32 {
            range "1..16384";
          }
          must '/bfd:bfd/bfd:sessions/bfd:session[bfd:local-discriminator-multicast-ipv4=current()] or /bfd:bfd/bfd:sessions/bfd:session[bfd:local-discriminator=current()] or /bfd:bfd/bfd:sessions/bfd:session[bfd:local-discriminator-static-ldp-lsp=current()]' {
            tailf:xpath-root 3;
          }
          description
            "Configure the local discriminator of a BFD session.";
        }
        leaf bind-type {
          type efm-bind-bfd-type;
          description
            "Configure a binding type.";
        }
      }
    }
  }
}
