module huawei-twamp-fwd-notification {
  // Generated by yanger -t ncs
  tailf:mount-id "huawei-nc-1.0:huawei-nc-1.0";
  tailf:ncs-device-type "netconf";

  yang-version 1;
  namespace "urn:huawei:yang:huawei-twamp-fwd-notification";
  prefix twamp-fwd-notification;

  import huawei-twamp-responder {
    prefix twamp-responder;
  }
  import huawei-extension {
    prefix ext;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Notification of twamp-fwd-notification.";

  revision 2020-03-05 {
    description
      "Add task-name and import huawei-extension.";
    reference "Huawei private.";
  }
  revision 2019-07-08 {
    description
      "Initial revision.";
    reference "Huawei private.";
  }
  ext:task-name "twamp";

  augment "/ncs:devices/ncs:device/ncs:notifications/ncs:received-notifications/ncs:notification/ncs:data" {
    container twamp-nonsupport-serv-resume {
      presence "";
      config false;
      description
        "TWAMP does not support service alarm clearing on the bound interface.";
      leaf session-id {
        type string;
        description
          "Session ID.";
      }
    }
  }
  augment "/ncs:devices/ncs:device/ncs:notifications/ncs:received-notifications/ncs:notification/ncs:data" {
    container twamp-nonsupport-serv {
      presence "";
      config false;
      description
        "TWAMP does not support services on the bound interface.";
      leaf session-id {
        type string;
        description
          "Session ID.";
      }
    }
  }
  augment "/ncs:devices/ncs:device/ncs:netconf-notifications/ncs:received-notifications/ncs:notification/ncs:data" {
    container twamp-nonsupport-serv-resume {
      presence "";
      config false;
      description
        "TWAMP does not support service alarm clearing on the bound interface.";
      leaf session-id {
        type string;
        description
          "Session ID.";
      }
    }
  }
  augment "/ncs:devices/ncs:device/ncs:netconf-notifications/ncs:received-notifications/ncs:notification/ncs:data" {
    container twamp-nonsupport-serv {
      presence "";
      config false;
      description
        "TWAMP does not support services on the bound interface.";
      leaf session-id {
        type string;
        description
          "Session ID.";
      }
    }
  }
}
