module huawei-vaccess-master {
  // Generated by yanger -t ncs
  tailf:mount-id "huawei-nc-1.0:huawei-nc-1.0";
  tailf:ncs-device-type "netconf";

  namespace "urn:huawei:yang:huawei-vaccess-master";
  prefix vaccess-master;

  import huawei-vaccess {
    prefix vaccess;
  }
  import huawei-ifm {
    prefix ifm;
  }
  import ietf-inet-types {
    prefix inet;
  }
  import huawei-extension {
    prefix ext;
  }
  import ietf-yang-types {
    prefix yang;
  }
  import huawei-network-instance {
    prefix ni;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Virtual Access Master Information.";

  revision 2020-07-11 {
    description
      "Add private syntax to the Control-tunnel keychain name.";
    reference "Huawei private.";
  }
  revision 2020-03-24 {
    description
      "Fixed some descriptions.";
    reference "Huawei private.";
  }
  revision 2020-03-05 {
    description
      "Add some nodes for virtual access master.";
    reference "Huawei private.";
  }
  revision 2019-12-13 {
    description
      "Some compatibility conditions are modified.";
    reference "Huawei private.";
  }
  revision 2019-11-13 {
    description
      "Initial revision.";
    reference "Huawei private.";
  }
  ext:task-name "virtual-access";

  typedef ncs_template_vaccess-run-state {
    type string;
    description
      "Ap run state.";
  }

  typedef ncs_template_vaccess-ap-if-state {
    type string;
    description
      "Ap interface state.";
  }

  typedef ncs_template_vaccess-ap-if-type {
    type string;
    description
      "Ap interface attribute.";
  }

  typedef ncs_template_vaccess-inner-if-type {
    type string;
    description
      "Virtual access inner interface type.";
  }

  typedef ncs_rpc_notif_vaccess-run-state {
    type enumeration {
      enum "offline" {
        value 0;
        description
          "Offline state.";
      }
      enum "online" {
        value 1;
        description
          "Online state.";
      }
    }
    description
      "Ap run state.";
  }

  typedef ncs_rpc_notif_vaccess-ap-if-state {
    type enumeration {
      enum "down" {
        value 0;
        description
          "Down.";
      }
      enum "up" {
        value 1;
        description
          "Up.";
      }
    }
    description
      "Ap interface state.";
  }

  typedef ncs_rpc_notif_vaccess-ap-if-type {
    type enumeration {
      enum "inner" {
        value 0;
        description
          "Inner.";
      }
      enum "outer" {
        value 1;
        description
          "Outer.";
      }
    }
    description
      "Ap interface attribute.";
  }

  typedef ncs_rpc_notif_vaccess-inner-if-type {
    type enumeration {
      enum "to-master" {
        value 1;
        description
          "Connect master interface.";
      }
      enum "to-ap" {
        value 2;
        description
          "Connect ap interface.";
      }
    }
    description
      "Virtual access inner interface type.";
  }

  typedef live_ncs_vaccess-run-state {
    type enumeration {
      enum "offline" {
        value 0;
        description
          "Offline state.";
      }
      enum "online" {
        value 1;
        description
          "Online state.";
      }
    }
    description
      "Ap run state.";
  }

  typedef live_ncs_vaccess-ap-if-state {
    type enumeration {
      enum "down" {
        value 0;
        description
          "Down.";
      }
      enum "up" {
        value 1;
        description
          "Up.";
      }
    }
    description
      "Ap interface state.";
  }

  typedef live_ncs_vaccess-ap-if-type {
    type enumeration {
      enum "inner" {
        value 0;
        description
          "Inner.";
      }
      enum "outer" {
        value 1;
        description
          "Outer.";
      }
    }
    description
      "Ap interface attribute.";
  }

  typedef live_ncs_vaccess-inner-if-type {
    type enumeration {
      enum "to-master" {
        value 1;
        description
          "Connect master interface.";
      }
      enum "to-ap" {
        value 2;
        description
          "Connect ap interface.";
      }
    }
    description
      "Virtual access inner interface type.";
  }

  typedef vaccess-run-state {
    type enumeration {
      enum "offline" {
        value 0;
        description
          "Offline state.";
      }
      enum "online" {
        value 1;
        description
          "Online state.";
      }
    }
    description
      "Ap run state.";
  }

  typedef vaccess-ap-if-state {
    type enumeration {
      enum "down" {
        value 0;
        description
          "Down.";
      }
      enum "up" {
        value 1;
        description
          "Up.";
      }
    }
    description
      "Ap interface state.";
  }

  typedef vaccess-ap-if-type {
    type enumeration {
      enum "inner" {
        value 0;
        description
          "Inner.";
      }
      enum "outer" {
        value 1;
        description
          "Outer.";
      }
    }
    description
      "Ap interface attribute.";
  }

  typedef vaccess-inner-if-type {
    type enumeration {
      enum "to-master" {
        value 1;
        description
          "Connect master interface.";
      }
      enum "to-ap" {
        value 2;
        description
          "Connect ap interface.";
      }
    }
    description
      "Virtual access inner interface type.";
  }

  augment "/ncs:devices/ncs:template/ncs:ned-id/ncs:config/vaccess:vaccess" {
    description
      "Virtual access master Configuration information augment to module vaccess.";
    container master {
      // NCS drop when statement
      description
        "Configure virtual access master function.";
      container global {
        description
          "Configure bisic master function of virtural access.";
        leaf admin-ip-address {
          type string;
          description
            "Admin IP of master.";
        }
        leaf control-tunnel-keychain-name {
          type string;
          ext:case-sensitivity "lower-only";
          description
            "Control-tunnel keychain name of master.";
        }
      }
      container aps {
        description
          "List of ap configuration of virtural access.";
        list ap {
          // NCS patched for predictable order
          ordered-by user;
          key "ap-id";
          unique "admin-ip-address";
          description
            "Configure ap function for virtural access.";
          leaf ap-id {
            type string;
            description
              "Ap ID.";
          }
          leaf description {
            type string;
            description
              "Sysname of ap.";
          }
          leaf admin-ip-address {
            ext:operation-exclude "delete";
            type string;
            // NCS drop must statement
            description
              "Ap admin IP address. After this node is deleted, the ap and master are disconnected, affecting normal service functions.";
          }
          leaf esn {
            type string;
            description
              "ESN number.";
          }
          // NCS drop config false leaf 'primary-master-ip'
          // NCS drop config false leaf state
          // NCS drop config false leaf 'up-time'
          // NCS drop config false container 'ap-interface-infos'
        }
      }
    }
  }
  augment "/ncs:devices/ncs:device/ncs:live-status/vaccess:vaccess" {
    description
      "Virtual access master Configuration information augment to module vaccess.";
    container master {
      tailf:ncs-device-type "netconf";
      tailf:display-when "not(../../../ncs:module) or ../../../ncs:module[ncs:name='huawei-vaccess-master'] or (../../../ncs:live-status-protocol[not(ncs:capability)]) or (../../../ncs:live-status-protocol/ncs:capability/ncs:module[.='huawei-vaccess-master'])";
      // NCS drop when statement
      description
        "Configure virtual access master function.";
      container global {
        description
          "Configure bisic master function of virtural access.";
        leaf admin-ip-address {
          type inet:ip-address;
          description
            "Admin IP of master.";
        }
        leaf control-tunnel-keychain-name {
          type string {
            length "1..47";
            pattern '[^A-Z]+';
          }
          ext:case-sensitivity "lower-only";
          description
            "Control-tunnel keychain name of master.";
        }
      }
      container aps {
        description
          "List of ap configuration of virtural access.";
        list ap {
          key "ap-id";
          unique "admin-ip-address";
          description
            "Configure ap function for virtural access.";
          leaf ap-id {
            type uint32 {
              range "1024..8191";
            }
            description
              "Ap ID.";
          }
          leaf description {
            type string {
              length "1..246";
            }
            description
              "Sysname of ap.";
          }
          leaf admin-ip-address {
            ext:operation-exclude "delete";
            type inet:ip-address;
            // NCS drop must statement
            description
              "Ap admin IP address. After this node is deleted, the ap and master are disconnected, affecting normal service functions.";
          }
          leaf esn {
            type string {
              length "1..64";
            }
            description
              "ESN number.";
          }
          leaf primary-master-ip {
            type inet:ip-address;
            description
              "Primary master IP address.";
          }
          leaf state {
            type live_ncs_vaccess-run-state;
            description
              "Current run state of ap.";
          }
          leaf up-time {
            type yang:date-and-time;
            description
              "Online time.";
          }
          container ap-interface-infos {
            description
              "List of ap interface information parameter.";
            list ap-interface-info {
              key "interface-name";
              description
                "Operational data of ap interface information.";
              leaf interface-name {
                type leafref {
                  path "/ncs:devices/ncs:device/ncs:live-status/ifm:ifm/ifm:interfaces/ifm:interface/ifm:name" {
                    tailf:xpath-root 3;
                  }
                }
                description
                  "Interface name.";
              }
              leaf interface-status {
                type live_ncs_vaccess-ap-if-state;
                description
                  "Interface state.";
              }
              leaf interface-type {
                type live_ncs_vaccess-ap-if-type;
                description
                  "Interface type.";
              }
            }
          }
        }
      }
    }
  }
  augment "/ncs:devices/ncs:device/ncs:config/vaccess:vaccess" {
    description
      "Virtual access master Configuration information augment to module vaccess.";
    container master {
      tailf:ncs-device-type "netconf";
      tailf:display-when "not(../../../ncs:module) or ../../../ncs:module[ncs:name='huawei-vaccess-master']";
      when "/vaccess:vaccess/vaccess:global/vaccess:role='master'" {
        tailf:xpath-root 3;
      }
      description
        "Configure virtual access master function.";
      container global {
        description
          "Configure bisic master function of virtural access.";
        leaf admin-ip-address {
          type inet:ip-address;
          description
            "Admin IP of master.";
        }
        leaf control-tunnel-keychain-name {
          type string {
            length "1..47";
            pattern '[^A-Z]+';
          }
          ext:case-sensitivity "lower-only";
          description
            "Control-tunnel keychain name of master.";
        }
      }
      container aps {
        description
          "List of ap configuration of virtural access.";
        list ap {
          key "ap-id";
          unique "admin-ip-address";
          description
            "Configure ap function for virtural access.";
          leaf ap-id {
            type uint32 {
              range "1024..8191";
            }
            description
              "Ap ID.";
          }
          leaf description {
            type string {
              length "1..246";
            }
            description
              "Sysname of ap.";
          }
          leaf admin-ip-address {
            ext:operation-exclude "delete";
            type inet:ip-address;
            must '../admin-ip-address!=../../../global/admin-ip-address' {
              tailf:xpath-root 3;
            }
            description
              "Ap admin IP address. After this node is deleted, the ap and master are disconnected, affecting normal service functions.";
          }
          leaf esn {
            type string {
              length "1..64";
            }
            description
              "ESN number.";
          }
          // NCS drop config false leaf 'primary-master-ip'
          // NCS drop config false leaf state
          // NCS drop config false leaf 'up-time'
          // NCS drop config false container 'ap-interface-infos'
        }
      }
    }
  }
  augment "/ncs:devices/ncs:template/ncs:ned-id/ncs:config/ni:network-instance/ni:instances/ni:instance" {
    // NCS drop when statement
    description
      "Inner interface on master of virtual access.";
    container vaccess-interfaces {
      description
        "List of inner interface on master of virtual access.";
      list vaccess-interface {
        // NCS patched for predictable order
        ordered-by user;
        key "name";
        description
          "Configure inner interface on master of virtual access.";
        leaf name {
          type string;
          // NCS drop must statement
          // NCS drop must statement
          description
            "Inner interface name on master of virtual access.";
        }
      }
    }
  }
  augment "/ncs:devices/ncs:device/ncs:live-status/ni:network-instance/ni:instances/ni:instance" {
    // NCS drop when statement
    description
      "Inner interface on master of virtual access.";
    container vaccess-interfaces {
      tailf:ncs-device-type "netconf";
      tailf:display-when "not(../../../../../ncs:module) or ../../../../../ncs:module[ncs:name='huawei-vaccess-master'] or (../../../../../ncs:live-status-protocol[not(ncs:capability)]) or (../../../../../ncs:live-status-protocol/ncs:capability/ncs:module[.='huawei-vaccess-master'])";
      description
        "List of inner interface on master of virtual access.";
      list vaccess-interface {
        key "name";
        description
          "Configure inner interface on master of virtual access.";
        leaf name {
          type leafref {
            path "/ncs:devices/ncs:device/ncs:live-status/ifm:ifm/ifm:interfaces/ifm:interface/ifm:name" {
              tailf:xpath-root 3;
            }
          }
          // NCS drop must statement
          // NCS drop must statement
          description
            "Inner interface name on master of virtual access.";
        }
      }
    }
  }
  augment "/ncs:devices/ncs:device/ncs:config/ni:network-instance/ni:instances/ni:instance" {
    when "/vaccess:vaccess/vaccess:global/vaccess:role='master'" {
      tailf:xpath-root 3;
    }
    description
      "Inner interface on master of virtual access.";
    container vaccess-interfaces {
      tailf:ncs-device-type "netconf";
      tailf:display-when "not(../../../../../ncs:module) or ../../../../../ncs:module[ncs:name='huawei-vaccess-master']";
      description
        "List of inner interface on master of virtual access.";
      list vaccess-interface {
        key "name";
        description
          "Configure inner interface on master of virtual access.";
        leaf name {
          type leafref {
            path "/ncs:devices/ncs:device/ncs:config/ifm:ifm/ifm:interfaces/ifm:interface/ifm:name" {
              tailf:xpath-root 3;
            }
          }
          must "/ifm:ifm/ifm:interfaces/ifm:interface[ifm:name=current()]/ifm:vrf-name='_public_'" {
            tailf:xpath-root 3;
          }
          must '../../../ni:name=/ifm:ifm/ifm:interfaces/ifm:interface[ifm:name=current()]/ifm:vrf-name' {
            tailf:xpath-root 3;
          }
          description
            "Inner interface name on master of virtual access.";
        }
      }
    }
  }
}
