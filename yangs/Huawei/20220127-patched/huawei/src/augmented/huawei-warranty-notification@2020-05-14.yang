module huawei-warranty-notification {
  // Generated by yanger -t ncs
  tailf:mount-id "huawei-nc-1.0:huawei-nc-1.0";
  tailf:ncs-device-type "netconf";

  namespace "urn:huawei:yang:huawei-warranty-notification";
  prefix warranty-notification;

  import huawei-extension {
    prefix ext;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Notification of warranty.";

  revision 2020-05-14 {
    description
      "Initial revision.";
    reference "Huawei private.";
  }
  ext:task-name "warranty";

  augment "/ncs:devices/ncs:device/ncs:notifications/ncs:received-notifications/ncs:notification/ncs:data" {
    container warranty-missing-session-clear {
      presence "";
      config false;
      description
        "The alarm indicationg that the electronic warranty's session of the device is missing was cleared.";
      leaf type {
        type string {
          length "1..10";
        }
        description
          "Specify the unit of the electronic warranty.";
      }
      leaf slot {
        type string {
          length "1..32";
        }
        description
          "Specify the slot path.";
      }
      leaf serial-number {
        type string {
          length "1..100";
        }
        description
          "Serial number of the electronic warranty.";
      }
    }
  }
  augment "/ncs:devices/ncs:device/ncs:notifications/ncs:received-notifications/ncs:notification/ncs:data" {
    container warranty-missing-session {
      presence "";
      config false;
      description
        "The electronic warranty's session of the device is missing.";
      leaf type {
        type string {
          length "1..10";
        }
        description
          "Specify the unit of the electronic warranty.";
      }
      leaf slot {
        type string {
          length "1..32";
        }
        description
          "Specify the slot path.";
      }
      leaf serial-number {
        type string {
          length "1..100";
        }
        description
          "Serial number of the electronic warranty.";
      }
    }
  }
  augment "/ncs:devices/ncs:device/ncs:notifications/ncs:received-notifications/ncs:notification/ncs:data" {
    container warranty-expired-clear {
      presence "";
      config false;
      description
        "The alarm indicating that the electronic warranty of the device is expired cleared.";
      leaf type {
        type string {
          length "1..10";
        }
        description
          "Specify the unit of the electronic warranty.";
      }
      leaf slot {
        type string {
          length "1..32";
        }
        description
          "Specify the slot path.";
      }
      leaf serial-number {
        type string {
          length "1..100";
        }
        description
          "Serial number of the electronic warranty.";
      }
    }
  }
  augment "/ncs:devices/ncs:device/ncs:notifications/ncs:received-notifications/ncs:notification/ncs:data" {
    container warranty-expired {
      presence "";
      config false;
      description
        "The electronic warranty of the device is expired.";
      leaf type {
        type string {
          length "1..10";
        }
        description
          "Specify the unit of the electronic warranty.";
      }
      leaf slot {
        type string {
          length "1..32";
        }
        description
          "Specify the slot path.";
      }
      leaf serial-number {
        type string {
          length "1..100";
        }
        description
          "Serial number of the electronic warranty.";
      }
    }
  }
  augment "/ncs:devices/ncs:device/ncs:notifications/ncs:received-notifications/ncs:notification/ncs:data" {
    container warranty-to-be-expired-clear {
      presence "";
      config false;
      description
        "The ararm indicating that the electronic warranty of the device is expiring was cleared.";
      leaf type {
        type string {
          length "1..10";
        }
        description
          "Specify the unit of the electronic warranty.";
      }
      leaf slot {
        type string {
          length "1..32";
        }
        description
          "Specify the slot path.";
      }
      leaf serial-number {
        type string {
          length "1..100";
        }
        description
          "Serial number of the electronic warranty.";
      }
    }
  }
  augment "/ncs:devices/ncs:device/ncs:notifications/ncs:received-notifications/ncs:notification/ncs:data" {
    container warranty-to-be-expired {
      presence "";
      config false;
      description
        "The electronic warranty of the device is expiring.";
      leaf type {
        type string {
          length "1..10";
        }
        description
          "Specify the unit of the electronic warranty.";
      }
      leaf slot {
        type string {
          length "1..32";
        }
        description
          "Specify the slot path.";
      }
      leaf serial-number {
        type string {
          length "1..100";
        }
        description
          "Serial number of the electronic warranty.";
      }
      leaf remained-days {
        type uint32;
        description
          "Remained days of the electronic warranty.";
      }
    }
  }
  augment "/ncs:devices/ncs:device/ncs:netconf-notifications/ncs:received-notifications/ncs:notification/ncs:data" {
    container warranty-missing-session-clear {
      presence "";
      config false;
      description
        "The alarm indicationg that the electronic warranty's session of the device is missing was cleared.";
      leaf type {
        type string {
          length "1..10";
        }
        description
          "Specify the unit of the electronic warranty.";
      }
      leaf slot {
        type string {
          length "1..32";
        }
        description
          "Specify the slot path.";
      }
      leaf serial-number {
        type string {
          length "1..100";
        }
        description
          "Serial number of the electronic warranty.";
      }
    }
  }
  augment "/ncs:devices/ncs:device/ncs:netconf-notifications/ncs:received-notifications/ncs:notification/ncs:data" {
    container warranty-missing-session {
      presence "";
      config false;
      description
        "The electronic warranty's session of the device is missing.";
      leaf type {
        type string {
          length "1..10";
        }
        description
          "Specify the unit of the electronic warranty.";
      }
      leaf slot {
        type string {
          length "1..32";
        }
        description
          "Specify the slot path.";
      }
      leaf serial-number {
        type string {
          length "1..100";
        }
        description
          "Serial number of the electronic warranty.";
      }
    }
  }
  augment "/ncs:devices/ncs:device/ncs:netconf-notifications/ncs:received-notifications/ncs:notification/ncs:data" {
    container warranty-expired-clear {
      presence "";
      config false;
      description
        "The alarm indicating that the electronic warranty of the device is expired cleared.";
      leaf type {
        type string {
          length "1..10";
        }
        description
          "Specify the unit of the electronic warranty.";
      }
      leaf slot {
        type string {
          length "1..32";
        }
        description
          "Specify the slot path.";
      }
      leaf serial-number {
        type string {
          length "1..100";
        }
        description
          "Serial number of the electronic warranty.";
      }
    }
  }
  augment "/ncs:devices/ncs:device/ncs:netconf-notifications/ncs:received-notifications/ncs:notification/ncs:data" {
    container warranty-expired {
      presence "";
      config false;
      description
        "The electronic warranty of the device is expired.";
      leaf type {
        type string {
          length "1..10";
        }
        description
          "Specify the unit of the electronic warranty.";
      }
      leaf slot {
        type string {
          length "1..32";
        }
        description
          "Specify the slot path.";
      }
      leaf serial-number {
        type string {
          length "1..100";
        }
        description
          "Serial number of the electronic warranty.";
      }
    }
  }
  augment "/ncs:devices/ncs:device/ncs:netconf-notifications/ncs:received-notifications/ncs:notification/ncs:data" {
    container warranty-to-be-expired-clear {
      presence "";
      config false;
      description
        "The ararm indicating that the electronic warranty of the device is expiring was cleared.";
      leaf type {
        type string {
          length "1..10";
        }
        description
          "Specify the unit of the electronic warranty.";
      }
      leaf slot {
        type string {
          length "1..32";
        }
        description
          "Specify the slot path.";
      }
      leaf serial-number {
        type string {
          length "1..100";
        }
        description
          "Serial number of the electronic warranty.";
      }
    }
  }
  augment "/ncs:devices/ncs:device/ncs:netconf-notifications/ncs:received-notifications/ncs:notification/ncs:data" {
    container warranty-to-be-expired {
      presence "";
      config false;
      description
        "The electronic warranty of the device is expiring.";
      leaf type {
        type string {
          length "1..10";
        }
        description
          "Specify the unit of the electronic warranty.";
      }
      leaf slot {
        type string {
          length "1..32";
        }
        description
          "Specify the slot path.";
      }
      leaf serial-number {
        type string {
          length "1..100";
        }
        description
          "Serial number of the electronic warranty.";
      }
      leaf remained-days {
        type uint32;
        description
          "Remained days of the electronic warranty.";
      }
    }
  }
}
