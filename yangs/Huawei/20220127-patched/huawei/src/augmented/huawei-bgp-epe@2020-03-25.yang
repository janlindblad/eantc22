module huawei-bgp-epe {
  // Generated by yanger -t ncs
  tailf:mount-id "huawei-nc-1.0:huawei-nc-1.0";
  tailf:ncs-device-type "netconf";

  yang-version 1;
  namespace "urn:huawei:yang:huawei-bgp-epe";
  prefix bgp-epe;

  import huawei-network-instance {
    prefix ni;
  }
  import huawei-extension {
    prefix ext;
  }
  import huawei-bgp {
    prefix bgp;
  }
  import huawei-srv6 {
    prefix srv6;
  }
  import ietf-inet-types {
    prefix inet;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "BGP EPE configuration.";

  revision 2020-03-25 {
    description
      "Initial revision.";
    reference "Huawei private.";
  }
  ext:task-name "bgp";

  augment "/ncs:devices/ncs:template/ncs:ned-id/ncs:config/ni:network-instance/ni:instances/ni:instance/bgp:bgp/bgp:base-process" {
    description
      "BGP egress engineering segment-routing IPv6 configuration.";
    container epe-srv6 {
      // NCS drop when statement
      description
        "Configure BGP egress engineering segment-routing IPv6 information.";
      leaf locator-name {
        type string;
        description
          "Referenced locator name.";
      }
    }
  }
  augment "/ncs:devices/ncs:device/ncs:live-status/ni:network-instance/ni:instances/ni:instance/bgp:bgp/bgp:base-process" {
    description
      "BGP egress engineering segment-routing IPv6 configuration.";
    container epe-srv6 {
      tailf:ncs-device-type "netconf";
      tailf:display-when "not(../../../../../../../ncs:module) or ../../../../../../../ncs:module[ncs:name='huawei-bgp-epe'] or (../../../../../../../ncs:live-status-protocol[not(ncs:capability)]) or (../../../../../../../ncs:live-status-protocol/ncs:capability/ncs:module[.='huawei-bgp-epe'])";
      // NCS drop when statement
      description
        "Configure BGP egress engineering segment-routing IPv6 information.";
      leaf locator-name {
        type leafref {
          path "/ncs:devices/ncs:device/ncs:live-status/ni:network-instance/ni:instances/ni:instance/srv6:srv6/srv6:locators/srv6:locator/srv6:name" {
            tailf:xpath-root 3;
          }
        }
        description
          "Referenced locator name.";
      }
    }
  }
  augment "/ncs:devices/ncs:device/ncs:config/ni:network-instance/ni:instances/ni:instance/bgp:bgp/bgp:base-process" {
    description
      "BGP egress engineering segment-routing IPv6 configuration.";
    container epe-srv6 {
      tailf:ncs-device-type "netconf";
      tailf:display-when "not(../../../../../../../ncs:module) or ../../../../../../../ncs:module[ncs:name='huawei-bgp-epe']";
      when "../../../ni:name='_public_'" {
        tailf:xpath-root 3;
      }
      description
        "Configure BGP egress engineering segment-routing IPv6 information.";
      leaf locator-name {
        type leafref {
          path "/ncs:devices/ncs:device/ncs:config/ni:network-instance/ni:instances/ni:instance/srv6:srv6/srv6:locators/srv6:locator/srv6:name" {
            tailf:xpath-root 3;
          }
        }
        description
          "Referenced locator name.";
      }
    }
  }
  augment "/ncs:devices/ncs:template/ncs:ned-id/ncs:config/ni:network-instance/ni:instances/ni:instance/bgp:bgp/bgp:base-process/bgp:peers/bgp:peer" {
    description
      "BGP peer egress engineering segment-routing IPv6 configuration.";
    container epe-srv6 {
      // NCS drop when statement
      description
        "Configure BGP peer egress engineering segment-routing IPv6 information.";
      choice sid-option {
        description
          "Set automatic SID or static SID.";
        case auto-sid {
          description
            "Set automatic SID.";
          leaf locator-name {
            type string;
            description
              "Name of the locator referenced by a BGP peer.";
          }
        }
        case static-sid {
          // NCS drop when statement
          description
            "Set static SID value.";
          leaf psp-sid {
            type string;
            // NCS drop must statement
            description
              "Static End.X SID (PSP) of a BGP peer.";
          }
          leaf no-psp-usp-sid {
            type string;
            // NCS drop must statement
            description
              "Static End.X SID (no PSP, no USP) of a BGP peer.";
          }
        }
      }
    }
  }
  augment "/ncs:devices/ncs:device/ncs:live-status/ni:network-instance/ni:instances/ni:instance/bgp:bgp/bgp:base-process/bgp:peers/bgp:peer" {
    description
      "BGP peer egress engineering segment-routing IPv6 configuration.";
    container epe-srv6 {
      tailf:ncs-device-type "netconf";
      tailf:display-when "not(../../../../../../../../../ncs:module) or ../../../../../../../../../ncs:module[ncs:name='huawei-bgp-epe'] or (../../../../../../../../../ncs:live-status-protocol[not(ncs:capability)]) or (../../../../../../../../../ncs:live-status-protocol/ncs:capability/ncs:module[.='huawei-bgp-epe'])";
      // NCS drop when statement
      description
        "Configure BGP peer egress engineering segment-routing IPv6 information.";
      choice sid-option {
        description
          "Set automatic SID or static SID.";
        case auto-sid {
          description
            "Set automatic SID.";
          leaf locator-name {
            type leafref {
              path "/ncs:devices/ncs:device/ncs:live-status/ni:network-instance/ni:instances/ni:instance/srv6:srv6/srv6:locators/srv6:locator/srv6:name" {
                tailf:xpath-root 3;
              }
            }
            description
              "Name of the locator referenced by a BGP peer.";
          }
        }
        case static-sid {
          // NCS drop when statement
          description
            "Set static SID value.";
          leaf psp-sid {
            type inet:ipv6-address-no-zone;
            // NCS drop must statement
            description
              "Static End.X SID (PSP) of a BGP peer.";
          }
          leaf no-psp-usp-sid {
            type inet:ipv6-address-no-zone;
            // NCS drop must statement
            description
              "Static End.X SID (no PSP, no USP) of a BGP peer.";
          }
        }
      }
    }
  }
  augment "/ncs:devices/ncs:device/ncs:config/ni:network-instance/ni:instances/ni:instance/bgp:bgp/bgp:base-process/bgp:peers/bgp:peer" {
    description
      "BGP peer egress engineering segment-routing IPv6 configuration.";
    container epe-srv6 {
      tailf:ncs-device-type "netconf";
      tailf:display-when "not(../../../../../../../../../ncs:module) or ../../../../../../../../../ncs:module[ncs:name='huawei-bgp-epe']";
      when "../../../../../ni:name='_public_' and ../bgp:egress-engineer='enable'" {
        tailf:xpath-root 3;
      }
      description
        "Configure BGP peer egress engineering segment-routing IPv6 information.";
      choice sid-option {
        description
          "Set automatic SID or static SID.";
        case auto-sid {
          description
            "Set automatic SID.";
          leaf locator-name {
            type leafref {
              path "/ncs:devices/ncs:device/ncs:config/ni:network-instance/ni:instances/ni:instance/srv6:srv6/srv6:locators/srv6:locator/srv6:name" {
                tailf:xpath-root 3;
              }
            }
            description
              "Name of the locator referenced by a BGP peer.";
          }
        }
        case static-sid {
          when '../../../bgp-epe:epe-srv6/bgp-epe:locator-name' {
            tailf:xpath-root 3;
          }
          description
            "Set static SID value.";
          leaf psp-sid {
            type inet:ipv6-address-no-zone;
            must 'not(../no-psp-usp-sid) or (../psp-sid != ../no-psp-usp-sid)' {
              tailf:xpath-root 3;
            }
            description
              "Static End.X SID (PSP) of a BGP peer.";
          }
          leaf no-psp-usp-sid {
            type inet:ipv6-address-no-zone;
            must 'not(../psp-sid) or (../psp-sid != ../no-psp-usp-sid)' {
              tailf:xpath-root 3;
            }
            description
              "Static End.X SID (no PSP, no USP) of a BGP peer.";
          }
        }
      }
    }
  }
}
