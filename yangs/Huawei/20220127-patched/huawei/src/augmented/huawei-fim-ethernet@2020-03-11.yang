module huawei-fim-ethernet {
  // Generated by yanger -t ncs
  tailf:mount-id "huawei-nc-1.0:huawei-nc-1.0";
  tailf:ncs-device-type "netconf";

  namespace "urn:huawei:yang:huawei-fim-ethernet";
  prefix fim-ethernet;

  import huawei-ethernet {
    prefix ethernet;
  }
  import huawei-ifm {
    prefix ifm;
  }
  import huawei-extension {
    prefix ext;
  }
  import huawei-ifm-trunk {
    prefix ifm-trunk;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Common interface management, which includes the public configuration of interfaces.";
  reference "Huawei private.";

  revision 2020-03-11 {
    description
      "Initial revision.";
    reference "Huawei private.";
  }
  ext:task-name "forwarding";

  typedef ncs_template_enable-type {
    type string;
    description
      "Enable type.";
  }

  typedef ncs_rpc_notif_enable-type {
    type enumeration {
      enum "disable" {
        value 0;
        description
          "Disable.";
      }
      enum "enable" {
        value 1;
        description
          "Enable.";
      }
    }
    description
      "Enable type.";
  }

  typedef live_ncs_enable-type {
    type enumeration {
      enum "disable" {
        value 0;
        description
          "Disable.";
      }
      enum "enable" {
        value 1;
        description
          "Enable.";
      }
    }
    description
      "Enable type.";
  }

  typedef enable-type {
    type enumeration {
      enum "disable" {
        value 0;
        description
          "Disable.";
      }
      enum "enable" {
        value 1;
        description
          "Enable.";
      }
    }
    description
      "Enable type.";
  }

  augment "/ncs:devices/ncs:template/ncs:ned-id/ncs:config/ifm:ifm/ifm:interfaces/ifm:interface/ethernet:ethernet/ethernet:l3-sub-interface" {
    description
      "FIM configuration to the IFM module.";
    container mode-channel {
      // NCS drop when statement
      description
        "Configure the mode Channel sub-interface.";
      leaf mode-channel-enable {
        type ncs_template_enable-type;
        // NCS drop default statement
        description
          "Enable or disable mode channel sub-interface.";
      }
      leaf bandwidth {
        // NCS drop when statement
        type string;
        units "Mbit/s";
        // NCS drop default statement
        description
          "Specify bandwidth of an mode channel sub-interface (Mbit/s).";
      }
    }
  }
  augment "/ncs:devices/ncs:device/ncs:live-status/ifm:ifm/ifm:interfaces/ifm:interface/ethernet:ethernet/ethernet:l3-sub-interface" {
    description
      "FIM configuration to the IFM module.";
    container mode-channel {
      tailf:ncs-device-type "netconf";
      tailf:display-when "not(../../../../../../../ncs:module) or ../../../../../../../ncs:module[ncs:name='huawei-fim-ethernet'] or (../../../../../../../ncs:live-status-protocol[not(ncs:capability)]) or (../../../../../../../ncs:live-status-protocol/ncs:capability/ncs:module[.='huawei-fim-ethernet'])";
      // NCS drop when statement
      description
        "Configure the mode Channel sub-interface.";
      leaf mode-channel-enable {
        type live_ncs_enable-type;
        // NCS drop default statement
        description
          "Enable or disable mode channel sub-interface.";
      }
      leaf bandwidth {
        // NCS drop when statement
        type uint32 {
          range "2..1000000000";
        }
        units "Mbit/s";
        // NCS drop default statement
        description
          "Specify bandwidth of an mode channel sub-interface (Mbit/s).";
      }
    }
  }
  augment "/ncs:devices/ncs:device/ncs:config/ifm:ifm/ifm:interfaces/ifm:interface/ethernet:ethernet/ethernet:l3-sub-interface" {
    description
      "FIM configuration to the IFM module.";
    container mode-channel {
      tailf:ncs-device-type "netconf";
      tailf:display-when "not(../../../../../../../ncs:module) or ../../../../../../../ncs:module[ncs:name='huawei-fim-ethernet']";
      when '(../ethernet:vlan-type-dot1q)' {
        tailf:xpath-root 3;
      }
      description
        "Configure the mode Channel sub-interface.";
      leaf mode-channel-enable {
        type enable-type;
        default "disable";
        description
          "Enable or disable mode channel sub-interface.";
      }
      leaf bandwidth {
        when "../mode-channel-enable='enable'" {
          tailf:xpath-root 3;
        }
        type uint32 {
          range "2..1000000000";
        }
        units "Mbit/s";
        default "2";
        description
          "Specify bandwidth of an mode channel sub-interface (Mbit/s).";
      }
    }
  }
  augment "/ncs:devices/ncs:template/ncs:ned-id/ncs:config/ifm:ifm/ifm:interfaces/ifm:interface/ethernet:ethernet/ethernet:main-interface" {
    description
      "FIM configuration to the IFM module.";
    container fim-main {
      // NCS drop when statement
      description
        "Configure the FIM configuration to the main interface.";
      leaf outer-vlan-enable {
        type ncs_template_enable-type;
        // NCS drop default statement
        description
          "Modify one tag ethernet type.";
      }
    }
  }
  augment "/ncs:devices/ncs:device/ncs:live-status/ifm:ifm/ifm:interfaces/ifm:interface/ethernet:ethernet/ethernet:main-interface" {
    description
      "FIM configuration to the IFM module.";
    container fim-main {
      tailf:ncs-device-type "netconf";
      tailf:display-when "not(../../../../../../../ncs:module) or ../../../../../../../ncs:module[ncs:name='huawei-fim-ethernet'] or (../../../../../../../ncs:live-status-protocol[not(ncs:capability)]) or (../../../../../../../ncs:live-status-protocol/ncs:capability/ncs:module[.='huawei-fim-ethernet'])";
      // NCS drop when statement
      description
        "Configure the FIM configuration to the main interface.";
      leaf outer-vlan-enable {
        type live_ncs_enable-type;
        // NCS drop default statement
        description
          "Modify one tag ethernet type.";
      }
    }
  }
  augment "/ncs:devices/ncs:device/ncs:config/ifm:ifm/ifm:interfaces/ifm:interface/ethernet:ethernet/ethernet:main-interface" {
    description
      "FIM configuration to the IFM module.";
    container fim-main {
      tailf:ncs-device-type "netconf";
      tailf:display-when "not(../../../../../../../ncs:module) or ../../../../../../../ncs:module[ncs:name='huawei-fim-ethernet']";
      when "not((../../../ifm:name) = (/ifm:ifm/ifm:interfaces/ifm:interface/ifm-trunk:trunk/ifm-trunk:members/ifm-trunk:member/ifm-trunk:name)) and ../../../ifm:type!='FlexE-200GE' and ../../../ifm:type!='FlexE-50G' and ../../../ifm:type!='FlexE-100G' and ../../../ifm:type!='FlexE-400G' and ../../../ifm:type!='FlexE-50|100G' and ../../../ifm:type!='Virtual-Ethernet' and ../../../ifm:type!='Tunnel' and ../../../ifm:type!='NULL' and ../../../ifm:type!='LoopBack' and ../../../ifm:type!='Global-VE' and ../../../ifm:type!='Nve' and ../../../ifm:type!='Vbdif' and ../../../ifm:type!='Vlanif' and ../../../ifm:type!='PW-VE'" {
        tailf:xpath-root 3;
      }
      description
        "Configure the FIM configuration to the main interface.";
      leaf outer-vlan-enable {
        type enable-type;
        default "disable";
        description
          "Modify one tag ethernet type.";
      }
    }
  }
  augment "/ncs:devices/ncs:template/ncs:ned-id/ncs:config/ifm:ifm/ifm:interfaces/ifm:interface/ethernet:ethernet/ethernet:l2-sub-interface" {
    description
      "FIM configuration to the IFM module.";
    container fim-l2-sub {
      description
        "Configure the FIM configuration to L2 sub interface.";
      leaf egress-strict-filter {
        type ncs_template_enable-type;
        // NCS drop default statement
        description
          "Enable or disable strict filter on an EVC sub-interface.";
      }
    }
  }
  augment "/ncs:devices/ncs:device/ncs:live-status/ifm:ifm/ifm:interfaces/ifm:interface/ethernet:ethernet/ethernet:l2-sub-interface" {
    description
      "FIM configuration to the IFM module.";
    container fim-l2-sub {
      tailf:ncs-device-type "netconf";
      tailf:display-when "not(../../../../../../../ncs:module) or ../../../../../../../ncs:module[ncs:name='huawei-fim-ethernet'] or (../../../../../../../ncs:live-status-protocol[not(ncs:capability)]) or (../../../../../../../ncs:live-status-protocol/ncs:capability/ncs:module[.='huawei-fim-ethernet'])";
      description
        "Configure the FIM configuration to L2 sub interface.";
      leaf egress-strict-filter {
        type live_ncs_enable-type;
        // NCS drop default statement
        description
          "Enable or disable strict filter on an EVC sub-interface.";
      }
    }
  }
  augment "/ncs:devices/ncs:device/ncs:config/ifm:ifm/ifm:interfaces/ifm:interface/ethernet:ethernet/ethernet:l2-sub-interface" {
    description
      "FIM configuration to the IFM module.";
    container fim-l2-sub {
      tailf:ncs-device-type "netconf";
      tailf:display-when "not(../../../../../../../ncs:module) or ../../../../../../../ncs:module[ncs:name='huawei-fim-ethernet']";
      description
        "Configure the FIM configuration to L2 sub interface.";
      leaf egress-strict-filter {
        type enable-type;
        default "disable";
        description
          "Enable or disable strict filter on an EVC sub-interface.";
      }
    }
  }
}
