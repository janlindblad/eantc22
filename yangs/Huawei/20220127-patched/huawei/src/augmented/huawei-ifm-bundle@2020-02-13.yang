module huawei-ifm-bundle {
  // Generated by yanger -t ncs
  tailf:mount-id "huawei-nc-1.0:huawei-nc-1.0";
  tailf:ncs-device-type "netconf";

  namespace "urn:huawei:yang:huawei-ifm-bundle";
  prefix ifm-bundle;

  import huawei-ifm {
    prefix ifm;
  }
  import huawei-extension {
    prefix ext;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Define the interface that bundles multiple ATM sub-interfaces into a logical interface.";

  revision 2020-02-13 {
    description
      "Initial revision.";
    reference "Huawei private.";
  }
  ext:task-name "trunk";

  augment "/ncs:devices/ncs:template/ncs:ned-id/ncs:config/ifm:ifm/ifm:interfaces/ifm:interface" {
    // NCS drop when statement
    description
      "Active when the interface is set to type Atm-Bundle.";
    container bundle {
      description
        "Configure the interface that bundles multiple ATM sub-interfaces into a logical interface.";
      // NCS drop config false leaf 'up-member-num'
      container members {
        description
          "List of ATM-Bundle member interfaces.";
        list member {
          // NCS patched for predictable order
          ordered-by user;
          key "name";
          description
            "Configure ATM-Bundle member interfaces.";
          leaf name {
            type string;
            // NCS drop must statement
            description
              "Name of an ATM-Bundle member interface.";
          }
          // NCS drop config false leaf status
        }
      }
    }
  }
  augment "/ncs:devices/ncs:device/ncs:live-status/ifm:ifm/ifm:interfaces/ifm:interface" {
    // NCS drop when statement
    description
      "Active when the interface is set to type Atm-Bundle.";
    container bundle {
      tailf:ncs-device-type "netconf";
      tailf:display-when "not(../../../../../ncs:module) or ../../../../../ncs:module[ncs:name='huawei-ifm-bundle'] or (../../../../../ncs:live-status-protocol[not(ncs:capability)]) or (../../../../../ncs:live-status-protocol/ncs:capability/ncs:module[.='huawei-ifm-bundle'])";
      description
        "Configure the interface that bundles multiple ATM sub-interfaces into a logical interface.";
      leaf up-member-num {
        type uint32;
        description
          "Display the number of ATM-Bundle member interfaces in the Up state.";
      }
      container members {
        description
          "List of ATM-Bundle member interfaces.";
        list member {
          key "name";
          description
            "Configure ATM-Bundle member interfaces.";
          leaf name {
            type leafref {
              path "/ncs:devices/ncs:device/ncs:live-status/ifm:ifm/ifm:interfaces/ifm:interface/ifm:name" {
                tailf:xpath-root 3;
              }
            }
            // NCS drop must statement
            description
              "Name of an ATM-Bundle member interface.";
          }
          leaf status {
            type ifm:live_ncs_port-status;
            description
              "Display the status of an ATM-Bundle member interface.";
          }
        }
      }
    }
  }
  augment "/ncs:devices/ncs:device/ncs:config/ifm:ifm/ifm:interfaces/ifm:interface" {
    when "ifm:type='Atm-Bundle'" {
      tailf:xpath-root 3;
    }
    description
      "Active when the interface is set to type Atm-Bundle.";
    container bundle {
      tailf:ncs-device-type "netconf";
      tailf:display-when "not(../../../../../ncs:module) or ../../../../../ncs:module[ncs:name='huawei-ifm-bundle']";
      description
        "Configure the interface that bundles multiple ATM sub-interfaces into a logical interface.";
      // NCS drop config false leaf 'up-member-num'
      container members {
        description
          "List of ATM-Bundle member interfaces.";
        list member {
          key "name";
          description
            "Configure ATM-Bundle member interfaces.";
          leaf name {
            type leafref {
              path "/ncs:devices/ncs:device/ncs:config/ifm:ifm/ifm:interfaces/ifm:interface/ifm:name" {
                tailf:xpath-root 3;
              }
            }
            must "/ifm:ifm/ifm:interfaces/ifm:interface[ifm:name=current()]/ifm:class='sub-interface' and (/ifm:ifm/ifm:interfaces/ifm:interface[ifm:name=current()]/ifm:type='Serial' or /ifm:ifm/ifm:interfaces/ifm:interface[ifm:name=current()]/ifm:type='Ima-group')" {
              tailf:xpath-root 3;
            }
            description
              "Name of an ATM-Bundle member interface.";
          }
          // NCS drop config false leaf status
        }
      }
    }
  }
}
