module huawei-macm-notification {
  // Generated by yanger -t ncs
  tailf:mount-id "huawei-nc-1.0:huawei-nc-1.0";
  tailf:ncs-device-type "netconf";

  yang-version 1;
  namespace "urn:huawei:yang:huawei-macm-notification";
  prefix macm-notification;

  import huawei-extension {
    prefix ext;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Notification of macm-notification.";

  revision 2020-03-30 {
    description
      "The modifications in the schema file are synchronized to the YANG file.";
    reference "Huawei private.";
  }
  revision 2019-07-08 {
    description
      "Initial revision.";
    reference "Huawei private.";
  }
  ext:task-name "vstm";

  augment "/ncs:devices/ncs:device/ncs:notifications/ncs:received-notifications/ncs:notification/ncs:data" {
    container lr-mac-exceed-clear {
      presence "";
      config false;
      description
        "The number of MAC routes on the device fell below the maximum value.";
      leaf vstm-cur-mac-num {
        type uint32;
        description
          "Current MAC route number of the device.";
      }
      leaf vstm-max-mac-num {
        type uint32;
        description
          "Maximum number of MAC addresses.";
      }
    }
  }
  augment "/ncs:devices/ncs:device/ncs:notifications/ncs:received-notifications/ncs:notification/ncs:data" {
    container lr-mac-exceed {
      presence "";
      config false;
      description
        "The number of MAC routes on the device exceeded the maximum value.";
      leaf vstm-cur-mac-num {
        type uint32;
        description
          "Current MAC route number of the device.";
      }
      leaf vstm-max-mac-num {
        type uint32;
        description
          "Maximum number of MAC addresses.";
      }
    }
  }
  augment "/ncs:devices/ncs:device/ncs:netconf-notifications/ncs:received-notifications/ncs:notification/ncs:data" {
    container lr-mac-exceed-clear {
      presence "";
      config false;
      description
        "The number of MAC routes on the device fell below the maximum value.";
      leaf vstm-cur-mac-num {
        type uint32;
        description
          "Current MAC route number of the device.";
      }
      leaf vstm-max-mac-num {
        type uint32;
        description
          "Maximum number of MAC addresses.";
      }
    }
  }
  augment "/ncs:devices/ncs:device/ncs:netconf-notifications/ncs:received-notifications/ncs:notification/ncs:data" {
    container lr-mac-exceed {
      presence "";
      config false;
      description
        "The number of MAC routes on the device exceeded the maximum value.";
      leaf vstm-cur-mac-num {
        type uint32;
        description
          "Current MAC route number of the device.";
      }
      leaf vstm-max-mac-num {
        type uint32;
        description
          "Maximum number of MAC addresses.";
      }
    }
  }
}
