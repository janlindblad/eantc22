module huawei-bras-ipv6-address-manage {
  // Generated by yanger -t ncs
  tailf:mount-id "huawei-nc-1.0:huawei-nc-1.0";
  tailf:ncs-device-type "netconf";

  namespace "urn:huawei:yang:huawei-bras-ipv6-address-manage";
  prefix bras-ipv6-address-manage;

  import ietf-inet-types {
    prefix inet;
  }
  import huawei-extension {
    prefix ext;
  }
  import huawei-network-instance {
    prefix ni;
  }
  import huawei-l3vpn {
    prefix l3vpn;
  }
  import huawei-aaa {
    prefix aaa;
  }
  import huawei-bras-ipv4-address-manage {
    prefix bras-ipv4-address-manage;
  }
  import huawei-bras-cu-controller {
    prefix bras-cu-controller;
  }
  import huawei-bras-dhcpv6-server {
    prefix bras-dhcpv6-server;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "IPv6 address management.";

  revision 2020-02-22 {
    description
      "Description modification.";
    reference "Huawei private.";
  }
  revision 2019-10-17 {
    description
      "Second revision.";
    reference "Huawei private.";
  }
  revision 2019-05-08 {
    description
      "Initial revision.";
    reference "Huawei private.";
  }
  ext:task-name "ipv6pool";

  typedef ncs_template_reserved-type {
    type string;
    description
      "Reserve IPv6 address or IPv6 prefix type.";
  }

  typedef ncs_template_pool-type {
    type string;
    description
      "IPv6 pool type.";
  }

  typedef ncs_template_prefix-type {
    type string;
    description
      "IPv6 prefix type.";
  }

  typedef ncs_template_pool-usage-type {
    type string;
    description
      "Statistical granularity.";
  }

  typedef ncs_template_threshold-type {
    type string;
    description
      "Define the threshod limite type.";
  }

  typedef ncs_rpc_notif_reserved-type {
    type enumeration {
      enum "mac" {
        value 1;
        description
          "Reserves IPv6 address or IPv6 prefix by mac.";
      }
      enum "duid" {
        value 2;
        description
          "Reserves IPv6 address or IPv6 prefix by duid.";
      }
    }
    description
      "Reserve IPv6 address or IPv6 prefix type.";
  }

  typedef ncs_rpc_notif_pool-type {
    type enumeration {
      enum "local" {
        value 1;
        description
          "The type of local IPv6 address pool.";
      }
      enum "delegation" {
        value 2;
        description
          "The type of delegation IPv6 address pool.";
      }
      enum "remote" {
        value 3;
        description
          "The type of remote IPv6 address pool.";
      }
      enum "relay" {
        value 4;
        description
          "The type of relay IPv6 address pool.";
      }
    }
    description
      "IPv6 pool type.";
  }

  typedef ncs_rpc_notif_prefix-type {
    type enumeration {
      enum "local" {
        value 1;
        description
          "Local type.";
      }
      enum "delegation" {
        value 2;
        description
          "Delegation type.";
      }
      enum "remote" {
        value 3;
        description
          "Remote type.";
      }
      enum "dynamic" {
        value 4;
        description
          "Dynamic type.";
      }
    }
    description
      "IPv6 prefix type.";
  }

  typedef ncs_rpc_notif_pool-usage-type {
    type enumeration {
      enum "domain" {
        value 0;
        description
          "Domain-based statistics.";
      }
    }
    description
      "Statistical granularity.";
  }

  typedef ncs_rpc_notif_threshold-type {
    type enumeration {
      enum "all-threshold" {
        value 0;
        description
          "All threshold.";
      }
      enum "upper-threshold" {
        value 1;
        description
          "Upper threshold.";
      }
      enum "lower-threshold" {
        value 2;
        description
          "Lower threshold.";
      }
    }
    description
      "Define the threshod limite type.";
  }

  typedef live_ncs_reserved-type {
    type enumeration {
      enum "mac" {
        value 1;
        description
          "Reserves IPv6 address or IPv6 prefix by mac.";
      }
      enum "duid" {
        value 2;
        description
          "Reserves IPv6 address or IPv6 prefix by duid.";
      }
    }
    description
      "Reserve IPv6 address or IPv6 prefix type.";
  }

  typedef live_ncs_pool-type {
    type enumeration {
      enum "local" {
        value 1;
        description
          "The type of local IPv6 address pool.";
      }
      enum "delegation" {
        value 2;
        description
          "The type of delegation IPv6 address pool.";
      }
      enum "remote" {
        value 3;
        description
          "The type of remote IPv6 address pool.";
      }
      enum "relay" {
        value 4;
        description
          "The type of relay IPv6 address pool.";
      }
    }
    description
      "IPv6 pool type.";
  }

  typedef live_ncs_prefix-type {
    type enumeration {
      enum "local" {
        value 1;
        description
          "Local type.";
      }
      enum "delegation" {
        value 2;
        description
          "Delegation type.";
      }
      enum "remote" {
        value 3;
        description
          "Remote type.";
      }
      enum "dynamic" {
        value 4;
        description
          "Dynamic type.";
      }
    }
    description
      "IPv6 prefix type.";
  }

  typedef live_ncs_pool-usage-type {
    type enumeration {
      enum "domain" {
        value 0;
        description
          "Domain-based statistics.";
      }
    }
    description
      "Statistical granularity.";
  }

  typedef live_ncs_threshold-type {
    type enumeration {
      enum "all-threshold" {
        value 0;
        description
          "All threshold.";
      }
      enum "upper-threshold" {
        value 1;
        description
          "Upper threshold.";
      }
      enum "lower-threshold" {
        value 2;
        description
          "Lower threshold.";
      }
    }
    description
      "Define the threshod limite type.";
  }

  typedef reserved-type {
    type enumeration {
      enum "mac" {
        value 1;
        description
          "Reserves IPv6 address or IPv6 prefix by mac.";
      }
      enum "duid" {
        value 2;
        description
          "Reserves IPv6 address or IPv6 prefix by duid.";
      }
    }
    description
      "Reserve IPv6 address or IPv6 prefix type.";
  }

  typedef pool-type {
    type enumeration {
      enum "local" {
        value 1;
        description
          "The type of local IPv6 address pool.";
      }
      enum "delegation" {
        value 2;
        description
          "The type of delegation IPv6 address pool.";
      }
      enum "remote" {
        value 3;
        description
          "The type of remote IPv6 address pool.";
      }
      enum "relay" {
        value 4;
        description
          "The type of relay IPv6 address pool.";
      }
    }
    description
      "IPv6 pool type.";
  }

  typedef prefix-type {
    type enumeration {
      enum "local" {
        value 1;
        description
          "Local type.";
      }
      enum "delegation" {
        value 2;
        description
          "Delegation type.";
      }
      enum "remote" {
        value 3;
        description
          "Remote type.";
      }
      enum "dynamic" {
        value 4;
        description
          "Dynamic type.";
      }
    }
    description
      "IPv6 prefix type.";
  }

  typedef pool-usage-type {
    type enumeration {
      enum "domain" {
        value 0;
        description
          "Domain-based statistics.";
      }
    }
    description
      "Statistical granularity.";
  }

  typedef threshold-type {
    type enumeration {
      enum "all-threshold" {
        value 0;
        description
          "All threshold.";
      }
      enum "upper-threshold" {
        value 1;
        description
          "Upper threshold.";
      }
      enum "lower-threshold" {
        value 2;
        description
          "Lower threshold.";
      }
    }
    description
      "Define the threshod limite type.";
  }

  grouping ncs_template_specified-up {
    description
      "Configure an IPv6 prefix pool to be exclusively used by a vBRAS-UP or UP backup policy profile in CU separation multi-instance scenarios.";
    container occupied-policy {
      description
        "Configure a specific policy to specify the IPv6 prefix pool to be occupied.";
      choice occupied-policy {
        description
          "Select a specific policy to specify the IPv6 prefix pool to be occupied.";
        case up-id {
          description
            "The specified IPv6 prefix pool is exclusive to be used by vBRAS-UP UP ID.";
          leaf up-id {
            type string;
            // NCS drop must statement
            description
              "Specify the ID of a vBRAS-UP.";
          }
        }
        case up-backup-profile {
          description
            "The specified IPv6 prefix pool is exclusive to be used by vBRAS-UP backup policy profile.";
          leaf up-backup-profile {
            type string;
            // NCS drop must statement
            description
              "Specify the name of a vBRAS-UP backup policy profile.";
          }
        }
        case hot-standby-up-group {
          description
            "The specified IPv6 prefix pool is exclusive to be used by vBRAS-UP hot backup groups.";
          leaf master-up {
            type string;
            // NCS drop must statement
            // NCS drop must statement
            // NCS drop mandatory statement
            description
              "Specify the ID of the vBRAS-UP where the master interface in a vBRAS-UP hot backup group resides.";
          }
          leaf slave-up {
            type string;
            // NCS drop must statement
            // NCS drop mandatory statement
            description
              "Specify the ID of the vBRAS-UP where the slave interface in a vBRAS-UP hot backup group resides.";
          }
        }
      }
    }
  }

  grouping ncs_template_vpn-instance {
    description
      "Specify the VPN instance name of a IPv6 prefix pool.";
    container vpn-instance {
      description
        "Configure the VPN instance name of a IPv6 prefix pool.";
      leaf name {
        type string;
        // NCS drop must statement
        description
          "Specify the VPN instance name of a IPv6 prefix pool.";
      }
    }
  }

  grouping ncs_template_slaac-unshare-only {
    description
      "Configure the prefix pool to allocate IP addresses by using only the unshared-mode stateless address autoconfiguration (SLAAC) protocol.";
    container slaac-unshare-only {
      description
        "Configure the prefix pool to allocate IP addresses by using only the unshared-mode stateless address autoconfiguration (SLAAC) protocol.";
      leaf enable {
        type string;
        // NCS drop default statement
        description
          "Enable/disable the prefix pool to allocate IP addresses by using only the unshared-mode stateless address autoconfiguration (SLAAC) protocol.";
      }
    }
  }

  grouping ncs_template_pd-unshare-only {
    description
      "Configure the prefix pool to allocate IP addresses by using only the unshared-mode stateless address autoconfiguration (DHCPv6 IA_PD) protocol.";
    container pd-unshare-only {
      description
        "Configure the prefix pool to allocate IP addresses by using only the unshared-mode stateless address autoconfiguration (DHCPv6 IA_PD) protocol.";
      leaf enable {
        type string;
        // NCS drop default statement
        description
          "Enable/disable the prefix pool to allocate IP addresses by using only the unshared-mode stateless address autoconfiguration (DHCPv6 IA_PD) protocol.";
      }
    }
  }

  grouping ncs_template_dhcpv6-unshare-only {
    description
      "Configure an IPv6 prefix pool to assign only IPv6 addresses not prefixes to users.";
    leaf enable {
      type empty;
      description
        "Configure an IPv6 prefix pool to assign only IPv6 addresses not prefixes to users.";
    }
  }

  grouping ncs_template_lifetime-config {
    description
      "Configure the preferred lifetime anf valid lifetime of an IPv6 prefix.";
    container lifetime {
      // NCS drop must statement
      description
        "Configure the preferred lifetime anf valid lifetime of an IPv6 prefix.
         The valid lifetime should not be smaller than the preferred lifetime.";
      choice preferred-lifetime {
        // NCS drop default statement
        description
          "Configure the preferred lifetime.";
        case preferred-infinite {
          description
            "Specify the preferred lifetime of IPv6 prefix is infinite.";
          leaf preferred-infinite {
            type empty;
            description
              "Specify the preferred lifetime of IPv6 prefix is infinite.";
          }
        }
        case preferred-time {
          description
            "Configure the preferred lifetime that is not infinite.";
          leaf preferred-day {
            type string;
            units "d";
            // NCS drop must statement
            // NCS drop default statement
            description
              "Prefer day.";
          }
          leaf preferred-hour {
            type string;
            units "h";
            // NCS drop default statement
            description
              "Prefer hour.";
          }
          leaf preferred-minute {
            type string;
            units "min";
            // NCS drop default statement
            description
              "Prefer minute.";
          }
        }
      }
      choice valid-lifetime {
        // NCS drop default statement
        description
          "Configure the valid lifetime.";
        case valid-infinite {
          description
            "Configure the valid lifetime of IPv6 prefix is infinite.";
          leaf valid-infinite {
            type empty;
            description
              "Specify the valid lifetime of IPv6 prefix is infinite.";
          }
        }
        case valid-time {
          description
            "Configure the valid lifetime that is not infinite.";
          leaf valid-day {
            type string;
            units "d";
            // NCS drop must statement
            // NCS drop default statement
            description
              "Valid day.";
          }
          leaf valid-hour {
            type string;
            units "h";
            // NCS drop default statement
            description
              "Valid hour.";
          }
          leaf valid-minute {
            type string;
            units "min";
            // NCS drop default statement
            description
              "Valid minute.";
          }
        }
      }
    }
  }

  grouping ncs_template_rapid-commit-config {
    description
      "Configure the DHCPv6 server to support a rapid two-message exchange (solicit, reply).";
    container rapid-commit {
      description
        "Configure the DHCPv6 server to support a rapid two-message exchange (solicit, reply).";
      leaf enable {
        type string;
        // NCS drop default statement
        description
          "Enable/disable rapid commit.";
      }
    }
  }

  grouping ncs_template_remote-not-support {
    description
      "Configure the common information for IPv6 pool which is not remote type.";
    container dns-server {
      // NCS drop must statement
      description
        "Configure an IPv6 address for binding a DNS server to an IPv6 address pool.";
      leaf ipv6-address1 {
        type string;
        description
          "Specify the first IPv6 address of a DNS server.";
      }
      leaf ipv6-address2 {
        type string;
        description
          "Specify the second IPv6 address of a DNS server.";
      }
    }
    container dns-search-list {
      description
        "Configure a domain name suffix.";
      leaf name {
        type string;
        // NCS drop must statement
        description
          "Specify the domain name suffix.";
      }
    }
    container renew-rebind-time {
      // NCS drop must statement
      description
        "Configure the renewal time of an IPv6 address pool. renew-time-percent is the percentage of the renewal time to the preferred lifetime.";
      leaf renew-time-percent {
        type string;
        units "%";
        // NCS drop default statement
        description
          "Set the renewal time and rebinding time of an IPv6 address pool.";
      }
      leaf rebind-time-percent {
        type string;
        units "%";
        // NCS drop default statement
        description
          "Specify the rebinding time of an IPv6 address pool. rebind-time-percent is the percentage of the rebinding time to the preferred lifetime.";
      }
    }
  }

  grouping ncs_template_lock {
    description
      "Lock an IPv6 prefix pool.";
    container lock {
      description
        "Configure a locked IPv6 prefix pool.";
      leaf enable {
        type empty;
        description
          "Lock an IPv6 prefix pool.";
      }
    }
  }

  grouping ncs_template_reserved-ipv6 {
    description
      "Configure a reservation type for the prefix pool.";
    container reserved-ipv6 {
      description
        "Configure a reservation type for the prefix pool.";
      leaf reserved-type {
        type ncs_template_reserved-type;
        description
          "Reservation type for the IPv6 prefix or address, after the reserved type of an IPv6 prefix or address is set to mac, one-to-many mapping between one MAC address and multiple sessions cannot be enabled.";
      }
      leaf lease {
        // NCS drop when statement
        type empty;
        description
          "Reserve the IPv6 prefixes or address during a lease.";
      }
    }
  }

  grouping ncs_template_frame-ipv6-lease {
    description
      "Configure lease for an IPv6 prefix pool.";
    container frame-ipv6-lease {
      description
        "Configure manage the leases of RADIUS-delivered IPv6 addresses that are in the supported address pools.";
      leaf enable {
        type string;
        // NCS drop default statement
        description
          "Enable/disable manage the leases of RADIUS-delivered IPv6 addresses that are in the supported address pools.";
      }
    }
  }

  grouping ncs_template_exclude-ipv6-address {
    description
      "List of specified IPv6 addresses to prevent it from being allocated to users. The start IPv6 address must be smaller than or equal to the end IPv6 address.";
    list exclude-ipv6-address {
      // NCS patched for predictable order
      ordered-by user;
      key "start-ipv6-address end-ipv6-address";
      description
        "Configure a specified IPv6 address to prevent it from being allocated to users. The start IPv6 address must be smaller than or equal to the end IPv6 address.";
      leaf start-ipv6-address {
        type string;
        description
          "Specify the start IPv6 address.";
      }
      leaf end-ipv6-address {
        type string;
        description
          "Specify the end IPv6 address.";
      }
    }
  }

  grouping ncs_template_ipv6-constant-index {
    description
      "Configure a constant index for an IPv6 address or prefix pool.";
    // NCS drop config false container 'constant-index'
  }

  grouping ncs_template_ipv6-pool-comm {
    description
      "Set the preference value of an IPv6 address pool.";
    container preference {
      description
        "Configure the preference value of an IPv6 address pool.";
      leaf value {
        type string;
        // NCS drop default statement
        description
          "Specify the preference value of an IPv6 address pool.";
      }
    }
    container lock {
      presence "Create lock pool";
      description
        "Enable/disable an IPv6 address pool.";
      leaf drain {
        type string;
        // NCS drop default statement
        description
          "Enable/disable an IPv6 address pool. If it is disable, the address pool cannot be used to assign IPv6 addresses to new users and DHCP renew or rebind.";
      }
    }
    container wait-request-time {
      description
        "Configure the timeout period for a router to wait for a request message from a client in response to an advertise message sent to the client.";
      leaf value {
        type string;
        units "s";
        description
          "Specify the timeout period for a router to wait for a request message from a client.";
      }
    }
    container warning {
      description
        "Configure warning of IPv6 address usage.";
      leaf threshold-value {
        type string;
        // NCS drop default statement
        description
          "The alarm threshold for the address usage of an IPv6 address pool is a percentage.";
      }
      leaf exhaust {
        type empty;
        description
          "Enable the address exhaustion alarm function for an IPv6 address pool.";
      }
    }
    container unr-tag {
      description
        "Configure a route tag for an IPv6 address pool.";
      leaf value {
        type string;
        description
          "Specify the route tag for the IPv6 address pool.";
      }
    }
  }

  grouping ncs_template_weight {
    description
      "Configure a weight for an IPv6 address pool.";
    leaf value {
      type string;
      // NCS drop default statement
      description
        "Specify a weight for an IPv6 address pool.";
    }
  }

  grouping ncs_template_aftr-config {
    description
      "Configure an Address Family Transition Router (AFTR) name.";
    container aftr {
      description
        "Configure an Address Family Transition Router (AFTR) name.";
      leaf name {
        type string;
        // NCS drop must statement
        description
          "Specify an AFTR name.";
      }
    }
  }

  grouping ncs_template_export-host-route {
    description
      "Enable a device to advertise host routes in a remote address pool.";
    container export-host-route {
      description
        "Configure a device to advertise host routes in a remote address pool.";
      leaf ipv6-address {
        type empty;
        description
          "Advertise IPv6 routes.";
      }
      leaf pd-prefix {
        type empty;
        description
          "Advertise PD routes.";
      }
      leaf nd-prefix {
        type empty;
        description
          "Advertise ND routes.";
      }
    }
  }

  grouping ncs_template_pool-usage {
    description
      "Display IPv6 address pool usage.";
    leaf address-total-number {
      type string;
      description
        "Total number of IPv6 address.";
    }
    leaf address-used-number {
      type string;
      description
        "Used number of IPv6 address.";
    }
    leaf address-used-radio {
      type string;
      description
        "IPv6 address usage (in percentage).";
    }
    leaf ndra-total-number {
      type string;
      description
        "Total number of in-use unshare NDRA prefixs.";
    }
    leaf ndra-used-number {
      type string;
      description
        "Used number of in-use unshare NDRA prefixs.";
    }
    leaf ndra-used-radio {
      type string;
      description
        "Usage (in percentage) of unshared NDRA prefixes.";
    }
    leaf delegation-total-number {
      type string;
      description
        "Total number of delegation prefixs.";
    }
    leaf delegation-used-number {
      type string;
      description
        "Used number of delegation prefixs.";
    }
    leaf delegation-used-radio {
      type string;
      description
        "Usage (in percentage) of delegation prefixes.";
    }
  }

  grouping ncs_template_pool-statistics {
    description
      "Statistics of IPv6 pool.";
    leaf address-idle-total-number {
      type string;
      description
        "Number of idle IPv6 addresses on the equipment.";
    }
    leaf address-used-total-number {
      type string;
      description
        "Number of IPv6 addresses in use on the equipment.";
    }
    leaf prefix-idle-total-number {
      type string;
      description
        "Number of idle IPv6 prefixes on the equipment.";
    }
    leaf prefix-used-total-number {
      type string;
      description
        "Number of IPv6 prefixes in use on the equipment.";
    }
    leaf address-total-number {
      type string;
      description
        "The total IPv6 address number.";
    }
    leaf address-used-number {
      type string;
      description
        "The used IPv6 address number.";
    }
    leaf address-idle-number {
      type string;
      description
        "The free IPv6 address number.";
    }
    leaf address-conflict-number {
      type string;
      description
        "The conflict IPv6 address number.";
    }
    leaf address-excluded-number {
      type string;
      description
        "The excluded IPv6 address number.";
    }
    leaf address-used-percent {
      type string;
      description
        "The percent of used IPv6 address.";
    }
    leaf ndra-total-number {
      type string;
      description
        "The total NDRA prefix number.";
    }
    leaf ndra-used-number {
      type string;
      description
        "The used NDRA prefix number.";
    }
    leaf ndra-free-number {
      type string;
      description
        "The free NDRA prefix number.";
    }
    leaf ndra-conflict-number {
      type string;
      description
        "The conflict NDRA prefix number.";
    }
    leaf ndra-excluded-number {
      type string;
      description
        "The excluded NDRA prefix number.";
    }
    leaf ndra-used-percent {
      type string;
      description
        "The percent of used IPv6 NDRA prefix.";
    }
    leaf pd-total-number {
      type string;
      description
        "The total PD prefix number.";
    }
    leaf pd-used-number {
      type string;
      description
        "The used PD prefix number.";
    }
    leaf pd-free-number {
      type string;
      description
        "The free PD prefix number.";
    }
    leaf pd-conflict-number {
      type string;
      description
        "The conflict PD prefix number.";
    }
    leaf pd-excluded-number {
      type string;
      description
        "The excluded PD prefix number.";
    }
    leaf pd-used-percent {
      type string;
      description
        "The percent of used IPv6 PD prefix.";
    }
  }

  grouping ncs_rpc_notif_specified-up {
    description
      "Configure an IPv6 prefix pool to be exclusively used by a vBRAS-UP or UP backup policy profile in CU separation multi-instance scenarios.";
    container occupied-policy {
      description
        "Configure a specific policy to specify the IPv6 prefix pool to be occupied.";
      choice occupied-policy {
        description
          "Select a specific policy to specify the IPv6 prefix pool to be occupied.";
        case up-id {
          description
            "The specified IPv6 prefix pool is exclusive to be used by vBRAS-UP UP ID.";
          leaf up-id {
            type uint16 {
              range "1024..2023 | 2048..3047 | 3072..4071 | 4096..5095";
            }
            must '(../up-id<=(/bras-cu-controller:bras-cu-controller/bras-cu-controller:global-attribute/bras-cu-controller:up-base-id + 999) and ../up-id>=/bras-cu-controller:bras-cu-controller/bras-cu-controller:global-attribute/bras-cu-controller:up-base-id)' {
              tailf:xpath-root 3;
            }
            description
              "Specify the ID of a vBRAS-UP.";
          }
        }
        case up-backup-profile {
          description
            "The specified IPv6 prefix pool is exclusive to be used by vBRAS-UP backup policy profile.";
          leaf up-backup-profile {
            type string;
            must '/bras-cu-controller:bras-cu-controller/bras-cu-controller:hot-profiles/bras-cu-controller:hot-profile[bras-cu-controller:name=current()]/bras-cu-controller:backup-groups/bras-cu-controller:backup-group/bras-cu-controller:master-interface' {
              tailf:xpath-root 3;
            }
            description
              "Specify the name of a vBRAS-UP backup policy profile.";
          }
        }
        case hot-standby-up-group {
          description
            "The specified IPv6 prefix pool is exclusive to be used by vBRAS-UP hot backup groups.";
          leaf master-up {
            type uint16 {
              range "1024..2023 | 2048..3047 | 3072..4071 | 4096..5095";
            }
            must '../master-up!=../slave-up' {
              tailf:xpath-root 3;
            }
            must '(../master-up<=(/bras-cu-controller:bras-cu-controller/bras-cu-controller:global-attribute/bras-cu-controller:up-base-id + 999) and ../master-up>=/bras-cu-controller:bras-cu-controller/bras-cu-controller:global-attribute/bras-cu-controller:up-base-id)' {
              tailf:xpath-root 3;
            }
            mandatory true;
            description
              "Specify the ID of the vBRAS-UP where the master interface in a vBRAS-UP hot backup group resides.";
          }
          leaf slave-up {
            type uint16 {
              range "1024..2023 | 2048..3047 | 3072..4071 | 4096..5095";
            }
            must '(../slave-up<=(/bras-cu-controller:bras-cu-controller/bras-cu-controller:global-attribute/bras-cu-controller:up-base-id + 999) and ../slave-up>=/bras-cu-controller:bras-cu-controller/bras-cu-controller:global-attribute/bras-cu-controller:up-base-id)' {
              tailf:xpath-root 3;
            }
            mandatory true;
            description
              "Specify the ID of the vBRAS-UP where the slave interface in a vBRAS-UP hot backup group resides.";
          }
        }
      }
    }
  }

  grouping ncs_rpc_notif_vpn-instance {
    description
      "Specify the VPN instance name of a IPv6 prefix pool.";
    container vpn-instance {
      description
        "Configure the VPN instance name of a IPv6 prefix pool.";
      leaf name {
        type string;
        must "/ni:network-instance/ni:instances/ni:instance[ni:name=current()]/l3vpn:afs/l3vpn:af[l3vpn:type='ipv6-unicast'] and ../name != '_public_'" {
          tailf:xpath-root 3;
        }
        description
          "Specify the VPN instance name of a IPv6 prefix pool.";
      }
    }
  }

  grouping ncs_rpc_notif_slaac-unshare-only {
    description
      "Configure the prefix pool to allocate IP addresses by using only the unshared-mode stateless address autoconfiguration (SLAAC) protocol.";
    container slaac-unshare-only {
      description
        "Configure the prefix pool to allocate IP addresses by using only the unshared-mode stateless address autoconfiguration (SLAAC) protocol.";
      leaf enable {
        type boolean;
        default "false";
        description
          "Enable/disable the prefix pool to allocate IP addresses by using only the unshared-mode stateless address autoconfiguration (SLAAC) protocol.";
      }
    }
  }

  grouping ncs_rpc_notif_pd-unshare-only {
    description
      "Configure the prefix pool to allocate IP addresses by using only the unshared-mode stateless address autoconfiguration (DHCPv6 IA_PD) protocol.";
    container pd-unshare-only {
      description
        "Configure the prefix pool to allocate IP addresses by using only the unshared-mode stateless address autoconfiguration (DHCPv6 IA_PD) protocol.";
      leaf enable {
        type boolean;
        default "false";
        description
          "Enable/disable the prefix pool to allocate IP addresses by using only the unshared-mode stateless address autoconfiguration (DHCPv6 IA_PD) protocol.";
      }
    }
  }

  grouping ncs_rpc_notif_dhcpv6-unshare-only {
    description
      "Configure an IPv6 prefix pool to assign only IPv6 addresses not prefixes to users.";
    leaf enable {
      type empty;
      description
        "Configure an IPv6 prefix pool to assign only IPv6 addresses not prefixes to users.";
    }
  }

  grouping ncs_rpc_notif_lifetime-config {
    description
      "Configure the preferred lifetime anf valid lifetime of an IPv6 prefix.";
    container lifetime {
      must 'not(./preferred-infinite) or ./valid-infinite' {
        tailf:xpath-root 3;
      }
      description
        "Configure the preferred lifetime anf valid lifetime of an IPv6 prefix.
         The valid lifetime should not be smaller than the preferred lifetime.";
      choice preferred-lifetime {
        default "preferred-time";
        description
          "Configure the preferred lifetime.";
        case preferred-infinite {
          description
            "Specify the preferred lifetime of IPv6 prefix is infinite.";
          leaf preferred-infinite {
            type empty;
            description
              "Specify the preferred lifetime of IPv6 prefix is infinite.";
          }
        }
        case preferred-time {
          description
            "Configure the preferred lifetime that is not infinite.";
          leaf preferred-day {
            type uint16 {
              range "0..999";
            }
            units "d";
            must '../preferred-day != 0 or ../preferred-hour != 0 or ../preferred-minute != 0' {
              tailf:xpath-root 3;
            }
            default "2";
            description
              "Prefer day.";
          }
          leaf preferred-hour {
            type uint8 {
              range "0..23";
            }
            units "h";
            default "0";
            description
              "Prefer hour.";
          }
          leaf preferred-minute {
            type uint8 {
              range "0..59";
            }
            units "min";
            default "0";
            description
              "Prefer minute.";
          }
        }
      }
      choice valid-lifetime {
        default "valid-time";
        description
          "Configure the valid lifetime.";
        case valid-infinite {
          description
            "Configure the valid lifetime of IPv6 prefix is infinite.";
          leaf valid-infinite {
            type empty;
            description
              "Specify the valid lifetime of IPv6 prefix is infinite.";
          }
        }
        case valid-time {
          description
            "Configure the valid lifetime that is not infinite.";
          leaf valid-day {
            type uint16 {
              range "0..999";
            }
            units "d";
            must '../valid-day != 0 or ../valid-hour != 0 or ../valid-minute != 0' {
              tailf:xpath-root 3;
            }
            default "3";
            description
              "Valid day.";
          }
          leaf valid-hour {
            type uint8 {
              range "0..23";
            }
            units "h";
            default "0";
            description
              "Valid hour.";
          }
          leaf valid-minute {
            type uint8 {
              range "0..59";
            }
            units "min";
            default "0";
            description
              "Valid minute.";
          }
        }
      }
    }
  }

  grouping ncs_rpc_notif_rapid-commit-config {
    description
      "Configure the DHCPv6 server to support a rapid two-message exchange (solicit, reply).";
    container rapid-commit {
      description
        "Configure the DHCPv6 server to support a rapid two-message exchange (solicit, reply).";
      leaf enable {
        type boolean;
        default "false";
        description
          "Enable/disable rapid commit.";
      }
    }
  }

  grouping ncs_rpc_notif_remote-not-support {
    description
      "Configure the common information for IPv6 pool which is not remote type.";
    container dns-server {
      must 'not(./ipv6-address1) or not(./ipv6-address2) or ./ipv6-address1!=./ipv6-address2' {
        tailf:xpath-root 3;
      }
      description
        "Configure an IPv6 address for binding a DNS server to an IPv6 address pool.";
      leaf ipv6-address1 {
        type inet:ipv6-address-no-zone;
        description
          "Specify the first IPv6 address of a DNS server.";
      }
      leaf ipv6-address2 {
        type inet:ipv6-address-no-zone;
        description
          "Specify the second IPv6 address of a DNS server.";
      }
    }
    container dns-search-list {
      description
        "Configure a domain name suffix.";
      leaf name {
        type string {
          length "1..32";
          pattern '[a-zA-Z0-9._-]{1,32}';
        }
        must "../name != '-' and ../name != '--'" {
          tailf:xpath-root 3;
        }
        description
          "Specify the domain name suffix.";
      }
    }
    container renew-rebind-time {
      must './rebind-time-percent >= ./renew-time-percent + 10' {
        tailf:xpath-root 3;
      }
      description
        "Configure the renewal time of an IPv6 address pool. renew-time-percent is the percentage of the renewal time to the preferred lifetime.";
      leaf renew-time-percent {
        type uint8 {
          range "10..99";
        }
        units "%";
        default "50";
        description
          "Set the renewal time and rebinding time of an IPv6 address pool.";
      }
      leaf rebind-time-percent {
        type uint8 {
          range "10..99";
        }
        units "%";
        default "80";
        description
          "Specify the rebinding time of an IPv6 address pool. rebind-time-percent is the percentage of the rebinding time to the preferred lifetime.";
      }
    }
  }

  grouping ncs_rpc_notif_lock {
    description
      "Lock an IPv6 prefix pool.";
    container lock {
      description
        "Configure a locked IPv6 prefix pool.";
      leaf enable {
        type empty;
        description
          "Lock an IPv6 prefix pool.";
      }
    }
  }

  grouping ncs_rpc_notif_reserved-ipv6 {
    description
      "Configure a reservation type for the prefix pool.";
    container reserved-ipv6 {
      description
        "Configure a reservation type for the prefix pool.";
      leaf reserved-type {
        type ncs_rpc_notif_reserved-type;
        description
          "Reservation type for the IPv6 prefix or address, after the reserved type of an IPv6 prefix or address is set to mac, one-to-many mapping between one MAC address and multiple sessions cannot be enabled.";
      }
      leaf lease {
        when '../reserved-type' {
          tailf:xpath-root 3;
        }
        type empty;
        description
          "Reserve the IPv6 prefixes or address during a lease.";
      }
    }
  }

  grouping ncs_rpc_notif_frame-ipv6-lease {
    description
      "Configure lease for an IPv6 prefix pool.";
    container frame-ipv6-lease {
      description
        "Configure manage the leases of RADIUS-delivered IPv6 addresses that are in the supported address pools.";
      leaf enable {
        type boolean;
        default "false";
        description
          "Enable/disable manage the leases of RADIUS-delivered IPv6 addresses that are in the supported address pools.";
      }
    }
  }

  grouping ncs_rpc_notif_exclude-ipv6-address {
    description
      "List of specified IPv6 addresses to prevent it from being allocated to users. The start IPv6 address must be smaller than or equal to the end IPv6 address.";
    list exclude-ipv6-address {
      key "start-ipv6-address end-ipv6-address";
      description
        "Configure a specified IPv6 address to prevent it from being allocated to users. The start IPv6 address must be smaller than or equal to the end IPv6 address.";
      leaf start-ipv6-address {
        type inet:ipv6-address-no-zone;
        description
          "Specify the start IPv6 address.";
      }
      leaf end-ipv6-address {
        type inet:ipv6-address-no-zone;
        description
          "Specify the end IPv6 address.";
      }
    }
  }

  grouping ncs_rpc_notif_ipv6-constant-index {
    description
      "Configure a constant index for an IPv6 address or prefix pool.";
    container constant-index {
      config false;
      description
        "Statistics of a constant index for an IPv6 address or prefix pool.";
      leaf value {
        type uint16 {
          range "0..16383";
        }
        description
          "Specify an index for an IPv6 address or prefix pool.";
      }
    }
  }

  grouping ncs_rpc_notif_ipv6-pool-comm {
    description
      "Set the preference value of an IPv6 address pool.";
    container preference {
      description
        "Configure the preference value of an IPv6 address pool.";
      leaf value {
        type uint8 {
          range "0..255";
        }
        default "255";
        description
          "Specify the preference value of an IPv6 address pool.";
      }
    }
    container lock {
      presence "Create lock pool";
      description
        "Enable/disable an IPv6 address pool.";
      leaf drain {
        type boolean;
        default "false";
        description
          "Enable/disable an IPv6 address pool. If it is disable, the address pool cannot be used to assign IPv6 addresses to new users and DHCP renew or rebind.";
      }
    }
    container wait-request-time {
      description
        "Configure the timeout period for a router to wait for a request message from a client in response to an advertise message sent to the client.";
      leaf value {
        type uint8 {
          range "5..60";
        }
        units "s";
        description
          "Specify the timeout period for a router to wait for a request message from a client.";
      }
    }
    container warning {
      description
        "Configure warning of IPv6 address usage.";
      leaf threshold-value {
        type uint8 {
          range "0..100";
        }
        default "80";
        description
          "The alarm threshold for the address usage of an IPv6 address pool is a percentage.";
      }
      leaf exhaust {
        type empty;
        description
          "Enable the address exhaustion alarm function for an IPv6 address pool.";
      }
    }
    container unr-tag {
      description
        "Configure a route tag for an IPv6 address pool.";
      leaf value {
        type uint32 {
          range "0..4294967295";
        }
        description
          "Specify the route tag for the IPv6 address pool.";
      }
    }
  }

  grouping ncs_rpc_notif_weight {
    description
      "Configure a weight for an IPv6 address pool.";
    leaf value {
      type uint8 {
        range "0..100";
      }
      default "5";
      description
        "Specify a weight for an IPv6 address pool.";
    }
  }

  grouping ncs_rpc_notif_aftr-config {
    description
      "Configure an Address Family Transition Router (AFTR) name.";
    container aftr {
      description
        "Configure an Address Family Transition Router (AFTR) name.";
      leaf name {
        type string {
          length "1..63";
          pattern '[a-zA-Z0-9._-]{1,63}';
        }
        must "../name != '-' and ../name != '--'" {
          tailf:xpath-root 3;
        }
        description
          "Specify an AFTR name.";
      }
    }
  }

  grouping ncs_rpc_notif_export-host-route {
    description
      "Enable a device to advertise host routes in a remote address pool.";
    container export-host-route {
      description
        "Configure a device to advertise host routes in a remote address pool.";
      leaf ipv6-address {
        type empty;
        description
          "Advertise IPv6 routes.";
      }
      leaf pd-prefix {
        type empty;
        description
          "Advertise PD routes.";
      }
      leaf nd-prefix {
        type empty;
        description
          "Advertise ND routes.";
      }
    }
  }

  grouping ncs_rpc_notif_pool-usage {
    description
      "Display IPv6 address pool usage.";
    leaf address-total-number {
      type uint32;
      description
        "Total number of IPv6 address.";
    }
    leaf address-used-number {
      type uint32;
      description
        "Used number of IPv6 address.";
    }
    leaf address-used-radio {
      type uint32;
      description
        "IPv6 address usage (in percentage).";
    }
    leaf ndra-total-number {
      type uint32;
      description
        "Total number of in-use unshare NDRA prefixs.";
    }
    leaf ndra-used-number {
      type uint32;
      description
        "Used number of in-use unshare NDRA prefixs.";
    }
    leaf ndra-used-radio {
      type uint32;
      description
        "Usage (in percentage) of unshared NDRA prefixes.";
    }
    leaf delegation-total-number {
      type uint32;
      description
        "Total number of delegation prefixs.";
    }
    leaf delegation-used-number {
      type uint32;
      description
        "Used number of delegation prefixs.";
    }
    leaf delegation-used-radio {
      type uint32;
      description
        "Usage (in percentage) of delegation prefixes.";
    }
  }

  grouping ncs_rpc_notif_pool-statistics {
    description
      "Statistics of IPv6 pool.";
    leaf address-idle-total-number {
      type int32;
      description
        "Number of idle IPv6 addresses on the equipment.";
    }
    leaf address-used-total-number {
      type int32;
      description
        "Number of IPv6 addresses in use on the equipment.";
    }
    leaf prefix-idle-total-number {
      type int32;
      description
        "Number of idle IPv6 prefixes on the equipment.";
    }
    leaf prefix-used-total-number {
      type int32;
      description
        "Number of IPv6 prefixes in use on the equipment.";
    }
    leaf address-total-number {
      type int32;
      description
        "The total IPv6 address number.";
    }
    leaf address-used-number {
      type int32;
      description
        "The used IPv6 address number.";
    }
    leaf address-idle-number {
      type int32;
      description
        "The free IPv6 address number.";
    }
    leaf address-conflict-number {
      type int32;
      description
        "The conflict IPv6 address number.";
    }
    leaf address-excluded-number {
      type int32;
      description
        "The excluded IPv6 address number.";
    }
    leaf address-used-percent {
      type int32;
      description
        "The percent of used IPv6 address.";
    }
    leaf ndra-total-number {
      type int32;
      description
        "The total NDRA prefix number.";
    }
    leaf ndra-used-number {
      type int32;
      description
        "The used NDRA prefix number.";
    }
    leaf ndra-free-number {
      type int32;
      description
        "The free NDRA prefix number.";
    }
    leaf ndra-conflict-number {
      type int32;
      description
        "The conflict NDRA prefix number.";
    }
    leaf ndra-excluded-number {
      type int32;
      description
        "The excluded NDRA prefix number.";
    }
    leaf ndra-used-percent {
      type int32;
      description
        "The percent of used IPv6 NDRA prefix.";
    }
    leaf pd-total-number {
      type int32;
      description
        "The total PD prefix number.";
    }
    leaf pd-used-number {
      type int32;
      description
        "The used PD prefix number.";
    }
    leaf pd-free-number {
      type int32;
      description
        "The free PD prefix number.";
    }
    leaf pd-conflict-number {
      type int32;
      description
        "The conflict PD prefix number.";
    }
    leaf pd-excluded-number {
      type int32;
      description
        "The excluded PD prefix number.";
    }
    leaf pd-used-percent {
      type int32;
      description
        "The percent of used IPv6 PD prefix.";
    }
  }

  grouping live_ncs_specified-up {
    description
      "Configure an IPv6 prefix pool to be exclusively used by a vBRAS-UP or UP backup policy profile in CU separation multi-instance scenarios.";
    container occupied-policy {
      description
        "Configure a specific policy to specify the IPv6 prefix pool to be occupied.";
      choice occupied-policy {
        description
          "Select a specific policy to specify the IPv6 prefix pool to be occupied.";
        case up-id {
          description
            "The specified IPv6 prefix pool is exclusive to be used by vBRAS-UP UP ID.";
          leaf up-id {
            type uint16 {
              range "1024..2023 | 2048..3047 | 3072..4071 | 4096..5095";
            }
            // NCS drop must statement
            description
              "Specify the ID of a vBRAS-UP.";
          }
        }
        case up-backup-profile {
          description
            "The specified IPv6 prefix pool is exclusive to be used by vBRAS-UP backup policy profile.";
          leaf up-backup-profile {
            type leafref {
              path "/ncs:devices/ncs:device/ncs:live-status/bras-cu-controller:bras-cu-controller/bras-cu-controller:hot-profiles/bras-cu-controller:hot-profile/bras-cu-controller:name" {
                tailf:xpath-root 3;
              }
            }
            // NCS drop must statement
            description
              "Specify the name of a vBRAS-UP backup policy profile.";
          }
        }
        case hot-standby-up-group {
          description
            "The specified IPv6 prefix pool is exclusive to be used by vBRAS-UP hot backup groups.";
          leaf master-up {
            type uint16 {
              range "1024..2023 | 2048..3047 | 3072..4071 | 4096..5095";
            }
            // NCS drop must statement
            // NCS drop must statement
            // NCS drop mandatory statement
            description
              "Specify the ID of the vBRAS-UP where the master interface in a vBRAS-UP hot backup group resides.";
          }
          leaf slave-up {
            type uint16 {
              range "1024..2023 | 2048..3047 | 3072..4071 | 4096..5095";
            }
            // NCS drop must statement
            // NCS drop mandatory statement
            description
              "Specify the ID of the vBRAS-UP where the slave interface in a vBRAS-UP hot backup group resides.";
          }
        }
      }
    }
  }

  grouping live_ncs_vpn-instance {
    description
      "Specify the VPN instance name of a IPv6 prefix pool.";
    container vpn-instance {
      description
        "Configure the VPN instance name of a IPv6 prefix pool.";
      leaf name {
        type leafref {
          path "/ncs:devices/ncs:device/ncs:live-status/ni:network-instance/ni:instances/ni:instance/ni:name" {
            tailf:xpath-root 3;
          }
        }
        // NCS drop must statement
        description
          "Specify the VPN instance name of a IPv6 prefix pool.";
      }
    }
  }

  grouping live_ncs_slaac-unshare-only {
    description
      "Configure the prefix pool to allocate IP addresses by using only the unshared-mode stateless address autoconfiguration (SLAAC) protocol.";
    container slaac-unshare-only {
      description
        "Configure the prefix pool to allocate IP addresses by using only the unshared-mode stateless address autoconfiguration (SLAAC) protocol.";
      leaf enable {
        type boolean;
        // NCS drop default statement
        description
          "Enable/disable the prefix pool to allocate IP addresses by using only the unshared-mode stateless address autoconfiguration (SLAAC) protocol.";
      }
    }
  }

  grouping live_ncs_pd-unshare-only {
    description
      "Configure the prefix pool to allocate IP addresses by using only the unshared-mode stateless address autoconfiguration (DHCPv6 IA_PD) protocol.";
    container pd-unshare-only {
      description
        "Configure the prefix pool to allocate IP addresses by using only the unshared-mode stateless address autoconfiguration (DHCPv6 IA_PD) protocol.";
      leaf enable {
        type boolean;
        // NCS drop default statement
        description
          "Enable/disable the prefix pool to allocate IP addresses by using only the unshared-mode stateless address autoconfiguration (DHCPv6 IA_PD) protocol.";
      }
    }
  }

  grouping live_ncs_dhcpv6-unshare-only {
    description
      "Configure an IPv6 prefix pool to assign only IPv6 addresses not prefixes to users.";
    leaf enable {
      type empty;
      description
        "Configure an IPv6 prefix pool to assign only IPv6 addresses not prefixes to users.";
    }
  }

  grouping live_ncs_lifetime-config {
    description
      "Configure the preferred lifetime anf valid lifetime of an IPv6 prefix.";
    container lifetime {
      // NCS drop must statement
      description
        "Configure the preferred lifetime anf valid lifetime of an IPv6 prefix.
         The valid lifetime should not be smaller than the preferred lifetime.";
      choice preferred-lifetime {
        // NCS drop default statement
        description
          "Configure the preferred lifetime.";
        case preferred-infinite {
          description
            "Specify the preferred lifetime of IPv6 prefix is infinite.";
          leaf preferred-infinite {
            type empty;
            description
              "Specify the preferred lifetime of IPv6 prefix is infinite.";
          }
        }
        case preferred-time {
          description
            "Configure the preferred lifetime that is not infinite.";
          leaf preferred-day {
            type uint16 {
              range "0..999";
            }
            units "d";
            // NCS drop must statement
            // NCS drop default statement
            description
              "Prefer day.";
          }
          leaf preferred-hour {
            type uint8 {
              range "0..23";
            }
            units "h";
            // NCS drop default statement
            description
              "Prefer hour.";
          }
          leaf preferred-minute {
            type uint8 {
              range "0..59";
            }
            units "min";
            // NCS drop default statement
            description
              "Prefer minute.";
          }
        }
      }
      choice valid-lifetime {
        // NCS drop default statement
        description
          "Configure the valid lifetime.";
        case valid-infinite {
          description
            "Configure the valid lifetime of IPv6 prefix is infinite.";
          leaf valid-infinite {
            type empty;
            description
              "Specify the valid lifetime of IPv6 prefix is infinite.";
          }
        }
        case valid-time {
          description
            "Configure the valid lifetime that is not infinite.";
          leaf valid-day {
            type uint16 {
              range "0..999";
            }
            units "d";
            // NCS drop must statement
            // NCS drop default statement
            description
              "Valid day.";
          }
          leaf valid-hour {
            type uint8 {
              range "0..23";
            }
            units "h";
            // NCS drop default statement
            description
              "Valid hour.";
          }
          leaf valid-minute {
            type uint8 {
              range "0..59";
            }
            units "min";
            // NCS drop default statement
            description
              "Valid minute.";
          }
        }
      }
    }
  }

  grouping live_ncs_rapid-commit-config {
    description
      "Configure the DHCPv6 server to support a rapid two-message exchange (solicit, reply).";
    container rapid-commit {
      description
        "Configure the DHCPv6 server to support a rapid two-message exchange (solicit, reply).";
      leaf enable {
        type boolean;
        // NCS drop default statement
        description
          "Enable/disable rapid commit.";
      }
    }
  }

  grouping live_ncs_remote-not-support {
    description
      "Configure the common information for IPv6 pool which is not remote type.";
    container dns-server {
      // NCS drop must statement
      description
        "Configure an IPv6 address for binding a DNS server to an IPv6 address pool.";
      leaf ipv6-address1 {
        type inet:ipv6-address-no-zone;
        description
          "Specify the first IPv6 address of a DNS server.";
      }
      leaf ipv6-address2 {
        type inet:ipv6-address-no-zone;
        description
          "Specify the second IPv6 address of a DNS server.";
      }
    }
    container dns-search-list {
      description
        "Configure a domain name suffix.";
      leaf name {
        type string {
          length "1..32";
          pattern '[a-zA-Z0-9._-]{1,32}';
        }
        // NCS drop must statement
        description
          "Specify the domain name suffix.";
      }
    }
    container renew-rebind-time {
      // NCS drop must statement
      description
        "Configure the renewal time of an IPv6 address pool. renew-time-percent is the percentage of the renewal time to the preferred lifetime.";
      leaf renew-time-percent {
        type uint8 {
          range "10..99";
        }
        units "%";
        // NCS drop default statement
        description
          "Set the renewal time and rebinding time of an IPv6 address pool.";
      }
      leaf rebind-time-percent {
        type uint8 {
          range "10..99";
        }
        units "%";
        // NCS drop default statement
        description
          "Specify the rebinding time of an IPv6 address pool. rebind-time-percent is the percentage of the rebinding time to the preferred lifetime.";
      }
    }
  }

  grouping live_ncs_lock {
    description
      "Lock an IPv6 prefix pool.";
    container lock {
      description
        "Configure a locked IPv6 prefix pool.";
      leaf enable {
        type empty;
        description
          "Lock an IPv6 prefix pool.";
      }
    }
  }

  grouping live_ncs_reserved-ipv6 {
    description
      "Configure a reservation type for the prefix pool.";
    container reserved-ipv6 {
      description
        "Configure a reservation type for the prefix pool.";
      leaf reserved-type {
        type live_ncs_reserved-type;
        description
          "Reservation type for the IPv6 prefix or address, after the reserved type of an IPv6 prefix or address is set to mac, one-to-many mapping between one MAC address and multiple sessions cannot be enabled.";
      }
      leaf lease {
        // NCS drop when statement
        type empty;
        description
          "Reserve the IPv6 prefixes or address during a lease.";
      }
    }
  }

  grouping live_ncs_frame-ipv6-lease {
    description
      "Configure lease for an IPv6 prefix pool.";
    container frame-ipv6-lease {
      description
        "Configure manage the leases of RADIUS-delivered IPv6 addresses that are in the supported address pools.";
      leaf enable {
        type boolean;
        // NCS drop default statement
        description
          "Enable/disable manage the leases of RADIUS-delivered IPv6 addresses that are in the supported address pools.";
      }
    }
  }

  grouping live_ncs_exclude-ipv6-address {
    description
      "List of specified IPv6 addresses to prevent it from being allocated to users. The start IPv6 address must be smaller than or equal to the end IPv6 address.";
    list exclude-ipv6-address {
      key "start-ipv6-address end-ipv6-address";
      description
        "Configure a specified IPv6 address to prevent it from being allocated to users. The start IPv6 address must be smaller than or equal to the end IPv6 address.";
      leaf start-ipv6-address {
        type inet:ipv6-address-no-zone;
        description
          "Specify the start IPv6 address.";
      }
      leaf end-ipv6-address {
        type inet:ipv6-address-no-zone;
        description
          "Specify the end IPv6 address.";
      }
    }
  }

  grouping live_ncs_ipv6-constant-index {
    description
      "Configure a constant index for an IPv6 address or prefix pool.";
    container constant-index {
      description
        "Statistics of a constant index for an IPv6 address or prefix pool.";
      leaf value {
        type uint16 {
          range "0..16383";
        }
        description
          "Specify an index for an IPv6 address or prefix pool.";
      }
    }
  }

  grouping live_ncs_ipv6-pool-comm {
    description
      "Set the preference value of an IPv6 address pool.";
    container preference {
      description
        "Configure the preference value of an IPv6 address pool.";
      leaf value {
        type uint8 {
          range "0..255";
        }
        // NCS drop default statement
        description
          "Specify the preference value of an IPv6 address pool.";
      }
    }
    container lock {
      presence "Create lock pool";
      description
        "Enable/disable an IPv6 address pool.";
      leaf drain {
        type boolean;
        // NCS drop default statement
        description
          "Enable/disable an IPv6 address pool. If it is disable, the address pool cannot be used to assign IPv6 addresses to new users and DHCP renew or rebind.";
      }
    }
    container wait-request-time {
      description
        "Configure the timeout period for a router to wait for a request message from a client in response to an advertise message sent to the client.";
      leaf value {
        type uint8 {
          range "5..60";
        }
        units "s";
        description
          "Specify the timeout period for a router to wait for a request message from a client.";
      }
    }
    container warning {
      description
        "Configure warning of IPv6 address usage.";
      leaf threshold-value {
        type uint8 {
          range "0..100";
        }
        // NCS drop default statement
        description
          "The alarm threshold for the address usage of an IPv6 address pool is a percentage.";
      }
      leaf exhaust {
        type empty;
        description
          "Enable the address exhaustion alarm function for an IPv6 address pool.";
      }
    }
    container unr-tag {
      description
        "Configure a route tag for an IPv6 address pool.";
      leaf value {
        type uint32 {
          range "0..4294967295";
        }
        description
          "Specify the route tag for the IPv6 address pool.";
      }
    }
  }

  grouping live_ncs_weight {
    description
      "Configure a weight for an IPv6 address pool.";
    leaf value {
      type uint8 {
        range "0..100";
      }
      // NCS drop default statement
      description
        "Specify a weight for an IPv6 address pool.";
    }
  }

  grouping live_ncs_aftr-config {
    description
      "Configure an Address Family Transition Router (AFTR) name.";
    container aftr {
      description
        "Configure an Address Family Transition Router (AFTR) name.";
      leaf name {
        type string {
          length "1..63";
          pattern '[a-zA-Z0-9._-]{1,63}';
        }
        // NCS drop must statement
        description
          "Specify an AFTR name.";
      }
    }
  }

  grouping live_ncs_export-host-route {
    description
      "Enable a device to advertise host routes in a remote address pool.";
    container export-host-route {
      description
        "Configure a device to advertise host routes in a remote address pool.";
      leaf ipv6-address {
        type empty;
        description
          "Advertise IPv6 routes.";
      }
      leaf pd-prefix {
        type empty;
        description
          "Advertise PD routes.";
      }
      leaf nd-prefix {
        type empty;
        description
          "Advertise ND routes.";
      }
    }
  }

  grouping live_ncs_pool-usage {
    description
      "Display IPv6 address pool usage.";
    leaf address-total-number {
      type uint32;
      description
        "Total number of IPv6 address.";
    }
    leaf address-used-number {
      type uint32;
      description
        "Used number of IPv6 address.";
    }
    leaf address-used-radio {
      type uint32;
      description
        "IPv6 address usage (in percentage).";
    }
    leaf ndra-total-number {
      type uint32;
      description
        "Total number of in-use unshare NDRA prefixs.";
    }
    leaf ndra-used-number {
      type uint32;
      description
        "Used number of in-use unshare NDRA prefixs.";
    }
    leaf ndra-used-radio {
      type uint32;
      description
        "Usage (in percentage) of unshared NDRA prefixes.";
    }
    leaf delegation-total-number {
      type uint32;
      description
        "Total number of delegation prefixs.";
    }
    leaf delegation-used-number {
      type uint32;
      description
        "Used number of delegation prefixs.";
    }
    leaf delegation-used-radio {
      type uint32;
      description
        "Usage (in percentage) of delegation prefixes.";
    }
  }

  grouping live_ncs_pool-statistics {
    description
      "Statistics of IPv6 pool.";
    leaf address-idle-total-number {
      type int32;
      description
        "Number of idle IPv6 addresses on the equipment.";
    }
    leaf address-used-total-number {
      type int32;
      description
        "Number of IPv6 addresses in use on the equipment.";
    }
    leaf prefix-idle-total-number {
      type int32;
      description
        "Number of idle IPv6 prefixes on the equipment.";
    }
    leaf prefix-used-total-number {
      type int32;
      description
        "Number of IPv6 prefixes in use on the equipment.";
    }
    leaf address-total-number {
      type int32;
      description
        "The total IPv6 address number.";
    }
    leaf address-used-number {
      type int32;
      description
        "The used IPv6 address number.";
    }
    leaf address-idle-number {
      type int32;
      description
        "The free IPv6 address number.";
    }
    leaf address-conflict-number {
      type int32;
      description
        "The conflict IPv6 address number.";
    }
    leaf address-excluded-number {
      type int32;
      description
        "The excluded IPv6 address number.";
    }
    leaf address-used-percent {
      type int32;
      description
        "The percent of used IPv6 address.";
    }
    leaf ndra-total-number {
      type int32;
      description
        "The total NDRA prefix number.";
    }
    leaf ndra-used-number {
      type int32;
      description
        "The used NDRA prefix number.";
    }
    leaf ndra-free-number {
      type int32;
      description
        "The free NDRA prefix number.";
    }
    leaf ndra-conflict-number {
      type int32;
      description
        "The conflict NDRA prefix number.";
    }
    leaf ndra-excluded-number {
      type int32;
      description
        "The excluded NDRA prefix number.";
    }
    leaf ndra-used-percent {
      type int32;
      description
        "The percent of used IPv6 NDRA prefix.";
    }
    leaf pd-total-number {
      type int32;
      description
        "The total PD prefix number.";
    }
    leaf pd-used-number {
      type int32;
      description
        "The used PD prefix number.";
    }
    leaf pd-free-number {
      type int32;
      description
        "The free PD prefix number.";
    }
    leaf pd-conflict-number {
      type int32;
      description
        "The conflict PD prefix number.";
    }
    leaf pd-excluded-number {
      type int32;
      description
        "The excluded PD prefix number.";
    }
    leaf pd-used-percent {
      type int32;
      description
        "The percent of used IPv6 PD prefix.";
    }
  }

  grouping specified-up {
    description
      "Configure an IPv6 prefix pool to be exclusively used by a vBRAS-UP or UP backup policy profile in CU separation multi-instance scenarios.";
    container occupied-policy {
      description
        "Configure a specific policy to specify the IPv6 prefix pool to be occupied.";
      choice occupied-policy {
        description
          "Select a specific policy to specify the IPv6 prefix pool to be occupied.";
        case up-id {
          description
            "The specified IPv6 prefix pool is exclusive to be used by vBRAS-UP UP ID.";
          leaf up-id {
            type uint16 {
              range "1024..2023 | 2048..3047 | 3072..4071 | 4096..5095";
            }
            must '(../up-id<=(/bras-cu-controller:bras-cu-controller/bras-cu-controller:global-attribute/bras-cu-controller:up-base-id + 999) and ../up-id>=/bras-cu-controller:bras-cu-controller/bras-cu-controller:global-attribute/bras-cu-controller:up-base-id)' {
              tailf:xpath-root 3;
            }
            description
              "Specify the ID of a vBRAS-UP.";
          }
        }
        case up-backup-profile {
          description
            "The specified IPv6 prefix pool is exclusive to be used by vBRAS-UP backup policy profile.";
          leaf up-backup-profile {
            type leafref {
              path "/ncs:devices/ncs:device/ncs:config/bras-cu-controller:bras-cu-controller/bras-cu-controller:hot-profiles/bras-cu-controller:hot-profile/bras-cu-controller:name" {
                tailf:xpath-root 3;
              }
            }
            must '/bras-cu-controller:bras-cu-controller/bras-cu-controller:hot-profiles/bras-cu-controller:hot-profile[bras-cu-controller:name=current()]/bras-cu-controller:backup-groups/bras-cu-controller:backup-group/bras-cu-controller:master-interface' {
              tailf:xpath-root 3;
            }
            description
              "Specify the name of a vBRAS-UP backup policy profile.";
          }
        }
        case hot-standby-up-group {
          description
            "The specified IPv6 prefix pool is exclusive to be used by vBRAS-UP hot backup groups.";
          leaf master-up {
            type uint16 {
              range "1024..2023 | 2048..3047 | 3072..4071 | 4096..5095";
            }
            must '../master-up!=../slave-up' {
              tailf:xpath-root 3;
            }
            must '(../master-up<=(/bras-cu-controller:bras-cu-controller/bras-cu-controller:global-attribute/bras-cu-controller:up-base-id + 999) and ../master-up>=/bras-cu-controller:bras-cu-controller/bras-cu-controller:global-attribute/bras-cu-controller:up-base-id)' {
              tailf:xpath-root 3;
            }
            mandatory true;
            description
              "Specify the ID of the vBRAS-UP where the master interface in a vBRAS-UP hot backup group resides.";
          }
          leaf slave-up {
            type uint16 {
              range "1024..2023 | 2048..3047 | 3072..4071 | 4096..5095";
            }
            must '(../slave-up<=(/bras-cu-controller:bras-cu-controller/bras-cu-controller:global-attribute/bras-cu-controller:up-base-id + 999) and ../slave-up>=/bras-cu-controller:bras-cu-controller/bras-cu-controller:global-attribute/bras-cu-controller:up-base-id)' {
              tailf:xpath-root 3;
            }
            mandatory true;
            description
              "Specify the ID of the vBRAS-UP where the slave interface in a vBRAS-UP hot backup group resides.";
          }
        }
      }
    }
  }

  grouping vpn-instance {
    description
      "Specify the VPN instance name of a IPv6 prefix pool.";
    container vpn-instance {
      description
        "Configure the VPN instance name of a IPv6 prefix pool.";
      leaf name {
        type leafref {
          path "/ncs:devices/ncs:device/ncs:config/ni:network-instance/ni:instances/ni:instance/ni:name" {
            tailf:xpath-root 3;
          }
        }
        must "/ni:network-instance/ni:instances/ni:instance[ni:name=current()]/l3vpn:afs/l3vpn:af[l3vpn:type='ipv6-unicast'] and ../name != '_public_'" {
          tailf:xpath-root 3;
        }
        description
          "Specify the VPN instance name of a IPv6 prefix pool.";
      }
    }
  }

  grouping slaac-unshare-only {
    description
      "Configure the prefix pool to allocate IP addresses by using only the unshared-mode stateless address autoconfiguration (SLAAC) protocol.";
    container slaac-unshare-only {
      description
        "Configure the prefix pool to allocate IP addresses by using only the unshared-mode stateless address autoconfiguration (SLAAC) protocol.";
      leaf enable {
        type boolean;
        default "false";
        description
          "Enable/disable the prefix pool to allocate IP addresses by using only the unshared-mode stateless address autoconfiguration (SLAAC) protocol.";
      }
    }
  }

  grouping pd-unshare-only {
    description
      "Configure the prefix pool to allocate IP addresses by using only the unshared-mode stateless address autoconfiguration (DHCPv6 IA_PD) protocol.";
    container pd-unshare-only {
      description
        "Configure the prefix pool to allocate IP addresses by using only the unshared-mode stateless address autoconfiguration (DHCPv6 IA_PD) protocol.";
      leaf enable {
        type boolean;
        default "false";
        description
          "Enable/disable the prefix pool to allocate IP addresses by using only the unshared-mode stateless address autoconfiguration (DHCPv6 IA_PD) protocol.";
      }
    }
  }

  grouping dhcpv6-unshare-only {
    description
      "Configure an IPv6 prefix pool to assign only IPv6 addresses not prefixes to users.";
    leaf enable {
      type empty;
      description
        "Configure an IPv6 prefix pool to assign only IPv6 addresses not prefixes to users.";
    }
  }

  grouping lifetime-config {
    description
      "Configure the preferred lifetime anf valid lifetime of an IPv6 prefix.";
    container lifetime {
      must 'not(./preferred-infinite) or ./valid-infinite' {
        tailf:xpath-root 3;
      }
      description
        "Configure the preferred lifetime anf valid lifetime of an IPv6 prefix.
         The valid lifetime should not be smaller than the preferred lifetime.";
      choice preferred-lifetime {
        default "preferred-time";
        description
          "Configure the preferred lifetime.";
        case preferred-infinite {
          description
            "Specify the preferred lifetime of IPv6 prefix is infinite.";
          leaf preferred-infinite {
            type empty;
            description
              "Specify the preferred lifetime of IPv6 prefix is infinite.";
          }
        }
        case preferred-time {
          description
            "Configure the preferred lifetime that is not infinite.";
          leaf preferred-day {
            type uint16 {
              range "0..999";
            }
            units "d";
            must '../preferred-day != 0 or ../preferred-hour != 0 or ../preferred-minute != 0' {
              tailf:xpath-root 3;
            }
            default "2";
            description
              "Prefer day.";
          }
          leaf preferred-hour {
            type uint8 {
              range "0..23";
            }
            units "h";
            default "0";
            description
              "Prefer hour.";
          }
          leaf preferred-minute {
            type uint8 {
              range "0..59";
            }
            units "min";
            default "0";
            description
              "Prefer minute.";
          }
        }
      }
      choice valid-lifetime {
        default "valid-time";
        description
          "Configure the valid lifetime.";
        case valid-infinite {
          description
            "Configure the valid lifetime of IPv6 prefix is infinite.";
          leaf valid-infinite {
            type empty;
            description
              "Specify the valid lifetime of IPv6 prefix is infinite.";
          }
        }
        case valid-time {
          description
            "Configure the valid lifetime that is not infinite.";
          leaf valid-day {
            type uint16 {
              range "0..999";
            }
            units "d";
            must '../valid-day != 0 or ../valid-hour != 0 or ../valid-minute != 0' {
              tailf:xpath-root 3;
            }
            default "3";
            description
              "Valid day.";
          }
          leaf valid-hour {
            type uint8 {
              range "0..23";
            }
            units "h";
            default "0";
            description
              "Valid hour.";
          }
          leaf valid-minute {
            type uint8 {
              range "0..59";
            }
            units "min";
            default "0";
            description
              "Valid minute.";
          }
        }
      }
    }
  }

  grouping rapid-commit-config {
    description
      "Configure the DHCPv6 server to support a rapid two-message exchange (solicit, reply).";
    container rapid-commit {
      description
        "Configure the DHCPv6 server to support a rapid two-message exchange (solicit, reply).";
      leaf enable {
        type boolean;
        default "false";
        description
          "Enable/disable rapid commit.";
      }
    }
  }

  grouping remote-not-support {
    description
      "Configure the common information for IPv6 pool which is not remote type.";
    container dns-server {
      must 'not(./ipv6-address1) or not(./ipv6-address2) or ./ipv6-address1!=./ipv6-address2' {
        tailf:xpath-root 3;
      }
      description
        "Configure an IPv6 address for binding a DNS server to an IPv6 address pool.";
      leaf ipv6-address1 {
        type inet:ipv6-address-no-zone;
        description
          "Specify the first IPv6 address of a DNS server.";
      }
      leaf ipv6-address2 {
        type inet:ipv6-address-no-zone;
        description
          "Specify the second IPv6 address of a DNS server.";
      }
    }
    container dns-search-list {
      description
        "Configure a domain name suffix.";
      leaf name {
        type string {
          length "1..32";
          pattern '[a-zA-Z0-9._-]{1,32}';
        }
        must "../name != '-' and ../name != '--'" {
          tailf:xpath-root 3;
        }
        description
          "Specify the domain name suffix.";
      }
    }
    container renew-rebind-time {
      must './rebind-time-percent >= ./renew-time-percent + 10' {
        tailf:xpath-root 3;
      }
      description
        "Configure the renewal time of an IPv6 address pool. renew-time-percent is the percentage of the renewal time to the preferred lifetime.";
      leaf renew-time-percent {
        type uint8 {
          range "10..99";
        }
        units "%";
        default "50";
        description
          "Set the renewal time and rebinding time of an IPv6 address pool.";
      }
      leaf rebind-time-percent {
        type uint8 {
          range "10..99";
        }
        units "%";
        default "80";
        description
          "Specify the rebinding time of an IPv6 address pool. rebind-time-percent is the percentage of the rebinding time to the preferred lifetime.";
      }
    }
  }

  grouping lock {
    description
      "Lock an IPv6 prefix pool.";
    container lock {
      description
        "Configure a locked IPv6 prefix pool.";
      leaf enable {
        type empty;
        description
          "Lock an IPv6 prefix pool.";
      }
    }
  }

  grouping reserved-ipv6 {
    description
      "Configure a reservation type for the prefix pool.";
    container reserved-ipv6 {
      description
        "Configure a reservation type for the prefix pool.";
      leaf reserved-type {
        type reserved-type;
        description
          "Reservation type for the IPv6 prefix or address, after the reserved type of an IPv6 prefix or address is set to mac, one-to-many mapping between one MAC address and multiple sessions cannot be enabled.";
      }
      leaf lease {
        when '../reserved-type' {
          tailf:xpath-root 3;
        }
        type empty;
        description
          "Reserve the IPv6 prefixes or address during a lease.";
      }
    }
  }

  grouping frame-ipv6-lease {
    description
      "Configure lease for an IPv6 prefix pool.";
    container frame-ipv6-lease {
      description
        "Configure manage the leases of RADIUS-delivered IPv6 addresses that are in the supported address pools.";
      leaf enable {
        type boolean;
        default "false";
        description
          "Enable/disable manage the leases of RADIUS-delivered IPv6 addresses that are in the supported address pools.";
      }
    }
  }

  grouping exclude-ipv6-address {
    description
      "List of specified IPv6 addresses to prevent it from being allocated to users. The start IPv6 address must be smaller than or equal to the end IPv6 address.";
    list exclude-ipv6-address {
      key "start-ipv6-address end-ipv6-address";
      description
        "Configure a specified IPv6 address to prevent it from being allocated to users. The start IPv6 address must be smaller than or equal to the end IPv6 address.";
      leaf start-ipv6-address {
        type inet:ipv6-address-no-zone;
        description
          "Specify the start IPv6 address.";
      }
      leaf end-ipv6-address {
        type inet:ipv6-address-no-zone;
        description
          "Specify the end IPv6 address.";
      }
    }
  }

  grouping ipv6-constant-index {
    description
      "Configure a constant index for an IPv6 address or prefix pool.";
    // NCS drop config false container 'constant-index'
  }

  grouping ipv6-pool-comm {
    description
      "Set the preference value of an IPv6 address pool.";
    container preference {
      description
        "Configure the preference value of an IPv6 address pool.";
      leaf value {
        type uint8 {
          range "0..255";
        }
        default "255";
        description
          "Specify the preference value of an IPv6 address pool.";
      }
    }
    container lock {
      presence "Create lock pool";
      description
        "Enable/disable an IPv6 address pool.";
      leaf drain {
        type boolean;
        default "false";
        description
          "Enable/disable an IPv6 address pool. If it is disable, the address pool cannot be used to assign IPv6 addresses to new users and DHCP renew or rebind.";
      }
    }
    container wait-request-time {
      description
        "Configure the timeout period for a router to wait for a request message from a client in response to an advertise message sent to the client.";
      leaf value {
        type uint8 {
          range "5..60";
        }
        units "s";
        description
          "Specify the timeout period for a router to wait for a request message from a client.";
      }
    }
    container warning {
      description
        "Configure warning of IPv6 address usage.";
      leaf threshold-value {
        type uint8 {
          range "0..100";
        }
        default "80";
        description
          "The alarm threshold for the address usage of an IPv6 address pool is a percentage.";
      }
      leaf exhaust {
        type empty;
        description
          "Enable the address exhaustion alarm function for an IPv6 address pool.";
      }
    }
    container unr-tag {
      description
        "Configure a route tag for an IPv6 address pool.";
      leaf value {
        type uint32 {
          range "0..4294967295";
        }
        description
          "Specify the route tag for the IPv6 address pool.";
      }
    }
  }

  grouping weight {
    description
      "Configure a weight for an IPv6 address pool.";
    leaf value {
      type uint8 {
        range "0..100";
      }
      default "5";
      description
        "Specify a weight for an IPv6 address pool.";
    }
  }

  grouping aftr-config {
    description
      "Configure an Address Family Transition Router (AFTR) name.";
    container aftr {
      description
        "Configure an Address Family Transition Router (AFTR) name.";
      leaf name {
        type string {
          length "1..63";
          pattern '[a-zA-Z0-9._-]{1,63}';
        }
        must "../name != '-' and ../name != '--'" {
          tailf:xpath-root 3;
        }
        description
          "Specify an AFTR name.";
      }
    }
  }

  grouping export-host-route {
    description
      "Enable a device to advertise host routes in a remote address pool.";
    container export-host-route {
      description
        "Configure a device to advertise host routes in a remote address pool.";
      leaf ipv6-address {
        type empty;
        description
          "Advertise IPv6 routes.";
      }
      leaf pd-prefix {
        type empty;
        description
          "Advertise PD routes.";
      }
      leaf nd-prefix {
        type empty;
        description
          "Advertise ND routes.";
      }
    }
  }

  grouping pool-usage {
    description
      "Display IPv6 address pool usage.";
    leaf address-total-number {
      type uint32;
      description
        "Total number of IPv6 address.";
    }
    leaf address-used-number {
      type uint32;
      description
        "Used number of IPv6 address.";
    }
    leaf address-used-radio {
      type uint32;
      description
        "IPv6 address usage (in percentage).";
    }
    leaf ndra-total-number {
      type uint32;
      description
        "Total number of in-use unshare NDRA prefixs.";
    }
    leaf ndra-used-number {
      type uint32;
      description
        "Used number of in-use unshare NDRA prefixs.";
    }
    leaf ndra-used-radio {
      type uint32;
      description
        "Usage (in percentage) of unshared NDRA prefixes.";
    }
    leaf delegation-total-number {
      type uint32;
      description
        "Total number of delegation prefixs.";
    }
    leaf delegation-used-number {
      type uint32;
      description
        "Used number of delegation prefixs.";
    }
    leaf delegation-used-radio {
      type uint32;
      description
        "Usage (in percentage) of delegation prefixes.";
    }
  }

  grouping pool-statistics {
    description
      "Statistics of IPv6 pool.";
    leaf address-idle-total-number {
      type int32;
      description
        "Number of idle IPv6 addresses on the equipment.";
    }
    leaf address-used-total-number {
      type int32;
      description
        "Number of IPv6 addresses in use on the equipment.";
    }
    leaf prefix-idle-total-number {
      type int32;
      description
        "Number of idle IPv6 prefixes on the equipment.";
    }
    leaf prefix-used-total-number {
      type int32;
      description
        "Number of IPv6 prefixes in use on the equipment.";
    }
    leaf address-total-number {
      type int32;
      description
        "The total IPv6 address number.";
    }
    leaf address-used-number {
      type int32;
      description
        "The used IPv6 address number.";
    }
    leaf address-idle-number {
      type int32;
      description
        "The free IPv6 address number.";
    }
    leaf address-conflict-number {
      type int32;
      description
        "The conflict IPv6 address number.";
    }
    leaf address-excluded-number {
      type int32;
      description
        "The excluded IPv6 address number.";
    }
    leaf address-used-percent {
      type int32;
      description
        "The percent of used IPv6 address.";
    }
    leaf ndra-total-number {
      type int32;
      description
        "The total NDRA prefix number.";
    }
    leaf ndra-used-number {
      type int32;
      description
        "The used NDRA prefix number.";
    }
    leaf ndra-free-number {
      type int32;
      description
        "The free NDRA prefix number.";
    }
    leaf ndra-conflict-number {
      type int32;
      description
        "The conflict NDRA prefix number.";
    }
    leaf ndra-excluded-number {
      type int32;
      description
        "The excluded NDRA prefix number.";
    }
    leaf ndra-used-percent {
      type int32;
      description
        "The percent of used IPv6 NDRA prefix.";
    }
    leaf pd-total-number {
      type int32;
      description
        "The total PD prefix number.";
    }
    leaf pd-used-number {
      type int32;
      description
        "The used PD prefix number.";
    }
    leaf pd-free-number {
      type int32;
      description
        "The free PD prefix number.";
    }
    leaf pd-conflict-number {
      type int32;
      description
        "The conflict PD prefix number.";
    }
    leaf pd-excluded-number {
      type int32;
      description
        "The excluded PD prefix number.";
    }
    leaf pd-used-percent {
      type int32;
      description
        "The percent of used IPv6 PD prefix.";
    }
  }

  augment "/ncs:devices/ncs:device/ncs:config" {
    container bras-ipv6-address-manage {
      tailf:ncs-device-type "netconf";
      tailf:display-when "not(../../ncs:module) or ../../ncs:module[ncs:name='huawei-bras-ipv6-address-manage']";
      description
        "Configure the IPv6 repfix pool and IPv6 address pool.";
      container ipv6-prefixs {
        description
          "List of IPv6 prefix pools.";
        list ipv6-prefix {
          key "name";
          max-elements 16384;
          description
            "Configure an IPv6 prefix pool.";
          leaf name {
            ext:case-sensitivity "lower-only";
            type string {
              length "1..32";
              pattern '[a-z0-9._-]{1,32}';
            }
            must "../name != '-' and ../name != '--'" {
              tailf:xpath-root 3;
            }
            description
              "Specify the name of the IPv6 prefix pool to be created.";
          }
          leaf type {
            ext:operation-exclude "update";
            type prefix-type;
            mandatory true;
            description
              "Specify the type of the IPv6 prefix pool, and the type cannot be modified.";
          }
          container local {
            when "../type = 'local'" {
              tailf:xpath-root 3;
            }
            description
              "Configure a local IPv6 prefix pool. The specified IPv6 address must be in the IPv6 prefix pool.";
            uses specified-up;
            container prefix-address {
              description
                "Configure the IPv6 prefix address for an IPv6 prefix pool.";
              leaf prefix {
                type inet:ipv6-prefix;
                description
                  "Specify the address and length of an IPv6 prefix, not support modify. The prefix address must be calculated based on the prefix length.";
              }
            }
            uses vpn-instance;
            container exclude-ipv6-addresss {
              when '../prefix-address/prefix' {
                tailf:xpath-root 3;
              }
              description
                "Configure IPv6 addresses to prevent it from being allocated to users. The start IPv6 address must be smaller than or equal to the end IPv6 address.";
              uses exclude-ipv6-address;
            }
            uses lifetime-config;
            uses reserved-ipv6;
            uses frame-ipv6-lease;
            uses ipv6-constant-index;
          }
          container delegation {
            when "../type = 'delegation'" {
              tailf:xpath-root 3;
            }
            must "./slaac-unshare-only/enable='false' and ./pd-unshare-only/enable='false' or ./slaac-unshare-only/enable='false' and not(./dhcpv6-unshare-only/enable) or ./pd-unshare-only/enable='false' and not(./dhcpv6-unshare-only/enable)" {
              tailf:xpath-root 3;
            }
            description
              "Configure a delegation IPv6 prefix pool. The specified IPv6 address must be in the IPv6 prefix pool.";
            uses specified-up;
            container prefix-address {
              description
                "Configure the IPv6 prefix address for an IPv6 prefix pool.";
              leaf prefix {
                type inet:ipv6-prefix;
                description
                  "Specify the address and length of an IPv6 prefix, not support modify. The prefix address must be calculated based on the prefix length.";
              }
              leaf prefix-length {
                when '../prefix' {
                  tailf:xpath-root 3;
                }
                type uint8 {
                  range "1..128";
                }
                default "64";
                description
                  "Specify the length of the IPv6 prefix assigned by the delegating router to the requesting router. Not support modify or delete.
                   The delegating prefix length must be longer than or the same as IPv6 prefix length.";
              }
            }
            uses slaac-unshare-only;
            uses pd-unshare-only;
            container dhcpv6-unshare-only {
              when '../prefix-address/prefix' {
                tailf:xpath-root 3;
              }
              description
                "Configure an IPv6 prefix pool to assign only IPv6 addresses not prefixes to users.";
              uses dhcpv6-unshare-only;
            }
            uses vpn-instance;
            container exclude-ipv6-addresss {
              when '../dhcpv6-unshare-only/enable' {
                tailf:xpath-root 3;
              }
              description
                "Configure IPv6 addresses to prevent it from being allocated to users.";
              uses exclude-ipv6-address;
            }
            uses lifetime-config;
            uses reserved-ipv6;
            uses frame-ipv6-lease;
            uses ipv6-constant-index;
          }
          container remote {
            when "../type = 'remote'" {
              tailf:xpath-root 3;
            }
            must "./slaac-unshare-only/enable='false' or not(./dhcpv6-only/enable)" {
              tailf:xpath-root 3;
            }
            description
              "Configure a remote IPv6 prefix pool.";
            uses specified-up;
            uses vpn-instance;
            container link-address {
              description
                "Configure a link address.";
              leaf ipv6-address {
                type inet:ipv6-prefix;
                description
                  "Specify a global unicast address or a site-local unicast address.";
              }
            }
            container dhcpv6-only {
              description
                "Configure a remote prefix pool for only DHCPv6 prefix or address allocation.";
              leaf enable {
                type empty;
                description
                  "Specify a remote prefix pool for only DHCPv6 prefix or address allocation.";
              }
            }
            container lease-management {
              description
                "Configure the lease management function for remote IPv6 prefix pool.";
              leaf enable {
                type boolean;
                default "false";
                description
                  "Enable/disable the lease management function for remote IPv6 prefix pool.";
              }
            }
            container reserved-ipv6 {
              description
                "Configure a reservation type for the prefix pool.";
              leaf reserved-type {
                type reserved-type;
                description
                  "Reservation type for the IPv6 prefix or address, after the reserved type of an IPv6 prefix or address is set to mac, one-to-many mapping between one MAC address and multiple sessions cannot be enabled.";
              }
            }
            uses lock;
            uses slaac-unshare-only;
            uses ipv6-constant-index;
          }
          container dynamic {
            when "../type = 'dynamic'" {
              tailf:xpath-root 3;
            }
            description
              "Configure a dynamic IPv6 prefix pool.";
            container prefix-length {
              must 'not(./unshared-initial > ./unshared-delegating or ./unshared-extend > ./unshared-delegating)' {
                tailf:xpath-root 3;
              }
              must "not(./slaac-unshare-only/enable = 'true' and ./unshared-delegating != 64)" {
                tailf:xpath-root 3;
              }
              must "not(./slaac-unshare-only/enable = 'true' and ./pd-unshare-only/enable = 'true')" {
                tailf:xpath-root 3;
              }
              description
                "Configure the share mode for a dynamic IPv6 prefix pool to configure the prefix length.";
              choice share-mode {
                description
                  "Select the share mode for a dynamic IPv6 prefix pool to configure the prefix length.";
                case shared {
                  description
                    "Configure initial and subsequent prefix lengths for a shared dynamic prefix pool.";
                  leaf shared-initial {
                    type uint8 {
                      range "3..127";
                    }
                    mandatory true;
                    description
                      "Configure the initial prefix length.";
                  }
                  leaf shared-extend {
                    type uint8 {
                      range "3..127";
                    }
                    ext:dynamic-default {
                      ext:default-value "../shared-initial" {
                        description
                          "The default value is equal to initial length.";
                      }
                    }
                    description
                      "Configure the subsequent prefix length.";
                  }
                }
                case unshared {
                  description
                    "Configure initial, subsequent and delegating prefix lengths for a unshared dynamic prefix pool.";
                  leaf unshared-initial {
                    type uint8 {
                      range "3..127";
                    }
                    mandatory true;
                    description
                      "Configure the initial prefix length.";
                  }
                  leaf unshared-extend {
                    type uint8 {
                      range "3..127";
                    }
                    ext:dynamic-default {
                      ext:default-value "../unshared-initial" {
                        description
                          "The default value is equal to initial length.";
                      }
                    }
                    description
                      "Configure the subsequent prefix length.";
                  }
                  leaf unshared-delegating {
                    type uint8 {
                      range "3..127";
                    }
                    default "64";
                    description
                      "Configure the delegating prefix length.";
                  }
                  container slaac-unshare-only {
                    description
                      "Configure the prefix pool to allocate IP addresses by using only the unshared-mode stateless address autoconfiguration (SLAAC) protocol.";
                    leaf enable {
                      type boolean;
                      default "false";
                      description
                        "Enable/disable the prefix pool to allocate IP addresses by using only the unshared-mode stateless address autoconfiguration (SLAAC) protocol.";
                    }
                  }
                  container pd-unshare-only {
                    description
                      "Configure the prefix pool to allocate IP addresses by using only the unshared-mode stateless address autoconfiguration (DHCPv6 IA_PD) protocol.";
                    leaf enable {
                      type boolean;
                      default "false";
                      description
                        "Enable/disable the prefix pool to allocate IP addresses by using only the unshared-mode stateless address autoconfiguration (DHCPv6 IA_PD) protocol.";
                    }
                  }
                }
              }
            }
            uses vpn-instance;
            uses ipv6-constant-index;
          }
        }
      }
      container ipv6-pools {
        description
          "List of IPv6 address pools.";
        list ipv6-pool {
          key "name";
          max-elements 16384;
          description
            "Configure an IPv6 address pool.";
          leaf name {
            ext:case-sensitivity "lower-only";
            type string {
              length "1..32";
              pattern '[a-z0-9._-]{1,32}';
            }
            must "../name != '-' and ../name != '--'" {
              tailf:xpath-root 3;
            }
            description
              "Specify the name of an IPv6 address pool.";
          }
          leaf type {
            ext:operation-exclude "update";
            type pool-type;
            mandatory true;
            description
              "Specify the type of the IPv6 address pool, and the type cannot be modified.";
          }
          leaf rui-slave {
            ext:operation-exclude "update|delete";
            when "not(../type = 'relay')" {
              tailf:xpath-root 3;
            }
            type boolean;
            default "false";
            description
              "Enable/disable a hybrid IP address pool that can be used as a local address pool or remote address pool or delegation address pool. The rui-slave cannot be modified.";
          }
          container local {
            when "../type = 'local'" {
              tailf:xpath-root 3;
            }
            description
              "Configure a local IPv6 address pool.";
            container bind-prefix {
              description
                "Configure binding an IPv6 prefix pool to an IPv6 address pool.";
              leaf prefix-name {
                type leafref {
                  path "/ncs:devices/ncs:device/ncs:config/bras-ipv6-address-manage:bras-ipv6-address-manage/bras-ipv6-address-manage:ipv6-prefixs/bras-ipv6-address-manage:ipv6-prefix/bras-ipv6-address-manage:name" {
                    tailf:xpath-root 3;
                  }
                }
                must "/bras-ipv6-address-manage:bras-ipv6-address-manage/bras-ipv6-address-manage:ipv6-prefixs/bras-ipv6-address-manage:ipv6-prefix[name=current()]/bras-ipv6-address-manage:type ='local'" {
                  tailf:xpath-root 3;
                }
                description
                  "Bind an IPv6 prefix pool to an IPv6 address pool.";
              }
            }
            uses remote-not-support;
            uses rapid-commit-config;
            container weight {
              when "../../rui-slave = 'true'" {
                tailf:xpath-root 3;
              }
              description
                "Configure a weight for an IPv6 address pool.";
              uses weight;
            }
            uses ipv6-pool-comm;
            uses aftr-config;
            container export-host-route {
              description
                "Configure a device to advertise host routes in a remote address pool.";
              leaf ipv6-address {
                type empty;
                description
                  "Advertise IPv6 routes.";
              }
            }
            uses ipv6-constant-index;
          }
          container delegation {
            when "../type = 'delegation'" {
              tailf:xpath-root 3;
            }
            description
              "Configure a delegation IPv6 address pool.";
            container bind-prefix {
              description
                "Configure binding an IPv6 prefix pool to an IPv6 address pool.";
              leaf prefix-name {
                type leafref {
                  path "/ncs:devices/ncs:device/ncs:config/bras-ipv6-address-manage:bras-ipv6-address-manage/bras-ipv6-address-manage:ipv6-prefixs/bras-ipv6-address-manage:ipv6-prefix/bras-ipv6-address-manage:name" {
                    tailf:xpath-root 3;
                  }
                }
                must "/bras-ipv6-address-manage:bras-ipv6-address-manage/bras-ipv6-address-manage:ipv6-prefixs/bras-ipv6-address-manage:ipv6-prefix[name=current()]/bras-ipv6-address-manage:type ='delegation'" {
                  tailf:xpath-root 3;
                }
                description
                  "Bind an IPv6 prefix pool to an IPv6 address pool.";
              }
            }
            uses remote-not-support;
            uses rapid-commit-config;
            container weight {
              when "../../rui-slave = 'true'" {
                tailf:xpath-root 3;
              }
              description
                "Configure a weight for an IPv6 address pool.";
              uses weight;
            }
            uses ipv6-pool-comm;
            uses aftr-config;
            uses export-host-route;
            uses ipv6-constant-index;
          }
          container remote {
            when "../type = 'remote'" {
              tailf:xpath-root 3;
            }
            description
              "Configure a remote IPv6 address pool.";
            container bind-prefix {
              description
                "Configure binding an IPv6 prefix pool to an IPv6 address pool.";
              leaf prefix-name {
                type leafref {
                  path "/ncs:devices/ncs:device/ncs:config/bras-ipv6-address-manage:bras-ipv6-address-manage/bras-ipv6-address-manage:ipv6-prefixs/bras-ipv6-address-manage:ipv6-prefix/bras-ipv6-address-manage:name" {
                    tailf:xpath-root 3;
                  }
                }
                must "/bras-ipv6-address-manage:bras-ipv6-address-manage/bras-ipv6-address-manage:ipv6-prefixs/bras-ipv6-address-manage:ipv6-prefix[name=current()]/bras-ipv6-address-manage:type ='remote'" {
                  tailf:xpath-root 3;
                }
                description
                  "Bind an IPv6 prefix pool to an IPv6 address pool.";
              }
            }
            container weight {
              description
                "Configure a weight for an IPv6 address pool.";
              uses weight;
            }
            uses ipv6-pool-comm;
            uses export-host-route;
            uses ipv6-constant-index;
            container dhcpv6-server-group {
              description
                "Configure the DHCPv6 server group for this IPv6 address pool.";
              leaf name {
                type leafref {
                  path "/ncs:devices/ncs:device/ncs:config/bras-dhcpv6-server:bras-dhcpv6-server/bras-dhcpv6-server:dhcpv6-server-groups/bras-dhcpv6-server:dhcpv6-server-group/bras-dhcpv6-server:name" {
                    tailf:xpath-root 3;
                  }
                }
                description
                  "The DHCPv6 server group name.";
              }
            }
          }
          container relay {
            when "../type = 'relay'" {
              tailf:xpath-root 3;
            }
            description
              "Configure a relay IPv6 address pool.";
            container bind-prefix {
              description
                "Configure binding an IPv6 prefix pool to an IPv6 address pool.";
              leaf prefix-name {
                type leafref {
                  path "/ncs:devices/ncs:device/ncs:config/bras-ipv6-address-manage:bras-ipv6-address-manage/bras-ipv6-address-manage:ipv6-prefixs/bras-ipv6-address-manage:ipv6-prefix/bras-ipv6-address-manage:name" {
                    tailf:xpath-root 3;
                  }
                }
                must "/bras-ipv6-address-manage:bras-ipv6-address-manage/bras-ipv6-address-manage:ipv6-prefixs/bras-ipv6-address-manage:ipv6-prefix[name=current()]/bras-ipv6-address-manage:type ='local'" {
                  tailf:xpath-root 3;
                }
                description
                  "Bind an IPv6 prefix pool to an IPv6 address pool.";
              }
            }
            uses remote-not-support;
            uses rapid-commit-config;
            uses ipv6-pool-comm;
            uses ipv6-constant-index;
          }
          // NCS drop config false container usage
          // NCS drop config false container statistic
        }
      }
      container ipv6-unr-route-tag {
        description
          "Configure route tags for IPv6 users.";
        leaf delegated-ipv6-prefix-tag {
          type uint32;
          default "0";
          description
            "Set a route tag for PD IPv6 addresses delivered by a RADIUS server.";
        }
        leaf delegated-pool-tag {
          type uint32;
          default "0";
          description
            "Set a route tag for delegation IPv6 address pools.";
        }
        leaf framed-ipv6-address-tag {
          type uint32;
          default "0";
          description
            "Set a route tag for IA_NA IPv6 addresses delivered by a RADIUS server.";
        }
        leaf framed-ipv6-prefix-tag {
          type uint32;
          default "0";
          description
            "Set a route tag for ND IPv6 addresses delivered by a RADIUS server.";
        }
        leaf framed-ipv6-route-tag {
          type uint32;
          default "0";
          description
            "Set a route tag for IPv6 route addresses delivered by a RADIUS server.";
        }
        leaf local-pool-tag {
          type uint32;
          default "0";
          description
            "Set a route tag for local IPv6 address pools.";
        }
        leaf relay-pool-tag {
          type uint32;
          default "0";
          description
            "Set a route tag for relay IPv6 address pools.";
        }
        leaf remote-pool-tag {
          type uint32;
          default "0";
          description
            "Set a route tag for remote IPv6 address pools.";
        }
      }
      container address-assign-eui-64 {
        description
          "Configure an interface ID to be in the standard EUI-64 format when DHCPv6 is used to allocate addresses.";
        leaf enable {
          type boolean;
          default "false";
          description
            "Enable/disable an interface ID to be in the standard EUI-64 format when DHCPv6 is used to allocate addresses.";
        }
      }
      container statistic-include-shared-user {
        description
          "Configure the IPv6 address pool statistics to include statistics about users sharing the prefix pool.";
        leaf enable {
          type boolean;
          default "false";
          description
            "Enable/disable the IPv6 address pool statistics to include statistics about users sharing the prefix pool.";
        }
      }
      container pool-select-algorithm {
        must "not (./remote-loading-share = 'true' and ./remote-round-robin = 'true')" {
          tailf:xpath-root 3;
        }
        description
          "Configure a device to assign addresses from IPv6 remote address pools based on weights of the address pools.";
        leaf remote-loading-share {
          type boolean;
          default "false";
          description
            "Enable/disable a device to assign addresses from IPv6 remote address pools based on weights of the address pools.";
        }
        leaf remote-round-robin {
          type boolean;
          default "false";
          description
            "Enable/disable the round robin algorithm for remote IPv6 address pool.";
        }
        leaf local-round-robin {
          type boolean;
          default "false";
          description
            "Enable/disable the round robin algorithm for local IPv6 address pool.";
        }
      }
      container auto-block {
        description
          "Configure automatic isolation of IPv6 prefix pools.";
        leaf enable {
          type boolean;
          default "true";
          description
            "Enable/disable automatic isolation of IPv6 prefix pools.";
        }
        leaf slave-switch {
          type boolean;
          default "true";
          description
            "Enable/disable the switchover function for IPv6 prefix pool isolation.";
        }
      }
      // NCS drop config false container 'statistics-by-domains'
      // NCS drop config false container 'pool-statistics'
      // NCS drop config false container 'statistics-by-vpn-instance'
      // NCS drop config false container 'global-statistic'
    }
  }
  augment "/ncs:devices/ncs:device/ncs:live-status" {
    container bras-ipv6-address-manage {
      tailf:ncs-device-type "netconf";
      tailf:display-when "not(../../ncs:module) or ../../ncs:module[ncs:name='huawei-bras-ipv6-address-manage'] or (../../ncs:live-status-protocol[not(ncs:capability)]) or (../../ncs:live-status-protocol/ncs:capability/ncs:module[.='huawei-bras-ipv6-address-manage'])";
      description
        "Configure the IPv6 repfix pool and IPv6 address pool.";
      container ipv6-prefixs {
        description
          "List of IPv6 prefix pools.";
        list ipv6-prefix {
          key "name";
          // NCS drop max-elements statement
          description
            "Configure an IPv6 prefix pool.";
          leaf name {
            ext:case-sensitivity "lower-only";
            type string {
              length "1..32";
              pattern '[a-z0-9._-]{1,32}';
            }
            // NCS drop must statement
            description
              "Specify the name of the IPv6 prefix pool to be created.";
          }
          leaf type {
            ext:operation-exclude "update";
            type live_ncs_prefix-type;
            // NCS drop mandatory statement
            description
              "Specify the type of the IPv6 prefix pool, and the type cannot be modified.";
          }
          container local {
            // NCS drop when statement
            description
              "Configure a local IPv6 prefix pool. The specified IPv6 address must be in the IPv6 prefix pool.";
            uses live_ncs_specified-up;
            container prefix-address {
              description
                "Configure the IPv6 prefix address for an IPv6 prefix pool.";
              leaf prefix {
                type inet:ipv6-prefix;
                description
                  "Specify the address and length of an IPv6 prefix, not support modify. The prefix address must be calculated based on the prefix length.";
              }
            }
            uses live_ncs_vpn-instance;
            container exclude-ipv6-addresss {
              // NCS drop when statement
              description
                "Configure IPv6 addresses to prevent it from being allocated to users. The start IPv6 address must be smaller than or equal to the end IPv6 address.";
              uses live_ncs_exclude-ipv6-address;
            }
            uses live_ncs_lifetime-config;
            uses live_ncs_reserved-ipv6;
            uses live_ncs_frame-ipv6-lease;
            uses live_ncs_ipv6-constant-index;
          }
          container delegation {
            // NCS drop when statement
            // NCS drop must statement
            description
              "Configure a delegation IPv6 prefix pool. The specified IPv6 address must be in the IPv6 prefix pool.";
            uses live_ncs_specified-up;
            container prefix-address {
              description
                "Configure the IPv6 prefix address for an IPv6 prefix pool.";
              leaf prefix {
                type inet:ipv6-prefix;
                description
                  "Specify the address and length of an IPv6 prefix, not support modify. The prefix address must be calculated based on the prefix length.";
              }
              leaf prefix-length {
                // NCS drop when statement
                type uint8 {
                  range "1..128";
                }
                // NCS drop default statement
                description
                  "Specify the length of the IPv6 prefix assigned by the delegating router to the requesting router. Not support modify or delete.
                   The delegating prefix length must be longer than or the same as IPv6 prefix length.";
              }
            }
            uses live_ncs_slaac-unshare-only;
            uses live_ncs_pd-unshare-only;
            container dhcpv6-unshare-only {
              // NCS drop when statement
              description
                "Configure an IPv6 prefix pool to assign only IPv6 addresses not prefixes to users.";
              uses live_ncs_dhcpv6-unshare-only;
            }
            uses live_ncs_vpn-instance;
            container exclude-ipv6-addresss {
              // NCS drop when statement
              description
                "Configure IPv6 addresses to prevent it from being allocated to users.";
              uses live_ncs_exclude-ipv6-address;
            }
            uses live_ncs_lifetime-config;
            uses live_ncs_reserved-ipv6;
            uses live_ncs_frame-ipv6-lease;
            uses live_ncs_ipv6-constant-index;
          }
          container remote {
            // NCS drop when statement
            // NCS drop must statement
            description
              "Configure a remote IPv6 prefix pool.";
            uses live_ncs_specified-up;
            uses live_ncs_vpn-instance;
            container link-address {
              description
                "Configure a link address.";
              leaf ipv6-address {
                type inet:ipv6-prefix;
                description
                  "Specify a global unicast address or a site-local unicast address.";
              }
            }
            container dhcpv6-only {
              description
                "Configure a remote prefix pool for only DHCPv6 prefix or address allocation.";
              leaf enable {
                type empty;
                description
                  "Specify a remote prefix pool for only DHCPv6 prefix or address allocation.";
              }
            }
            container lease-management {
              description
                "Configure the lease management function for remote IPv6 prefix pool.";
              leaf enable {
                type boolean;
                // NCS drop default statement
                description
                  "Enable/disable the lease management function for remote IPv6 prefix pool.";
              }
            }
            container reserved-ipv6 {
              description
                "Configure a reservation type for the prefix pool.";
              leaf reserved-type {
                type live_ncs_reserved-type;
                description
                  "Reservation type for the IPv6 prefix or address, after the reserved type of an IPv6 prefix or address is set to mac, one-to-many mapping between one MAC address and multiple sessions cannot be enabled.";
              }
            }
            uses live_ncs_lock;
            uses live_ncs_slaac-unshare-only;
            uses live_ncs_ipv6-constant-index;
          }
          container dynamic {
            // NCS drop when statement
            description
              "Configure a dynamic IPv6 prefix pool.";
            container prefix-length {
              // NCS drop must statement
              // NCS drop must statement
              // NCS drop must statement
              description
                "Configure the share mode for a dynamic IPv6 prefix pool to configure the prefix length.";
              choice share-mode {
                description
                  "Select the share mode for a dynamic IPv6 prefix pool to configure the prefix length.";
                case shared {
                  description
                    "Configure initial and subsequent prefix lengths for a shared dynamic prefix pool.";
                  leaf shared-initial {
                    type uint8 {
                      range "3..127";
                    }
                    // NCS drop mandatory statement
                    description
                      "Configure the initial prefix length.";
                  }
                  leaf shared-extend {
                    type uint8 {
                      range "3..127";
                    }
                    ext:dynamic-default {
                      ext:default-value "../shared-initial" {
                        description
                          "The default value is equal to initial length.";
                      }
                    }
                    description
                      "Configure the subsequent prefix length.";
                  }
                }
                case unshared {
                  description
                    "Configure initial, subsequent and delegating prefix lengths for a unshared dynamic prefix pool.";
                  leaf unshared-initial {
                    type uint8 {
                      range "3..127";
                    }
                    // NCS drop mandatory statement
                    description
                      "Configure the initial prefix length.";
                  }
                  leaf unshared-extend {
                    type uint8 {
                      range "3..127";
                    }
                    ext:dynamic-default {
                      ext:default-value "../unshared-initial" {
                        description
                          "The default value is equal to initial length.";
                      }
                    }
                    description
                      "Configure the subsequent prefix length.";
                  }
                  leaf unshared-delegating {
                    type uint8 {
                      range "3..127";
                    }
                    // NCS drop default statement
                    description
                      "Configure the delegating prefix length.";
                  }
                  container slaac-unshare-only {
                    description
                      "Configure the prefix pool to allocate IP addresses by using only the unshared-mode stateless address autoconfiguration (SLAAC) protocol.";
                    leaf enable {
                      type boolean;
                      // NCS drop default statement
                      description
                        "Enable/disable the prefix pool to allocate IP addresses by using only the unshared-mode stateless address autoconfiguration (SLAAC) protocol.";
                    }
                  }
                  container pd-unshare-only {
                    description
                      "Configure the prefix pool to allocate IP addresses by using only the unshared-mode stateless address autoconfiguration (DHCPv6 IA_PD) protocol.";
                    leaf enable {
                      type boolean;
                      // NCS drop default statement
                      description
                        "Enable/disable the prefix pool to allocate IP addresses by using only the unshared-mode stateless address autoconfiguration (DHCPv6 IA_PD) protocol.";
                    }
                  }
                }
              }
            }
            uses live_ncs_vpn-instance;
            uses live_ncs_ipv6-constant-index;
          }
        }
      }
      container ipv6-pools {
        description
          "List of IPv6 address pools.";
        list ipv6-pool {
          key "name";
          // NCS drop max-elements statement
          description
            "Configure an IPv6 address pool.";
          leaf name {
            ext:case-sensitivity "lower-only";
            type string {
              length "1..32";
              pattern '[a-z0-9._-]{1,32}';
            }
            // NCS drop must statement
            description
              "Specify the name of an IPv6 address pool.";
          }
          leaf type {
            ext:operation-exclude "update";
            type live_ncs_pool-type;
            // NCS drop mandatory statement
            description
              "Specify the type of the IPv6 address pool, and the type cannot be modified.";
          }
          leaf rui-slave {
            ext:operation-exclude "update|delete";
            // NCS drop when statement
            type boolean;
            // NCS drop default statement
            description
              "Enable/disable a hybrid IP address pool that can be used as a local address pool or remote address pool or delegation address pool. The rui-slave cannot be modified.";
          }
          container local {
            // NCS drop when statement
            description
              "Configure a local IPv6 address pool.";
            container bind-prefix {
              description
                "Configure binding an IPv6 prefix pool to an IPv6 address pool.";
              leaf prefix-name {
                type leafref {
                  path "/ncs:devices/ncs:device/ncs:live-status/bras-ipv6-address-manage:bras-ipv6-address-manage/bras-ipv6-address-manage:ipv6-prefixs/bras-ipv6-address-manage:ipv6-prefix/bras-ipv6-address-manage:name" {
                    tailf:xpath-root 3;
                  }
                }
                // NCS drop must statement
                description
                  "Bind an IPv6 prefix pool to an IPv6 address pool.";
              }
            }
            uses live_ncs_remote-not-support;
            uses live_ncs_rapid-commit-config;
            container weight {
              // NCS drop when statement
              description
                "Configure a weight for an IPv6 address pool.";
              uses live_ncs_weight;
            }
            uses live_ncs_ipv6-pool-comm;
            uses live_ncs_aftr-config;
            container export-host-route {
              description
                "Configure a device to advertise host routes in a remote address pool.";
              leaf ipv6-address {
                type empty;
                description
                  "Advertise IPv6 routes.";
              }
            }
            uses live_ncs_ipv6-constant-index;
          }
          container delegation {
            // NCS drop when statement
            description
              "Configure a delegation IPv6 address pool.";
            container bind-prefix {
              description
                "Configure binding an IPv6 prefix pool to an IPv6 address pool.";
              leaf prefix-name {
                type leafref {
                  path "/ncs:devices/ncs:device/ncs:live-status/bras-ipv6-address-manage:bras-ipv6-address-manage/bras-ipv6-address-manage:ipv6-prefixs/bras-ipv6-address-manage:ipv6-prefix/bras-ipv6-address-manage:name" {
                    tailf:xpath-root 3;
                  }
                }
                // NCS drop must statement
                description
                  "Bind an IPv6 prefix pool to an IPv6 address pool.";
              }
            }
            uses live_ncs_remote-not-support;
            uses live_ncs_rapid-commit-config;
            container weight {
              // NCS drop when statement
              description
                "Configure a weight for an IPv6 address pool.";
              uses live_ncs_weight;
            }
            uses live_ncs_ipv6-pool-comm;
            uses live_ncs_aftr-config;
            uses live_ncs_export-host-route;
            uses live_ncs_ipv6-constant-index;
          }
          container remote {
            // NCS drop when statement
            description
              "Configure a remote IPv6 address pool.";
            container bind-prefix {
              description
                "Configure binding an IPv6 prefix pool to an IPv6 address pool.";
              leaf prefix-name {
                type leafref {
                  path "/ncs:devices/ncs:device/ncs:live-status/bras-ipv6-address-manage:bras-ipv6-address-manage/bras-ipv6-address-manage:ipv6-prefixs/bras-ipv6-address-manage:ipv6-prefix/bras-ipv6-address-manage:name" {
                    tailf:xpath-root 3;
                  }
                }
                // NCS drop must statement
                description
                  "Bind an IPv6 prefix pool to an IPv6 address pool.";
              }
            }
            container weight {
              description
                "Configure a weight for an IPv6 address pool.";
              uses live_ncs_weight;
            }
            uses live_ncs_ipv6-pool-comm;
            uses live_ncs_export-host-route;
            uses live_ncs_ipv6-constant-index;
            container dhcpv6-server-group {
              description
                "Configure the DHCPv6 server group for this IPv6 address pool.";
              leaf name {
                type leafref {
                  path "/ncs:devices/ncs:device/ncs:live-status/bras-dhcpv6-server:bras-dhcpv6-server/bras-dhcpv6-server:dhcpv6-server-groups/bras-dhcpv6-server:dhcpv6-server-group/bras-dhcpv6-server:name" {
                    tailf:xpath-root 3;
                  }
                }
                description
                  "The DHCPv6 server group name.";
              }
            }
          }
          container relay {
            // NCS drop when statement
            description
              "Configure a relay IPv6 address pool.";
            container bind-prefix {
              description
                "Configure binding an IPv6 prefix pool to an IPv6 address pool.";
              leaf prefix-name {
                type leafref {
                  path "/ncs:devices/ncs:device/ncs:live-status/bras-ipv6-address-manage:bras-ipv6-address-manage/bras-ipv6-address-manage:ipv6-prefixs/bras-ipv6-address-manage:ipv6-prefix/bras-ipv6-address-manage:name" {
                    tailf:xpath-root 3;
                  }
                }
                // NCS drop must statement
                description
                  "Bind an IPv6 prefix pool to an IPv6 address pool.";
              }
            }
            uses live_ncs_remote-not-support;
            uses live_ncs_rapid-commit-config;
            uses live_ncs_ipv6-pool-comm;
            uses live_ncs_ipv6-constant-index;
          }
          container usage {
            description
              "Display the usage statistics for IPv6 address pool.";
            leaf vpn-instance {
              type leafref {
                path "/ncs:devices/ncs:device/ncs:live-status/ni:network-instance/ni:instances/ni:instance/ni:name" {
                  tailf:xpath-root 3;
                }
              }
              description
                "Specify the VPN instance name.";
              ext:support-filter "true";
            }
            uses live_ncs_pool-usage;
          }
          container statistic {
            description
              "Display the IPv6 address or prefix statistics.";
            leaf pool-index {
              type int32 {
                range "0..16383";
              }
              description
                "The index of IPv6 pool.";
            }
            uses live_ncs_pool-statistics;
          }
        }
      }
      container ipv6-unr-route-tag {
        description
          "Configure route tags for IPv6 users.";
        leaf delegated-ipv6-prefix-tag {
          type uint32;
          // NCS drop default statement
          description
            "Set a route tag for PD IPv6 addresses delivered by a RADIUS server.";
        }
        leaf delegated-pool-tag {
          type uint32;
          // NCS drop default statement
          description
            "Set a route tag for delegation IPv6 address pools.";
        }
        leaf framed-ipv6-address-tag {
          type uint32;
          // NCS drop default statement
          description
            "Set a route tag for IA_NA IPv6 addresses delivered by a RADIUS server.";
        }
        leaf framed-ipv6-prefix-tag {
          type uint32;
          // NCS drop default statement
          description
            "Set a route tag for ND IPv6 addresses delivered by a RADIUS server.";
        }
        leaf framed-ipv6-route-tag {
          type uint32;
          // NCS drop default statement
          description
            "Set a route tag for IPv6 route addresses delivered by a RADIUS server.";
        }
        leaf local-pool-tag {
          type uint32;
          // NCS drop default statement
          description
            "Set a route tag for local IPv6 address pools.";
        }
        leaf relay-pool-tag {
          type uint32;
          // NCS drop default statement
          description
            "Set a route tag for relay IPv6 address pools.";
        }
        leaf remote-pool-tag {
          type uint32;
          // NCS drop default statement
          description
            "Set a route tag for remote IPv6 address pools.";
        }
      }
      container address-assign-eui-64 {
        description
          "Configure an interface ID to be in the standard EUI-64 format when DHCPv6 is used to allocate addresses.";
        leaf enable {
          type boolean;
          // NCS drop default statement
          description
            "Enable/disable an interface ID to be in the standard EUI-64 format when DHCPv6 is used to allocate addresses.";
        }
      }
      container statistic-include-shared-user {
        description
          "Configure the IPv6 address pool statistics to include statistics about users sharing the prefix pool.";
        leaf enable {
          type boolean;
          // NCS drop default statement
          description
            "Enable/disable the IPv6 address pool statistics to include statistics about users sharing the prefix pool.";
        }
      }
      container pool-select-algorithm {
        // NCS drop must statement
        description
          "Configure a device to assign addresses from IPv6 remote address pools based on weights of the address pools.";
        leaf remote-loading-share {
          type boolean;
          // NCS drop default statement
          description
            "Enable/disable a device to assign addresses from IPv6 remote address pools based on weights of the address pools.";
        }
        leaf remote-round-robin {
          type boolean;
          // NCS drop default statement
          description
            "Enable/disable the round robin algorithm for remote IPv6 address pool.";
        }
        leaf local-round-robin {
          type boolean;
          // NCS drop default statement
          description
            "Enable/disable the round robin algorithm for local IPv6 address pool.";
        }
      }
      container auto-block {
        description
          "Configure automatic isolation of IPv6 prefix pools.";
        leaf enable {
          type boolean;
          // NCS drop default statement
          description
            "Enable/disable automatic isolation of IPv6 prefix pools.";
        }
        leaf slave-switch {
          type boolean;
          // NCS drop default statement
          description
            "Enable/disable the switchover function for IPv6 prefix pool isolation.";
        }
      }
      container statistics-by-domains {
        description
          "List of domain-based statistics.";
        list statistics-by-domain {
          key "domain-name";
          description
            "Domain-based statistics.";
          leaf domain-name {
            type leafref {
              path "/ncs:devices/ncs:device/ncs:live-status/aaa:aaa/aaa:domains/aaa:domain/aaa:name" {
                tailf:xpath-root 3;
              }
            }
            description
              "Specify the name of a domain.";
          }
          container pool-usage {
            description
              "Display the statistics for IPv6 address pool usage.";
            uses live_ncs_pool-usage;
          }
          container cu-pool-usages {
            description
              "List of statistics for IPv6 addresses pool usage.";
            list cu-pool-usage {
              key "up-id";
              description
                "Display the statistics for IPv6 address pool usage.";
              leaf up-id {
                type uint16 {
                  range "1024..2023 | 2048..3047 | 3072..4071 | 4096..5095";
                }
                // NCS drop must statement
                description
                  "The ID of a vBRAS-UP.";
              }
              uses live_ncs_pool-usage;
            }
          }
          container usage-threshold {
            description
              "Display the statistics for domains whose IPv6 address pool or prefix pool usage exceeds a specified threshold.";
            leaf threshold-type {
              type live_ncs_threshold-type;
              description
                "Include upper-threshold and lower-threshold.";
              ext:support-filter "true";
            }
            uses live_ncs_pool-usage;
          }
        }
      }
      container pool-statistics {
        description
          "Statistics of IPv6 pool usage.";
        leaf statistical-unit {
          type live_ncs_pool-usage-type;
          // NCS drop default statement
          description
            "Statistical unit.";
        }
        uses live_ncs_pool-usage;
      }
      container statistics-by-vpn-instance {
        description
          "Display the statistics for IPv6 address pools bound by the vpn-instance.";
        container statistics {
          description
            "List of statistics for IPv6 address pools bound by the vpn-instance.";
          list statistic {
            key "vpn-instance";
            description
              "Display the statistics for IPv6 address pools bound by the vpn-instance.";
            leaf vpn-instance {
              type leafref {
                path "/ncs:devices/ncs:device/ncs:live-status/ni:network-instance/ni:instances/ni:instance/ni:name" {
                  tailf:xpath-root 3;
                }
              }
              description
                "Specify the VPN instance name.";
            }
            container usage {
              description
                "Display the usage statistics for IPv6 address pools bound by vpn-instance.";
              uses live_ncs_pool-usage;
            }
            container usage-warning-threshold {
              description
                "Display the statistics for address pool usage based on a specified VPN instance.";
              leaf total-number {
                type int32;
                description
                  "Total number of IP addresses.";
              }
              leaf used-number {
                type int32;
                description
                  "Number of used IP addresses.";
              }
              leaf idle-number {
                type int32;
                description
                  "Number of idle IP addresses.";
              }
              leaf conflict-number {
                type int32;
                description
                  "Number of conflicting IP addresses.";
              }
              leaf exclude-number {
                type int32;
                description
                  "Number of excluded IP addresses.";
              }
              leaf used-ratio {
                type int32;
                description
                  "IP address usage.";
              }
            }
          }
        }
        container total-usage {
          description
            "Display the usage statistics for IPv6 address pools which are for all vpn-instance.";
          uses live_ncs_pool-usage;
        }
      }
      container global-statistic {
        description
          "Statistics of IPv6 pool.";
        leaf total-pool-number {
          type int32;
          description
            "Number of configured IPv6 address pools.";
        }
        uses live_ncs_pool-statistics;
      }
    }
  }
  augment "/ncs:devices/ncs:template/ncs:ned-id/ncs:config" {
    container bras-ipv6-address-manage {
      description
        "Configure the IPv6 repfix pool and IPv6 address pool.";
      container ipv6-prefixs {
        description
          "List of IPv6 prefix pools.";
        list ipv6-prefix {
          // NCS patched for predictable order
          ordered-by user;
          key "name";
          // NCS drop max-elements statement
          description
            "Configure an IPv6 prefix pool.";
          leaf name {
            ext:case-sensitivity "lower-only";
            type string;
            // NCS drop must statement
            description
              "Specify the name of the IPv6 prefix pool to be created.";
          }
          leaf type {
            ext:operation-exclude "update";
            type ncs_template_prefix-type;
            // NCS drop mandatory statement
            description
              "Specify the type of the IPv6 prefix pool, and the type cannot be modified.";
          }
          container local {
            // NCS drop when statement
            description
              "Configure a local IPv6 prefix pool. The specified IPv6 address must be in the IPv6 prefix pool.";
            uses ncs_template_specified-up;
            container prefix-address {
              description
                "Configure the IPv6 prefix address for an IPv6 prefix pool.";
              leaf prefix {
                type string;
                description
                  "Specify the address and length of an IPv6 prefix, not support modify. The prefix address must be calculated based on the prefix length.";
              }
            }
            uses ncs_template_vpn-instance;
            container exclude-ipv6-addresss {
              // NCS drop when statement
              description
                "Configure IPv6 addresses to prevent it from being allocated to users. The start IPv6 address must be smaller than or equal to the end IPv6 address.";
              uses ncs_template_exclude-ipv6-address;
            }
            uses ncs_template_lifetime-config;
            uses ncs_template_reserved-ipv6;
            uses ncs_template_frame-ipv6-lease;
            uses ncs_template_ipv6-constant-index;
          }
          container delegation {
            // NCS drop when statement
            // NCS drop must statement
            description
              "Configure a delegation IPv6 prefix pool. The specified IPv6 address must be in the IPv6 prefix pool.";
            uses ncs_template_specified-up;
            container prefix-address {
              description
                "Configure the IPv6 prefix address for an IPv6 prefix pool.";
              leaf prefix {
                type string;
                description
                  "Specify the address and length of an IPv6 prefix, not support modify. The prefix address must be calculated based on the prefix length.";
              }
              leaf prefix-length {
                // NCS drop when statement
                type string;
                // NCS drop default statement
                description
                  "Specify the length of the IPv6 prefix assigned by the delegating router to the requesting router. Not support modify or delete.
                   The delegating prefix length must be longer than or the same as IPv6 prefix length.";
              }
            }
            uses ncs_template_slaac-unshare-only;
            uses ncs_template_pd-unshare-only;
            container dhcpv6-unshare-only {
              // NCS drop when statement
              description
                "Configure an IPv6 prefix pool to assign only IPv6 addresses not prefixes to users.";
              uses ncs_template_dhcpv6-unshare-only;
            }
            uses ncs_template_vpn-instance;
            container exclude-ipv6-addresss {
              // NCS drop when statement
              description
                "Configure IPv6 addresses to prevent it from being allocated to users.";
              uses ncs_template_exclude-ipv6-address;
            }
            uses ncs_template_lifetime-config;
            uses ncs_template_reserved-ipv6;
            uses ncs_template_frame-ipv6-lease;
            uses ncs_template_ipv6-constant-index;
          }
          container remote {
            // NCS drop when statement
            // NCS drop must statement
            description
              "Configure a remote IPv6 prefix pool.";
            uses ncs_template_specified-up;
            uses ncs_template_vpn-instance;
            container link-address {
              description
                "Configure a link address.";
              leaf ipv6-address {
                type string;
                description
                  "Specify a global unicast address or a site-local unicast address.";
              }
            }
            container dhcpv6-only {
              description
                "Configure a remote prefix pool for only DHCPv6 prefix or address allocation.";
              leaf enable {
                type empty;
                description
                  "Specify a remote prefix pool for only DHCPv6 prefix or address allocation.";
              }
            }
            container lease-management {
              description
                "Configure the lease management function for remote IPv6 prefix pool.";
              leaf enable {
                type string;
                // NCS drop default statement
                description
                  "Enable/disable the lease management function for remote IPv6 prefix pool.";
              }
            }
            container reserved-ipv6 {
              description
                "Configure a reservation type for the prefix pool.";
              leaf reserved-type {
                type ncs_template_reserved-type;
                description
                  "Reservation type for the IPv6 prefix or address, after the reserved type of an IPv6 prefix or address is set to mac, one-to-many mapping between one MAC address and multiple sessions cannot be enabled.";
              }
            }
            uses ncs_template_lock;
            uses ncs_template_slaac-unshare-only;
            uses ncs_template_ipv6-constant-index;
          }
          container dynamic {
            // NCS drop when statement
            description
              "Configure a dynamic IPv6 prefix pool.";
            container prefix-length {
              // NCS drop must statement
              // NCS drop must statement
              // NCS drop must statement
              description
                "Configure the share mode for a dynamic IPv6 prefix pool to configure the prefix length.";
              choice share-mode {
                description
                  "Select the share mode for a dynamic IPv6 prefix pool to configure the prefix length.";
                case shared {
                  description
                    "Configure initial and subsequent prefix lengths for a shared dynamic prefix pool.";
                  leaf shared-initial {
                    type string;
                    // NCS drop mandatory statement
                    description
                      "Configure the initial prefix length.";
                  }
                  leaf shared-extend {
                    type string;
                    ext:dynamic-default {
                      ext:default-value "../shared-initial" {
                        description
                          "The default value is equal to initial length.";
                      }
                    }
                    description
                      "Configure the subsequent prefix length.";
                  }
                }
                case unshared {
                  description
                    "Configure initial, subsequent and delegating prefix lengths for a unshared dynamic prefix pool.";
                  leaf unshared-initial {
                    type string;
                    // NCS drop mandatory statement
                    description
                      "Configure the initial prefix length.";
                  }
                  leaf unshared-extend {
                    type string;
                    ext:dynamic-default {
                      ext:default-value "../unshared-initial" {
                        description
                          "The default value is equal to initial length.";
                      }
                    }
                    description
                      "Configure the subsequent prefix length.";
                  }
                  leaf unshared-delegating {
                    type string;
                    // NCS drop default statement
                    description
                      "Configure the delegating prefix length.";
                  }
                  container slaac-unshare-only {
                    description
                      "Configure the prefix pool to allocate IP addresses by using only the unshared-mode stateless address autoconfiguration (SLAAC) protocol.";
                    leaf enable {
                      type string;
                      // NCS drop default statement
                      description
                        "Enable/disable the prefix pool to allocate IP addresses by using only the unshared-mode stateless address autoconfiguration (SLAAC) protocol.";
                    }
                  }
                  container pd-unshare-only {
                    description
                      "Configure the prefix pool to allocate IP addresses by using only the unshared-mode stateless address autoconfiguration (DHCPv6 IA_PD) protocol.";
                    leaf enable {
                      type string;
                      // NCS drop default statement
                      description
                        "Enable/disable the prefix pool to allocate IP addresses by using only the unshared-mode stateless address autoconfiguration (DHCPv6 IA_PD) protocol.";
                    }
                  }
                }
              }
            }
            uses ncs_template_vpn-instance;
            uses ncs_template_ipv6-constant-index;
          }
        }
      }
      container ipv6-pools {
        description
          "List of IPv6 address pools.";
        list ipv6-pool {
          // NCS patched for predictable order
          ordered-by user;
          key "name";
          // NCS drop max-elements statement
          description
            "Configure an IPv6 address pool.";
          leaf name {
            ext:case-sensitivity "lower-only";
            type string;
            // NCS drop must statement
            description
              "Specify the name of an IPv6 address pool.";
          }
          leaf type {
            ext:operation-exclude "update";
            type ncs_template_pool-type;
            // NCS drop mandatory statement
            description
              "Specify the type of the IPv6 address pool, and the type cannot be modified.";
          }
          leaf rui-slave {
            ext:operation-exclude "update|delete";
            // NCS drop when statement
            type string;
            // NCS drop default statement
            description
              "Enable/disable a hybrid IP address pool that can be used as a local address pool or remote address pool or delegation address pool. The rui-slave cannot be modified.";
          }
          container local {
            // NCS drop when statement
            description
              "Configure a local IPv6 address pool.";
            container bind-prefix {
              description
                "Configure binding an IPv6 prefix pool to an IPv6 address pool.";
              leaf prefix-name {
                type string;
                // NCS drop must statement
                description
                  "Bind an IPv6 prefix pool to an IPv6 address pool.";
              }
            }
            uses ncs_template_remote-not-support;
            uses ncs_template_rapid-commit-config;
            container weight {
              // NCS drop when statement
              description
                "Configure a weight for an IPv6 address pool.";
              uses ncs_template_weight;
            }
            uses ncs_template_ipv6-pool-comm;
            uses ncs_template_aftr-config;
            container export-host-route {
              description
                "Configure a device to advertise host routes in a remote address pool.";
              leaf ipv6-address {
                type empty;
                description
                  "Advertise IPv6 routes.";
              }
            }
            uses ncs_template_ipv6-constant-index;
          }
          container delegation {
            // NCS drop when statement
            description
              "Configure a delegation IPv6 address pool.";
            container bind-prefix {
              description
                "Configure binding an IPv6 prefix pool to an IPv6 address pool.";
              leaf prefix-name {
                type string;
                // NCS drop must statement
                description
                  "Bind an IPv6 prefix pool to an IPv6 address pool.";
              }
            }
            uses ncs_template_remote-not-support;
            uses ncs_template_rapid-commit-config;
            container weight {
              // NCS drop when statement
              description
                "Configure a weight for an IPv6 address pool.";
              uses ncs_template_weight;
            }
            uses ncs_template_ipv6-pool-comm;
            uses ncs_template_aftr-config;
            uses ncs_template_export-host-route;
            uses ncs_template_ipv6-constant-index;
          }
          container remote {
            // NCS drop when statement
            description
              "Configure a remote IPv6 address pool.";
            container bind-prefix {
              description
                "Configure binding an IPv6 prefix pool to an IPv6 address pool.";
              leaf prefix-name {
                type string;
                // NCS drop must statement
                description
                  "Bind an IPv6 prefix pool to an IPv6 address pool.";
              }
            }
            container weight {
              description
                "Configure a weight for an IPv6 address pool.";
              uses ncs_template_weight;
            }
            uses ncs_template_ipv6-pool-comm;
            uses ncs_template_export-host-route;
            uses ncs_template_ipv6-constant-index;
            container dhcpv6-server-group {
              description
                "Configure the DHCPv6 server group for this IPv6 address pool.";
              leaf name {
                type string;
                description
                  "The DHCPv6 server group name.";
              }
            }
          }
          container relay {
            // NCS drop when statement
            description
              "Configure a relay IPv6 address pool.";
            container bind-prefix {
              description
                "Configure binding an IPv6 prefix pool to an IPv6 address pool.";
              leaf prefix-name {
                type string;
                // NCS drop must statement
                description
                  "Bind an IPv6 prefix pool to an IPv6 address pool.";
              }
            }
            uses ncs_template_remote-not-support;
            uses ncs_template_rapid-commit-config;
            uses ncs_template_ipv6-pool-comm;
            uses ncs_template_ipv6-constant-index;
          }
          // NCS drop config false container usage
          // NCS drop config false container statistic
        }
      }
      container ipv6-unr-route-tag {
        description
          "Configure route tags for IPv6 users.";
        leaf delegated-ipv6-prefix-tag {
          type string;
          // NCS drop default statement
          description
            "Set a route tag for PD IPv6 addresses delivered by a RADIUS server.";
        }
        leaf delegated-pool-tag {
          type string;
          // NCS drop default statement
          description
            "Set a route tag for delegation IPv6 address pools.";
        }
        leaf framed-ipv6-address-tag {
          type string;
          // NCS drop default statement
          description
            "Set a route tag for IA_NA IPv6 addresses delivered by a RADIUS server.";
        }
        leaf framed-ipv6-prefix-tag {
          type string;
          // NCS drop default statement
          description
            "Set a route tag for ND IPv6 addresses delivered by a RADIUS server.";
        }
        leaf framed-ipv6-route-tag {
          type string;
          // NCS drop default statement
          description
            "Set a route tag for IPv6 route addresses delivered by a RADIUS server.";
        }
        leaf local-pool-tag {
          type string;
          // NCS drop default statement
          description
            "Set a route tag for local IPv6 address pools.";
        }
        leaf relay-pool-tag {
          type string;
          // NCS drop default statement
          description
            "Set a route tag for relay IPv6 address pools.";
        }
        leaf remote-pool-tag {
          type string;
          // NCS drop default statement
          description
            "Set a route tag for remote IPv6 address pools.";
        }
      }
      container address-assign-eui-64 {
        description
          "Configure an interface ID to be in the standard EUI-64 format when DHCPv6 is used to allocate addresses.";
        leaf enable {
          type string;
          // NCS drop default statement
          description
            "Enable/disable an interface ID to be in the standard EUI-64 format when DHCPv6 is used to allocate addresses.";
        }
      }
      container statistic-include-shared-user {
        description
          "Configure the IPv6 address pool statistics to include statistics about users sharing the prefix pool.";
        leaf enable {
          type string;
          // NCS drop default statement
          description
            "Enable/disable the IPv6 address pool statistics to include statistics about users sharing the prefix pool.";
        }
      }
      container pool-select-algorithm {
        // NCS drop must statement
        description
          "Configure a device to assign addresses from IPv6 remote address pools based on weights of the address pools.";
        leaf remote-loading-share {
          type string;
          // NCS drop default statement
          description
            "Enable/disable a device to assign addresses from IPv6 remote address pools based on weights of the address pools.";
        }
        leaf remote-round-robin {
          type string;
          // NCS drop default statement
          description
            "Enable/disable the round robin algorithm for remote IPv6 address pool.";
        }
        leaf local-round-robin {
          type string;
          // NCS drop default statement
          description
            "Enable/disable the round robin algorithm for local IPv6 address pool.";
        }
      }
      container auto-block {
        description
          "Configure automatic isolation of IPv6 prefix pools.";
        leaf enable {
          type string;
          // NCS drop default statement
          description
            "Enable/disable automatic isolation of IPv6 prefix pools.";
        }
        leaf slave-switch {
          type string;
          // NCS drop default statement
          description
            "Enable/disable the switchover function for IPv6 prefix pool isolation.";
        }
      }
      // NCS drop config false container 'statistics-by-domains'
      // NCS drop config false container 'pool-statistics'
      // NCS drop config false container 'statistics-by-vpn-instance'
      // NCS drop config false container 'global-statistic'
    }
  }
  augment "/ncs:devices/ncs:template/ncs:ned-id/ncs:config/ni:network-instance/ni:instances/ni:instance/l3vpn:afs/l3vpn:af/bras-ipv4-address-manage:bas" {
    description
      "The vpn instance who is enabled the IPv6 address family.";
    container ipv6-address-manage {
      // NCS drop when statement
      description
        "Configure the vpn instance who is enabled the IPv6 address family.";
      container warning-threshold {
        description
          "Configure the warning threshold of IPv6 pools who bound with the vpn instance.";
        leaf value {
          type string;
          // NCS drop default statement
          description
            "The percentage of IPv6 pools warning threshold.";
        }
      }
    }
  }
  augment "/ncs:devices/ncs:device/ncs:live-status/ni:network-instance/ni:instances/ni:instance/l3vpn:afs/l3vpn:af/bras-ipv4-address-manage:bas" {
    description
      "The vpn instance who is enabled the IPv6 address family.";
    container ipv6-address-manage {
      tailf:ncs-device-type "netconf";
      tailf:display-when "not(../../../../../../../../ncs:module) or ../../../../../../../../ncs:module[ncs:name='huawei-bras-ipv6-address-manage'] or (../../../../../../../../ncs:live-status-protocol[not(ncs:capability)]) or (../../../../../../../../ncs:live-status-protocol/ncs:capability/ncs:module[.='huawei-bras-ipv6-address-manage'])";
      // NCS drop when statement
      description
        "Configure the vpn instance who is enabled the IPv6 address family.";
      container warning-threshold {
        description
          "Configure the warning threshold of IPv6 pools who bound with the vpn instance.";
        leaf value {
          type uint8 {
            range "0..100";
          }
          // NCS drop default statement
          description
            "The percentage of IPv6 pools warning threshold.";
        }
      }
    }
  }
  augment "/ncs:devices/ncs:device/ncs:config/ni:network-instance/ni:instances/ni:instance/l3vpn:afs/l3vpn:af/bras-ipv4-address-manage:bas" {
    description
      "The vpn instance who is enabled the IPv6 address family.";
    container ipv6-address-manage {
      tailf:ncs-device-type "netconf";
      tailf:display-when "not(../../../../../../../../ncs:module) or ../../../../../../../../ncs:module[ncs:name='huawei-bras-ipv6-address-manage']";
      when "../../l3vpn:type='ipv6-unicast' and ../../../../ni:name!='_public_'" {
        tailf:xpath-root 3;
      }
      description
        "Configure the vpn instance who is enabled the IPv6 address family.";
      container warning-threshold {
        description
          "Configure the warning threshold of IPv6 pools who bound with the vpn instance.";
        leaf value {
          type uint8 {
            range "0..100";
          }
          default "80";
          description
            "The percentage of IPv6 pools warning threshold.";
        }
      }
    }
  }
}
