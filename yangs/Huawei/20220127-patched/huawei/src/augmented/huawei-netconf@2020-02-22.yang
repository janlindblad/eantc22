module huawei-netconf {
  // Generated by yanger -t ncs
  tailf:mount-id "huawei-nc-1.0:huawei-nc-1.0";
  tailf:ncs-device-type "netconf";

  namespace "urn:huawei:yang:huawei-netconf";
  prefix netconf;

  import huawei-extension {
    prefix ext;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "The NETCONF protocol defines a simple mechanism through which a network device can be managed, configuration data information can be retrieved, and new configuration data can be uploaded and manipulated.";

  revision 2020-02-22 {
    description
      "Add rpc to manage active YANG modules.";
    reference "Huawei private.";
  }
  revision 2019-05-05 {
    description
      "Init revision.";
    reference "Huawei private.";
  }
  ext:task-name "netconf";

  augment "/ncs:devices/ncs:device/ncs:rpc" {
    container rpc-activate-module {
      tailf:ncs-device-type "netconf";
      tailf:display-when "not(../../ncs:module) or ../../ncs:module[ncs:name='huawei-netconf']";
      tailf:action activate-module {
        tailf:actionpoint ncsproxy {
          tailf:internal;
        }
        description
          "Activate YANG modules.";
        ext:node-ref "/netconf/active-modules/active-module";
        input {
          leaf module-name {
            type string;
            mandatory true;
            description
              "The YANG module name to activate.";
          }
        }
      }
    }
  }
  augment "/ncs:devices/ncs:device-group/ncs:ned-id/ncs:rpc" {
    container rpc-activate-module {
      tailf:ncs-device-type "netconf";
      tailf:display-when "/ncs:devices/ncs:device[ncs:name=current()/../../../ncs:member]/ncs:module[ncs:name='huawei-netconf']";
      tailf:action activate-module {
        tailf:actionpoint ncsproxy {
          tailf:internal;
        }
        description
          "Activate YANG modules.";
        ext:node-ref "/netconf/active-modules/active-module";
        input {
          leaf module-name {
            type string;
            mandatory true;
            description
              "The YANG module name to activate.";
          }
        }
      }
    }
  }
  augment "/ncs:devices/ncs:device/ncs:config" {
    container netconf {
      tailf:ncs-device-type "netconf";
      tailf:display-when "not(../../ncs:module) or ../../ncs:module[ncs:name='huawei-netconf']";
      description
        "The NETCONF protocol defines a simple mechanism through which a network device can be managed, configuration data information can be retrieved, and new configuration data can be uploaded and manipulated.";
      container operation-log-switch {
        description
          "Configure to get RPC operation log.";
        leaf get {
          type boolean;
          default "false";
          description
            "Enable/disable to get operation log.";
        }
      }
      // NCS drop config false container 'active-modules'
    }
  }
  augment "/ncs:devices/ncs:device/ncs:live-status" {
    container netconf {
      tailf:ncs-device-type "netconf";
      tailf:display-when "not(../../ncs:module) or ../../ncs:module[ncs:name='huawei-netconf'] or (../../ncs:live-status-protocol[not(ncs:capability)]) or (../../ncs:live-status-protocol/ncs:capability/ncs:module[.='huawei-netconf'])";
      description
        "The NETCONF protocol defines a simple mechanism through which a network device can be managed, configuration data information can be retrieved, and new configuration data can be uploaded and manipulated.";
      container operation-log-switch {
        description
          "Configure to get RPC operation log.";
        leaf get {
          type boolean;
          // NCS drop default statement
          description
            "Enable/disable to get operation log.";
        }
      }
      container active-modules {
        description
          "List of active YANG modules.";
        list active-module {
          key "module-name";
          description
            "Statistics of active YANG module.";
          leaf module-name {
            type string {
              length "1..127";
            }
            description
              "Active YANG module name.";
          }
        }
      }
    }
  }
  augment "/ncs:devices/ncs:template/ncs:ned-id/ncs:config" {
    container netconf {
      description
        "The NETCONF protocol defines a simple mechanism through which a network device can be managed, configuration data information can be retrieved, and new configuration data can be uploaded and manipulated.";
      container operation-log-switch {
        description
          "Configure to get RPC operation log.";
        leaf get {
          type string;
          // NCS drop default statement
          description
            "Enable/disable to get operation log.";
        }
      }
      // NCS drop config false container 'active-modules'
    }
  }
}
