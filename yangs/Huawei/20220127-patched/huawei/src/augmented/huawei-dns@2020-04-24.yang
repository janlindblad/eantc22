module huawei-dns {
  // Generated by yanger -t ncs
  tailf:mount-id "huawei-nc-1.0:huawei-nc-1.0";
  tailf:ncs-device-type "netconf";

  yang-version 1;
  namespace "urn:huawei:yang:huawei-dns";
  prefix dns;

  import huawei-network-instance {
    prefix ni;
  }
  import huawei-l3vpn {
    prefix l3vpn;
  }
  import ietf-inet-types {
    prefix inet;
  }
  import huawei-extension {
    prefix ext;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "DNS management.";

  revision 2020-04-24 {
    description
      "Init revision.";
    reference "Huawei private.";
  }
  ext:task-name "dns";

  augment "/ncs:devices/ncs:device/ncs:config" {
    container dns {
      tailf:ncs-device-type "netconf";
      tailf:display-when "not(../../ncs:module) or ../../ncs:module[ncs:name='huawei-dns']";
      description
        "DNS management.";
      container global {
        description
          "Configure determine whether to enable DNS.";
        leaf enable {
          type boolean;
          default "false";
          description
            "Enable/disable DNS enable flag.";
        }
      }
      container src-ips {
        description
          "List of IPv4 Source Server.";
        list src-ip {
          key "vrf-name source-ipv4-addr";
          description
            "Configure IPv4 Source Server.";
          leaf vrf-name {
            type leafref {
              path "/ncs:devices/ncs:device/ncs:config/ni:network-instance/ni:instances/ni:instance/ni:name" {
                tailf:xpath-root 3;
              }
            }
            must "/ni:network-instance/ni:instances/ni:instance[ni:name = current()]/l3vpn:afs/l3vpn:af[l3vpn:type='ipv4-unicast']" {
              tailf:xpath-root 3;
            }
            description
              "VPN name.";
          }
          leaf source-ipv4-addr {
            type inet:ipv4-address-no-zone;
            description
              "IPv4 address of source server.";
          }
        }
      }
      container timeout {
        description
          "Configure specifies the amount of time to wait for a response to a DNS query. If the ip domain timeout command is not configured, system will wait 3 seconds for a response to a DNS query.";
        leaf interval-time {
          type uint32 {
            range "1..10";
          }
          units "s";
          default "5";
          description
            "The amount of time to wait for a response to a DNS query (s).";
        }
      }
      container try-number {
        description
          "Configure specifies the number of times to retry sending DNS queries. If the ip domain retry command is not configured, system will retry DNS queries twice.";
        leaf probe-count {
          type uint32 {
            range "1..3";
          }
          default "2";
          description
            "Specifies the number of times to retry sending DNS queries.";
        }
      }
      container domains {
        description
          "List of domain.";
        list domain {
          key "vpn name";
          description
            "Configure domain name.";
          leaf vpn {
            type leafref {
              path "/ncs:devices/ncs:device/ncs:config/ni:network-instance/ni:instances/ni:instance/ni:name" {
                tailf:xpath-root 3;
              }
            }
            must "/ni:network-instance/ni:instances/ni:instance[ni:name = current()]/l3vpn:afs/l3vpn:af[l3vpn:type='ipv4-unicast']" {
              tailf:xpath-root 3;
            }
            description
              "VPN name.";
          }
          leaf name {
            type string {
              length "1..63";
            }
            description
              "Domain name.";
          }
        }
      }
      container ipv4-servers {
        description
          "List of DNS IPv4 server.";
        list ipv4-server {
          key "vpn address";
          description
            "Configure DNS IPv4 server.";
          leaf vpn {
            type leafref {
              path "/ncs:devices/ncs:device/ncs:config/ni:network-instance/ni:instances/ni:instance/ni:name" {
                tailf:xpath-root 3;
              }
            }
            must "/ni:network-instance/ni:instances/ni:instance[ni:name = current()]/l3vpn:afs/l3vpn:af[l3vpn:type='ipv4-unicast']" {
              tailf:xpath-root 3;
            }
            description
              "VPN name.";
          }
          leaf address {
            type inet:ipv4-address-no-zone;
            description
              "Address of IPv4 server.";
          }
        }
      }
      // NCS drop config false container 'dns-pkt-stats'
    }
  }
  augment "/ncs:devices/ncs:device/ncs:live-status" {
    container dns {
      tailf:ncs-device-type "netconf";
      tailf:display-when "not(../../ncs:module) or ../../ncs:module[ncs:name='huawei-dns'] or (../../ncs:live-status-protocol[not(ncs:capability)]) or (../../ncs:live-status-protocol/ncs:capability/ncs:module[.='huawei-dns'])";
      description
        "DNS management.";
      container global {
        description
          "Configure determine whether to enable DNS.";
        leaf enable {
          type boolean;
          // NCS drop default statement
          description
            "Enable/disable DNS enable flag.";
        }
      }
      container src-ips {
        description
          "List of IPv4 Source Server.";
        list src-ip {
          key "vrf-name source-ipv4-addr";
          description
            "Configure IPv4 Source Server.";
          leaf vrf-name {
            type leafref {
              path "/ncs:devices/ncs:device/ncs:live-status/ni:network-instance/ni:instances/ni:instance/ni:name" {
                tailf:xpath-root 3;
              }
            }
            // NCS drop must statement
            description
              "VPN name.";
          }
          leaf source-ipv4-addr {
            type inet:ipv4-address-no-zone;
            description
              "IPv4 address of source server.";
          }
        }
      }
      container timeout {
        description
          "Configure specifies the amount of time to wait for a response to a DNS query. If the ip domain timeout command is not configured, system will wait 3 seconds for a response to a DNS query.";
        leaf interval-time {
          type uint32 {
            range "1..10";
          }
          units "s";
          // NCS drop default statement
          description
            "The amount of time to wait for a response to a DNS query (s).";
        }
      }
      container try-number {
        description
          "Configure specifies the number of times to retry sending DNS queries. If the ip domain retry command is not configured, system will retry DNS queries twice.";
        leaf probe-count {
          type uint32 {
            range "1..3";
          }
          // NCS drop default statement
          description
            "Specifies the number of times to retry sending DNS queries.";
        }
      }
      container domains {
        description
          "List of domain.";
        list domain {
          key "vpn name";
          description
            "Configure domain name.";
          leaf vpn {
            type leafref {
              path "/ncs:devices/ncs:device/ncs:live-status/ni:network-instance/ni:instances/ni:instance/ni:name" {
                tailf:xpath-root 3;
              }
            }
            // NCS drop must statement
            description
              "VPN name.";
          }
          leaf name {
            type string {
              length "1..63";
            }
            description
              "Domain name.";
          }
        }
      }
      container ipv4-servers {
        description
          "List of DNS IPv4 server.";
        list ipv4-server {
          key "vpn address";
          description
            "Configure DNS IPv4 server.";
          leaf vpn {
            type leafref {
              path "/ncs:devices/ncs:device/ncs:live-status/ni:network-instance/ni:instances/ni:instance/ni:name" {
                tailf:xpath-root 3;
              }
            }
            // NCS drop must statement
            description
              "VPN name.";
          }
          leaf address {
            type inet:ipv4-address-no-zone;
            description
              "Address of IPv4 server.";
          }
        }
      }
      container dns-pkt-stats {
        description
          "Statistics of DNS packets.";
        leaf input-total {
          type uint32;
          description
            "Total count of received packets.";
        }
        leaf output-total {
          type uint32;
          description
            "Total count of sent packets.";
        }
        leaf drop-total {
          type uint32;
          description
            "Total count of discarded packets.";
        }
        leaf rr-a {
          type uint32;
          description
            "Count of received 'A' resource record types.";
        }
        leaf rr-aaaa {
          type uint32;
          description
            "Count of received 'AAAA' resource record types.";
        }
        leaf rr-ptr {
          type uint32;
          description
            "Count of received 'PTR' resource record types.";
        }
        leaf rr-cname {
          type uint32;
          description
            "Count of received 'CNAME' resource record types.";
        }
        leaf rr-unknown {
          type uint32;
          description
            "Count of received unknown resource record types.";
        }
        leaf standard {
          type uint32;
          description
            "Count of sent standard query packets.";
        }
        leaf question-a {
          type uint32;
          description
            "Count of sent 'A' query types.";
        }
        leaf question-aaaa {
          type uint32;
          description
            "Count of sent 'AAAA' query types.";
        }
        leaf question-ptr {
          type uint32;
          description
            "Count of sent 'PTR' query types.";
        }
        leaf rcv-tcp-total {
          type uint32;
          description
            "Total count of received TCP packets.";
        }
        leaf rcv-udp-total {
          type uint32;
          description
            "Total count of received UDP packets.";
        }
        leaf drop-tcp-total {
          type uint32;
          description
            "Total count of discarded TCP packets.";
        }
        leaf drop-udp-total {
          type uint32;
          description
            "Total count of discarded UDP packets.";
        }
        leaf drop-len {
          type uint32;
          description
            "Count of discarded length error packets.";
        }
        leaf drop-id {
          type uint32;
          description
            "Count of discarded ID error packets.";
        }
        leaf drop-server {
          type uint32;
          description
            "Count of discarded server error packets.";
        }
        leaf drop-code {
          type uint32;
          description
            "Count of discarded code error packets.";
        }
        leaf drop-tc {
          type uint32;
          description
            "Count of discarded truncated error packets.";
        }
        leaf drop-query-cnt {
          type uint32;
          description
            "Count of discarded query count error packets.";
        }
        leaf drop-answer-cnt {
          type uint32;
          description
            "Count of discarded answer count error packets.";
        }
        leaf drop-expand-name {
          type uint32;
          description
            "Count of discarded expand name error packets.";
        }
        leaf drop-class {
          type uint32;
          description
            "Count of discarded class error packets.";
        }
        leaf drop-other {
          type uint32;
          description
            "Count of discarded other error packets.";
        }
        leaf sent-udp-total {
          type uint32;
          description
            "Total count of sent UDP packets.";
        }
        leaf sent-tcp-total {
          type uint32;
          description
            "Total count of sent TCP packets.";
        }
      }
    }
  }
  augment "/ncs:devices/ncs:template/ncs:ned-id/ncs:config" {
    container dns {
      description
        "DNS management.";
      container global {
        description
          "Configure determine whether to enable DNS.";
        leaf enable {
          type string;
          // NCS drop default statement
          description
            "Enable/disable DNS enable flag.";
        }
      }
      container src-ips {
        description
          "List of IPv4 Source Server.";
        list src-ip {
          // NCS patched for predictable order
          ordered-by user;
          key "vrf-name source-ipv4-addr";
          description
            "Configure IPv4 Source Server.";
          leaf vrf-name {
            type string;
            // NCS drop must statement
            description
              "VPN name.";
          }
          leaf source-ipv4-addr {
            type string;
            description
              "IPv4 address of source server.";
          }
        }
      }
      container timeout {
        description
          "Configure specifies the amount of time to wait for a response to a DNS query. If the ip domain timeout command is not configured, system will wait 3 seconds for a response to a DNS query.";
        leaf interval-time {
          type string;
          units "s";
          // NCS drop default statement
          description
            "The amount of time to wait for a response to a DNS query (s).";
        }
      }
      container try-number {
        description
          "Configure specifies the number of times to retry sending DNS queries. If the ip domain retry command is not configured, system will retry DNS queries twice.";
        leaf probe-count {
          type string;
          // NCS drop default statement
          description
            "Specifies the number of times to retry sending DNS queries.";
        }
      }
      container domains {
        description
          "List of domain.";
        list domain {
          // NCS patched for predictable order
          ordered-by user;
          key "vpn name";
          description
            "Configure domain name.";
          leaf vpn {
            type string;
            // NCS drop must statement
            description
              "VPN name.";
          }
          leaf name {
            type string;
            description
              "Domain name.";
          }
        }
      }
      container ipv4-servers {
        description
          "List of DNS IPv4 server.";
        list ipv4-server {
          // NCS patched for predictable order
          ordered-by user;
          key "vpn address";
          description
            "Configure DNS IPv4 server.";
          leaf vpn {
            type string;
            // NCS drop must statement
            description
              "VPN name.";
          }
          leaf address {
            type string;
            description
              "Address of IPv4 server.";
          }
        }
      }
      // NCS drop config false container 'dns-pkt-stats'
    }
  }
}
