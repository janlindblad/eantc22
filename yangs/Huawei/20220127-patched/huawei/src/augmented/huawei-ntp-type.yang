submodule huawei-ntp-type {
  // Generated by yanger -t ncs
  tailf:mount-id "huawei-nc-1.0:huawei-nc-1.0";

  belongs-to huawei-ntp {
    prefix ntp;
  }

  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Network Time Protocol.";

  revision 2019-04-13 {
    description
      "Initial revision.";
    reference "Huawei private.";
  }

  typedef ncs_template_debug-type {
    type string;
    description
      "It is bit flag used for enabling and disabling ntp debug.";
  }

  typedef ncs_template_authentication-mode {
    type string;
    description
      "Used to identify which mode of authentication, Md5 or Hmac.";
  }

  typedef ncs_template_access-level {
    type string;
    description
      "NTP has 5 ACL level, it identify NTP acl level.";
  }

  typedef ncs_template_cast-mode {
    type string;
    description
      "It defines NTP server client mode.";
  }

  typedef ncs_template_port-version {
    type string;
    description
      "It identifies version of NTP.";
  }

  typedef ncs_template_peer-mode {
    type string;
    description
      "It defines NTP server or peer mode.";
  }

  typedef ncs_template_sync-state {
    type string;
    description
      "It defines NTP clock sync state.";
  }

  typedef ncs_template_clock-status {
    type string;
    description
      "It defines NTP clock sync status.";
  }

  typedef ncs_template_is-configured {
    type string;
    description
      "It tells weather current source is configured source or not.";
  }

  typedef ncs_template_addr-family-type {
    type string;
    description
      "It defines address family supported by NTP.";
  }

  typedef ncs_template_extend-addr-family-type {
    type string;
    description
      "It defines extended address family supported by NTP.";
  }

  typedef ncs_rpc_notif_debug-type {
    type string;
    description
      "It is bit flag used for enabling and disabling ntp debug.";
  }

  typedef ncs_rpc_notif_authentication-mode {
    type enumeration {
      enum "MD5" {
        value 1;
        description
          "The NTP authentication mode is MD5.";
      }
      enum "HMAC-SHA256" {
        value 2;
        description
          "The NTP authentication mode is HMAC-SHA256.";
      }
    }
    description
      "Used to identify which mode of authentication, Md5 or Hmac.";
  }

  typedef ncs_rpc_notif_access-level {
    type enumeration {
      enum "Peer" {
        value 1;
        description
          "Indicates the NTP Access Level is Peer. It sets the fully access authority. Both time request and control query can be performed on the local NTP service, and the local clock can be synchronized to the remote server.";
      }
      enum "Query" {
        value 2;
        description
          "Indicates the NTP Access Level is Query. It sets the maximum access limitation. Only control query can be performed on the local NTP service.";
      }
      enum "Server" {
        value 3;
        description
          "Indicates the NTP Access Level is Server. It enables the server access and query. Both time requests and control query can be performed on the local NTP service, but the local clock cannot be synchronized to the remote server.";
      }
      enum "Synchronization" {
        value 4;
        description
          "Indicates the NTP Access Level is Synchronization. It enables the server to access. Only time request can be performed on the local NTP service.";
      }
      enum "Limited" {
        value 5;
        description
          "Indicates the NTP Access Level is Limited.";
      }
    }
    description
      "NTP has 5 ACL level, it identify NTP acl level.";
  }

  typedef ncs_rpc_notif_cast-mode {
    type enumeration {
      enum "Client" {
        value 1;
        description
          "Indicates that the current mode is client.";
      }
      enum "Server" {
        value 2;
        description
          "Indicates that the current mode is server.";
      }
    }
    description
      "It defines NTP server client mode.";
  }

  typedef ncs_rpc_notif_port-version {
    type enumeration {
      enum "Version1" {
        value 1;
        description
          "Version1:";
      }
      enum "Version2" {
        value 2;
        description
          "Version2:";
      }
      enum "Version3" {
        value 3;
        description
          "Version3:";
      }
    }
    description
      "It identifies version of NTP.";
  }

  typedef ncs_rpc_notif_peer-mode {
    type enumeration {
      enum "Peer" {
        value 1;
        description
          "Indicates that the system's current configuration type is peer.";
      }
      enum "Server" {
        value 2;
        description
          "Indicates that the system's current configuration type is server.";
      }
    }
    description
      "It defines NTP server or peer mode.";
  }

  typedef ncs_rpc_notif_sync-state {
    type enumeration {
      enum "clock-is-not-set" {
        value 0;
        description
          "Indicates that the clock is not set.";
      }
      enum "frequency-is-set" {
        value 1;
        description
          "Indicates that clock frequency is obtained from the configuration.";
      }
      enum "time-is-set" {
        value 2;
        description
          "Indicates that the time is set.";
      }
      enum "mode-is-frequency" {
        value 3;
        description
          "Indicates that the clock is set but the frequency is not determined.";
      }
      enum "clock-is-synchronized" {
        value 4;
        description
          "Indicates that the clock is synchronized.";
      }
      enum "spike-is-detected." {
        value 5;
        description
          "Indicates that the spike is detected.";
      }
    }
    description
      "It defines NTP clock sync state.";
  }

  typedef ncs_rpc_notif_clock-status {
    type enumeration {
      enum "unsynchronized" {
        value 0;
        description
          "Indicates that the clock is unsynchronized.";
      }
      enum "synchronized" {
        value 1;
        description
          "Indicates that the clock is synchronized.";
      }
    }
    description
      "It defines NTP clock sync status.";
  }

  typedef ncs_rpc_notif_is-configured {
    type enumeration {
      enum "No" {
        value 0;
        description
          "NTP is not configured.";
      }
      enum "Yes" {
        value 1;
        description
          "NTP is configured.";
      }
    }
    description
      "It tells weather current source is configured source or not.";
  }

  typedef ncs_rpc_notif_addr-family-type {
    type enumeration {
      enum "IPv4" {
        value 1;
        description
          "IPv4 address family.";
      }
      enum "IPv6" {
        value 2;
        description
          "IPv6 address family.";
      }
    }
    description
      "It defines address family supported by NTP.";
  }

  typedef ncs_rpc_notif_extend-addr-family-type {
    type enumeration {
      enum "IPv4" {
        value 1;
        description
          "IPv4 address family.";
      }
      enum "IPv6" {
        value 2;
        description
          "IPv6 address family.";
      }
      enum "IPv4-AND-IPv6" {
        value 3;
        description
          "IPv4 and IPv6 address family.";
      }
    }
    description
      "It defines extended address family supported by NTP.";
  }

  typedef live_ncs_debug-type {
    type string;
    description
      "It is bit flag used for enabling and disabling ntp debug.";
  }

  typedef live_ncs_authentication-mode {
    type enumeration {
      enum "MD5" {
        value 1;
        description
          "The NTP authentication mode is MD5.";
      }
      enum "HMAC-SHA256" {
        value 2;
        description
          "The NTP authentication mode is HMAC-SHA256.";
      }
    }
    description
      "Used to identify which mode of authentication, Md5 or Hmac.";
  }

  typedef live_ncs_access-level {
    type enumeration {
      enum "Peer" {
        value 1;
        description
          "Indicates the NTP Access Level is Peer. It sets the fully access authority. Both time request and control query can be performed on the local NTP service, and the local clock can be synchronized to the remote server.";
      }
      enum "Query" {
        value 2;
        description
          "Indicates the NTP Access Level is Query. It sets the maximum access limitation. Only control query can be performed on the local NTP service.";
      }
      enum "Server" {
        value 3;
        description
          "Indicates the NTP Access Level is Server. It enables the server access and query. Both time requests and control query can be performed on the local NTP service, but the local clock cannot be synchronized to the remote server.";
      }
      enum "Synchronization" {
        value 4;
        description
          "Indicates the NTP Access Level is Synchronization. It enables the server to access. Only time request can be performed on the local NTP service.";
      }
      enum "Limited" {
        value 5;
        description
          "Indicates the NTP Access Level is Limited.";
      }
    }
    description
      "NTP has 5 ACL level, it identify NTP acl level.";
  }

  typedef live_ncs_cast-mode {
    type enumeration {
      enum "Client" {
        value 1;
        description
          "Indicates that the current mode is client.";
      }
      enum "Server" {
        value 2;
        description
          "Indicates that the current mode is server.";
      }
    }
    description
      "It defines NTP server client mode.";
  }

  typedef live_ncs_port-version {
    type enumeration {
      enum "Version1" {
        value 1;
        description
          "Version1:";
      }
      enum "Version2" {
        value 2;
        description
          "Version2:";
      }
      enum "Version3" {
        value 3;
        description
          "Version3:";
      }
    }
    description
      "It identifies version of NTP.";
  }

  typedef live_ncs_peer-mode {
    type enumeration {
      enum "Peer" {
        value 1;
        description
          "Indicates that the system's current configuration type is peer.";
      }
      enum "Server" {
        value 2;
        description
          "Indicates that the system's current configuration type is server.";
      }
    }
    description
      "It defines NTP server or peer mode.";
  }

  typedef live_ncs_sync-state {
    type enumeration {
      enum "clock-is-not-set" {
        value 0;
        description
          "Indicates that the clock is not set.";
      }
      enum "frequency-is-set" {
        value 1;
        description
          "Indicates that clock frequency is obtained from the configuration.";
      }
      enum "time-is-set" {
        value 2;
        description
          "Indicates that the time is set.";
      }
      enum "mode-is-frequency" {
        value 3;
        description
          "Indicates that the clock is set but the frequency is not determined.";
      }
      enum "clock-is-synchronized" {
        value 4;
        description
          "Indicates that the clock is synchronized.";
      }
      enum "spike-is-detected." {
        value 5;
        description
          "Indicates that the spike is detected.";
      }
    }
    description
      "It defines NTP clock sync state.";
  }

  typedef live_ncs_clock-status {
    type enumeration {
      enum "unsynchronized" {
        value 0;
        description
          "Indicates that the clock is unsynchronized.";
      }
      enum "synchronized" {
        value 1;
        description
          "Indicates that the clock is synchronized.";
      }
    }
    description
      "It defines NTP clock sync status.";
  }

  typedef live_ncs_is-configured {
    type enumeration {
      enum "No" {
        value 0;
        description
          "NTP is not configured.";
      }
      enum "Yes" {
        value 1;
        description
          "NTP is configured.";
      }
    }
    description
      "It tells weather current source is configured source or not.";
  }

  typedef live_ncs_addr-family-type {
    type enumeration {
      enum "IPv4" {
        value 1;
        description
          "IPv4 address family.";
      }
      enum "IPv6" {
        value 2;
        description
          "IPv6 address family.";
      }
    }
    description
      "It defines address family supported by NTP.";
  }

  typedef live_ncs_extend-addr-family-type {
    type enumeration {
      enum "IPv4" {
        value 1;
        description
          "IPv4 address family.";
      }
      enum "IPv6" {
        value 2;
        description
          "IPv6 address family.";
      }
      enum "IPv4-AND-IPv6" {
        value 3;
        description
          "IPv4 and IPv6 address family.";
      }
    }
    description
      "It defines extended address family supported by NTP.";
  }

  typedef debug-type {
    type string;
    description
      "It is bit flag used for enabling and disabling ntp debug.";
  }

  typedef authentication-mode {
    type enumeration {
      enum "MD5" {
        value 1;
        description
          "The NTP authentication mode is MD5.";
      }
      enum "HMAC-SHA256" {
        value 2;
        description
          "The NTP authentication mode is HMAC-SHA256.";
      }
    }
    description
      "Used to identify which mode of authentication, Md5 or Hmac.";
  }

  typedef access-level {
    type enumeration {
      enum "Peer" {
        value 1;
        description
          "Indicates the NTP Access Level is Peer. It sets the fully access authority. Both time request and control query can be performed on the local NTP service, and the local clock can be synchronized to the remote server.";
      }
      enum "Query" {
        value 2;
        description
          "Indicates the NTP Access Level is Query. It sets the maximum access limitation. Only control query can be performed on the local NTP service.";
      }
      enum "Server" {
        value 3;
        description
          "Indicates the NTP Access Level is Server. It enables the server access and query. Both time requests and control query can be performed on the local NTP service, but the local clock cannot be synchronized to the remote server.";
      }
      enum "Synchronization" {
        value 4;
        description
          "Indicates the NTP Access Level is Synchronization. It enables the server to access. Only time request can be performed on the local NTP service.";
      }
      enum "Limited" {
        value 5;
        description
          "Indicates the NTP Access Level is Limited.";
      }
    }
    description
      "NTP has 5 ACL level, it identify NTP acl level.";
  }

  typedef cast-mode {
    type enumeration {
      enum "Client" {
        value 1;
        description
          "Indicates that the current mode is client.";
      }
      enum "Server" {
        value 2;
        description
          "Indicates that the current mode is server.";
      }
    }
    description
      "It defines NTP server client mode.";
  }

  typedef port-version {
    type enumeration {
      enum "Version1" {
        value 1;
        description
          "Version1:";
      }
      enum "Version2" {
        value 2;
        description
          "Version2:";
      }
      enum "Version3" {
        value 3;
        description
          "Version3:";
      }
    }
    description
      "It identifies version of NTP.";
  }

  typedef peer-mode {
    type enumeration {
      enum "Peer" {
        value 1;
        description
          "Indicates that the system's current configuration type is peer.";
      }
      enum "Server" {
        value 2;
        description
          "Indicates that the system's current configuration type is server.";
      }
    }
    description
      "It defines NTP server or peer mode.";
  }

  typedef sync-state {
    type enumeration {
      enum "clock-is-not-set" {
        value 0;
        description
          "Indicates that the clock is not set.";
      }
      enum "frequency-is-set" {
        value 1;
        description
          "Indicates that clock frequency is obtained from the configuration.";
      }
      enum "time-is-set" {
        value 2;
        description
          "Indicates that the time is set.";
      }
      enum "mode-is-frequency" {
        value 3;
        description
          "Indicates that the clock is set but the frequency is not determined.";
      }
      enum "clock-is-synchronized" {
        value 4;
        description
          "Indicates that the clock is synchronized.";
      }
      enum "spike-is-detected." {
        value 5;
        description
          "Indicates that the spike is detected.";
      }
    }
    description
      "It defines NTP clock sync state.";
  }

  typedef clock-status {
    type enumeration {
      enum "unsynchronized" {
        value 0;
        description
          "Indicates that the clock is unsynchronized.";
      }
      enum "synchronized" {
        value 1;
        description
          "Indicates that the clock is synchronized.";
      }
    }
    description
      "It defines NTP clock sync status.";
  }

  typedef is-configured {
    type enumeration {
      enum "No" {
        value 0;
        description
          "NTP is not configured.";
      }
      enum "Yes" {
        value 1;
        description
          "NTP is configured.";
      }
    }
    description
      "It tells weather current source is configured source or not.";
  }

  typedef addr-family-type {
    type enumeration {
      enum "IPv4" {
        value 1;
        description
          "IPv4 address family.";
      }
      enum "IPv6" {
        value 2;
        description
          "IPv6 address family.";
      }
    }
    description
      "It defines address family supported by NTP.";
  }

  typedef extend-addr-family-type {
    type enumeration {
      enum "IPv4" {
        value 1;
        description
          "IPv4 address family.";
      }
      enum "IPv6" {
        value 2;
        description
          "IPv6 address family.";
      }
      enum "IPv4-AND-IPv6" {
        value 3;
        description
          "IPv4 and IPv6 address family.";
      }
    }
    description
      "It defines extended address family supported by NTP.";
  }
}
