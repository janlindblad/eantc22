submodule huawei-segment-routing-type {
  // Generated by yanger -t ncs
  tailf:mount-id "huawei-nc-1.0:huawei-nc-1.0";

  belongs-to huawei-segment-routing {
    prefix sr;
  }

  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Segment routing type defined file.";

  revision 2020-02-04 {
    description
      "Modify the description.";
    reference "Huawei private.";
  }
  revision 2019-04-04 {
    description
      "Initial revision.";
    reference "Huawei private.";
  }

  typedef ncs_template_bfd-type {
    type string;
    description
      "Segment routing bfd session type.";
  }

  typedef ncs_template_bfd-session-mode-type {
    type string;
    description
      "Segment routing type for bfd.";
  }

  typedef ncs_rpc_notif_bfd-type {
    type enumeration {
      enum "seamless-bfd" {
        value 1;
        description
          "The BFD type is seamless BFD.";
      }
      enum "bfd" {
        value 2;
        description
          "The BFD type is BFD.";
      }
    }
    description
      "Segment routing bfd session type.";
  }

  typedef ncs_rpc_notif_bfd-session-mode-type {
    type enumeration {
      enum "tunnel" {
        value 1;
        description
          "The type of session mode is tunnel.";
      }
    }
    description
      "Segment routing type for bfd.";
  }

  typedef live_ncs_bfd-type {
    type enumeration {
      enum "seamless-bfd" {
        value 1;
        description
          "The BFD type is seamless BFD.";
      }
      enum "bfd" {
        value 2;
        description
          "The BFD type is BFD.";
      }
    }
    description
      "Segment routing bfd session type.";
  }

  typedef live_ncs_bfd-session-mode-type {
    type enumeration {
      enum "tunnel" {
        value 1;
        description
          "The type of session mode is tunnel.";
      }
    }
    description
      "Segment routing type for bfd.";
  }

  typedef bfd-type {
    type enumeration {
      enum "seamless-bfd" {
        value 1;
        description
          "The BFD type is seamless BFD.";
      }
      enum "bfd" {
        value 2;
        description
          "The BFD type is BFD.";
      }
    }
    description
      "Segment routing bfd session type.";
  }

  typedef bfd-session-mode-type {
    type enumeration {
      enum "tunnel" {
        value 1;
        description
          "The type of session mode is tunnel.";
      }
    }
    description
      "Segment routing type for bfd.";
  }
}
