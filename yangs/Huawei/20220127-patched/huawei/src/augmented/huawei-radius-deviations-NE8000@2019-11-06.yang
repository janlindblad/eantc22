module huawei-radius-deviations-NE8000 {
  // Generated by yanger -t ncs
  tailf:mount-id "huawei-nc-1.0:huawei-nc-1.0";
  tailf:ncs-device-type "netconf";

  namespace "urn:huawei:yang:huawei-radius-deviations-NE8000";
  prefix radius-devs-NE8000;

  import huawei-radius {
    prefix radius;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "This module defines deviation statements for huawei-radius module.";

  revision 2019-11-06 {
    description
      "Initial revision.";
    reference "Huawei private.";
  }

  deviation "/ncs:devices/ncs:template/ncs:ned-id/ncs:config/radius:radius/radius:radius-server-groups/radius:radius-server-group/radius:authen-account-attribute/radius:cmcc-up-identifier" {
    deviate not-supported;
  }
  deviation "/ncs:devices/ncs:device/ncs:live-status/radius:radius/radius:radius-server-groups/radius:radius-server-group/radius:authen-account-attribute/radius:cmcc-up-identifier" {
    deviate not-supported;
  }
  deviation "/ncs:devices/ncs:device/ncs:config/radius:radius/radius:radius-server-groups/radius:radius-server-group/radius:authen-account-attribute/radius:cmcc-up-identifier" {
    deviate not-supported;
  }
  deviation "/ncs:devices/ncs:template/ncs:ned-id/ncs:config/radius:radius/radius:radius-server-groups/radius:radius-server-group/radius:authen-account-attribute/radius:cmcc-up-ip" {
    deviate not-supported;
  }
  deviation "/ncs:devices/ncs:device/ncs:live-status/radius:radius/radius:radius-server-groups/radius:radius-server-group/radius:authen-account-attribute/radius:cmcc-up-ip" {
    deviate not-supported;
  }
  deviation "/ncs:devices/ncs:device/ncs:config/radius:radius/radius:radius-server-groups/radius:radius-server-group/radius:authen-account-attribute/radius:cmcc-up-ip" {
    deviate not-supported;
  }
  deviation "/ncs:devices/ncs:template/ncs:ned-id/ncs:config/radius:radius/radius:radius-server-groups/radius:radius-server-group/radius:authen-account-attribute/radius:avpair-subscriber-up-identifier" {
    deviate not-supported;
  }
  deviation "/ncs:devices/ncs:device/ncs:live-status/radius:radius/radius:radius-server-groups/radius:radius-server-group/radius:authen-account-attribute/radius:avpair-subscriber-up-identifier" {
    deviate not-supported;
  }
  deviation "/ncs:devices/ncs:device/ncs:config/radius:radius/radius:radius-server-groups/radius:radius-server-group/radius:authen-account-attribute/radius:avpair-subscriber-up-identifier" {
    deviate not-supported;
  }
  deviation "/ncs:devices/ncs:template/ncs:ned-id/ncs:config/radius:radius/radius:radius-server-groups/radius:radius-server-group/radius:authen-account-attribute/radius:avpair-subscriber-up-ip" {
    deviate not-supported;
  }
  deviation "/ncs:devices/ncs:device/ncs:live-status/radius:radius/radius:radius-server-groups/radius:radius-server-group/radius:authen-account-attribute/radius:avpair-subscriber-up-ip" {
    deviate not-supported;
  }
  deviation "/ncs:devices/ncs:device/ncs:config/radius:radius/radius:radius-server-groups/radius:radius-server-group/radius:authen-account-attribute/radius:avpair-subscriber-up-ip" {
    deviate not-supported;
  }
  deviation "/ncs:devices/ncs:template/ncs:ned-id/ncs:config/radius:radius/radius:radius-server-groups/radius:radius-server-group/radius:bod-account-attribute" {
    deviate not-supported;
  }
  deviation "/ncs:devices/ncs:device/ncs:live-status/radius:radius/radius:radius-server-groups/radius:radius-server-group/radius:bod-account-attribute" {
    deviate not-supported;
  }
  deviation "/ncs:devices/ncs:device/ncs:config/radius:radius/radius:radius-server-groups/radius:radius-server-group/radius:bod-account-attribute" {
    deviate not-supported;
  }
}
