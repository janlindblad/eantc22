module openconfig-bgp {
  // Generated by yanger -t ncs
  tailf:mount-id "huawei-nc-1.0:huawei-nc-1.0";
  tailf:ncs-device-type "netconf";

  yang-version 1;
  namespace "http://openconfig.net/yang/bgp";
  prefix oc-bgp;

  import openconfig-extensions {
    prefix oc-ext;
  }
  import openconfig-rib-bgp {
    prefix oc-bgprib;
  }
  include openconfig-bgp-common;
  include openconfig-bgp-common-multiprotocol;
  include openconfig-bgp-common-structure;
  include openconfig-bgp-peer-group;
  include openconfig-bgp-neighbor;
  include openconfig-bgp-global;
  import tailf-common {
    prefix tailf;
  }
  import tailf-ncs {
    prefix ncs;
  }

  organization
    "OpenConfig working group";
  contact
    "OpenConfig working group
     netopenconfig@googlegroups.com";
  description
    "This module describes a YANG model for BGP protocol
     configuration.It is a limited subset of all of the configuration
     parameters available in the variety of vendor implementations,
     hence it is expected that it would be augmented with vendor-
     specific configuration data as needed. Additional modules or
     submodules to handle other aspects of BGP configuration,
     including policy, VRFs, VPNs, and additional address families
     are also expected.

     This model supports the following BGP configuration level
     hierarchy:

      BGP
        |
        +-> [ global BGP configuration ]
          +-> AFI / SAFI global
        +-> peer group
          +-> [ peer group config ]
          +-> AFI / SAFI [ per-AFI overrides ]
        +-> neighbor
          +-> [ neighbor config ]
          +-> [ optional pointer to peer-group ]
          +-> AFI / SAFI [ per-AFI overrides ]";
  oc-ext:openconfig-version "6.0.0";

  revision 2019-07-10 {
    description
      "Normalise timestamp units to nanoseconds.";
    reference "6.0.0";
  }
  revision 2019-05-28 {
    description
      "Clarify prefix counter descriptions, add received-pre-policy
       counter.";
    reference "5.2.0";
  }
  revision 2019-04-16 {
    description
      "Add BGP RIB to the top-level BGP container";
    reference "5.1.0";
  }
  revision 2018-11-21 {
    description
      "Add OpenConfig module metadata extensions.";
    reference "5.0.2";
  }
  revision 2018-08-20 {
    description
      "Correct description of AFI-SAFI enabled leaf.";
    reference "5.0.1";
  }
  revision 2018-04-11 {
    description
      "Correct naming of BGP maximum prefix warning percentage leaf.";
    reference "5.0.0";
  }
  revision 2018-03-20 {
    description
      "Added SR-TE policy SAFI";
    reference "4.1.0";
  }
  revision 2017-07-30 {
    description
      "Clarification of add-paths send-max leaf";
    reference "4.0.1";
  }
  revision 2017-07-10 {
    description
      "Add error notifications; moved add-paths config; add AS
       prepend policy features; removed unneeded config leaves";
    reference "4.0.0";
  }
  revision 2017-02-02 {
    description
      "Bugfix to remove remaining global-level policy data";
    reference "3.0.1";
  }
  revision 2017-01-26 {
    description
      "Add dynamic neighbor support, migrate to OpenConfig types";
    reference "3.0.0";
  }
  revision 2016-06-21 {
    description
      "OpenConfig BGP refactor";
    reference "2.1.1";
  }
  revision 2016-06-06 {
    description
      "OpenConfig public release";
    reference "2.1.0";
  }
  revision 2016-03-31 {
    description
      "OpenConfig public release";
    reference "2.0.1";
  }
  oc-ext:regexp-posix;
  oc-ext:catalog-organization "openconfig";
  oc-ext:origin "openconfig";

  grouping ncs_template_bgp-top {
    description
      "Top-level grouping for the BGP model data";
    container bgp {
      description
        "Top-level configuration and state for the BGP router";
      container global {
        description
          "Global configuration for the BGP router";
        uses ncs_template_bgp-global-base;
      }
      container neighbors {
        description
          "Configuration for BGP neighbors";
        uses ncs_template_bgp-neighbor-list;
      }
      container peer-groups {
        description
          "Configuration for BGP peer-groups";
        uses ncs_template_bgp-peer-group-list;
      }
      uses oc-bgprib:ncs_template_bgp-rib-top;
    }
  }

  grouping ncs_rpc_notif_bgp-top {
    description
      "Top-level grouping for the BGP model data";
    container bgp {
      description
        "Top-level configuration and state for the BGP router";
      container global {
        description
          "Global configuration for the BGP router";
        uses ncs_rpc_notif_bgp-global-base;
      }
      container neighbors {
        description
          "Configuration for BGP neighbors";
        uses ncs_rpc_notif_bgp-neighbor-list;
      }
      container peer-groups {
        description
          "Configuration for BGP peer-groups";
        uses ncs_rpc_notif_bgp-peer-group-list;
      }
      uses oc-bgprib:ncs_rpc_notif_bgp-rib-top;
    }
  }

  grouping live_ncs_bgp-top {
    description
      "Top-level grouping for the BGP model data";
    container bgp {
      description
        "Top-level configuration and state for the BGP router";
      container global {
        description
          "Global configuration for the BGP router";
        uses live_ncs_bgp-global-base;
      }
      container neighbors {
        description
          "Configuration for BGP neighbors";
        uses live_ncs_bgp-neighbor-list;
      }
      container peer-groups {
        description
          "Configuration for BGP peer-groups";
        uses live_ncs_bgp-peer-group-list;
      }
      uses oc-bgprib:live_ncs_bgp-rib-top;
    }
  }

  grouping bgp-top {
    description
      "Top-level grouping for the BGP model data";
    container bgp {
      description
        "Top-level configuration and state for the BGP router";
      container global {
        description
          "Global configuration for the BGP router";
        uses bgp-global-base;
      }
      container neighbors {
        description
          "Configuration for BGP neighbors";
        uses bgp-neighbor-list;
      }
      container peer-groups {
        description
          "Configuration for BGP peer-groups";
        uses bgp-peer-group-list;
      }
      uses oc-bgprib:bgp-rib-top;
    }
  }

  augment "/ncs:devices/ncs:device/ncs:config" {
    uses bgp-top {
      refine bgp {
        tailf:ncs-device-type "netconf";
        tailf:display-when "not(../../ncs:module) or ../../ncs:module[ncs:name='openconfig-bgp']";
      }
    }
  }
  augment "/ncs:devices/ncs:device/ncs:live-status" {
    uses live_ncs_bgp-top {
      refine bgp {
        tailf:ncs-device-type "netconf";
        tailf:display-when "not(../../ncs:module) or ../../ncs:module[ncs:name='openconfig-bgp'] or (../../ncs:live-status-protocol[not(ncs:capability)]) or (../../ncs:live-status-protocol/ncs:capability/ncs:module[.='openconfig-bgp'])";
      }
    }
  }
  augment "/ncs:devices/ncs:template/ncs:ned-id/ncs:config" {
    uses ncs_template_bgp-top;
  }
}
