module huawei-l2vpn-aps-notification {
  // Generated by yanger -t ncs
  tailf:mount-id "huawei-nc-1.0:huawei-nc-1.0";
  tailf:ncs-device-type "netconf";

  yang-version 1;
  namespace "urn:huawei:yang:huawei-l2vpn-aps-notification";
  prefix l2vpn-aps-notification;

  import ietf-inet-types {
    prefix inet;
  }
  import huawei-l2vpn {
    prefix l2vpn;
  }
  import huawei-extension {
    prefix ext;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Notification of L2VPN-APS.";

  revision 2020-03-20 {
    description
      "Initial revision.";
    reference "Huawei private.";
  }
  ext:task-name "l2vpn";

  augment "/ncs:devices/ncs:device/ncs:notifications/ncs:received-notifications/ncs:notification/ncs:data" {
    container aps-tunnel-not-support-resume {
      presence "";
      config false;
      description
        "The alarm that PW APS does not support the current public tunnel is resumed.";
      leaf vc-id {
        type uint32;
        description
          "Identifier of the layer 2 virtual circuit.";
      }
      leaf vc-type {
        type l2vpn:ncs_rpc_notif_encapsulation-type;
        description
          "Encapsulation type of a L2VPN instance.";
      }
      leaf peer-address {
        type inet:ipv4-address-no-zone;
        description
          "Peer IP address.";
      }
    }
  }
  augment "/ncs:devices/ncs:device/ncs:notifications/ncs:received-notifications/ncs:notification/ncs:data" {
    container aps-tunnel-not-support {
      presence "";
      config false;
      description
        "PW APS does not support the current public tunnel.";
      leaf vc-id {
        type uint32;
        description
          "Identifier of the layer 2 virtual circuit.";
      }
      leaf vc-type {
        type l2vpn:ncs_rpc_notif_encapsulation-type;
        description
          "Encapsulation type of a L2VPN instance.";
      }
      leaf peer-address {
        type inet:ipv4-address-no-zone;
        description
          "Peer IP address.";
      }
    }
  }
  augment "/ncs:devices/ncs:device/ncs:netconf-notifications/ncs:received-notifications/ncs:notification/ncs:data" {
    container aps-tunnel-not-support-resume {
      presence "";
      config false;
      description
        "The alarm that PW APS does not support the current public tunnel is resumed.";
      leaf vc-id {
        type uint32;
        description
          "Identifier of the layer 2 virtual circuit.";
      }
      leaf vc-type {
        type l2vpn:ncs_rpc_notif_encapsulation-type;
        description
          "Encapsulation type of a L2VPN instance.";
      }
      leaf peer-address {
        type inet:ipv4-address-no-zone;
        description
          "Peer IP address.";
      }
    }
  }
  augment "/ncs:devices/ncs:device/ncs:netconf-notifications/ncs:received-notifications/ncs:notification/ncs:data" {
    container aps-tunnel-not-support {
      presence "";
      config false;
      description
        "PW APS does not support the current public tunnel.";
      leaf vc-id {
        type uint32;
        description
          "Identifier of the layer 2 virtual circuit.";
      }
      leaf vc-type {
        type l2vpn:ncs_rpc_notif_encapsulation-type;
        description
          "Encapsulation type of a L2VPN instance.";
      }
      leaf peer-address {
        type inet:ipv4-address-no-zone;
        description
          "Peer IP address.";
      }
    }
  }
}
