module huawei-bier-deviations-NE8000 {
  // Generated by yanger -t ncs
  tailf:mount-id "huawei-nc-1.0:huawei-nc-1.0";
  tailf:ncs-device-type "netconf";

  yang-version 1;
  namespace "urn:huawei:yang:huawei-bier-deviations-NE8000";
  prefix bier-devs-NE8000;

  import huawei-bier {
    prefix bier;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Model for Bit Index Explicit Replication (BIER).";

  revision 2019-09-06 {
    description
      "Init revision.";
    reference "Huawei private.";
  }

  typedef ncs_template_underlay-protocol-type-deviations {
    type string;
    description
      "BIER underlay protocol type.";
  }

  typedef ncs_rpc_notif_underlay-protocol-type-deviations {
    type enumeration {
      enum "isis" {
        value 2;
        description
          "IS-IS.";
      }
    }
    description
      "BIER underlay protocol type.";
  }

  typedef live_ncs_underlay-protocol-type-deviations {
    type enumeration {
      enum "isis" {
        value 2;
        description
          "IS-IS.";
      }
    }
    description
      "BIER underlay protocol type.";
  }

  typedef underlay-protocol-type-deviations {
    type enumeration {
      enum "isis" {
        value 2;
        description
          "IS-IS.";
      }
    }
    description
      "BIER underlay protocol type.";
  }

  deviation "/ncs:devices/ncs:template/ncs:ned-id/ncs:config/bier:bier/bier:sub-domains/bier:sub-domain/bier:underlay-protocol" {
    deviate replace {
      type bier-devs-NE8000:ncs_template_underlay-protocol-type-deviations;
    }
  }
  deviation "/ncs:devices/ncs:device/ncs:live-status/bier:bier/bier:sub-domains/bier:sub-domain/bier:underlay-protocol" {
    deviate replace {
      type bier-devs-NE8000:live_ncs_underlay-protocol-type-deviations;
    }
  }
  deviation "/ncs:devices/ncs:device/ncs:config/bier:bier/bier:sub-domains/bier:sub-domain/bier:underlay-protocol" {
    deviate replace {
      type bier-devs-NE8000:underlay-protocol-type-deviations;
    }
  }
  deviation "/ncs:devices/ncs:device/ncs:live-status/bier:bier/bier:sub-domains/bier:sub-domain/bier:routings/bier:routing/bier:underlay-protocol" {
    deviate replace {
      type bier-devs-NE8000:live_ncs_underlay-protocol-type-deviations;
    }
  }
  deviation "/ncs:devices/ncs:device/ncs:live-status/bier:bier/bier:sub-domains/bier:sub-domain/bier:routings/bier:routing/bier:nexthops/bier:nexthop/bier:underlay-protocol" {
    deviate replace {
      type bier-devs-NE8000:live_ncs_underlay-protocol-type-deviations;
    }
  }
  deviation "/ncs:devices/ncs:device/ncs:live-status/bier:bier/bier:sub-domains/bier:sub-domain/bier:routings/bier:routing/bier:invalid-nexthops/bier:invalid-nexthop/bier:underlay-protocol" {
    deviate replace {
      type bier-devs-NE8000:live_ncs_underlay-protocol-type-deviations;
    }
  }
  deviation "/ncs:devices/ncs:device/ncs:live-status/bier:bier/bier:prefixs/bier:prefix/bier:underlay-protocol" {
    deviate replace {
      type bier-devs-NE8000:live_ncs_underlay-protocol-type-deviations;
    }
  }
  deviation "/ncs:devices/ncs:device/ncs:live-status/bier:bier/bier:sub-domains/bier:sub-domain/bier:routings/bier:routing/bier:invalid-nexthops/bier:invalid-nexthop/bier:igp-attribute/bier:ospf-protocol" {
    deviate not-supported;
  }
  deviation "/ncs:devices/ncs:device/ncs:live-status/bier:bier/bier:sub-domains/bier:sub-domain/bier:routings/bier:routing/bier:nexthops/bier:nexthop/bier:igp-attribute/bier:ospf-protocol" {
    deviate not-supported;
  }
  deviation "/ncs:devices/ncs:device/ncs:live-status/bier:bier/bier:sub-domains/bier:sub-domain/bier:routings/bier:routing/bier:prefix-igp-attribute/bier:ospf-protocol" {
    deviate not-supported;
  }
  deviation "/ncs:devices/ncs:device/ncs:live-status/bier:bier/bier:prefixs/bier:prefix/bier:igp-attribute/bier:ospf-protocol" {
    deviate not-supported;
  }
}
