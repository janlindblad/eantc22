module huawei-vlan {
  // Generated by yanger -t ncs
  tailf:mount-id "huawei-nc-1.0:huawei-nc-1.0";
  tailf:ncs-device-type "netconf";

  namespace "urn:huawei:yang:huawei-vlan";
  prefix vlan;

  import huawei-extension {
    prefix ext;
  }
  import huawei-pub-type {
    prefix pub-type;
  }
  import huawei-ifm {
    prefix ifm;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "VLAN management.";

  revision 2020-02-07 {
    description
      "Add leaf band-width-kbps.";
    reference "Huawei private.";
  }
  revision 2019-04-29 {
    description
      "Initial revision.";
    reference "Huawei private.";
  }
  ext:task-name "vlan";

  typedef ncs_template_vlan-id {
    type string;
    description
      "VLAN ID.";
  }

  typedef ncs_template_vlan-type {
    type string;
    description
      "VLAN type.";
  }

  typedef ncs_template_admin-status {
    type string;
    description
      "VLAN administrative.";
  }

  typedef ncs_template_oper-status {
    type string;
    description
      "State.";
  }

  typedef ncs_template_enable-status {
    type string;
    description
      "VLAN enable status.";
  }

  typedef ncs_template_access-type {
    type string;
    description
      "VLAN access type.";
  }

  typedef ncs_template_tag-mode {
    type string;
    description
      "VLAN tag mode.";
  }

  typedef ncs_rpc_notif_vlan-id {
    type uint16 {
      range "1..4094";
    }
    description
      "VLAN ID.";
  }

  typedef ncs_rpc_notif_vlan-type {
    type enumeration {
      enum "common" {
        value 1;
        description
          "VLAN type is common VLAN.";
      }
      enum "super" {
        value 2;
        description
          "VLAN type is super-VLAN.";
      }
      enum "sub" {
        value 3;
        description
          "VLAN type is sub-VLAN.";
      }
    }
    description
      "VLAN type.";
  }

  typedef ncs_rpc_notif_admin-status {
    type enumeration {
      enum "up" {
        value 1;
        description
          "Administratively up.";
      }
      enum "down" {
        value 0;
        description
          "Administratively down.";
      }
    }
    description
      "VLAN administrative.";
  }

  typedef ncs_rpc_notif_oper-status {
    type enumeration {
      enum "up" {
        value 1;
        description
          "Status is up.";
      }
      enum "down" {
        value 0;
        description
          "Status is down.";
      }
    }
    description
      "State.";
  }

  typedef ncs_rpc_notif_enable-status {
    type enumeration {
      enum "enable" {
        value 1;
        description
          "VLAN enable status is enable.";
      }
      enum "disable" {
        value 0;
        description
          "VLAN enable status is disable.";
      }
    }
    description
      "VLAN enable status.";
  }

  typedef ncs_rpc_notif_access-type {
    type enumeration {
      enum "access" {
        value 1;
        description
          "Access port that accepts packets without VLAN tags.";
      }
      enum "trunk" {
        value 2;
        description
          "Trunk port that accepts packets with VLAN tags.";
      }
      enum "hybrid" {
        value 3;
        description
          "Hybrid port that accepts packets with or without VLAN tags.";
      }
      enum "dot1qtunnel" {
        value 4;
        description
          "Dot1q tunnel interface that allows packet with double VLAN tags to pass.";
      }
    }
    description
      "VLAN access type.";
  }

  typedef ncs_rpc_notif_tag-mode {
    type enumeration {
      enum "untag" {
        value 0;
        description
          "VLAN tag mode is untagged.";
      }
      enum "tag" {
        value 1;
        description
          "VLAN tag mode is tagged.";
      }
    }
    description
      "VLAN tag mode.";
  }

  typedef live_ncs_vlan-id {
    type uint16 {
      range "1..4094";
    }
    description
      "VLAN ID.";
  }

  typedef live_ncs_vlan-type {
    type enumeration {
      enum "common" {
        value 1;
        description
          "VLAN type is common VLAN.";
      }
      enum "super" {
        value 2;
        description
          "VLAN type is super-VLAN.";
      }
      enum "sub" {
        value 3;
        description
          "VLAN type is sub-VLAN.";
      }
    }
    description
      "VLAN type.";
  }

  typedef live_ncs_admin-status {
    type enumeration {
      enum "up" {
        value 1;
        description
          "Administratively up.";
      }
      enum "down" {
        value 0;
        description
          "Administratively down.";
      }
    }
    description
      "VLAN administrative.";
  }

  typedef live_ncs_oper-status {
    type enumeration {
      enum "up" {
        value 1;
        description
          "Status is up.";
      }
      enum "down" {
        value 0;
        description
          "Status is down.";
      }
    }
    description
      "State.";
  }

  typedef live_ncs_enable-status {
    type enumeration {
      enum "enable" {
        value 1;
        description
          "VLAN enable status is enable.";
      }
      enum "disable" {
        value 0;
        description
          "VLAN enable status is disable.";
      }
    }
    description
      "VLAN enable status.";
  }

  typedef live_ncs_access-type {
    type enumeration {
      enum "access" {
        value 1;
        description
          "Access port that accepts packets without VLAN tags.";
      }
      enum "trunk" {
        value 2;
        description
          "Trunk port that accepts packets with VLAN tags.";
      }
      enum "hybrid" {
        value 3;
        description
          "Hybrid port that accepts packets with or without VLAN tags.";
      }
      enum "dot1qtunnel" {
        value 4;
        description
          "Dot1q tunnel interface that allows packet with double VLAN tags to pass.";
      }
    }
    description
      "VLAN access type.";
  }

  typedef live_ncs_tag-mode {
    type enumeration {
      enum "untag" {
        value 0;
        description
          "VLAN tag mode is untagged.";
      }
      enum "tag" {
        value 1;
        description
          "VLAN tag mode is tagged.";
      }
    }
    description
      "VLAN tag mode.";
  }

  typedef vlan-id {
    type uint16 {
      range "1..4094";
    }
    description
      "VLAN ID.";
  }

  typedef vlan-type {
    type enumeration {
      enum "common" {
        value 1;
        description
          "VLAN type is common VLAN.";
      }
      enum "super" {
        value 2;
        description
          "VLAN type is super-VLAN.";
      }
      enum "sub" {
        value 3;
        description
          "VLAN type is sub-VLAN.";
      }
    }
    description
      "VLAN type.";
  }

  typedef admin-status {
    type enumeration {
      enum "up" {
        value 1;
        description
          "Administratively up.";
      }
      enum "down" {
        value 0;
        description
          "Administratively down.";
      }
    }
    description
      "VLAN administrative.";
  }

  typedef oper-status {
    type enumeration {
      enum "up" {
        value 1;
        description
          "Status is up.";
      }
      enum "down" {
        value 0;
        description
          "Status is down.";
      }
    }
    description
      "State.";
  }

  typedef enable-status {
    type enumeration {
      enum "enable" {
        value 1;
        description
          "VLAN enable status is enable.";
      }
      enum "disable" {
        value 0;
        description
          "VLAN enable status is disable.";
      }
    }
    description
      "VLAN enable status.";
  }

  typedef access-type {
    type enumeration {
      enum "access" {
        value 1;
        description
          "Access port that accepts packets without VLAN tags.";
      }
      enum "trunk" {
        value 2;
        description
          "Trunk port that accepts packets with VLAN tags.";
      }
      enum "hybrid" {
        value 3;
        description
          "Hybrid port that accepts packets with or without VLAN tags.";
      }
      enum "dot1qtunnel" {
        value 4;
        description
          "Dot1q tunnel interface that allows packet with double VLAN tags to pass.";
      }
    }
    description
      "VLAN access type.";
  }

  typedef tag-mode {
    type enumeration {
      enum "untag" {
        value 0;
        description
          "VLAN tag mode is untagged.";
      }
      enum "tag" {
        value 1;
        description
          "VLAN tag mode is tagged.";
      }
    }
    description
      "VLAN tag mode.";
  }

  augment "/ncs:devices/ncs:device/ncs:config" {
    container vlan {
      tailf:ncs-device-type "netconf";
      tailf:display-when "not(../../ncs:module) or ../../ncs:module[ncs:name='huawei-vlan']";
      description
        "VLAN management.";
      container vlans {
        description
          "List of VLAN.";
        list vlan {
          key "id";
          max-elements 4094;
          description
            "Configure VLAN information.";
          leaf id {
            type vlan-id;
            description
              "VLAN ID.";
          }
          leaf name {
            type string {
              length "1..31";
            }
            description
              "VLAN name.";
          }
          leaf description {
            type string {
              length "1..80";
            }
            description
              "VLAN description.";
          }
          leaf type {
            type vlan-type;
            default "common";
            description
              "VLAN type, such as common VLANs, super-VLANs, and sub-VLANs.";
          }
          leaf admin-status {
            type admin-status;
            default "up";
            description
              "Administrative status of a VLAN.";
          }
          leaf broadcast-discard {
            type enable-status;
            default "disable";
            description
              "Discard broadcast packets.";
          }
          leaf unknown-multicast-discard {
            type enable-status;
            default "disable";
            description
              "Discard unknown multicast packets.";
          }
          leaf mac-learning {
            type enable-status;
            default "enable";
            description
              "Whether MAC address leaning is enabled in a VLAN.";
          }
          leaf statistic-enable {
            type enable-status;
            default "disable";
            description
              "Whether VLAN statistics collection is enabled.";
          }
          leaf statistic-discard {
            when "../statistic-enable='enable'" {
              tailf:xpath-root 3;
            }
            type enable-status;
            default "disable";
            description
              "Whether BUM discard statistics collection is enabled.";
          }
          leaf mac-aging-time {
            when "not(../type='super')" {
              tailf:xpath-root 3;
            }
            type uint32 {
              range "0|60..1000000";
            }
            units "s";
            description
              "MAC address aging time, 0 indicates that MAC addresses do not age.";
          }
          leaf super-vlan {
            when "../type='sub'" {
              tailf:xpath-root 3;
            }
            type leafref {
              path "/ncs:devices/ncs:device/ncs:config/vlan:vlan/vlan:vlans/vlan:vlan/vlan:id" {
                tailf:xpath-root 3;
              }
            }
            must "/vlan:vlan/vlan:vlans/vlan:vlan[id=current()]/vlan:type = 'super'" {
              tailf:xpath-root 3;
            }
            mandatory true;
            description
              "The corresponding super-VLAN ID when the VLAN is a sub-VLAN.";
          }
          container unkown-unicast-discard {
            description
              "Configure drop unknown unicast.";
            leaf discard {
              type enable-status;
              default "disable";
              description
                "Discard unknown unicast packets.";
            }
            leaf mac-learning-enable {
              when "../discard='enable'" {
                tailf:xpath-root 3;
              }
              type enable-status;
              default "disable";
              description
                "Enable unknown unicast MAC address learning.";
            }
          }
          container suppression {
            description
              "Configure traffic suppression.";
            leaf inbound {
              type enable-status;
              default "disable";
              description
                "Whether inbound suppression is enable.";
            }
            leaf outbound {
              type enable-status;
              default "disable";
              description
                "Whether outbound suppression is enable.";
            }
          }
          // NCS drop config false container 'member-ports'
        }
      }
      container instances {
        description
          "List of VLAN instances.";
        list instance {
          key "id";
          description
            "Configure instances.";
          leaf id {
            type uint16 {
              range "1..4094";
            }
            description
              "Instance ID.";
          }
          leaf vlan-list {
            type pub-type:vlan-range;
            mandatory true;
            description
              "VLAN list.";
          }
        }
      }
      // NCS drop config false container 'default-instance'
    }
  }
  augment "/ncs:devices/ncs:device/ncs:live-status" {
    container vlan {
      tailf:ncs-device-type "netconf";
      tailf:display-when "not(../../ncs:module) or ../../ncs:module[ncs:name='huawei-vlan'] or (../../ncs:live-status-protocol[not(ncs:capability)]) or (../../ncs:live-status-protocol/ncs:capability/ncs:module[.='huawei-vlan'])";
      description
        "VLAN management.";
      container vlans {
        description
          "List of VLAN.";
        list vlan {
          key "id";
          // NCS drop max-elements statement
          description
            "Configure VLAN information.";
          leaf id {
            type live_ncs_vlan-id;
            description
              "VLAN ID.";
          }
          leaf name {
            type string {
              length "1..31";
            }
            description
              "VLAN name.";
          }
          leaf description {
            type string {
              length "1..80";
            }
            description
              "VLAN description.";
          }
          leaf type {
            type live_ncs_vlan-type;
            // NCS drop default statement
            description
              "VLAN type, such as common VLANs, super-VLANs, and sub-VLANs.";
          }
          leaf admin-status {
            type live_ncs_admin-status;
            // NCS drop default statement
            description
              "Administrative status of a VLAN.";
          }
          leaf broadcast-discard {
            type live_ncs_enable-status;
            // NCS drop default statement
            description
              "Discard broadcast packets.";
          }
          leaf unknown-multicast-discard {
            type live_ncs_enable-status;
            // NCS drop default statement
            description
              "Discard unknown multicast packets.";
          }
          leaf mac-learning {
            type live_ncs_enable-status;
            // NCS drop default statement
            description
              "Whether MAC address leaning is enabled in a VLAN.";
          }
          leaf statistic-enable {
            type live_ncs_enable-status;
            // NCS drop default statement
            description
              "Whether VLAN statistics collection is enabled.";
          }
          leaf statistic-discard {
            // NCS drop when statement
            type live_ncs_enable-status;
            // NCS drop default statement
            description
              "Whether BUM discard statistics collection is enabled.";
          }
          leaf mac-aging-time {
            // NCS drop when statement
            type uint32 {
              range "0|60..1000000";
            }
            units "s";
            description
              "MAC address aging time, 0 indicates that MAC addresses do not age.";
          }
          leaf super-vlan {
            // NCS drop when statement
            type leafref {
              path "/ncs:devices/ncs:device/ncs:live-status/vlan:vlan/vlan:vlans/vlan:vlan/vlan:id" {
                tailf:xpath-root 3;
              }
            }
            // NCS drop must statement
            // NCS drop mandatory statement
            description
              "The corresponding super-VLAN ID when the VLAN is a sub-VLAN.";
          }
          container unkown-unicast-discard {
            description
              "Configure drop unknown unicast.";
            leaf discard {
              type live_ncs_enable-status;
              // NCS drop default statement
              description
                "Discard unknown unicast packets.";
            }
            leaf mac-learning-enable {
              // NCS drop when statement
              type live_ncs_enable-status;
              // NCS drop default statement
              description
                "Enable unknown unicast MAC address learning.";
            }
          }
          container suppression {
            description
              "Configure traffic suppression.";
            leaf inbound {
              type live_ncs_enable-status;
              // NCS drop default statement
              description
                "Whether inbound suppression is enable.";
            }
            leaf outbound {
              type live_ncs_enable-status;
              // NCS drop default statement
              description
                "Whether outbound suppression is enable.";
            }
          }
          container member-ports {
            description
              "List of ports in a VLAN.";
            list member-port {
              key "interface-name";
              description
                "Statistics of port in a VLAN.";
              leaf interface-name {
                type leafref {
                  path "/ncs:devices/ncs:device/ncs:live-status/ifm:ifm/ifm:interfaces/ifm:interface/ifm:name" {
                    tailf:xpath-root 3;
                  }
                }
                description
                  "Names of ports in a VLAN.";
              }
              leaf access-type {
                type live_ncs_access-type;
                description
                  "Port link type.";
              }
              leaf state {
                type live_ncs_oper-status;
                description
                  "Port state.";
              }
              leaf tag-mode {
                type live_ncs_tag-mode;
                description
                  "Port tag mode.";
              }
            }
          }
        }
      }
      container instances {
        description
          "List of VLAN instances.";
        list instance {
          key "id";
          description
            "Configure instances.";
          leaf id {
            type uint16 {
              range "1..4094";
            }
            description
              "Instance ID.";
          }
          leaf vlan-list {
            type pub-type:live_ncs_vlan-range;
            // NCS drop mandatory statement
            description
              "VLAN list.";
          }
        }
      }
      container default-instance {
        description
          "Statistics of default instance VLANs.";
        leaf vlan-list {
          type pub-type:live_ncs_vlan-range;
          description
            "VLAN list.";
        }
      }
    }
  }
  augment "/ncs:devices/ncs:template/ncs:ned-id/ncs:config" {
    container vlan {
      description
        "VLAN management.";
      container vlans {
        description
          "List of VLAN.";
        list vlan {
          // NCS patched for predictable order
          ordered-by user;
          key "id";
          // NCS drop max-elements statement
          description
            "Configure VLAN information.";
          leaf id {
            type ncs_template_vlan-id;
            description
              "VLAN ID.";
          }
          leaf name {
            type string;
            description
              "VLAN name.";
          }
          leaf description {
            type string;
            description
              "VLAN description.";
          }
          leaf type {
            type ncs_template_vlan-type;
            // NCS drop default statement
            description
              "VLAN type, such as common VLANs, super-VLANs, and sub-VLANs.";
          }
          leaf admin-status {
            type ncs_template_admin-status;
            // NCS drop default statement
            description
              "Administrative status of a VLAN.";
          }
          leaf broadcast-discard {
            type ncs_template_enable-status;
            // NCS drop default statement
            description
              "Discard broadcast packets.";
          }
          leaf unknown-multicast-discard {
            type ncs_template_enable-status;
            // NCS drop default statement
            description
              "Discard unknown multicast packets.";
          }
          leaf mac-learning {
            type ncs_template_enable-status;
            // NCS drop default statement
            description
              "Whether MAC address leaning is enabled in a VLAN.";
          }
          leaf statistic-enable {
            type ncs_template_enable-status;
            // NCS drop default statement
            description
              "Whether VLAN statistics collection is enabled.";
          }
          leaf statistic-discard {
            // NCS drop when statement
            type ncs_template_enable-status;
            // NCS drop default statement
            description
              "Whether BUM discard statistics collection is enabled.";
          }
          leaf mac-aging-time {
            // NCS drop when statement
            type string;
            units "s";
            description
              "MAC address aging time, 0 indicates that MAC addresses do not age.";
          }
          leaf super-vlan {
            // NCS drop when statement
            type string;
            // NCS drop must statement
            // NCS drop mandatory statement
            description
              "The corresponding super-VLAN ID when the VLAN is a sub-VLAN.";
          }
          container unkown-unicast-discard {
            description
              "Configure drop unknown unicast.";
            leaf discard {
              type ncs_template_enable-status;
              // NCS drop default statement
              description
                "Discard unknown unicast packets.";
            }
            leaf mac-learning-enable {
              // NCS drop when statement
              type ncs_template_enable-status;
              // NCS drop default statement
              description
                "Enable unknown unicast MAC address learning.";
            }
          }
          container suppression {
            description
              "Configure traffic suppression.";
            leaf inbound {
              type ncs_template_enable-status;
              // NCS drop default statement
              description
                "Whether inbound suppression is enable.";
            }
            leaf outbound {
              type ncs_template_enable-status;
              // NCS drop default statement
              description
                "Whether outbound suppression is enable.";
            }
          }
          // NCS drop config false container 'member-ports'
        }
      }
      container instances {
        description
          "List of VLAN instances.";
        list instance {
          // NCS patched for predictable order
          ordered-by user;
          key "id";
          description
            "Configure instances.";
          leaf id {
            type string;
            description
              "Instance ID.";
          }
          leaf vlan-list {
            type pub-type:ncs_template_vlan-range;
            // NCS drop mandatory statement
            description
              "VLAN list.";
          }
        }
      }
      // NCS drop config false container 'default-instance'
    }
  }
  augment "/ncs:devices/ncs:template/ncs:ned-id/ncs:config/ifm:ifm/ifm:interfaces/ifm:interface" {
    // NCS drop when statement
    description
      "Extend interface attribute.";
    container vlanif-attribute {
      description
        "Configure VLANIF attribute.";
      choice band-width-type {
        // NCS drop default statement
        description
          "VLANIF interface bandwidth.";
        case band-width-mbps {
          description
            "VLANIF interface bandwidth with mbps.";
          leaf band-width {
            type string;
            units "Mbit/s";
            // NCS drop default statement
            description
              "VLANIF interface bandwidth.";
          }
        }
        case band-width-kbps {
          description
            "VLANIF interface bandwidth with kbps.";
          leaf band-width-kbps {
            type string;
            units "kbit/s";
            description
              "VLANIF interface bandwidth with kbps.";
          }
        }
      }
      leaf damping-time {
        type string;
        units "s";
        // NCS drop default statement
        description
          "Delay time after which a VLANIF interface goes down.";
      }
    }
  }
  augment "/ncs:devices/ncs:device/ncs:live-status/ifm:ifm/ifm:interfaces/ifm:interface" {
    // NCS drop when statement
    description
      "Extend interface attribute.";
    container vlanif-attribute {
      tailf:ncs-device-type "netconf";
      tailf:display-when "not(../../../../../ncs:module) or ../../../../../ncs:module[ncs:name='huawei-vlan'] or (../../../../../ncs:live-status-protocol[not(ncs:capability)]) or (../../../../../ncs:live-status-protocol/ncs:capability/ncs:module[.='huawei-vlan'])";
      description
        "Configure VLANIF attribute.";
      choice band-width-type {
        // NCS drop default statement
        description
          "VLANIF interface bandwidth.";
        case band-width-mbps {
          description
            "VLANIF interface bandwidth with mbps.";
          leaf band-width {
            type uint32 {
              range "1..1000000";
            }
            units "Mbit/s";
            // NCS drop default statement
            description
              "VLANIF interface bandwidth.";
          }
        }
        case band-width-kbps {
          description
            "VLANIF interface bandwidth with kbps.";
          leaf band-width-kbps {
            type uint32 {
              range "1..1000000";
            }
            units "kbit/s";
            description
              "VLANIF interface bandwidth with kbps.";
          }
        }
      }
      leaf damping-time {
        type uint16 {
          range "0..20";
        }
        units "s";
        // NCS drop default statement
        description
          "Delay time after which a VLANIF interface goes down.";
      }
    }
  }
  augment "/ncs:devices/ncs:device/ncs:config/ifm:ifm/ifm:interfaces/ifm:interface" {
    when "ifm:type='Vlanif'" {
      tailf:xpath-root 3;
    }
    description
      "Extend interface attribute.";
    container vlanif-attribute {
      tailf:ncs-device-type "netconf";
      tailf:display-when "not(../../../../../ncs:module) or ../../../../../ncs:module[ncs:name='huawei-vlan']";
      description
        "Configure VLANIF attribute.";
      choice band-width-type {
        default "band-width-mbps";
        description
          "VLANIF interface bandwidth.";
        case band-width-mbps {
          description
            "VLANIF interface bandwidth with mbps.";
          leaf band-width {
            type uint32 {
              range "1..1000000";
            }
            units "Mbit/s";
            default "1000";
            description
              "VLANIF interface bandwidth.";
          }
        }
        case band-width-kbps {
          description
            "VLANIF interface bandwidth with kbps.";
          leaf band-width-kbps {
            type uint32 {
              range "1..1000000";
            }
            units "kbit/s";
            description
              "VLANIF interface bandwidth with kbps.";
          }
        }
      }
      leaf damping-time {
        type uint16 {
          range "0..20";
        }
        units "s";
        default "0";
        description
          "Delay time after which a VLANIF interface goes down.";
      }
    }
  }
}
