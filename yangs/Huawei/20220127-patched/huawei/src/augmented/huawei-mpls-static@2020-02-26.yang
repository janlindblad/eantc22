module huawei-mpls-static {
  // Generated by yanger -t ncs
  tailf:mount-id "huawei-nc-1.0:huawei-nc-1.0";
  tailf:ncs-device-type "netconf";

  namespace "urn:huawei:yang:huawei-mpls-static";
  prefix mpls-static;

  import ietf-inet-types {
    prefix inet;
  }
  import huawei-mpls {
    prefix mpls;
  }
  import huawei-extension {
    prefix ext;
  }
  import huawei-pub-type {
    prefix pub-type;
  }
  import huawei-ifm {
    prefix ifm;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Specifies the multi-protocol label switching protocol.";

  revision 2020-02-26 {
    description
      "Added an extension of one node.";
    reference "Huawei private.";
  }
  revision 2019-11-20 {
    description
      "Modify the static lsp model.";
    reference "Huawei private.";
  }
  revision 2019-03-27 {
    description
      "Initial revision.";
    reference "Huawei private.";
  }
  ext:task-name "mpls-ldp";

  typedef ncs_template_lsr-role-type {
    type string;
    description
      "LSR role type.";
  }

  typedef ncs_template_lsp-status-type {
    type string;
    description
      "LSP status type.";
  }

  typedef ncs_rpc_notif_lsr-role-type {
    type enumeration {
      enum "ingress" {
        value 1;
        description
          "The role of the current LSR is ingress.";
      }
      enum "transit" {
        value 2;
        description
          "The role of the current LSR is transit.";
      }
      enum "egress" {
        value 3;
        description
          "The role of the current LSR is egress.";
      }
    }
    description
      "LSR role type.";
  }

  typedef ncs_rpc_notif_lsp-status-type {
    type enumeration {
      enum "down" {
        value 0;
        description
          "The status of the LSP is down.";
      }
      enum "up" {
        value 1;
        description
          "The status of the LSP is up.";
      }
    }
    description
      "LSP status type.";
  }

  typedef live_ncs_lsr-role-type {
    type enumeration {
      enum "ingress" {
        value 1;
        description
          "The role of the current LSR is ingress.";
      }
      enum "transit" {
        value 2;
        description
          "The role of the current LSR is transit.";
      }
      enum "egress" {
        value 3;
        description
          "The role of the current LSR is egress.";
      }
    }
    description
      "LSR role type.";
  }

  typedef live_ncs_lsp-status-type {
    type enumeration {
      enum "down" {
        value 0;
        description
          "The status of the LSP is down.";
      }
      enum "up" {
        value 1;
        description
          "The status of the LSP is up.";
      }
    }
    description
      "LSP status type.";
  }

  typedef lsr-role-type {
    type enumeration {
      enum "ingress" {
        value 1;
        description
          "The role of the current LSR is ingress.";
      }
      enum "transit" {
        value 2;
        description
          "The role of the current LSR is transit.";
      }
      enum "egress" {
        value 3;
        description
          "The role of the current LSR is egress.";
      }
    }
    description
      "LSR role type.";
  }

  typedef lsp-status-type {
    type enumeration {
      enum "down" {
        value 0;
        description
          "The status of the LSP is down.";
      }
      enum "up" {
        value 1;
        description
          "The status of the LSP is up.";
      }
    }
    description
      "LSP status type.";
  }

  augment "/ncs:devices/ncs:template/ncs:ned-id/ncs:config/mpls:mpls" {
    // NCS drop when statement
    description
      "MPLS static configuration information augment to module MPLS.";
    container static {
      // NCS drop when statement
      description
        "Configure MPLS static LSP.";
      container lsps {
        description
          "List of statist static LSPs.";
        list lsp {
          // NCS patched for predictable order
          ordered-by user;
          key "lsp-name";
          unique "transit/in-label";
          unique "egress/in-label";
          description
            "Configure a list of defined static LSPs.";
          leaf lsp-name {
            type string;
            description
              "The name of an LSP.";
          }
          leaf lsr-type {
            ext:operation-exclude "update";
            type ncs_template_lsr-role-type;
            // NCS drop mandatory statement
            description
              "The LSR role of an LSP.";
          }
          container ingress {
            // NCS drop when statement
            // NCS drop must statement
            description
              "Configure ingress.";
            leaf fec-address {
              type string;
              // NCS drop mandatory statement
              description
                "The destination IP address.";
            }
            leaf prefix-length {
              type string;
              // NCS drop mandatory statement
              description
                "The mask length of the destination IP address.";
            }
            leaf out-interface-name {
              type string;
              description
                "The outbound interface.";
            }
            leaf next-hop {
              type string;
              description
                "The next-hop address.";
            }
            leaf out-label {
              type string;
              // NCS drop mandatory statement
              description
                "The value of an outgoing label.";
            }
          }
          container transit {
            // NCS drop when statement
            // NCS drop must statement
            description
              "Configure transit.";
            leaf in-interface-name {
              type string;
              description
                "The inbound interface.";
            }
            leaf out-interface-name {
              type string;
              description
                "The outbound interface.";
            }
            leaf next-hop {
              type string;
              description
                "The next-hop address.";
            }
            leaf in-label {
              type string;
              // NCS drop must statement
              // NCS drop mandatory statement
              description
                "The value of an incoming label.
                 Special explanation:
                 Incoming label Range is the max configured value, the actual value is dynamic according to different devices.";
            }
            leaf out-label {
              type string;
              // NCS drop mandatory statement
              description
                "The value of an outgoing label.";
            }
          }
          container egress {
            // NCS drop when statement
            description
              "Configure egress.";
            leaf in-interface-name {
              type string;
              description
                "The inbound interface.";
            }
            leaf in-label {
              type string;
              // NCS drop must statement
              // NCS drop mandatory statement
              description
                "The value of an incoming label.
                 Special explanation:
                 Incoming label Range is the max configured value, the actual value is dynamic according to different devices.";
            }
          }
        }
        // NCS drop config false list 'lsp-state'
      }
      // NCS drop config false container 'lsp-statistics'
    }
  }
  augment "/ncs:devices/ncs:device/ncs:live-status/mpls:mpls" {
    // NCS drop when statement
    description
      "MPLS static configuration information augment to module MPLS.";
    container static {
      tailf:ncs-device-type "netconf";
      tailf:display-when "not(../../../ncs:module) or ../../../ncs:module[ncs:name='huawei-mpls-static'] or (../../../ncs:live-status-protocol[not(ncs:capability)]) or (../../../ncs:live-status-protocol/ncs:capability/ncs:module[.='huawei-mpls-static'])";
      // NCS drop when statement
      description
        "Configure MPLS static LSP.";
      container lsps {
        description
          "List of statist static LSPs.";
        list lsp {
          key "lsp-name";
          unique "transit/in-label";
          unique "egress/in-label";
          description
            "Configure a list of defined static LSPs.";
          leaf lsp-name {
            type string {
              length "1..19";
            }
            description
              "The name of an LSP.";
          }
          leaf lsr-type {
            ext:operation-exclude "update";
            type live_ncs_lsr-role-type;
            // NCS drop mandatory statement
            description
              "The LSR role of an LSP.";
          }
          container ingress {
            // NCS drop when statement
            // NCS drop must statement
            description
              "Configure ingress.";
            leaf fec-address {
              type inet:ipv4-address-no-zone;
              // NCS drop mandatory statement
              description
                "The destination IP address.";
            }
            leaf prefix-length {
              type uint8 {
                range "0..32";
              }
              // NCS drop mandatory statement
              description
                "The mask length of the destination IP address.";
            }
            leaf out-interface-name {
              type leafref {
                path "/ncs:devices/ncs:device/ncs:live-status/ifm:ifm/ifm:interfaces/ifm:interface/ifm:name" {
                  tailf:xpath-root 3;
                }
              }
              description
                "The outbound interface.";
            }
            leaf next-hop {
              type inet:ipv4-address-no-zone;
              description
                "The next-hop address.";
            }
            leaf out-label {
              type uint32 {
                range "16..1048575";
              }
              // NCS drop mandatory statement
              description
                "The value of an outgoing label.";
            }
          }
          container transit {
            // NCS drop when statement
            // NCS drop must statement
            description
              "Configure transit.";
            leaf in-interface-name {
              type leafref {
                path "/ncs:devices/ncs:device/ncs:live-status/ifm:ifm/ifm:interfaces/ifm:interface/ifm:name" {
                  tailf:xpath-root 3;
                }
              }
              description
                "The inbound interface.";
            }
            leaf out-interface-name {
              type leafref {
                path "/ncs:devices/ncs:device/ncs:live-status/ifm:ifm/ifm:interfaces/ifm:interface/ifm:name" {
                  tailf:xpath-root 3;
                }
              }
              description
                "The outbound interface.";
            }
            leaf next-hop {
              type inet:ipv4-address-no-zone;
              description
                "The next-hop address.";
            }
            leaf in-label {
              type uint32 {
                range "16..32783";
              }
              // NCS drop must statement
              // NCS drop mandatory statement
              description
                "The value of an incoming label.
                 Special explanation:
                 Incoming label Range is the max configured value, the actual value is dynamic according to different devices.";
            }
            leaf out-label {
              type uint32 {
                range "16..1048575";
              }
              // NCS drop mandatory statement
              description
                "The value of an outgoing label.";
            }
          }
          container egress {
            // NCS drop when statement
            description
              "Configure egress.";
            leaf in-interface-name {
              type leafref {
                path "/ncs:devices/ncs:device/ncs:live-status/ifm:ifm/ifm:interfaces/ifm:interface/ifm:name" {
                  tailf:xpath-root 3;
                }
              }
              description
                "The inbound interface.";
            }
            leaf in-label {
              type uint32 {
                range "16..32783";
              }
              // NCS drop must statement
              // NCS drop mandatory statement
              description
                "The value of an incoming label.
                 Special explanation:
                 Incoming label Range is the max configured value, the actual value is dynamic according to different devices.";
            }
          }
        }
        list lsp-state {
          key "name";
          description
            "MPLS static lsp state.";
          leaf name {
            type string {
              length "1..19";
            }
            description
              "The name of an LSP.";
          }
          leaf type {
            type live_ncs_lsr-role-type;
            description
              "The LSR Role of an LSP.";
          }
          leaf fec-address {
            type inet:ipv4-address-no-zone;
            description
              "The destination IP address.";
          }
          leaf prefix-length {
            type uint8 {
              range "0..32";
            }
            description
              "The mask length of the destination IP address.";
          }
          leaf status {
            type live_ncs_lsp-status-type;
            description
              "The status of an LSP.";
          }
          leaf index {
            type uint32;
            description
              "The index of an LSP.";
          }
          leaf next-hop {
            type inet:ipv4-address-no-zone;
            description
              "The next-hop address.";
          }
          leaf in-label {
            type uint32 {
              range "16..1048575";
            }
            description
              "The value of an incoming label.
               Special explanation:
               Incoming label Range is the max configured value, the actual value is dynamic according to different devices.";
          }
          leaf out-label {
            type uint32 {
              range "16..1048575";
            }
            description
              "The value of an outgoing label.";
          }
          leaf incoming-interface {
            type pub-type:live_ncs_if-name;
            description
              "The incoming interface name.";
          }
          leaf outgoing-interface {
            type pub-type:live_ncs_if-name;
            description
              "The outgoing interface name.";
          }
          leaf mtu {
            type uint32 {
              range "0..65535";
            }
            units "Byte";
            description
              "The Mtu of an LSP.";
          }
          leaf time-stamp {
            type uint32 {
              range "0..4294967295";
            }
            units "s";
            description
              "The time stamp of an LSP.";
          }
        }
      }
      container lsp-statistics {
        description
          "Statistics of static LSPs.";
        leaf up-lsp-number {
          type uint32;
          description
            "Total number of static LSPs.";
        }
        leaf down-lsp-number {
          type uint32;
          description
            "Number of static LSPs that are in the down state.";
        }
        leaf total-lsp-number {
          type uint32;
          description
            "Total number of static LSPs.";
        }
      }
    }
  }
  augment "/ncs:devices/ncs:device/ncs:config/mpls:mpls" {
    when "/mpls:mpls/mpls:common/mpls:global/mpls:mpls-enable='true'" {
      tailf:xpath-root 3;
    }
    description
      "MPLS static configuration information augment to module MPLS.";
    container static {
      tailf:ncs-device-type "netconf";
      tailf:display-when "not(../../../ncs:module) or ../../../ncs:module[ncs:name='huawei-mpls-static']";
      when "/mpls:mpls/mpls:common/mpls:global/mpls:mpls-enable='true'" {
        tailf:xpath-root 3;
      }
      description
        "Configure MPLS static LSP.";
      container lsps {
        description
          "List of statist static LSPs.";
        list lsp {
          key "lsp-name";
          unique "transit/in-label";
          unique "egress/in-label";
          description
            "Configure a list of defined static LSPs.";
          leaf lsp-name {
            type string {
              length "1..19";
            }
            description
              "The name of an LSP.";
          }
          leaf lsr-type {
            ext:operation-exclude "update";
            type lsr-role-type;
            mandatory true;
            description
              "The LSR role of an LSP.";
          }
          container ingress {
            when "../lsr-type='ingress'" {
              tailf:xpath-root 3;
            }
            must '(out-interface-name or next-hop)' {
              tailf:xpath-root 3;
            }
            description
              "Configure ingress.";
            leaf fec-address {
              type inet:ipv4-address-no-zone;
              mandatory true;
              description
                "The destination IP address.";
            }
            leaf prefix-length {
              type uint8 {
                range "0..32";
              }
              mandatory true;
              description
                "The mask length of the destination IP address.";
            }
            leaf out-interface-name {
              type leafref {
                path "/ncs:devices/ncs:device/ncs:config/ifm:ifm/ifm:interfaces/ifm:interface/ifm:name" {
                  tailf:xpath-root 3;
                }
              }
              description
                "The outbound interface.";
            }
            leaf next-hop {
              type inet:ipv4-address-no-zone;
              description
                "The next-hop address.";
            }
            leaf out-label {
              type uint32 {
                range "16..1048575";
              }
              mandatory true;
              description
                "The value of an outgoing label.";
            }
          }
          container transit {
            when "../lsr-type='transit'" {
              tailf:xpath-root 3;
            }
            must '(out-interface-name or next-hop)' {
              tailf:xpath-root 3;
            }
            description
              "Configure transit.";
            leaf in-interface-name {
              type leafref {
                path "/ncs:devices/ncs:device/ncs:config/ifm:ifm/ifm:interfaces/ifm:interface/ifm:name" {
                  tailf:xpath-root 3;
                }
              }
              description
                "The inbound interface.";
            }
            leaf out-interface-name {
              type leafref {
                path "/ncs:devices/ncs:device/ncs:config/ifm:ifm/ifm:interfaces/ifm:interface/ifm:name" {
                  tailf:xpath-root 3;
                }
              }
              description
                "The outbound interface.";
            }
            leaf next-hop {
              type inet:ipv4-address-no-zone;
              description
                "The next-hop address.";
            }
            leaf in-label {
              type uint32 {
                range "16..32783";
              }
              must 'count(../../../lsp[egress/in-label=current()])=0' {
                tailf:xpath-root 3;
              }
              mandatory true;
              description
                "The value of an incoming label.
                 Special explanation:
                 Incoming label Range is the max configured value, the actual value is dynamic according to different devices.";
            }
            leaf out-label {
              type uint32 {
                range "16..1048575";
              }
              mandatory true;
              description
                "The value of an outgoing label.";
            }
          }
          container egress {
            when "../lsr-type='egress'" {
              tailf:xpath-root 3;
            }
            description
              "Configure egress.";
            leaf in-interface-name {
              type leafref {
                path "/ncs:devices/ncs:device/ncs:config/ifm:ifm/ifm:interfaces/ifm:interface/ifm:name" {
                  tailf:xpath-root 3;
                }
              }
              description
                "The inbound interface.";
            }
            leaf in-label {
              type uint32 {
                range "16..32783";
              }
              must 'count(../../../lsp[transit/in-label=current()])=0' {
                tailf:xpath-root 3;
              }
              mandatory true;
              description
                "The value of an incoming label.
                 Special explanation:
                 Incoming label Range is the max configured value, the actual value is dynamic according to different devices.";
            }
          }
        }
        // NCS drop config false list 'lsp-state'
      }
      // NCS drop config false container 'lsp-statistics'
    }
  }
}
