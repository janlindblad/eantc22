module huawei-l2vpn {
  // Generated by yanger -t ncs
  tailf:mount-id "huawei-nc-1.0:huawei-nc-1.0";
  tailf:ncs-device-type "netconf";

  yang-version 1;
  namespace "urn:huawei:yang:huawei-l2vpn";
  prefix l2vpn;

  import ietf-yang-types {
    prefix yang;
  }
  import ietf-inet-types {
    prefix inet;
  }
  import huawei-pub-type {
    prefix pub-type;
  }
  import huawei-extension {
    prefix ext;
  }
  import huawei-ifm {
    prefix ifm;
  }
  import huawei-network-instance {
    prefix ni;
  }
  import huawei-bd {
    prefix bd;
  }
  import huawei-mpls {
    prefix mpls;
  }
  import huawei-bfd {
    prefix bfd;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "L2 virtual private network.";

  revision 2020-10-22 {
    description
      "Add query nodes.";
    reference "Huawei private.";
  }
  revision 2020-05-14 {
    description
      "Add operation-exclude.";
    reference "Huawei private.";
  }
  revision 2019-09-16 {
    description
      "Add nodes.";
    reference "Huawei private.";
  }
  revision 2019-07-08 {
    description
      "Add nodes.";
    reference "Huawei private.";
  }
  revision 2019-04-04 {
    description
      "Init revision.";
    reference "Huawei private.";
  }
  ext:task-name "l2vpn";

  typedef ncs_template_l2vpn-instance-name {
    type string;
    description
      "L2VPN instance name.";
  }

  typedef ncs_template_l2vpn-peer-address-type {
    type string;
    description
      "IP address of a peer.";
  }

  typedef ncs_template_l2vpn-vpls-encap-type {
    type string;
    description
      "L2VPN VPLS encapsulation type.";
  }

  typedef ncs_template_l2vpn-vpls-ldp-pw-encap-type {
    type string;
    description
      "L2VPN VPLS LDP PW encapsulation type.";
  }

  typedef ncs_template_l2vpn-mac-learn-style {
    type string;
    description
      "L2VPN MAC learn style.";
  }

  typedef ncs_template_pw-role-type {
    type string;
    description
      "L2VPN PW role type.";
  }

  typedef ncs_template_vpls-pw-role-type {
    type string;
    description
      "VPLS PW role type.";
  }

  typedef ncs_template_ms-pw-role-type {
    type string;
    description
      "L2VPN multi-segment PW role.";
  }

  typedef ncs_template_l2vpn-pw-template-name {
    type string;
    description
      "L2VPN PW template name.";
  }

  typedef ncs_template_l2vpn-pw-name {
    type string;
    description
      "L2VPN PW name.";
  }

  typedef ncs_template_l2vpn-state {
    type string;
    description
      "L2VPN state.";
  }

  typedef ncs_template_instance-state {
    type string;
    description
      "L2VPN instance state.";
  }

  typedef ncs_template_ac-state {
    type string;
    description
      "L2VPN AC state.";
  }

  typedef ncs_template_l2vpn-pw-state {
    type string;
    description
      "L2VPN PW state.";
  }

  typedef ncs_template_l2vpn-forward-state {
    type string;
    description
      "L2VPN forward state.";
  }

  typedef ncs_template_ldp-signal-type {
    type string;
    description
      "L2VPN LDP signal mode.";
  }

  typedef ncs_template_l2vpn-peer-ldp-signal-mode {
    type string;
    description
      "L2VPN peer LDP signal mode.";
  }

  typedef ncs_template_l2vpn-control-word {
    type string;
    description
      "L2VPN control word.";
  }

  typedef ncs_template_l2vpn-instance-type {
    type string;
    description
      "L2VPN instance type.";
  }

  typedef ncs_template_l2vpn-switch-type {
    type string;
    description
      "L2VPN switch type.";
  }

  typedef ncs_template_encapsulation-type {
    type string;
    description
      "L2VPN encapsulate type.";
  }

  typedef ncs_template_l2vpn-backup-mode {
    type string;
    description
      "L2VPN backup mode.";
  }

  typedef ncs_template_l2vpn-tunnel-type {
    type string;
    description
      "L2VPN tunnel type.";
  }

  typedef ncs_template_l2vpn-mac-type {
    type string;
    description
      "L2VPN MAC type.";
  }

  typedef ncs_template_l2vpn-pw-aps-oper-type {
    type string;
    description
      "L2VPN PW APS oper type.";
  }

  typedef ncs_template_l2vpn-pw-aps-mode {
    type string;
    description
      "L2VPN PW APS mode.";
  }

  typedef ncs_template_l2vpn-pw-aps-type {
    type string;
    description
      "L2VPN PW APS type.";
  }

  typedef ncs_template_l2vpn-pw-aps-role {
    type string;
    description
      "L2VPN PW APS role.";
  }

  typedef ncs_template_l2vpn-reroute-mode {
    type string;
    description
      "L2VPN reroute mode.";
  }

  typedef ncs_template_pw-redundancy-mode {
    type string;
    description
      "PW redundancy mode.";
  }

  typedef ncs_template_vpls-redundancy-mode {
    type string;
    description
      "PW redundancy mode.";
  }

  typedef ncs_template_l2vpn-vpls-vsi-mem-disc-type {
    type string;
    description
      "L2VPN VPLS VSI member discovery type.";
  }

  typedef ncs_template_l2vpn-vpls-unknow-frame-act {
    type string;
    description
      "L2VPN VPLS unknown frame act.";
  }

  typedef ncs_template_l2vpn-vpls-pw-type {
    type string;
    description
      "L2VPN VPLS PW type.";
  }

  typedef ncs_template_l2vpn-vpls-traffic-statistics-enable-type {
    type string;
    description
      "L2VPN VPLS traffic statistics enable type.";
  }

  typedef ncs_template_l2vpn-vpls-ldp-pw-state-code {
    type string;
    description
      "L2VPN VPLS LDP PW state code.";
  }

  typedef ncs_template_l2vpn-vpws-vrrp-state {
    type string;
    description
      "L2VPN VPWS VRRP state.";
  }

  typedef ncs_template_l2vpn-vpws-bfd-state {
    type string;
    description
      "L2VPN VPWS BFD state.";
  }

  typedef ncs_template_l2vpn-aps-bind-type {
    type string;
    description
      "L2VPN APS bind type.";
  }

  typedef ncs_template_oam-protocal {
    type string;
    description
      "L2VPN OAM protocol.";
  }

  typedef ncs_template_oam-status {
    type string;
    description
      "L2VPN OAM status.";
  }

  typedef ncs_template_l2vpn-aps-status {
    type string;
    description
      "L2VPN APS status.";
  }

  typedef ncs_template_l2vpn-aps-path-status {
    type string;
    description
      "L2VPN APS path status.";
  }

  typedef ncs_template_l2vpn-aps-result {
    type string;
    description
      "L2VPN APS result.";
  }

  typedef ncs_template_l2vpn-protect-group-name {
    type string;
    description
      "L2VPN protect group name.";
  }

  typedef ncs_template_vpn-rt-type {
    type string;
    description
      "L2VPN common VPN RT type.";
  }

  typedef ncs_template_vpls-split-horizon-mode-type {
    type string;
    description
      "L2VPN VPLS split horizon mode type.";
  }

  typedef ncs_template_pw-signal-type {
    type string;
    description
      "L2VPN PW signal type.";
  }

  typedef ncs_template_l2vpn-rtp-header-type {
    type string;
    description
      "L2VPN RT header type.";
  }

  typedef ncs_template_l2vpn-payload-comp {
    type string;
    description
      "L2VPN payload compression.";
  }

  typedef ncs_template_l2vpn-route-status {
    type string;
    description
      "L2VPN route status.";
  }

  typedef ncs_template_ac-oam-mapping-type {
    type string;
    description
      "L2VPN AC OAM mapping type.";
  }

  typedef ncs_template_oam-state {
    type string;
    description
      "L2VPN MC OAM state.";
  }

  typedef ncs_template_flow-label-ability {
    type string;
    description
      "L2VPN flow label ability.";
  }

  typedef ncs_template_l2vpn-load-balance-type {
    type string;
    description
      "L2VPN load balance type.";
  }

  typedef ncs_template_bgp-encap-type {
    type string;
    description
      "L2VPN BGP encapsulation type.";
  }

  typedef ncs_template_vsi-work-mode {
    type string;
    description
      "L2VPN VPLS VSI work mode.";
  }

  typedef ncs_template_send-receive-active-status {
    type string;
    description
      "L2VPN sernd recv active status.";
  }

  typedef ncs_template_ac-block-status {
    type string;
    description
      "L2VPN AC block status.";
  }

  typedef ncs_template_vpws-bgp-ce-name-type {
    type string;
    description
      "L2VPN VPWS BGP CE name.";
  }

  typedef ncs_template_vpls-multi-homing-site-name {
    type string;
    description
      "L2VPN VPLS multi-homing site name.";
  }

  typedef ncs_template_bfd-vccv-cv-type {
    type string;
    description
      "L2VPN BFD VCCV CV type.";
  }

  typedef ncs_template_l2vpn-common-enable-type {
    type string;
    description
      "L2VPN common enable.";
  }

  typedef ncs_template_interface-change-withdraw-type {
    type string;
    description
      "Interface change withdraw type.";
  }

  typedef ncs_template_suppression-type {
    type string;
    description
      "L2VPN suppression type.";
  }

  typedef ncs_template_mac-remove-type {
    type string;
    description
      "L2VPN MAC remove type.";
  }

  typedef ncs_template_l2vpn-arp-send-type {
    type string;
    description
      "L2VPN ARP send type.";
  }

  typedef ncs_template_l2vpn-nd-send-type {
    type string;
    description
      "L2VPN ND send type.";
  }

  typedef ncs_template_l2vpn-pw-aps-ps-type {
    type string;
    description
      "L2VPN PW APS PS type.";
  }

  typedef ncs_template_l2vpn-protect-group-ps-type {
    type string;
    description
      "L2VPN protect group PS type.";
  }

  typedef ncs_template_multicast-tunnel-type {
    type string;
    description
      "L2VPN MC tunnel type.";
  }

  typedef ncs_template_pw-block-status {
    type string;
    description
      "L2VPN PW block status.";
  }

  typedef ncs_template_vpws-bgp-vpn-encap {
    type string;
    description
      "Encapsulation type for a VPWS BGP VPN instance.";
  }

  typedef ncs_template_l2vpn-vpls-pw-bfd-state {
    type string;
    description
      "BFD for VPLS PW state.";
  }

  typedef ncs_template_vpws-bgp-pw-type {
    type string;
    description
      "L2VPN VPWS BGP PW type.";
  }

  typedef ncs_template_vpws-bgp-ac-oam-state {
    type string;
    description
      "L2VPN VPWS BGP AC OAM state.";
  }

  typedef ncs_template_vpls-ldp-peer-type {
    type string;
    description
      "L2VPN VPLS LDP peer type.";
  }

  typedef ncs_template_vpls-loop-detect-type {
    type string;
    description
      "L2VPN VPLS loop detect type.";
  }

  typedef ncs_template_vpls-bgp-encapsulation-type {
    type string;
    description
      "L2VPN BGP encapsulation type.";
  }

  typedef ncs_template_control-flag-bits-type {
    type string;
    description
      "Indicates the control flag.";
  }

  typedef ncs_template_vsi-pbb-instance-type {
    type string;
    description
      "L2VPN VSI PBB instance style.";
  }

  typedef ncs_template_vsi-pbb-learned-flag {
    type string;
    description
      "L2VPN VSI PBB learned flag.";
  }

  typedef ncs_template_multicast-active-state {
    type string;
    description
      "L2VPN MC active state.";
  }

  typedef ncs_template_multicast-oam-type {
    type string;
    description
      "L2VPN MC OAM type.";
  }

  typedef ncs_template_suppression-direction {
    type string;
    description
      "L2VPN suppression direction.";
  }

  typedef ncs_template_etree-work-mode {
    type string;
    description
      "The e-tree work mode of the PW.";
  }

  typedef ncs_template_etree-access-role {
    type string;
    description
      "The e-tree access role of the AC.";
  }

  typedef ncs_rpc_notif_l2vpn-instance-name {
    type string {
      length "1..31";
    }
    description
      "L2VPN instance name.";
  }

  typedef ncs_rpc_notif_l2vpn-peer-address-type {
    type inet:ipv4-address-no-zone {
      pattern '(([1-9]|[1-9][0-9]|1[0-1][0-9]|12[0-6]|12[8-9]|1[3-9][0-9]|2[0-1][0-9]|22[0-4])\.)(([0-9]|[1-9][0-9]|1[0-9][0-9]|2[0-4][0-9]|25[0-5])\.){2}([0-9]|[1-9][0-9]|1[0-9][0-9]|2[0-4][0-9]|25[0-5])';
    }
    description
      "IP address of a peer.";
  }

  typedef ncs_rpc_notif_l2vpn-vpls-encap-type {
    type enumeration {
      enum "vlan" {
        value 4;
        description
          "The encapsulation type of VPLS is VLAN.";
      }
      enum "ethernet" {
        value 5;
        description
          "The encapsulation type of VPLS is ethernet.";
      }
    }
    description
      "L2VPN VPLS encapsulation type.";
  }

  typedef ncs_rpc_notif_l2vpn-vpls-ldp-pw-encap-type {
    type enumeration {
      enum "vlan" {
        value 4;
        description
          "The VPLS LDP PW encapsulation type is VLAN.";
      }
      enum "ethernet" {
        value 5;
        description
          "The VPLS LDP PW encapsulation type is ethernet.";
      }
      enum "unsupport" {
        value 255;
        description
          "Unsupported encapsulation type.";
      }
    }
    description
      "L2VPN VPLS LDP PW encapsulation type.";
  }

  typedef ncs_rpc_notif_l2vpn-mac-learn-style {
    type enumeration {
      enum "unqualify" {
        value 1;
        description
          "The MAC learn style is unqualify.";
      }
      enum "qualify" {
        value 2;
        description
          "The MAC learn style is qualify.";
      }
      enum "qualify-outer-vlan" {
        value 3;
        description
          "Learn MAC addresses in qualified mode by explicitly using outer VLAN ID.";
      }
      enum "qualify-inner-vlan" {
        value 4;
        description
          "Learn MAC addresses in qualified mode by explicitly using inner VLAN ID.";
      }
    }
    description
      "L2VPN MAC learn style.";
  }

  typedef ncs_rpc_notif_pw-role-type {
    type enumeration {
      enum "primary" {
        value 1;
        description
          "The PW role type is primary.";
      }
      enum "backup" {
        value 2;
        description
          "The PW role type is backup.";
      }
      enum "bypass" {
        value 3;
        description
          "The PW role type is bypass.";
      }
      enum "ac-bypass" {
        value 7;
        description
          "The PW role type is AC-bypass.";
      }
      enum "pw-bypass" {
        value 8;
        description
          "The PW role type is PW-bypass.";
      }
    }
    description
      "L2VPN PW role type.";
  }

  typedef ncs_rpc_notif_vpls-pw-role-type {
    type enumeration {
      enum "primary" {
        value 1;
        description
          "The PW role type is primary.";
      }
      enum "backup" {
        value 2;
        description
          "The PW role type is backup.";
      }
    }
    description
      "VPLS PW role type.";
  }

  typedef ncs_rpc_notif_ms-pw-role-type {
    type enumeration {
      enum "left-primary" {
        value 4;
        description
          "The left side PW of multi-segment instance.";
      }
      enum "right-primary" {
        value 5;
        description
          "The right side PW of multi-segment instance.";
      }
      enum "right-backup" {
        value 6;
        description
          "The backup of the right side PW.";
      }
    }
    description
      "L2VPN multi-segment PW role.";
  }

  typedef ncs_rpc_notif_l2vpn-pw-template-name {
    type string {
      length "1..19";
    }
    description
      "L2VPN PW template name.";
  }

  typedef ncs_rpc_notif_l2vpn-pw-name {
    type string {
      length "1..15";
    }
    description
      "L2VPN PW name.";
  }

  typedef ncs_rpc_notif_l2vpn-state {
    type enumeration {
      enum "default" {
        value 0;
        description
          "The state is default.";
      }
      enum "down" {
        value 1;
        description
          "The state is down.";
      }
      enum "up" {
        value 2;
        description
          "The state is up.";
      }
    }
    description
      "L2VPN state.";
  }

  typedef ncs_rpc_notif_instance-state {
    type enumeration {
      enum "down" {
        value 0;
        description
          "The instance state is down.";
      }
      enum "up" {
        value 1;
        description
          "The instance state is up.";
      }
      enum "admin-down" {
        value 2;
        description
          "The instance state is admin down.";
      }
    }
    description
      "L2VPN instance state.";
  }

  typedef ncs_rpc_notif_ac-state {
    type enumeration {
      enum "down" {
        value 0;
        description
          "The AC state is down.";
      }
      enum "up" {
        value 1;
        description
          "The AC state is up.";
      }
      enum "plug-out" {
        value 2;
        description
          "The AC state is plug-out.";
      }
      enum "notify-down" {
        value 3;
        description
          "The AC state is notify-down.";
      }
      enum "down-notify" {
        value 4;
        description
          "The AC state is down-notify.";
      }
    }
    description
      "L2VPN AC state.";
  }

  typedef ncs_rpc_notif_l2vpn-pw-state {
    type enumeration {
      enum "down" {
        value 0;
        description
          "The PW state is down.";
      }
      enum "up" {
        value 1;
        description
          "The PW state is up.";
      }
      enum "backup" {
        value 2;
        description
          "The PW state is backup.";
      }
    }
    description
      "L2VPN PW state.";
  }

  typedef ncs_rpc_notif_l2vpn-forward-state {
    type enumeration {
      enum "not-forwarding" {
        value 0;
        description
          "The forward state is not forwarding.";
      }
      enum "forwarding" {
        value 1;
        description
          "The forward state is forwarding.";
      }
    }
    description
      "L2VPN forward state.";
  }

  typedef ncs_rpc_notif_ldp-signal-type {
    type enumeration {
      enum "pwe3" {
        value 0;
        description
          "Pseudo-wire emulation edge to edge.";
      }
      enum "martini" {
        value 1;
        description
          "Martini mode.";
      }
    }
    description
      "L2VPN LDP signal mode.";
  }

  typedef ncs_rpc_notif_l2vpn-peer-ldp-signal-mode {
    type enumeration {
      enum "pwe3" {
        value 0;
        description
          "Pseudo-Wire Emulation Edge to Edge.";
      }
      enum "martini" {
        value 1;
        description
          "Martini mode.";
      }
      enum "default" {
        value 2;
        description
          "Default mode.";
      }
    }
    description
      "L2VPN peer LDP signal mode.";
  }

  typedef ncs_rpc_notif_l2vpn-control-word {
    type enumeration {
      enum "default" {
        value 0;
        description
          "The control word mode is default.";
      }
      enum "disable" {
        value 1;
        description
          "The control word mode is disable.";
      }
      enum "enable" {
        value 2;
        description
          "The control word mode is enable.";
      }
      enum "prefer" {
        value 3;
        description
          "The control word mode is prefer.";
      }
    }
    description
      "L2VPN control word.";
  }

  typedef ncs_rpc_notif_l2vpn-instance-type {
    type enumeration {
      enum "vpws-local-ccc" {
        value 1;
        description
          "The instance type is VPWS local CCC.";
      }
      enum "vpws-remote-ccc" {
        value 2;
        description
          "The instance type is VPWS remote CCC.";
      }
      enum "vpws-svc" {
        value 3;
        description
          "The instance type is VPWS SVC.";
      }
      enum "vpws-ldp" {
        value 4;
        description
          "The instance type is VPWS LDP.";
      }
      enum "vpws-switch" {
        value 5;
        description
          "The instance type is VPWS switching.";
      }
      enum "vpls" {
        value 6;
        description
          "Virtual private LAN service.";
      }
      enum "vpws-bgp" {
        value 8;
        description
          "The instance type is VPWS BGP.";
      }
      enum "vpws-single-ccc" {
        value 9;
        description
          "The instance type is VPWS single CCC.";
      }
    }
    description
      "L2VPN instance type.";
  }

  typedef ncs_rpc_notif_l2vpn-switch-type {
    type enumeration {
      enum "svc-svc" {
        value 1;
        description
          "SVC to SVC.";
      }
      enum "ldp-svc" {
        value 2;
        description
          "LDP to SVC.";
      }
      enum "ldp-ldp" {
        value 3;
        description
          "LDP to LDP.";
      }
      enum "upe" {
        value 4;
        description
          "User-end provider edge.";
      }
      enum "ldp-ldp-bak" {
        value 5;
        description
          "PW redundancy of LDP to LDP.";
      }
    }
    description
      "L2VPN switch type.";
  }

  typedef ncs_rpc_notif_encapsulation-type {
    type enumeration {
      enum "fr" {
        value 1;
        description
          "The encapsulation type is FR.";
      }
      enum "atm-aal5-sdu" {
        value 2;
        description
          "The encapsulation type is ATM-AAL5-SDU.";
      }
      enum "atm-trans-cell" {
        value 3;
        description
          "The encapsulation type is ATM-TRANS-CELL.";
      }
      enum "vlan" {
        value 4;
        description
          "The encapsulation type is VLAN.";
      }
      enum "ethernet" {
        value 5;
        description
          "The encapsulation type is ethernet.";
      }
      enum "hdlc" {
        value 6;
        description
          "The encapsulation type is HDLC.";
      }
      enum "ppp" {
        value 7;
        description
          "The encapsulation type is PPP.";
      }
      enum "cem" {
        value 8;
        description
          "The encapsulation type is CEM.";
      }
      enum "atm-nto1-vcc" {
        value 9;
        description
          "The encapsulation type is ATM-Nto1-VCC.";
      }
      enum "atm-nto1-vpc" {
        value 10;
        description
          "The encapsulation type is ATM-Nto1-VPC.";
      }
      enum "ip-layer2" {
        value 11;
        description
          "The encapsulation type is IP-Layer2.";
      }
      enum "atm-1to1-vcc" {
        value 12;
        description
          "The encapsulation type is ATM-1to1-VCC.";
      }
      enum "atm-1to1-vpc" {
        value 13;
        description
          "The encapsulation type is ATM-1to1-VPC.";
      }
      enum "atm-aal5-pdu" {
        value 14;
        description
          "The encapsulation type is ATM-AAL5-PDU.";
      }
      enum "fr-port-mode" {
        value 15;
        description
          "The encapsulation type is FR-PORT-MODE.";
      }
      enum "cep" {
        value 16;
        description
          "The encapsulation type is CEP.";
      }
      enum "satop-e1" {
        value 17;
        description
          "The encapsulation type is SAToP-E1.";
      }
      enum "satop-t1" {
        value 18;
        description
          "The encapsulation type is SAToP-T1.";
      }
      enum "satop-e3" {
        value 19;
        description
          "The encapsulation type is SAToP-E3.";
      }
      enum "satop-t3" {
        value 20;
        description
          "The encapsulation type is SAToP-T3.";
      }
      enum "cesopsn-basic" {
        value 21;
        description
          "The encapsulation type is CESoPSN-BASIC.";
      }
      enum "tdmoip-aal1" {
        value 22;
        description
          "The encapsulation type is TDMoIP-AAL1.";
      }
      enum "cesopsn-tdm" {
        value 23;
        description
          "The encapsulation type is CESoPSN-TDM.";
      }
      enum "tdmoip-aal2" {
        value 24;
        description
          "The encapsulation type is TDMoIP-AAL2.";
      }
      enum "fr-dlci" {
        value 25;
        description
          "The encapsulation type is FR-DLCI.";
      }
      enum "ip-interworking" {
        value 64;
        description
          "The encapsulation type is IP interworking.";
      }
      enum "unsupport" {
        value 255;
        description
          "This encapsulation type is used when the encapsulation types of AC interfaces at the two ends of a local CCC are different, or the ATM bundle interfaces do not have any member, or the VPLS LDP PW on a router inherits the encapsulation type of a VSI.";
      }
    }
    description
      "L2VPN encapsulate type.";
  }

  typedef ncs_rpc_notif_l2vpn-backup-mode {
    type enumeration {
      enum "primary" {
        value 1;
        description
          "The backup mode is primary.";
      }
      enum "secondary" {
        value 2;
        description
          "The backup mode is secondary.";
      }
      enum "bypass" {
        value 3;
        description
          "The backup mode is bypass.";
      }
      enum "ac-bypass" {
        value 4;
        description
          "The backup mode is AC-bypass.";
      }
      enum "pw-bypass" {
        value 5;
        description
          "The backup mode is PW-bypass.";
      }
    }
    description
      "L2VPN backup mode.";
  }

  typedef ncs_rpc_notif_l2vpn-tunnel-type {
    type enumeration {
      enum "invalid" {
        value 0;
        description
          "The tunnel type is invalid.";
      }
      enum "ldp" {
        value 1;
        description
          "The tunnel type is LDP.";
      }
      enum "bgp" {
        value 2;
        description
          "The tunnel type is BGP.";
      }
      enum "te" {
        value 3;
        description
          "The tunnel type is TE.";
      }
      enum "static-lsp" {
        value 4;
        description
          "The tunnel type is static LSP.";
      }
      enum "gre" {
        value 5;
        description
          "The tunnel type is GRE.";
      }
      enum "uni" {
        value 6;
        description
          "The tunnel type is UNI.";
      }
      enum "tnl-group" {
        value 7;
        description
          "The tunnel type is Tunnel group.";
      }
      enum "sub-te" {
        value 8;
        description
          "The tunnel type is Sub-TE.";
      }
      enum "sub-group" {
        value 9;
        description
          "The tunnel type is Sub-group.";
      }
      enum "6over4" {
        value 10;
        description
          "The tunnel type is IPv6-over-IPv4.";
      }
      enum "6to4" {
        value 11;
        description
          "The tunnel type is IPv6-to-IPv4.";
      }
      enum "bgp-local-ifnet" {
        value 12;
        description
          "The tunnel type is BGP local-ifnet.";
      }
      enum "ldp6" {
        value 13;
        description
          "The tunnel type is LDP6.";
      }
      enum "srbe-lsp" {
        value 41;
        description
          "The tunnel type is SRBE LSP.";
      }
    }
    description
      "L2VPN tunnel type.";
  }

  typedef ncs_rpc_notif_l2vpn-mac-type {
    type enumeration {
      enum "static" {
        value 1;
        description
          "The MAC type is static.";
      }
      enum "dynamic" {
        value 2;
        description
          "The MAC type is dynamic.";
      }
      enum "broadcast" {
        value 3;
        description
          "The MAC type is broadcast.";
      }
    }
    description
      "L2VPN MAC type.";
  }

  typedef ncs_rpc_notif_l2vpn-pw-aps-oper-type {
    type enumeration {
      enum "non-revertive" {
        value 0;
        description
          "The PW APS instance is in non-revertive mode.";
      }
      enum "revertive" {
        value 1;
        description
          "The PW APS instance is in revertive mode.";
      }
    }
    description
      "L2VPN PW APS oper type.";
  }

  typedef ncs_rpc_notif_l2vpn-pw-aps-mode {
    type enumeration {
      enum "1to1" {
        value 1;
        description
          "The PW APS mode is 1:1.";
      }
    }
    description
      "L2VPN PW APS mode.";
  }

  typedef ncs_rpc_notif_l2vpn-pw-aps-type {
    type enumeration {
      enum "pw-aps" {
        value 1;
        description
          "The PW APS type is PW APS.";
      }
      enum "mc-pw-aps" {
        value 2;
        description
          "The PW APS type is MC PW APS.";
      }
      enum "pw-fps" {
        value 3;
        description
          "The PW APS type is PW FPS.";
      }
    }
    description
      "L2VPN PW APS type.";
  }

  typedef ncs_rpc_notif_l2vpn-pw-aps-role {
    type enumeration {
      enum "pw-aps" {
        value 1;
        description
          "Default PW APS role for a PW APS instance.";
      }
      enum "master" {
        value 2;
        description
          "Master role for a PW APS instance in the E-PW APS scenario.";
      }
      enum "slave" {
        value 3;
        description
          "Slave role for a PW APS instance in the E-PW APS scenario.";
      }
    }
    description
      "L2VPN PW APS role.";
  }

  typedef ncs_rpc_notif_l2vpn-reroute-mode {
    type enumeration {
      enum "delay" {
        value 1;
        description
          "Delayed switchback.";
      }
      enum "immediately" {
        value 2;
        description
          "Immediate switchback.";
      }
      enum "never" {
        value 3;
        description
          "Never switchback.";
      }
    }
    description
      "L2VPN reroute mode.";
  }

  typedef ncs_rpc_notif_pw-redundancy-mode {
    type enumeration {
      enum "frr" {
        value 0;
        description
          "The PW redundancy mode is FRR.";
      }
      enum "independent" {
        value 1;
        description
          "The PW redundancy mode is independent.";
      }
      enum "master" {
        value 2;
        description
          "The PW redundancy mode is master.";
      }
      enum "none" {
        value 3;
        description
          "The PW redundancy mode is not configured.";
      }
    }
    description
      "PW redundancy mode.";
  }

  typedef ncs_rpc_notif_vpls-redundancy-mode {
    type enumeration {
      enum "independent" {
        value 1;
        description
          "The PW redundancy mode is independent.";
      }
      enum "master" {
        value 2;
        description
          "The PW redundancy mode is master.";
      }
      enum "none" {
        value 3;
        description
          "The PW redundancy mode is not configured.";
      }
    }
    description
      "PW redundancy mode.";
  }

  typedef ncs_rpc_notif_l2vpn-vpls-vsi-mem-disc-type {
    type enumeration {
      enum "default" {
        value 0;
        description
          "The member discovery type is composite.";
      }
      enum "auto" {
        value 1;
        description
          "The member discovery type is automatic.";
      }
      enum "static" {
        value 2;
        description
          "The member discovery type is static.";
      }
    }
    description
      "L2VPN VPLS VSI member discovery type.";
  }

  typedef ncs_rpc_notif_l2vpn-vpls-unknow-frame-act {
    type enumeration {
      enum "broadcast" {
        value 0;
        description
          "Broadcast unknown frames.";
      }
      enum "drop" {
        value 1;
        description
          "Drop unknown frames.";
      }
      enum "local-handle" {
        value 2;
        description
          "Locally handle unknown frames.";
      }
      enum "drop-learn" {
        value 3;
        description
          "Drop unknown frames but learn the MAC addresses of these frames.";
      }
    }
    description
      "L2VPN VPLS unknown frame act.";
  }

  typedef ncs_rpc_notif_l2vpn-vpls-pw-type {
    type enumeration {
      enum "label" {
        value 0;
        description
          "The PW type is label.";
      }
      enum "qinq" {
        value 1;
        description
          "The PW type is QinQ.";
      }
      enum "mehvpls" {
        value 2;
        description
          "The PW type is MEHVPLS. An AC interface is an interface bound to a VSI. On a LDP VPLS network, if the peer is a UPE, the PW connecting the UPE is processed as an AC in internal processing. The detailed VSI information shows that the PW type of the UPE is MEHVPLS.";
      }
    }
    description
      "L2VPN VPLS PW type.";
  }

  typedef ncs_rpc_notif_l2vpn-vpls-traffic-statistics-enable-type {
    type enumeration {
      enum "default" {
        value 0;
        description
          "VSI traffic statistics collection configurations are inherited.";
      }
      enum "disable" {
        value 1;
        description
          "The function to collect VPLS traffic statistics is disabled.";
      }
      enum "enable" {
        value 2;
        description
          "The function to collect VPLS traffic statistics is enabled.";
      }
    }
    description
      "L2VPN VPLS traffic statistics enable type.";
  }

  typedef ncs_rpc_notif_l2vpn-vpls-ldp-pw-state-code {
    type enumeration {
      enum "forward" {
        value 0;
        description
          "Forwarding is supported.";
      }
      enum "standby" {
        value 1;
        description
          "The PW is a secondary PW.";
      }
      enum "ac-fault" {
        value 2;
        description
          "The peer AC interface is faulty.";
      }
      enum "psn-fault" {
        value 3;
        description
          "A fault occurs on the public network between the local end and peer end.";
      }
      enum "not-forward" {
        value 4;
        description
          "Forwarding is not supported.";
      }
    }
    description
      "L2VPN VPLS LDP PW state code.";
  }

  typedef ncs_rpc_notif_l2vpn-vpws-vrrp-state {
    type enumeration {
      enum "initialize" {
        value 0;
        description
          "The VRRP state is initializing.";
      }
      enum "backup" {
        value 1;
        description
          "The VRRP state is backup.";
      }
      enum "master" {
        value 2;
        description
          "The VRRP state is master.";
      }
    }
    description
      "L2VPN VPWS VRRP state.";
  }

  typedef ncs_rpc_notif_l2vpn-vpws-bfd-state {
    type enumeration {
      enum "invalid" {
        value 0;
        description
          "The state of BFD is invalid. The status code is 0.";
      }
      enum "down" {
        value 1;
        description
          "The state of BFD is down.";
      }
      enum "up" {
        value 2;
        description
          "The state of BFD is up.";
      }
      enum "admin-down" {
        value 3;
        description
          "The state of BFD is administratively down.";
      }
    }
    description
      "L2VPN VPWS BFD state.";
  }

  typedef ncs_rpc_notif_l2vpn-aps-bind-type {
    type enumeration {
      enum "admin" {
        value 1;
        description
          "The APS bind type is admin.";
      }
      enum "reference" {
        value 2;
        description
          "The APS bind type is reference.";
      }
    }
    description
      "L2VPN APS bind type.";
  }

  typedef ncs_rpc_notif_oam-protocal {
    type enumeration {
      enum "mpls-oam" {
        value 3;
        description
          "MPLS OAM is used to monitor the link status.";
      }
      enum "tp-oam" {
        value 4;
        description
          "MPLS-TP OAM is used to monitor the link status.";
      }
      enum "none" {
        value 5;
        description
          "No link detection protocol is used to detect the link status, or the packet receiving function of a configured link detection protocol is not enabled.";
      }
    }
    description
      "L2VPN OAM protocol.";
  }

  typedef ncs_rpc_notif_oam-status {
    type enumeration {
      enum "nondefect" {
        value 1;
        description
          "The link status is normal.";
      }
      enum "defect" {
        value 2;
        description
          "The link is faulty.";
      }
      enum "detect-stop" {
        value 3;
        description
          "Link detection stops.";
      }
      enum "invalid" {
        value 4;
        description
          "No link detection protocol is used to detect the link status, or the packet receiving function of a configured link detection protocol is not enabled.";
      }
    }
    description
      "L2VPN OAM status.";
  }

  typedef ncs_rpc_notif_l2vpn-aps-status {
    type enumeration {
      enum "LO" {
        value 1;
        description
          "Services are locked to the primary PW.";
      }
      enum "SF-P" {
        value 2;
        description
          "The secondary or bypass PW becomes faulty.";
      }
      enum "FS" {
        value 3;
        description
          "Services are forcibly switched from the primary PW to the secondary or bypass PW.";
      }
      enum "SF" {
        value 4;
        description
          "The primary PW becomes faulty.";
      }
      enum "SD-P" {
        value 5;
        description
          "Signals degrade on the secondary or bypass PW.";
      }
      enum "SD" {
        value 6;
        description
          "Signals degrade on the primary PW.";
      }
      enum "MS" {
        value 7;
        description
          "Services are manually switched from the primary PW to the secondary or bypass PW.";
      }
      enum "WTR" {
        value 8;
        description
          "The system is waiting to switch traffic back from the secondary or bypass PW to the primary PW.";
      }
      enum "EXER" {
        value 9;
        description
          "The status is exercise.";
      }
      enum "RR" {
        value 10;
        description
          "Revertive switching request.";
      }
      enum "DNR" {
        value 11;
        description
          "Do not revert.";
      }
      enum "NR" {
        value 12;
        description
          "The primary, secondary, or bypass PW is normal.";
      }
      enum "MS-P" {
        value 13;
        description
          "Services are manually switched from the primary PW to the secondary or bypass PW.";
      }
      enum "MS-W" {
        value 14;
        description
          "Services are manually switched from the secondary or bypass PW to the primary PW.";
      }
      enum "EXER-P" {
        value 15;
        description
          "The secondary or bypass PW exercises traffic switching.";
      }
      enum "EXER-W" {
        value 16;
        description
          "The primary PW exercises traffic switching.";
      }
      enum "RR-P" {
        value 17;
        description
          "Services are requested to switch from the primary PW to the secondary or bypass PW.";
      }
      enum "RR-W" {
        value 18;
        description
          "Services are requested to switch from the secondary or bypass PW to the primary PW.";
      }
      enum "NR-P" {
        value 19;
        description
          "Services are not requested to switch from the primary PW to the secondary or bypass PW.";
      }
      enum "NR-W" {
        value 20;
        description
          "Services are not requested to switch from the secondary or bypass PW to the primary PW.";
      }
    }
    description
      "L2VPN APS status.";
  }

  typedef ncs_rpc_notif_l2vpn-aps-path-status {
    type enumeration {
      enum "no-defect" {
        value 0;
        description
          "No fault exists.";
      }
      enum "defect" {
        value 1;
        description
          "A fault exists.";
      }
      enum "defect-sd" {
        value 2;
        description
          "Signals attenuated.";
      }
      enum "invalid" {
        value 3;
        description
          "The working path status cannot be detected because the PW APS instance is in the slave state.";
      }
    }
    description
      "L2VPN APS path status.";
  }

  typedef ncs_rpc_notif_l2vpn-aps-result {
    type enumeration {
      enum "work" {
        value 0;
        description
          "The traffic in the PW protection group is transmitted over the primary PW.";
      }
      enum "protect" {
        value 1;
        description
          "The traffic in the PW protection group is transmitted over the secondary or bypass PW.";
      }
    }
    description
      "L2VPN APS result.";
  }

  typedef ncs_rpc_notif_l2vpn-protect-group-name {
    type string {
      length "1..15";
    }
    description
      "L2VPN protect group name.";
  }

  typedef ncs_rpc_notif_vpn-rt-type {
    type enumeration {
      enum "export-extcommunity" {
        value 2;
        description
          "Extended community attribute of the route from an outbound interface to the destination VPN.";
      }
      enum "import-extcommunity" {
        value 3;
        description
          "Receive routes that carry the specified extended community attribute.";
      }
    }
    description
      "L2VPN common VPN RT type.";
  }

  typedef ncs_rpc_notif_vpls-split-horizon-mode-type {
    type enumeration {
      enum "spoke" {
        value 1;
        description
          "The split horizon mode type is spoke.";
      }
      enum "hub" {
        value 2;
        description
          "The split horizon mode type is hub.";
      }
    }
    description
      "L2VPN VPLS split horizon mode type.";
  }

  typedef ncs_rpc_notif_pw-signal-type {
    type enumeration {
      enum "ldp" {
        value 1;
        description
          "The PW signal type is LDP.";
      }
      enum "static" {
        value 2;
        description
          "The PW signal type is static.";
      }
    }
    description
      "L2VPN PW signal type.";
  }

  typedef ncs_rpc_notif_l2vpn-rtp-header-type {
    type enumeration {
      enum "false" {
        value 0;
        description
          "The function to add RTP headers to packets is disabled.";
      }
      enum "standard" {
        value 1;
        description
          "Add standard RTP headers to packets.";
      }
      enum "private" {
        value 2;
        description
          "Add vendor-specific RTP headers to packets.";
      }
    }
    description
      "L2VPN RT header type.";
  }

  typedef ncs_rpc_notif_l2vpn-payload-comp {
    type enumeration {
      enum "disable" {
        value 0;
        description
          "Disable payload compression.";
      }
      enum "uneq" {
        value 1;
        description
          "Send DBA packets when the unequipped circuit indication is detected.";
      }
    }
    description
      "L2VPN payload compression.";
  }

  typedef ncs_rpc_notif_l2vpn-route-status {
    type enumeration {
      enum "reachable" {
        value 1;
        description
          "The route status is reachable.";
      }
      enum "unreachable" {
        value 2;
        description
          "The route status is unreachable.";
      }
    }
    description
      "L2VPN route status.";
  }

  typedef ncs_rpc_notif_ac-oam-mapping-type {
    type enumeration {
      enum "default" {
        value 1;
        description
          "The AC OAM mapping type is default.";
      }
      enum "1ag" {
        value 2;
        description
          "The AC OAM mapping type is 1ag.";
      }
      enum "3ah" {
        value 3;
        description
          "The AC OAM mapping type is 3ah.";
      }
    }
    description
      "L2VPN AC OAM mapping type.";
  }

  typedef ncs_rpc_notif_oam-state {
    type enumeration {
      enum "down" {
        value 0;
        description
          "The MC OAM state is down.";
      }
      enum "up" {
        value 1;
        description
          "The MC OAM state is up.";
      }
      enum "invalid" {
        value 2;
        description
          "The MC OAM state is invalid.";
      }
    }
    description
      "L2VPN MC OAM state.";
  }

  typedef ncs_rpc_notif_flow-label-ability {
    type enumeration {
      enum "default" {
        value 0;
        description
          "The flow label ability is default.";
      }
      enum "send" {
        value 1;
        description
          "Ability to send flow labels.";
      }
      enum "receive" {
        value 2;
        description
          "Ability to receive flow labels.";
      }
      enum "both" {
        value 3;
        description
          "Ability to both send and receive flow labels.";
      }
      enum "disable" {
        value 4;
        description
          "Ability to disable flow labels.";
      }
    }
    description
      "L2VPN flow label ability.";
  }

  typedef ncs_rpc_notif_l2vpn-load-balance-type {
    type enumeration {
      enum "packet" {
        value 1;
        description
          "Per-packet load balancing.";
      }
      enum "flow" {
        value 2;
        description
          "Per-flow load balancing.";
      }
    }
    description
      "L2VPN load balance type.";
  }

  typedef ncs_rpc_notif_bgp-encap-type {
    type enumeration {
      enum "vpls" {
        value 19;
        description
          "The encapsulation type is BGP VPLS.";
      }
    }
    description
      "L2VPN BGP encapsulation type.";
  }

  typedef ncs_rpc_notif_vsi-work-mode {
    type enumeration {
      enum "normal" {
        value 0;
        description
          "The VSI work mode is normal.";
      }
      enum "bd-mode" {
        value 1;
        description
          "The VSI work mode is bd-mode.";
      }
      enum "b-vsi" {
        value 3;
        description
          "Used to process B-MAC addresses and determine a PW's remote PE based on the configured peer address.";
      }
      enum "i-vsi" {
        value 4;
        description
          "I-VSI with no service type specified.";
      }
      enum "i-vsi-p2p" {
        value 5;
        description
          "The VSI work mode is P2P I-VSI.";
      }
      enum "i-vsi-b-evpn-interworking" {
        value 7;
        description
          "The VSI work mode is I-VSI accessing B-EVPN.";
      }
    }
    description
      "L2VPN VPLS VSI work mode.";
  }

  typedef ncs_rpc_notif_send-receive-active-status {
    type enumeration {
      enum "send-receive-inactive" {
        value 0;
        description
          "Send inactive and receive inactive.";
      }
      enum "send-active-receive-inactive" {
        value 2;
        description
          "Send active and receive inactive.";
      }
      enum "send-inactive-receive-active" {
        value 4;
        description
          "Send inactive and receive active.";
      }
      enum "send-receive-active" {
        value 6;
        description
          "Send active and receive active.";
      }
    }
    description
      "L2VPN sernd recv active status.";
  }

  typedef ncs_rpc_notif_ac-block-status {
    type enumeration {
      enum "unblocked" {
        value 0;
        description
          "The block status of AC is unblocked.";
      }
      enum "blocked" {
        value 1;
        description
          "The block status of AC is blocked.";
      }
    }
    description
      "L2VPN AC block status.";
  }

  typedef ncs_rpc_notif_vpws-bgp-ce-name-type {
    type string {
      length "1..20";
    }
    description
      "L2VPN VPWS BGP CE name.";
  }

  typedef ncs_rpc_notif_vpls-multi-homing-site-name {
    type string {
      length "1..19";
      pattern '[a-zA-Z][a-zA-Z0-9_-]*';
    }
    description
      "L2VPN VPLS multi-homing site name.";
  }

  typedef ncs_rpc_notif_bfd-vccv-cv-type {
    type enumeration {
      enum "cv-linkage-bfd" {
        value 0;
        description
          "IP/UDP encapsulation supports fault detection and status signaling.";
      }
      enum "cv-bfd" {
        value 1;
        description
          "Fault Detection Only.";
      }
      enum "cv-pw-ach-bfd" {
        value 2;
        description
          "PW-ACH encapsulation supports only fault detection.";
      }
    }
    description
      "L2VPN BFD VCCV CV type.";
  }

  typedef ncs_rpc_notif_l2vpn-common-enable-type {
    type enumeration {
      enum "disable" {
        value 1;
        description
          "The setting is disabled.";
      }
      enum "enable" {
        value 2;
        description
          "The setting is enabled.";
      }
    }
    description
      "L2VPN common enable.";
  }

  typedef ncs_rpc_notif_interface-change-withdraw-type {
    type enumeration {
      enum "all" {
        value 0;
        description
          "The interface change withdraw type is all.";
      }
      enum "up" {
        value 1;
        description
          "The interface change withdraw type is up.";
      }
      enum "down" {
        value 2;
        description
          "The interface change withdraw type is down.";
      }
    }
    description
      "Interface change withdraw type.";
  }

  typedef ncs_rpc_notif_suppression-type {
    type enumeration {
      enum "broadcast" {
        value 0;
        description
          "The suppression type is broadcast.";
      }
      enum "multicast" {
        value 1;
        description
          "The suppression type is multicast.";
      }
      enum "unknown-unicast" {
        value 2;
        description
          "The suppression type is unknown-unicast.";
      }
    }
    description
      "L2VPN suppression type.";
  }

  typedef ncs_rpc_notif_mac-remove-type {
    type enumeration {
      enum "invalid" {
        value 0;
        description
          "The MAC remove type is invalid.";
      }
      enum "all-but-mine" {
        value 1;
        description
          "The MAC remove type is all-but-mine.";
      }
      enum "all-from-me" {
        value 2;
        description
          "The MAC remove type is all-from-me.";
      }
    }
    description
      "L2VPN MAC remove type.";
  }

  typedef ncs_rpc_notif_l2vpn-arp-send-type {
    type enumeration {
      enum "dual-send" {
        value 1;
        description
          "The ARP send type is dual send.";
      }
      enum "single-send" {
        value 2;
        description
          "The ARP send type is single send.";
      }
    }
    description
      "L2VPN ARP send type.";
  }

  typedef ncs_rpc_notif_l2vpn-nd-send-type {
    type enumeration {
      enum "dual-send" {
        value 1;
        description
          "The ND send type is dual send.";
      }
    }
    description
      "L2VPN ND send type.";
  }

  typedef ncs_rpc_notif_l2vpn-pw-aps-ps-type {
    type enumeration {
      enum "manual" {
        value 1;
        description
          "Traffic is switched to the protection path manually. If the protection path is down, traffic cannot be switched and an error message will be displayed.";
      }
      enum "force" {
        value 2;
        description
          "Traffic is forced to switch to the protection path regardless of whether the protection path is up.";
      }
      enum "lock" {
        value 3;
        description
          "Traffic is locked to the working path, and is not switched to the protection path even if the working path becomes faulty.";
      }
      enum "clear" {
        value 4;
        description
          "Clear the manual switch request configured.";
      }
      enum "manual-to-work" {
        value 5;
        description
          "Traffic is switched to the working path manually. If the working path is down, traffic cannot be switched and an error message will be displayed.";
      }
      enum "manual-to-protect" {
        value 6;
        description
          "Traffic is switched to the protection path manually. If the protection path is down, traffic cannot be switched and an error message will be displayed.";
      }
      enum "exercise" {
        value 7;
        description
          "Switching exercise mode.";
      }
    }
    description
      "L2VPN PW APS PS type.";
  }

  typedef ncs_rpc_notif_l2vpn-protect-group-ps-type {
    type enumeration {
      enum "manual" {
        value 1;
        description
          "The switching type of the PW protection group is manual switching.";
      }
      enum "clear" {
        value 2;
        description
          "The switching type of the PW protection group is clear.";
      }
    }
    description
      "L2VPN protect group PS type.";
  }

  typedef ncs_rpc_notif_multicast-tunnel-type {
    type enumeration {
      enum "invalid" {
        value 0;
        description
          "The MC tunnel type is invalid.";
      }
      enum "mldp-p2mp" {
        value 1;
        description
          "The MC tunnel type is mLDP P2MP.";
      }
      enum "te-p2mp" {
        value 3;
        description
          "The MC tunnel type is TE P2MP.";
      }
    }
    description
      "L2VPN MC tunnel type.";
  }

  typedef ncs_rpc_notif_pw-block-status {
    type enumeration {
      enum "default" {
        value 0;
        description
          "The block status of PW is default.";
      }
      enum "blocked" {
        value 1;
        description
          "The block status of PW is blocked.";
      }
      enum "unblocked" {
        value 2;
        description
          "The block status of PW is unblocked.";
      }
      enum "temp-blocked" {
        value 3;
        description
          "The block status of PW is temp blocked.";
      }
    }
    description
      "L2VPN PW block status.";
  }

  typedef ncs_rpc_notif_vpws-bgp-vpn-encap {
    type enumeration {
      enum "atm-aal5-sdu" {
        value 2;
        description
          "The encapsulation type is ATM-AAL5-SDU.";
      }
      enum "atm-trans-cell" {
        value 3;
        description
          "The encapsulation type is ATM-TRANS-CELL.";
      }
      enum "vlan" {
        value 4;
        description
          "The encapsulation type is VLAN.";
      }
      enum "ethernet" {
        value 5;
        description
          "The encapsulation type is ethernet.";
      }
      enum "hdlc" {
        value 6;
        description
          "The encapsulation type is HDLC.";
      }
      enum "ppp" {
        value 7;
        description
          "The encapsulation type is PPP.";
      }
      enum "atm-nto1-vcc" {
        value 9;
        description
          "The encapsulation type is ATM-Nto1-VCC.";
      }
      enum "atm-nto1-vpc" {
        value 10;
        description
          "The encapsulation type is ATM-Nto1-VPC.";
      }
      enum "ip-layer2" {
        value 11;
        description
          "The encapsulation type is IP-Layer2.";
      }
      enum "atm-1to1-vcc" {
        value 12;
        description
          "The encapsulation type is ATM-1to1-VCC.";
      }
      enum "atm-1to1-vpc" {
        value 13;
        description
          "The encapsulation type is ATM-1to1-VPC.";
      }
      enum "ip-interworking" {
        value 64;
        description
          "The encapsulation type is IP interworking.";
      }
    }
    description
      "Encapsulation type for a VPWS BGP VPN instance.";
  }

  typedef ncs_rpc_notif_l2vpn-vpls-pw-bfd-state {
    type enumeration {
      enum "invalid" {
        value 0;
        description
          "The state of BFD is invalid.";
      }
      enum "down" {
        value 1;
        description
          "The state of BFD is down.";
      }
      enum "up" {
        value 2;
        description
          "The state of BFD is up.";
      }
      enum "admin-down" {
        value 3;
        description
          "The state of BFD is administratively down.";
      }
      enum "remote-ac-error" {
        value 4;
        description
          "The state of BFD is remote AC error.";
      }
      enum "remote-ac-error-resume" {
        value 5;
        description
          "The state of BFD is remote AC error resume.";
      }
    }
    description
      "BFD for VPLS PW state.";
  }

  typedef ncs_rpc_notif_vpws-bgp-pw-type {
    type enumeration {
      enum "local" {
        value 0;
        description
          "The BGP PW type is local.";
      }
      enum "remote" {
        value 1;
        description
          "The BGP PW type is remote.";
      }
      enum "unknown" {
        value 2;
        description
          "The BGP PW type is unknown.";
      }
    }
    description
      "L2VPN VPWS BGP PW type.";
  }

  typedef ncs_rpc_notif_vpws-bgp-ac-oam-state {
    type enumeration {
      enum "down" {
        value 0;
        description
          "The AC OAM state is down.";
      }
      enum "up" {
        value 1;
        description
          "The AC OAM state is up.";
      }
      enum "invalid" {
        value 2;
        description
          "The AC OAM state is invalid.";
      }
    }
    description
      "L2VPN VPWS BGP AC OAM state.";
  }

  typedef ncs_rpc_notif_vpls-ldp-peer-type {
    type enumeration {
      enum "static" {
        value 0;
        description
          "The peer type is static.";
      }
      enum "dynamic" {
        value 1;
        description
          "The peer type is dynamic.";
      }
    }
    description
      "L2VPN VPLS LDP peer type.";
  }

  typedef ncs_rpc_notif_vpls-loop-detect-type {
    type enumeration {
      enum "detect-loop" {
        value 1;
        description
          "A loop is detected before the maximum number of hops is reached.";
      }
      enum "exceed-max-hop" {
        value 2;
        description
          "The maximum number of hops for loop detection has been exceeded.";
      }
    }
    description
      "L2VPN VPLS loop detect type.";
  }

  typedef ncs_rpc_notif_vpls-bgp-encapsulation-type {
    type enumeration {
      enum "vpls" {
        value 19;
        description
          "The encapsulation type is BGP VPLS.";
      }
    }
    description
      "L2VPN BGP encapsulation type.";
  }

  typedef ncs_rpc_notif_control-flag-bits-type {
    type bits {
      bit sbit {
        position 0;
        description
          "S bit.";
      }
      bit local-cbit {
        position 1;
        description
          "Local C bit.";
      }
      bit fbit {
        position 2;
        description
          "F bit.";
      }
      bit qbit {
        position 3;
        description
          "Q bit.";
      }
      bit remote-c-bit {
        position 4;
        description
          "Remote C bit.";
      }
    }
    description
      "Indicates the control flag.";
  }

  typedef ncs_rpc_notif_vsi-pbb-instance-type {
    type enumeration {
      enum "normal" {
        value 0;
        description
          "Normal mode.";
      }
      enum "b-vsi" {
        value 1;
        description
          "Used to process B-MAC addresses and determine a PW's remote PE based on the configured peer address.";
      }
      enum "i-vsi" {
        value 2;
        description
          "Used to encapsulate packets into PBB frames and is bound to an AC interface for local CE identification.";
      }
    }
    description
      "L2VPN VSI PBB instance style.";
  }

  typedef ncs_rpc_notif_vsi-pbb-learned-flag {
    type enumeration {
      enum "no-mac" {
        value 1;
        description
          "No B-MAC outbound interface has been learned.";
      }
      enum "first" {
        value 2;
        description
          "This B-MAC outbound interface was learned first.";
      }
      enum "master" {
        value 3;
        description
          "Primary B-MAC outbound interface learned.";
      }
      enum "backup" {
        value 4;
        description
          "Secondary B-MAC outbound interface learned.";
      }
    }
    description
      "L2VPN VSI PBB learned flag.";
  }

  typedef ncs_rpc_notif_multicast-active-state {
    type enumeration {
      enum "default" {
        value 0;
        description
          "The MC active state is none.";
      }
      enum "inactive" {
        value 1;
        description
          "The MC active state is inactive.";
      }
      enum "active" {
        value 2;
        description
          "The MC active state is active.";
      }
    }
    description
      "L2VPN MC active state.";
  }

  typedef ncs_rpc_notif_multicast-oam-type {
    type enumeration {
      enum "none" {
        value 0;
        description
          "The MC OAM type is none.";
      }
      enum "static-bfd" {
        value 1;
        description
          "The MC OAM type is static BFD.";
      }
      enum "bfd" {
        value 2;
        description
          "The MC OAM type is dynamic BFD.";
      }
      enum "mpls-oam" {
        value 3;
        description
          "MPLS OAM is used to detect the link status.";
      }
      enum "tp-oam" {
        value 4;
        description
          "MPLS-TP OAM is used to detect the link status.";
      }
    }
    description
      "L2VPN MC OAM type.";
  }

  typedef ncs_rpc_notif_suppression-direction {
    type enumeration {
      enum "both" {
        value 0;
        description
          "The suppression direction is both.";
      }
      enum "in-bound" {
        value 1;
        description
          "The suppression direction is inbound.";
      }
      enum "out-bound" {
        value 2;
        description
          "The suppression direction is outbound.";
      }
    }
    description
      "L2VPN suppression direction.";
  }

  typedef ncs_rpc_notif_etree-work-mode {
    type enumeration {
      enum "default" {
        value 0;
        description
          "The e-tree work mode of the PW is not specified.";
      }
      enum "optimized" {
        value 1;
        description
          "The e-tree work mode of the PW is optimized.";
      }
      enum "compatible" {
        value 2;
        description
          "The e-tree work mode of the PW is compatible.";
      }
    }
    description
      "The e-tree work mode of the PW.";
  }

  typedef ncs_rpc_notif_etree-access-role {
    type enumeration {
      enum "root" {
        value 1;
        description
          "The e-tree access role of the AC is root.";
      }
      enum "leaf" {
        value 2;
        description
          "The e-tree access role of the AC is leaf.";
      }
    }
    description
      "The e-tree access role of the AC.";
  }

  typedef live_ncs_l2vpn-instance-name {
    type string {
      length "1..31";
    }
    description
      "L2VPN instance name.";
  }

  typedef live_ncs_l2vpn-peer-address-type {
    type inet:ipv4-address-no-zone {
      pattern '(([1-9]|[1-9][0-9]|1[0-1][0-9]|12[0-6]|12[8-9]|1[3-9][0-9]|2[0-1][0-9]|22[0-4])\.)(([0-9]|[1-9][0-9]|1[0-9][0-9]|2[0-4][0-9]|25[0-5])\.){2}([0-9]|[1-9][0-9]|1[0-9][0-9]|2[0-4][0-9]|25[0-5])';
    }
    description
      "IP address of a peer.";
  }

  typedef live_ncs_l2vpn-vpls-encap-type {
    type enumeration {
      enum "vlan" {
        value 4;
        description
          "The encapsulation type of VPLS is VLAN.";
      }
      enum "ethernet" {
        value 5;
        description
          "The encapsulation type of VPLS is ethernet.";
      }
    }
    description
      "L2VPN VPLS encapsulation type.";
  }

  typedef live_ncs_l2vpn-vpls-ldp-pw-encap-type {
    type enumeration {
      enum "vlan" {
        value 4;
        description
          "The VPLS LDP PW encapsulation type is VLAN.";
      }
      enum "ethernet" {
        value 5;
        description
          "The VPLS LDP PW encapsulation type is ethernet.";
      }
      enum "unsupport" {
        value 255;
        description
          "Unsupported encapsulation type.";
      }
    }
    description
      "L2VPN VPLS LDP PW encapsulation type.";
  }

  typedef live_ncs_l2vpn-mac-learn-style {
    type enumeration {
      enum "unqualify" {
        value 1;
        description
          "The MAC learn style is unqualify.";
      }
      enum "qualify" {
        value 2;
        description
          "The MAC learn style is qualify.";
      }
      enum "qualify-outer-vlan" {
        value 3;
        description
          "Learn MAC addresses in qualified mode by explicitly using outer VLAN ID.";
      }
      enum "qualify-inner-vlan" {
        value 4;
        description
          "Learn MAC addresses in qualified mode by explicitly using inner VLAN ID.";
      }
    }
    description
      "L2VPN MAC learn style.";
  }

  typedef live_ncs_pw-role-type {
    type enumeration {
      enum "primary" {
        value 1;
        description
          "The PW role type is primary.";
      }
      enum "backup" {
        value 2;
        description
          "The PW role type is backup.";
      }
      enum "bypass" {
        value 3;
        description
          "The PW role type is bypass.";
      }
      enum "ac-bypass" {
        value 7;
        description
          "The PW role type is AC-bypass.";
      }
      enum "pw-bypass" {
        value 8;
        description
          "The PW role type is PW-bypass.";
      }
    }
    description
      "L2VPN PW role type.";
  }

  typedef live_ncs_vpls-pw-role-type {
    type enumeration {
      enum "primary" {
        value 1;
        description
          "The PW role type is primary.";
      }
      enum "backup" {
        value 2;
        description
          "The PW role type is backup.";
      }
    }
    description
      "VPLS PW role type.";
  }

  typedef live_ncs_ms-pw-role-type {
    type enumeration {
      enum "left-primary" {
        value 4;
        description
          "The left side PW of multi-segment instance.";
      }
      enum "right-primary" {
        value 5;
        description
          "The right side PW of multi-segment instance.";
      }
      enum "right-backup" {
        value 6;
        description
          "The backup of the right side PW.";
      }
    }
    description
      "L2VPN multi-segment PW role.";
  }

  typedef live_ncs_l2vpn-pw-template-name {
    type string {
      length "1..19";
    }
    description
      "L2VPN PW template name.";
  }

  typedef live_ncs_l2vpn-pw-name {
    type string {
      length "1..15";
    }
    description
      "L2VPN PW name.";
  }

  typedef live_ncs_l2vpn-state {
    type enumeration {
      enum "default" {
        value 0;
        description
          "The state is default.";
      }
      enum "down" {
        value 1;
        description
          "The state is down.";
      }
      enum "up" {
        value 2;
        description
          "The state is up.";
      }
    }
    description
      "L2VPN state.";
  }

  typedef live_ncs_instance-state {
    type enumeration {
      enum "down" {
        value 0;
        description
          "The instance state is down.";
      }
      enum "up" {
        value 1;
        description
          "The instance state is up.";
      }
      enum "admin-down" {
        value 2;
        description
          "The instance state is admin down.";
      }
    }
    description
      "L2VPN instance state.";
  }

  typedef live_ncs_ac-state {
    type enumeration {
      enum "down" {
        value 0;
        description
          "The AC state is down.";
      }
      enum "up" {
        value 1;
        description
          "The AC state is up.";
      }
      enum "plug-out" {
        value 2;
        description
          "The AC state is plug-out.";
      }
      enum "notify-down" {
        value 3;
        description
          "The AC state is notify-down.";
      }
      enum "down-notify" {
        value 4;
        description
          "The AC state is down-notify.";
      }
    }
    description
      "L2VPN AC state.";
  }

  typedef live_ncs_l2vpn-pw-state {
    type enumeration {
      enum "down" {
        value 0;
        description
          "The PW state is down.";
      }
      enum "up" {
        value 1;
        description
          "The PW state is up.";
      }
      enum "backup" {
        value 2;
        description
          "The PW state is backup.";
      }
    }
    description
      "L2VPN PW state.";
  }

  typedef live_ncs_l2vpn-forward-state {
    type enumeration {
      enum "not-forwarding" {
        value 0;
        description
          "The forward state is not forwarding.";
      }
      enum "forwarding" {
        value 1;
        description
          "The forward state is forwarding.";
      }
    }
    description
      "L2VPN forward state.";
  }

  typedef live_ncs_ldp-signal-type {
    type enumeration {
      enum "pwe3" {
        value 0;
        description
          "Pseudo-wire emulation edge to edge.";
      }
      enum "martini" {
        value 1;
        description
          "Martini mode.";
      }
    }
    description
      "L2VPN LDP signal mode.";
  }

  typedef live_ncs_l2vpn-peer-ldp-signal-mode {
    type enumeration {
      enum "pwe3" {
        value 0;
        description
          "Pseudo-Wire Emulation Edge to Edge.";
      }
      enum "martini" {
        value 1;
        description
          "Martini mode.";
      }
      enum "default" {
        value 2;
        description
          "Default mode.";
      }
    }
    description
      "L2VPN peer LDP signal mode.";
  }

  typedef live_ncs_l2vpn-control-word {
    type enumeration {
      enum "default" {
        value 0;
        description
          "The control word mode is default.";
      }
      enum "disable" {
        value 1;
        description
          "The control word mode is disable.";
      }
      enum "enable" {
        value 2;
        description
          "The control word mode is enable.";
      }
      enum "prefer" {
        value 3;
        description
          "The control word mode is prefer.";
      }
    }
    description
      "L2VPN control word.";
  }

  typedef live_ncs_l2vpn-instance-type {
    type enumeration {
      enum "vpws-local-ccc" {
        value 1;
        description
          "The instance type is VPWS local CCC.";
      }
      enum "vpws-remote-ccc" {
        value 2;
        description
          "The instance type is VPWS remote CCC.";
      }
      enum "vpws-svc" {
        value 3;
        description
          "The instance type is VPWS SVC.";
      }
      enum "vpws-ldp" {
        value 4;
        description
          "The instance type is VPWS LDP.";
      }
      enum "vpws-switch" {
        value 5;
        description
          "The instance type is VPWS switching.";
      }
      enum "vpls" {
        value 6;
        description
          "Virtual private LAN service.";
      }
      enum "vpws-bgp" {
        value 8;
        description
          "The instance type is VPWS BGP.";
      }
      enum "vpws-single-ccc" {
        value 9;
        description
          "The instance type is VPWS single CCC.";
      }
    }
    description
      "L2VPN instance type.";
  }

  typedef live_ncs_l2vpn-switch-type {
    type enumeration {
      enum "svc-svc" {
        value 1;
        description
          "SVC to SVC.";
      }
      enum "ldp-svc" {
        value 2;
        description
          "LDP to SVC.";
      }
      enum "ldp-ldp" {
        value 3;
        description
          "LDP to LDP.";
      }
      enum "upe" {
        value 4;
        description
          "User-end provider edge.";
      }
      enum "ldp-ldp-bak" {
        value 5;
        description
          "PW redundancy of LDP to LDP.";
      }
    }
    description
      "L2VPN switch type.";
  }

  typedef live_ncs_encapsulation-type {
    type enumeration {
      enum "fr" {
        value 1;
        description
          "The encapsulation type is FR.";
      }
      enum "atm-aal5-sdu" {
        value 2;
        description
          "The encapsulation type is ATM-AAL5-SDU.";
      }
      enum "atm-trans-cell" {
        value 3;
        description
          "The encapsulation type is ATM-TRANS-CELL.";
      }
      enum "vlan" {
        value 4;
        description
          "The encapsulation type is VLAN.";
      }
      enum "ethernet" {
        value 5;
        description
          "The encapsulation type is ethernet.";
      }
      enum "hdlc" {
        value 6;
        description
          "The encapsulation type is HDLC.";
      }
      enum "ppp" {
        value 7;
        description
          "The encapsulation type is PPP.";
      }
      enum "cem" {
        value 8;
        description
          "The encapsulation type is CEM.";
      }
      enum "atm-nto1-vcc" {
        value 9;
        description
          "The encapsulation type is ATM-Nto1-VCC.";
      }
      enum "atm-nto1-vpc" {
        value 10;
        description
          "The encapsulation type is ATM-Nto1-VPC.";
      }
      enum "ip-layer2" {
        value 11;
        description
          "The encapsulation type is IP-Layer2.";
      }
      enum "atm-1to1-vcc" {
        value 12;
        description
          "The encapsulation type is ATM-1to1-VCC.";
      }
      enum "atm-1to1-vpc" {
        value 13;
        description
          "The encapsulation type is ATM-1to1-VPC.";
      }
      enum "atm-aal5-pdu" {
        value 14;
        description
          "The encapsulation type is ATM-AAL5-PDU.";
      }
      enum "fr-port-mode" {
        value 15;
        description
          "The encapsulation type is FR-PORT-MODE.";
      }
      enum "cep" {
        value 16;
        description
          "The encapsulation type is CEP.";
      }
      enum "satop-e1" {
        value 17;
        description
          "The encapsulation type is SAToP-E1.";
      }
      enum "satop-t1" {
        value 18;
        description
          "The encapsulation type is SAToP-T1.";
      }
      enum "satop-e3" {
        value 19;
        description
          "The encapsulation type is SAToP-E3.";
      }
      enum "satop-t3" {
        value 20;
        description
          "The encapsulation type is SAToP-T3.";
      }
      enum "cesopsn-basic" {
        value 21;
        description
          "The encapsulation type is CESoPSN-BASIC.";
      }
      enum "tdmoip-aal1" {
        value 22;
        description
          "The encapsulation type is TDMoIP-AAL1.";
      }
      enum "cesopsn-tdm" {
        value 23;
        description
          "The encapsulation type is CESoPSN-TDM.";
      }
      enum "tdmoip-aal2" {
        value 24;
        description
          "The encapsulation type is TDMoIP-AAL2.";
      }
      enum "fr-dlci" {
        value 25;
        description
          "The encapsulation type is FR-DLCI.";
      }
      enum "ip-interworking" {
        value 64;
        description
          "The encapsulation type is IP interworking.";
      }
      enum "unsupport" {
        value 255;
        description
          "This encapsulation type is used when the encapsulation types of AC interfaces at the two ends of a local CCC are different, or the ATM bundle interfaces do not have any member, or the VPLS LDP PW on a router inherits the encapsulation type of a VSI.";
      }
    }
    description
      "L2VPN encapsulate type.";
  }

  typedef live_ncs_l2vpn-backup-mode {
    type enumeration {
      enum "primary" {
        value 1;
        description
          "The backup mode is primary.";
      }
      enum "secondary" {
        value 2;
        description
          "The backup mode is secondary.";
      }
      enum "bypass" {
        value 3;
        description
          "The backup mode is bypass.";
      }
      enum "ac-bypass" {
        value 4;
        description
          "The backup mode is AC-bypass.";
      }
      enum "pw-bypass" {
        value 5;
        description
          "The backup mode is PW-bypass.";
      }
    }
    description
      "L2VPN backup mode.";
  }

  typedef live_ncs_l2vpn-tunnel-type {
    type enumeration {
      enum "invalid" {
        value 0;
        description
          "The tunnel type is invalid.";
      }
      enum "ldp" {
        value 1;
        description
          "The tunnel type is LDP.";
      }
      enum "bgp" {
        value 2;
        description
          "The tunnel type is BGP.";
      }
      enum "te" {
        value 3;
        description
          "The tunnel type is TE.";
      }
      enum "static-lsp" {
        value 4;
        description
          "The tunnel type is static LSP.";
      }
      enum "gre" {
        value 5;
        description
          "The tunnel type is GRE.";
      }
      enum "uni" {
        value 6;
        description
          "The tunnel type is UNI.";
      }
      enum "tnl-group" {
        value 7;
        description
          "The tunnel type is Tunnel group.";
      }
      enum "sub-te" {
        value 8;
        description
          "The tunnel type is Sub-TE.";
      }
      enum "sub-group" {
        value 9;
        description
          "The tunnel type is Sub-group.";
      }
      enum "6over4" {
        value 10;
        description
          "The tunnel type is IPv6-over-IPv4.";
      }
      enum "6to4" {
        value 11;
        description
          "The tunnel type is IPv6-to-IPv4.";
      }
      enum "bgp-local-ifnet" {
        value 12;
        description
          "The tunnel type is BGP local-ifnet.";
      }
      enum "ldp6" {
        value 13;
        description
          "The tunnel type is LDP6.";
      }
      enum "srbe-lsp" {
        value 41;
        description
          "The tunnel type is SRBE LSP.";
      }
    }
    description
      "L2VPN tunnel type.";
  }

  typedef live_ncs_l2vpn-mac-type {
    type enumeration {
      enum "static" {
        value 1;
        description
          "The MAC type is static.";
      }
      enum "dynamic" {
        value 2;
        description
          "The MAC type is dynamic.";
      }
      enum "broadcast" {
        value 3;
        description
          "The MAC type is broadcast.";
      }
    }
    description
      "L2VPN MAC type.";
  }

  typedef live_ncs_l2vpn-pw-aps-oper-type {
    type enumeration {
      enum "non-revertive" {
        value 0;
        description
          "The PW APS instance is in non-revertive mode.";
      }
      enum "revertive" {
        value 1;
        description
          "The PW APS instance is in revertive mode.";
      }
    }
    description
      "L2VPN PW APS oper type.";
  }

  typedef live_ncs_l2vpn-pw-aps-mode {
    type enumeration {
      enum "1to1" {
        value 1;
        description
          "The PW APS mode is 1:1.";
      }
    }
    description
      "L2VPN PW APS mode.";
  }

  typedef live_ncs_l2vpn-pw-aps-type {
    type enumeration {
      enum "pw-aps" {
        value 1;
        description
          "The PW APS type is PW APS.";
      }
      enum "mc-pw-aps" {
        value 2;
        description
          "The PW APS type is MC PW APS.";
      }
      enum "pw-fps" {
        value 3;
        description
          "The PW APS type is PW FPS.";
      }
    }
    description
      "L2VPN PW APS type.";
  }

  typedef live_ncs_l2vpn-pw-aps-role {
    type enumeration {
      enum "pw-aps" {
        value 1;
        description
          "Default PW APS role for a PW APS instance.";
      }
      enum "master" {
        value 2;
        description
          "Master role for a PW APS instance in the E-PW APS scenario.";
      }
      enum "slave" {
        value 3;
        description
          "Slave role for a PW APS instance in the E-PW APS scenario.";
      }
    }
    description
      "L2VPN PW APS role.";
  }

  typedef live_ncs_l2vpn-reroute-mode {
    type enumeration {
      enum "delay" {
        value 1;
        description
          "Delayed switchback.";
      }
      enum "immediately" {
        value 2;
        description
          "Immediate switchback.";
      }
      enum "never" {
        value 3;
        description
          "Never switchback.";
      }
    }
    description
      "L2VPN reroute mode.";
  }

  typedef live_ncs_pw-redundancy-mode {
    type enumeration {
      enum "frr" {
        value 0;
        description
          "The PW redundancy mode is FRR.";
      }
      enum "independent" {
        value 1;
        description
          "The PW redundancy mode is independent.";
      }
      enum "master" {
        value 2;
        description
          "The PW redundancy mode is master.";
      }
      enum "none" {
        value 3;
        description
          "The PW redundancy mode is not configured.";
      }
    }
    description
      "PW redundancy mode.";
  }

  typedef live_ncs_vpls-redundancy-mode {
    type enumeration {
      enum "independent" {
        value 1;
        description
          "The PW redundancy mode is independent.";
      }
      enum "master" {
        value 2;
        description
          "The PW redundancy mode is master.";
      }
      enum "none" {
        value 3;
        description
          "The PW redundancy mode is not configured.";
      }
    }
    description
      "PW redundancy mode.";
  }

  typedef live_ncs_l2vpn-vpls-vsi-mem-disc-type {
    type enumeration {
      enum "default" {
        value 0;
        description
          "The member discovery type is composite.";
      }
      enum "auto" {
        value 1;
        description
          "The member discovery type is automatic.";
      }
      enum "static" {
        value 2;
        description
          "The member discovery type is static.";
      }
    }
    description
      "L2VPN VPLS VSI member discovery type.";
  }

  typedef live_ncs_l2vpn-vpls-unknow-frame-act {
    type enumeration {
      enum "broadcast" {
        value 0;
        description
          "Broadcast unknown frames.";
      }
      enum "drop" {
        value 1;
        description
          "Drop unknown frames.";
      }
      enum "local-handle" {
        value 2;
        description
          "Locally handle unknown frames.";
      }
      enum "drop-learn" {
        value 3;
        description
          "Drop unknown frames but learn the MAC addresses of these frames.";
      }
    }
    description
      "L2VPN VPLS unknown frame act.";
  }

  typedef live_ncs_l2vpn-vpls-pw-type {
    type enumeration {
      enum "label" {
        value 0;
        description
          "The PW type is label.";
      }
      enum "qinq" {
        value 1;
        description
          "The PW type is QinQ.";
      }
      enum "mehvpls" {
        value 2;
        description
          "The PW type is MEHVPLS. An AC interface is an interface bound to a VSI. On a LDP VPLS network, if the peer is a UPE, the PW connecting the UPE is processed as an AC in internal processing. The detailed VSI information shows that the PW type of the UPE is MEHVPLS.";
      }
    }
    description
      "L2VPN VPLS PW type.";
  }

  typedef live_ncs_l2vpn-vpls-traffic-statistics-enable-type {
    type enumeration {
      enum "default" {
        value 0;
        description
          "VSI traffic statistics collection configurations are inherited.";
      }
      enum "disable" {
        value 1;
        description
          "The function to collect VPLS traffic statistics is disabled.";
      }
      enum "enable" {
        value 2;
        description
          "The function to collect VPLS traffic statistics is enabled.";
      }
    }
    description
      "L2VPN VPLS traffic statistics enable type.";
  }

  typedef live_ncs_l2vpn-vpls-ldp-pw-state-code {
    type enumeration {
      enum "forward" {
        value 0;
        description
          "Forwarding is supported.";
      }
      enum "standby" {
        value 1;
        description
          "The PW is a secondary PW.";
      }
      enum "ac-fault" {
        value 2;
        description
          "The peer AC interface is faulty.";
      }
      enum "psn-fault" {
        value 3;
        description
          "A fault occurs on the public network between the local end and peer end.";
      }
      enum "not-forward" {
        value 4;
        description
          "Forwarding is not supported.";
      }
    }
    description
      "L2VPN VPLS LDP PW state code.";
  }

  typedef live_ncs_l2vpn-vpws-vrrp-state {
    type enumeration {
      enum "initialize" {
        value 0;
        description
          "The VRRP state is initializing.";
      }
      enum "backup" {
        value 1;
        description
          "The VRRP state is backup.";
      }
      enum "master" {
        value 2;
        description
          "The VRRP state is master.";
      }
    }
    description
      "L2VPN VPWS VRRP state.";
  }

  typedef live_ncs_l2vpn-vpws-bfd-state {
    type enumeration {
      enum "invalid" {
        value 0;
        description
          "The state of BFD is invalid. The status code is 0.";
      }
      enum "down" {
        value 1;
        description
          "The state of BFD is down.";
      }
      enum "up" {
        value 2;
        description
          "The state of BFD is up.";
      }
      enum "admin-down" {
        value 3;
        description
          "The state of BFD is administratively down.";
      }
    }
    description
      "L2VPN VPWS BFD state.";
  }

  typedef live_ncs_l2vpn-aps-bind-type {
    type enumeration {
      enum "admin" {
        value 1;
        description
          "The APS bind type is admin.";
      }
      enum "reference" {
        value 2;
        description
          "The APS bind type is reference.";
      }
    }
    description
      "L2VPN APS bind type.";
  }

  typedef live_ncs_oam-protocal {
    type enumeration {
      enum "mpls-oam" {
        value 3;
        description
          "MPLS OAM is used to monitor the link status.";
      }
      enum "tp-oam" {
        value 4;
        description
          "MPLS-TP OAM is used to monitor the link status.";
      }
      enum "none" {
        value 5;
        description
          "No link detection protocol is used to detect the link status, or the packet receiving function of a configured link detection protocol is not enabled.";
      }
    }
    description
      "L2VPN OAM protocol.";
  }

  typedef live_ncs_oam-status {
    type enumeration {
      enum "nondefect" {
        value 1;
        description
          "The link status is normal.";
      }
      enum "defect" {
        value 2;
        description
          "The link is faulty.";
      }
      enum "detect-stop" {
        value 3;
        description
          "Link detection stops.";
      }
      enum "invalid" {
        value 4;
        description
          "No link detection protocol is used to detect the link status, or the packet receiving function of a configured link detection protocol is not enabled.";
      }
    }
    description
      "L2VPN OAM status.";
  }

  typedef live_ncs_l2vpn-aps-status {
    type enumeration {
      enum "LO" {
        value 1;
        description
          "Services are locked to the primary PW.";
      }
      enum "SF-P" {
        value 2;
        description
          "The secondary or bypass PW becomes faulty.";
      }
      enum "FS" {
        value 3;
        description
          "Services are forcibly switched from the primary PW to the secondary or bypass PW.";
      }
      enum "SF" {
        value 4;
        description
          "The primary PW becomes faulty.";
      }
      enum "SD-P" {
        value 5;
        description
          "Signals degrade on the secondary or bypass PW.";
      }
      enum "SD" {
        value 6;
        description
          "Signals degrade on the primary PW.";
      }
      enum "MS" {
        value 7;
        description
          "Services are manually switched from the primary PW to the secondary or bypass PW.";
      }
      enum "WTR" {
        value 8;
        description
          "The system is waiting to switch traffic back from the secondary or bypass PW to the primary PW.";
      }
      enum "EXER" {
        value 9;
        description
          "The status is exercise.";
      }
      enum "RR" {
        value 10;
        description
          "Revertive switching request.";
      }
      enum "DNR" {
        value 11;
        description
          "Do not revert.";
      }
      enum "NR" {
        value 12;
        description
          "The primary, secondary, or bypass PW is normal.";
      }
      enum "MS-P" {
        value 13;
        description
          "Services are manually switched from the primary PW to the secondary or bypass PW.";
      }
      enum "MS-W" {
        value 14;
        description
          "Services are manually switched from the secondary or bypass PW to the primary PW.";
      }
      enum "EXER-P" {
        value 15;
        description
          "The secondary or bypass PW exercises traffic switching.";
      }
      enum "EXER-W" {
        value 16;
        description
          "The primary PW exercises traffic switching.";
      }
      enum "RR-P" {
        value 17;
        description
          "Services are requested to switch from the primary PW to the secondary or bypass PW.";
      }
      enum "RR-W" {
        value 18;
        description
          "Services are requested to switch from the secondary or bypass PW to the primary PW.";
      }
      enum "NR-P" {
        value 19;
        description
          "Services are not requested to switch from the primary PW to the secondary or bypass PW.";
      }
      enum "NR-W" {
        value 20;
        description
          "Services are not requested to switch from the secondary or bypass PW to the primary PW.";
      }
    }
    description
      "L2VPN APS status.";
  }

  typedef live_ncs_l2vpn-aps-path-status {
    type enumeration {
      enum "no-defect" {
        value 0;
        description
          "No fault exists.";
      }
      enum "defect" {
        value 1;
        description
          "A fault exists.";
      }
      enum "defect-sd" {
        value 2;
        description
          "Signals attenuated.";
      }
      enum "invalid" {
        value 3;
        description
          "The working path status cannot be detected because the PW APS instance is in the slave state.";
      }
    }
    description
      "L2VPN APS path status.";
  }

  typedef live_ncs_l2vpn-aps-result {
    type enumeration {
      enum "work" {
        value 0;
        description
          "The traffic in the PW protection group is transmitted over the primary PW.";
      }
      enum "protect" {
        value 1;
        description
          "The traffic in the PW protection group is transmitted over the secondary or bypass PW.";
      }
    }
    description
      "L2VPN APS result.";
  }

  typedef live_ncs_l2vpn-protect-group-name {
    type string {
      length "1..15";
    }
    description
      "L2VPN protect group name.";
  }

  typedef live_ncs_vpn-rt-type {
    type enumeration {
      enum "export-extcommunity" {
        value 2;
        description
          "Extended community attribute of the route from an outbound interface to the destination VPN.";
      }
      enum "import-extcommunity" {
        value 3;
        description
          "Receive routes that carry the specified extended community attribute.";
      }
    }
    description
      "L2VPN common VPN RT type.";
  }

  typedef live_ncs_vpls-split-horizon-mode-type {
    type enumeration {
      enum "spoke" {
        value 1;
        description
          "The split horizon mode type is spoke.";
      }
      enum "hub" {
        value 2;
        description
          "The split horizon mode type is hub.";
      }
    }
    description
      "L2VPN VPLS split horizon mode type.";
  }

  typedef live_ncs_pw-signal-type {
    type enumeration {
      enum "ldp" {
        value 1;
        description
          "The PW signal type is LDP.";
      }
      enum "static" {
        value 2;
        description
          "The PW signal type is static.";
      }
    }
    description
      "L2VPN PW signal type.";
  }

  typedef live_ncs_l2vpn-rtp-header-type {
    type enumeration {
      enum "false" {
        value 0;
        description
          "The function to add RTP headers to packets is disabled.";
      }
      enum "standard" {
        value 1;
        description
          "Add standard RTP headers to packets.";
      }
      enum "private" {
        value 2;
        description
          "Add vendor-specific RTP headers to packets.";
      }
    }
    description
      "L2VPN RT header type.";
  }

  typedef live_ncs_l2vpn-payload-comp {
    type enumeration {
      enum "disable" {
        value 0;
        description
          "Disable payload compression.";
      }
      enum "uneq" {
        value 1;
        description
          "Send DBA packets when the unequipped circuit indication is detected.";
      }
    }
    description
      "L2VPN payload compression.";
  }

  typedef live_ncs_l2vpn-route-status {
    type enumeration {
      enum "reachable" {
        value 1;
        description
          "The route status is reachable.";
      }
      enum "unreachable" {
        value 2;
        description
          "The route status is unreachable.";
      }
    }
    description
      "L2VPN route status.";
  }

  typedef live_ncs_ac-oam-mapping-type {
    type enumeration {
      enum "default" {
        value 1;
        description
          "The AC OAM mapping type is default.";
      }
      enum "1ag" {
        value 2;
        description
          "The AC OAM mapping type is 1ag.";
      }
      enum "3ah" {
        value 3;
        description
          "The AC OAM mapping type is 3ah.";
      }
    }
    description
      "L2VPN AC OAM mapping type.";
  }

  typedef live_ncs_oam-state {
    type enumeration {
      enum "down" {
        value 0;
        description
          "The MC OAM state is down.";
      }
      enum "up" {
        value 1;
        description
          "The MC OAM state is up.";
      }
      enum "invalid" {
        value 2;
        description
          "The MC OAM state is invalid.";
      }
    }
    description
      "L2VPN MC OAM state.";
  }

  typedef live_ncs_flow-label-ability {
    type enumeration {
      enum "default" {
        value 0;
        description
          "The flow label ability is default.";
      }
      enum "send" {
        value 1;
        description
          "Ability to send flow labels.";
      }
      enum "receive" {
        value 2;
        description
          "Ability to receive flow labels.";
      }
      enum "both" {
        value 3;
        description
          "Ability to both send and receive flow labels.";
      }
      enum "disable" {
        value 4;
        description
          "Ability to disable flow labels.";
      }
    }
    description
      "L2VPN flow label ability.";
  }

  typedef live_ncs_l2vpn-load-balance-type {
    type enumeration {
      enum "packet" {
        value 1;
        description
          "Per-packet load balancing.";
      }
      enum "flow" {
        value 2;
        description
          "Per-flow load balancing.";
      }
    }
    description
      "L2VPN load balance type.";
  }

  typedef live_ncs_bgp-encap-type {
    type enumeration {
      enum "vpls" {
        value 19;
        description
          "The encapsulation type is BGP VPLS.";
      }
    }
    description
      "L2VPN BGP encapsulation type.";
  }

  typedef live_ncs_vsi-work-mode {
    type enumeration {
      enum "normal" {
        value 0;
        description
          "The VSI work mode is normal.";
      }
      enum "bd-mode" {
        value 1;
        description
          "The VSI work mode is bd-mode.";
      }
      enum "b-vsi" {
        value 3;
        description
          "Used to process B-MAC addresses and determine a PW's remote PE based on the configured peer address.";
      }
      enum "i-vsi" {
        value 4;
        description
          "I-VSI with no service type specified.";
      }
      enum "i-vsi-p2p" {
        value 5;
        description
          "The VSI work mode is P2P I-VSI.";
      }
      enum "i-vsi-b-evpn-interworking" {
        value 7;
        description
          "The VSI work mode is I-VSI accessing B-EVPN.";
      }
    }
    description
      "L2VPN VPLS VSI work mode.";
  }

  typedef live_ncs_send-receive-active-status {
    type enumeration {
      enum "send-receive-inactive" {
        value 0;
        description
          "Send inactive and receive inactive.";
      }
      enum "send-active-receive-inactive" {
        value 2;
        description
          "Send active and receive inactive.";
      }
      enum "send-inactive-receive-active" {
        value 4;
        description
          "Send inactive and receive active.";
      }
      enum "send-receive-active" {
        value 6;
        description
          "Send active and receive active.";
      }
    }
    description
      "L2VPN sernd recv active status.";
  }

  typedef live_ncs_ac-block-status {
    type enumeration {
      enum "unblocked" {
        value 0;
        description
          "The block status of AC is unblocked.";
      }
      enum "blocked" {
        value 1;
        description
          "The block status of AC is blocked.";
      }
    }
    description
      "L2VPN AC block status.";
  }

  typedef live_ncs_vpws-bgp-ce-name-type {
    type string {
      length "1..20";
    }
    description
      "L2VPN VPWS BGP CE name.";
  }

  typedef live_ncs_vpls-multi-homing-site-name {
    type string {
      length "1..19";
      pattern '[a-zA-Z][a-zA-Z0-9_-]*';
    }
    description
      "L2VPN VPLS multi-homing site name.";
  }

  typedef live_ncs_bfd-vccv-cv-type {
    type enumeration {
      enum "cv-linkage-bfd" {
        value 0;
        description
          "IP/UDP encapsulation supports fault detection and status signaling.";
      }
      enum "cv-bfd" {
        value 1;
        description
          "Fault Detection Only.";
      }
      enum "cv-pw-ach-bfd" {
        value 2;
        description
          "PW-ACH encapsulation supports only fault detection.";
      }
    }
    description
      "L2VPN BFD VCCV CV type.";
  }

  typedef live_ncs_l2vpn-common-enable-type {
    type enumeration {
      enum "disable" {
        value 1;
        description
          "The setting is disabled.";
      }
      enum "enable" {
        value 2;
        description
          "The setting is enabled.";
      }
    }
    description
      "L2VPN common enable.";
  }

  typedef live_ncs_interface-change-withdraw-type {
    type enumeration {
      enum "all" {
        value 0;
        description
          "The interface change withdraw type is all.";
      }
      enum "up" {
        value 1;
        description
          "The interface change withdraw type is up.";
      }
      enum "down" {
        value 2;
        description
          "The interface change withdraw type is down.";
      }
    }
    description
      "Interface change withdraw type.";
  }

  typedef live_ncs_suppression-type {
    type enumeration {
      enum "broadcast" {
        value 0;
        description
          "The suppression type is broadcast.";
      }
      enum "multicast" {
        value 1;
        description
          "The suppression type is multicast.";
      }
      enum "unknown-unicast" {
        value 2;
        description
          "The suppression type is unknown-unicast.";
      }
    }
    description
      "L2VPN suppression type.";
  }

  typedef live_ncs_mac-remove-type {
    type enumeration {
      enum "invalid" {
        value 0;
        description
          "The MAC remove type is invalid.";
      }
      enum "all-but-mine" {
        value 1;
        description
          "The MAC remove type is all-but-mine.";
      }
      enum "all-from-me" {
        value 2;
        description
          "The MAC remove type is all-from-me.";
      }
    }
    description
      "L2VPN MAC remove type.";
  }

  typedef live_ncs_l2vpn-arp-send-type {
    type enumeration {
      enum "dual-send" {
        value 1;
        description
          "The ARP send type is dual send.";
      }
      enum "single-send" {
        value 2;
        description
          "The ARP send type is single send.";
      }
    }
    description
      "L2VPN ARP send type.";
  }

  typedef live_ncs_l2vpn-nd-send-type {
    type enumeration {
      enum "dual-send" {
        value 1;
        description
          "The ND send type is dual send.";
      }
    }
    description
      "L2VPN ND send type.";
  }

  typedef live_ncs_l2vpn-pw-aps-ps-type {
    type enumeration {
      enum "manual" {
        value 1;
        description
          "Traffic is switched to the protection path manually. If the protection path is down, traffic cannot be switched and an error message will be displayed.";
      }
      enum "force" {
        value 2;
        description
          "Traffic is forced to switch to the protection path regardless of whether the protection path is up.";
      }
      enum "lock" {
        value 3;
        description
          "Traffic is locked to the working path, and is not switched to the protection path even if the working path becomes faulty.";
      }
      enum "clear" {
        value 4;
        description
          "Clear the manual switch request configured.";
      }
      enum "manual-to-work" {
        value 5;
        description
          "Traffic is switched to the working path manually. If the working path is down, traffic cannot be switched and an error message will be displayed.";
      }
      enum "manual-to-protect" {
        value 6;
        description
          "Traffic is switched to the protection path manually. If the protection path is down, traffic cannot be switched and an error message will be displayed.";
      }
      enum "exercise" {
        value 7;
        description
          "Switching exercise mode.";
      }
    }
    description
      "L2VPN PW APS PS type.";
  }

  typedef live_ncs_l2vpn-protect-group-ps-type {
    type enumeration {
      enum "manual" {
        value 1;
        description
          "The switching type of the PW protection group is manual switching.";
      }
      enum "clear" {
        value 2;
        description
          "The switching type of the PW protection group is clear.";
      }
    }
    description
      "L2VPN protect group PS type.";
  }

  typedef live_ncs_multicast-tunnel-type {
    type enumeration {
      enum "invalid" {
        value 0;
        description
          "The MC tunnel type is invalid.";
      }
      enum "mldp-p2mp" {
        value 1;
        description
          "The MC tunnel type is mLDP P2MP.";
      }
      enum "te-p2mp" {
        value 3;
        description
          "The MC tunnel type is TE P2MP.";
      }
    }
    description
      "L2VPN MC tunnel type.";
  }

  typedef live_ncs_pw-block-status {
    type enumeration {
      enum "default" {
        value 0;
        description
          "The block status of PW is default.";
      }
      enum "blocked" {
        value 1;
        description
          "The block status of PW is blocked.";
      }
      enum "unblocked" {
        value 2;
        description
          "The block status of PW is unblocked.";
      }
      enum "temp-blocked" {
        value 3;
        description
          "The block status of PW is temp blocked.";
      }
    }
    description
      "L2VPN PW block status.";
  }

  typedef live_ncs_vpws-bgp-vpn-encap {
    type enumeration {
      enum "atm-aal5-sdu" {
        value 2;
        description
          "The encapsulation type is ATM-AAL5-SDU.";
      }
      enum "atm-trans-cell" {
        value 3;
        description
          "The encapsulation type is ATM-TRANS-CELL.";
      }
      enum "vlan" {
        value 4;
        description
          "The encapsulation type is VLAN.";
      }
      enum "ethernet" {
        value 5;
        description
          "The encapsulation type is ethernet.";
      }
      enum "hdlc" {
        value 6;
        description
          "The encapsulation type is HDLC.";
      }
      enum "ppp" {
        value 7;
        description
          "The encapsulation type is PPP.";
      }
      enum "atm-nto1-vcc" {
        value 9;
        description
          "The encapsulation type is ATM-Nto1-VCC.";
      }
      enum "atm-nto1-vpc" {
        value 10;
        description
          "The encapsulation type is ATM-Nto1-VPC.";
      }
      enum "ip-layer2" {
        value 11;
        description
          "The encapsulation type is IP-Layer2.";
      }
      enum "atm-1to1-vcc" {
        value 12;
        description
          "The encapsulation type is ATM-1to1-VCC.";
      }
      enum "atm-1to1-vpc" {
        value 13;
        description
          "The encapsulation type is ATM-1to1-VPC.";
      }
      enum "ip-interworking" {
        value 64;
        description
          "The encapsulation type is IP interworking.";
      }
    }
    description
      "Encapsulation type for a VPWS BGP VPN instance.";
  }

  typedef live_ncs_l2vpn-vpls-pw-bfd-state {
    type enumeration {
      enum "invalid" {
        value 0;
        description
          "The state of BFD is invalid.";
      }
      enum "down" {
        value 1;
        description
          "The state of BFD is down.";
      }
      enum "up" {
        value 2;
        description
          "The state of BFD is up.";
      }
      enum "admin-down" {
        value 3;
        description
          "The state of BFD is administratively down.";
      }
      enum "remote-ac-error" {
        value 4;
        description
          "The state of BFD is remote AC error.";
      }
      enum "remote-ac-error-resume" {
        value 5;
        description
          "The state of BFD is remote AC error resume.";
      }
    }
    description
      "BFD for VPLS PW state.";
  }

  typedef live_ncs_vpws-bgp-pw-type {
    type enumeration {
      enum "local" {
        value 0;
        description
          "The BGP PW type is local.";
      }
      enum "remote" {
        value 1;
        description
          "The BGP PW type is remote.";
      }
      enum "unknown" {
        value 2;
        description
          "The BGP PW type is unknown.";
      }
    }
    description
      "L2VPN VPWS BGP PW type.";
  }

  typedef live_ncs_vpws-bgp-ac-oam-state {
    type enumeration {
      enum "down" {
        value 0;
        description
          "The AC OAM state is down.";
      }
      enum "up" {
        value 1;
        description
          "The AC OAM state is up.";
      }
      enum "invalid" {
        value 2;
        description
          "The AC OAM state is invalid.";
      }
    }
    description
      "L2VPN VPWS BGP AC OAM state.";
  }

  typedef live_ncs_vpls-ldp-peer-type {
    type enumeration {
      enum "static" {
        value 0;
        description
          "The peer type is static.";
      }
      enum "dynamic" {
        value 1;
        description
          "The peer type is dynamic.";
      }
    }
    description
      "L2VPN VPLS LDP peer type.";
  }

  typedef live_ncs_vpls-loop-detect-type {
    type enumeration {
      enum "detect-loop" {
        value 1;
        description
          "A loop is detected before the maximum number of hops is reached.";
      }
      enum "exceed-max-hop" {
        value 2;
        description
          "The maximum number of hops for loop detection has been exceeded.";
      }
    }
    description
      "L2VPN VPLS loop detect type.";
  }

  typedef live_ncs_vpls-bgp-encapsulation-type {
    type enumeration {
      enum "vpls" {
        value 19;
        description
          "The encapsulation type is BGP VPLS.";
      }
    }
    description
      "L2VPN BGP encapsulation type.";
  }

  typedef live_ncs_control-flag-bits-type {
    type bits {
      bit sbit {
        position 0;
        description
          "S bit.";
      }
      bit local-cbit {
        position 1;
        description
          "Local C bit.";
      }
      bit fbit {
        position 2;
        description
          "F bit.";
      }
      bit qbit {
        position 3;
        description
          "Q bit.";
      }
      bit remote-c-bit {
        position 4;
        description
          "Remote C bit.";
      }
    }
    description
      "Indicates the control flag.";
  }

  typedef live_ncs_vsi-pbb-instance-type {
    type enumeration {
      enum "normal" {
        value 0;
        description
          "Normal mode.";
      }
      enum "b-vsi" {
        value 1;
        description
          "Used to process B-MAC addresses and determine a PW's remote PE based on the configured peer address.";
      }
      enum "i-vsi" {
        value 2;
        description
          "Used to encapsulate packets into PBB frames and is bound to an AC interface for local CE identification.";
      }
    }
    description
      "L2VPN VSI PBB instance style.";
  }

  typedef live_ncs_vsi-pbb-learned-flag {
    type enumeration {
      enum "no-mac" {
        value 1;
        description
          "No B-MAC outbound interface has been learned.";
      }
      enum "first" {
        value 2;
        description
          "This B-MAC outbound interface was learned first.";
      }
      enum "master" {
        value 3;
        description
          "Primary B-MAC outbound interface learned.";
      }
      enum "backup" {
        value 4;
        description
          "Secondary B-MAC outbound interface learned.";
      }
    }
    description
      "L2VPN VSI PBB learned flag.";
  }

  typedef live_ncs_multicast-active-state {
    type enumeration {
      enum "default" {
        value 0;
        description
          "The MC active state is none.";
      }
      enum "inactive" {
        value 1;
        description
          "The MC active state is inactive.";
      }
      enum "active" {
        value 2;
        description
          "The MC active state is active.";
      }
    }
    description
      "L2VPN MC active state.";
  }

  typedef live_ncs_multicast-oam-type {
    type enumeration {
      enum "none" {
        value 0;
        description
          "The MC OAM type is none.";
      }
      enum "static-bfd" {
        value 1;
        description
          "The MC OAM type is static BFD.";
      }
      enum "bfd" {
        value 2;
        description
          "The MC OAM type is dynamic BFD.";
      }
      enum "mpls-oam" {
        value 3;
        description
          "MPLS OAM is used to detect the link status.";
      }
      enum "tp-oam" {
        value 4;
        description
          "MPLS-TP OAM is used to detect the link status.";
      }
    }
    description
      "L2VPN MC OAM type.";
  }

  typedef live_ncs_suppression-direction {
    type enumeration {
      enum "both" {
        value 0;
        description
          "The suppression direction is both.";
      }
      enum "in-bound" {
        value 1;
        description
          "The suppression direction is inbound.";
      }
      enum "out-bound" {
        value 2;
        description
          "The suppression direction is outbound.";
      }
    }
    description
      "L2VPN suppression direction.";
  }

  typedef live_ncs_etree-work-mode {
    type enumeration {
      enum "default" {
        value 0;
        description
          "The e-tree work mode of the PW is not specified.";
      }
      enum "optimized" {
        value 1;
        description
          "The e-tree work mode of the PW is optimized.";
      }
      enum "compatible" {
        value 2;
        description
          "The e-tree work mode of the PW is compatible.";
      }
    }
    description
      "The e-tree work mode of the PW.";
  }

  typedef live_ncs_etree-access-role {
    type enumeration {
      enum "root" {
        value 1;
        description
          "The e-tree access role of the AC is root.";
      }
      enum "leaf" {
        value 2;
        description
          "The e-tree access role of the AC is leaf.";
      }
    }
    description
      "The e-tree access role of the AC.";
  }

  typedef l2vpn-instance-name {
    type string {
      length "1..31";
    }
    description
      "L2VPN instance name.";
  }

  typedef l2vpn-peer-address-type {
    type inet:ipv4-address-no-zone {
      pattern '(([1-9]|[1-9][0-9]|1[0-1][0-9]|12[0-6]|12[8-9]|1[3-9][0-9]|2[0-1][0-9]|22[0-4])\.)(([0-9]|[1-9][0-9]|1[0-9][0-9]|2[0-4][0-9]|25[0-5])\.){2}([0-9]|[1-9][0-9]|1[0-9][0-9]|2[0-4][0-9]|25[0-5])';
    }
    description
      "IP address of a peer.";
  }

  typedef l2vpn-vpls-encap-type {
    type enumeration {
      enum "vlan" {
        value 4;
        description
          "The encapsulation type of VPLS is VLAN.";
      }
      enum "ethernet" {
        value 5;
        description
          "The encapsulation type of VPLS is ethernet.";
      }
    }
    description
      "L2VPN VPLS encapsulation type.";
  }

  typedef l2vpn-vpls-ldp-pw-encap-type {
    type enumeration {
      enum "vlan" {
        value 4;
        description
          "The VPLS LDP PW encapsulation type is VLAN.";
      }
      enum "ethernet" {
        value 5;
        description
          "The VPLS LDP PW encapsulation type is ethernet.";
      }
      enum "unsupport" {
        value 255;
        description
          "Unsupported encapsulation type.";
      }
    }
    description
      "L2VPN VPLS LDP PW encapsulation type.";
  }

  typedef l2vpn-mac-learn-style {
    type enumeration {
      enum "unqualify" {
        value 1;
        description
          "The MAC learn style is unqualify.";
      }
      enum "qualify" {
        value 2;
        description
          "The MAC learn style is qualify.";
      }
      enum "qualify-outer-vlan" {
        value 3;
        description
          "Learn MAC addresses in qualified mode by explicitly using outer VLAN ID.";
      }
      enum "qualify-inner-vlan" {
        value 4;
        description
          "Learn MAC addresses in qualified mode by explicitly using inner VLAN ID.";
      }
    }
    description
      "L2VPN MAC learn style.";
  }

  typedef pw-role-type {
    type enumeration {
      enum "primary" {
        value 1;
        description
          "The PW role type is primary.";
      }
      enum "backup" {
        value 2;
        description
          "The PW role type is backup.";
      }
      enum "bypass" {
        value 3;
        description
          "The PW role type is bypass.";
      }
      enum "ac-bypass" {
        value 7;
        description
          "The PW role type is AC-bypass.";
      }
      enum "pw-bypass" {
        value 8;
        description
          "The PW role type is PW-bypass.";
      }
    }
    description
      "L2VPN PW role type.";
  }

  typedef vpls-pw-role-type {
    type enumeration {
      enum "primary" {
        value 1;
        description
          "The PW role type is primary.";
      }
      enum "backup" {
        value 2;
        description
          "The PW role type is backup.";
      }
    }
    description
      "VPLS PW role type.";
  }

  typedef ms-pw-role-type {
    type enumeration {
      enum "left-primary" {
        value 4;
        description
          "The left side PW of multi-segment instance.";
      }
      enum "right-primary" {
        value 5;
        description
          "The right side PW of multi-segment instance.";
      }
      enum "right-backup" {
        value 6;
        description
          "The backup of the right side PW.";
      }
    }
    description
      "L2VPN multi-segment PW role.";
  }

  typedef l2vpn-pw-template-name {
    type string {
      length "1..19";
    }
    description
      "L2VPN PW template name.";
  }

  typedef l2vpn-pw-name {
    type string {
      length "1..15";
    }
    description
      "L2VPN PW name.";
  }

  typedef l2vpn-state {
    type enumeration {
      enum "default" {
        value 0;
        description
          "The state is default.";
      }
      enum "down" {
        value 1;
        description
          "The state is down.";
      }
      enum "up" {
        value 2;
        description
          "The state is up.";
      }
    }
    description
      "L2VPN state.";
  }

  typedef instance-state {
    type enumeration {
      enum "down" {
        value 0;
        description
          "The instance state is down.";
      }
      enum "up" {
        value 1;
        description
          "The instance state is up.";
      }
      enum "admin-down" {
        value 2;
        description
          "The instance state is admin down.";
      }
    }
    description
      "L2VPN instance state.";
  }

  typedef ac-state {
    type enumeration {
      enum "down" {
        value 0;
        description
          "The AC state is down.";
      }
      enum "up" {
        value 1;
        description
          "The AC state is up.";
      }
      enum "plug-out" {
        value 2;
        description
          "The AC state is plug-out.";
      }
      enum "notify-down" {
        value 3;
        description
          "The AC state is notify-down.";
      }
      enum "down-notify" {
        value 4;
        description
          "The AC state is down-notify.";
      }
    }
    description
      "L2VPN AC state.";
  }

  typedef l2vpn-pw-state {
    type enumeration {
      enum "down" {
        value 0;
        description
          "The PW state is down.";
      }
      enum "up" {
        value 1;
        description
          "The PW state is up.";
      }
      enum "backup" {
        value 2;
        description
          "The PW state is backup.";
      }
    }
    description
      "L2VPN PW state.";
  }

  typedef l2vpn-forward-state {
    type enumeration {
      enum "not-forwarding" {
        value 0;
        description
          "The forward state is not forwarding.";
      }
      enum "forwarding" {
        value 1;
        description
          "The forward state is forwarding.";
      }
    }
    description
      "L2VPN forward state.";
  }

  typedef ldp-signal-type {
    type enumeration {
      enum "pwe3" {
        value 0;
        description
          "Pseudo-wire emulation edge to edge.";
      }
      enum "martini" {
        value 1;
        description
          "Martini mode.";
      }
    }
    description
      "L2VPN LDP signal mode.";
  }

  typedef l2vpn-peer-ldp-signal-mode {
    type enumeration {
      enum "pwe3" {
        value 0;
        description
          "Pseudo-Wire Emulation Edge to Edge.";
      }
      enum "martini" {
        value 1;
        description
          "Martini mode.";
      }
      enum "default" {
        value 2;
        description
          "Default mode.";
      }
    }
    description
      "L2VPN peer LDP signal mode.";
  }

  typedef l2vpn-control-word {
    type enumeration {
      enum "default" {
        value 0;
        description
          "The control word mode is default.";
      }
      enum "disable" {
        value 1;
        description
          "The control word mode is disable.";
      }
      enum "enable" {
        value 2;
        description
          "The control word mode is enable.";
      }
      enum "prefer" {
        value 3;
        description
          "The control word mode is prefer.";
      }
    }
    description
      "L2VPN control word.";
  }

  typedef l2vpn-instance-type {
    type enumeration {
      enum "vpws-local-ccc" {
        value 1;
        description
          "The instance type is VPWS local CCC.";
      }
      enum "vpws-remote-ccc" {
        value 2;
        description
          "The instance type is VPWS remote CCC.";
      }
      enum "vpws-svc" {
        value 3;
        description
          "The instance type is VPWS SVC.";
      }
      enum "vpws-ldp" {
        value 4;
        description
          "The instance type is VPWS LDP.";
      }
      enum "vpws-switch" {
        value 5;
        description
          "The instance type is VPWS switching.";
      }
      enum "vpls" {
        value 6;
        description
          "Virtual private LAN service.";
      }
      enum "vpws-bgp" {
        value 8;
        description
          "The instance type is VPWS BGP.";
      }
      enum "vpws-single-ccc" {
        value 9;
        description
          "The instance type is VPWS single CCC.";
      }
    }
    description
      "L2VPN instance type.";
  }

  typedef l2vpn-switch-type {
    type enumeration {
      enum "svc-svc" {
        value 1;
        description
          "SVC to SVC.";
      }
      enum "ldp-svc" {
        value 2;
        description
          "LDP to SVC.";
      }
      enum "ldp-ldp" {
        value 3;
        description
          "LDP to LDP.";
      }
      enum "upe" {
        value 4;
        description
          "User-end provider edge.";
      }
      enum "ldp-ldp-bak" {
        value 5;
        description
          "PW redundancy of LDP to LDP.";
      }
    }
    description
      "L2VPN switch type.";
  }

  typedef encapsulation-type {
    type enumeration {
      enum "fr" {
        value 1;
        description
          "The encapsulation type is FR.";
      }
      enum "atm-aal5-sdu" {
        value 2;
        description
          "The encapsulation type is ATM-AAL5-SDU.";
      }
      enum "atm-trans-cell" {
        value 3;
        description
          "The encapsulation type is ATM-TRANS-CELL.";
      }
      enum "vlan" {
        value 4;
        description
          "The encapsulation type is VLAN.";
      }
      enum "ethernet" {
        value 5;
        description
          "The encapsulation type is ethernet.";
      }
      enum "hdlc" {
        value 6;
        description
          "The encapsulation type is HDLC.";
      }
      enum "ppp" {
        value 7;
        description
          "The encapsulation type is PPP.";
      }
      enum "cem" {
        value 8;
        description
          "The encapsulation type is CEM.";
      }
      enum "atm-nto1-vcc" {
        value 9;
        description
          "The encapsulation type is ATM-Nto1-VCC.";
      }
      enum "atm-nto1-vpc" {
        value 10;
        description
          "The encapsulation type is ATM-Nto1-VPC.";
      }
      enum "ip-layer2" {
        value 11;
        description
          "The encapsulation type is IP-Layer2.";
      }
      enum "atm-1to1-vcc" {
        value 12;
        description
          "The encapsulation type is ATM-1to1-VCC.";
      }
      enum "atm-1to1-vpc" {
        value 13;
        description
          "The encapsulation type is ATM-1to1-VPC.";
      }
      enum "atm-aal5-pdu" {
        value 14;
        description
          "The encapsulation type is ATM-AAL5-PDU.";
      }
      enum "fr-port-mode" {
        value 15;
        description
          "The encapsulation type is FR-PORT-MODE.";
      }
      enum "cep" {
        value 16;
        description
          "The encapsulation type is CEP.";
      }
      enum "satop-e1" {
        value 17;
        description
          "The encapsulation type is SAToP-E1.";
      }
      enum "satop-t1" {
        value 18;
        description
          "The encapsulation type is SAToP-T1.";
      }
      enum "satop-e3" {
        value 19;
        description
          "The encapsulation type is SAToP-E3.";
      }
      enum "satop-t3" {
        value 20;
        description
          "The encapsulation type is SAToP-T3.";
      }
      enum "cesopsn-basic" {
        value 21;
        description
          "The encapsulation type is CESoPSN-BASIC.";
      }
      enum "tdmoip-aal1" {
        value 22;
        description
          "The encapsulation type is TDMoIP-AAL1.";
      }
      enum "cesopsn-tdm" {
        value 23;
        description
          "The encapsulation type is CESoPSN-TDM.";
      }
      enum "tdmoip-aal2" {
        value 24;
        description
          "The encapsulation type is TDMoIP-AAL2.";
      }
      enum "fr-dlci" {
        value 25;
        description
          "The encapsulation type is FR-DLCI.";
      }
      enum "ip-interworking" {
        value 64;
        description
          "The encapsulation type is IP interworking.";
      }
      enum "unsupport" {
        value 255;
        description
          "This encapsulation type is used when the encapsulation types of AC interfaces at the two ends of a local CCC are different, or the ATM bundle interfaces do not have any member, or the VPLS LDP PW on a router inherits the encapsulation type of a VSI.";
      }
    }
    description
      "L2VPN encapsulate type.";
  }

  typedef l2vpn-backup-mode {
    type enumeration {
      enum "primary" {
        value 1;
        description
          "The backup mode is primary.";
      }
      enum "secondary" {
        value 2;
        description
          "The backup mode is secondary.";
      }
      enum "bypass" {
        value 3;
        description
          "The backup mode is bypass.";
      }
      enum "ac-bypass" {
        value 4;
        description
          "The backup mode is AC-bypass.";
      }
      enum "pw-bypass" {
        value 5;
        description
          "The backup mode is PW-bypass.";
      }
    }
    description
      "L2VPN backup mode.";
  }

  typedef l2vpn-tunnel-type {
    type enumeration {
      enum "invalid" {
        value 0;
        description
          "The tunnel type is invalid.";
      }
      enum "ldp" {
        value 1;
        description
          "The tunnel type is LDP.";
      }
      enum "bgp" {
        value 2;
        description
          "The tunnel type is BGP.";
      }
      enum "te" {
        value 3;
        description
          "The tunnel type is TE.";
      }
      enum "static-lsp" {
        value 4;
        description
          "The tunnel type is static LSP.";
      }
      enum "gre" {
        value 5;
        description
          "The tunnel type is GRE.";
      }
      enum "uni" {
        value 6;
        description
          "The tunnel type is UNI.";
      }
      enum "tnl-group" {
        value 7;
        description
          "The tunnel type is Tunnel group.";
      }
      enum "sub-te" {
        value 8;
        description
          "The tunnel type is Sub-TE.";
      }
      enum "sub-group" {
        value 9;
        description
          "The tunnel type is Sub-group.";
      }
      enum "6over4" {
        value 10;
        description
          "The tunnel type is IPv6-over-IPv4.";
      }
      enum "6to4" {
        value 11;
        description
          "The tunnel type is IPv6-to-IPv4.";
      }
      enum "bgp-local-ifnet" {
        value 12;
        description
          "The tunnel type is BGP local-ifnet.";
      }
      enum "ldp6" {
        value 13;
        description
          "The tunnel type is LDP6.";
      }
      enum "srbe-lsp" {
        value 41;
        description
          "The tunnel type is SRBE LSP.";
      }
    }
    description
      "L2VPN tunnel type.";
  }

  typedef l2vpn-mac-type {
    type enumeration {
      enum "static" {
        value 1;
        description
          "The MAC type is static.";
      }
      enum "dynamic" {
        value 2;
        description
          "The MAC type is dynamic.";
      }
      enum "broadcast" {
        value 3;
        description
          "The MAC type is broadcast.";
      }
    }
    description
      "L2VPN MAC type.";
  }

  typedef l2vpn-pw-aps-oper-type {
    type enumeration {
      enum "non-revertive" {
        value 0;
        description
          "The PW APS instance is in non-revertive mode.";
      }
      enum "revertive" {
        value 1;
        description
          "The PW APS instance is in revertive mode.";
      }
    }
    description
      "L2VPN PW APS oper type.";
  }

  typedef l2vpn-pw-aps-mode {
    type enumeration {
      enum "1to1" {
        value 1;
        description
          "The PW APS mode is 1:1.";
      }
    }
    description
      "L2VPN PW APS mode.";
  }

  typedef l2vpn-pw-aps-type {
    type enumeration {
      enum "pw-aps" {
        value 1;
        description
          "The PW APS type is PW APS.";
      }
      enum "mc-pw-aps" {
        value 2;
        description
          "The PW APS type is MC PW APS.";
      }
      enum "pw-fps" {
        value 3;
        description
          "The PW APS type is PW FPS.";
      }
    }
    description
      "L2VPN PW APS type.";
  }

  typedef l2vpn-pw-aps-role {
    type enumeration {
      enum "pw-aps" {
        value 1;
        description
          "Default PW APS role for a PW APS instance.";
      }
      enum "master" {
        value 2;
        description
          "Master role for a PW APS instance in the E-PW APS scenario.";
      }
      enum "slave" {
        value 3;
        description
          "Slave role for a PW APS instance in the E-PW APS scenario.";
      }
    }
    description
      "L2VPN PW APS role.";
  }

  typedef l2vpn-reroute-mode {
    type enumeration {
      enum "delay" {
        value 1;
        description
          "Delayed switchback.";
      }
      enum "immediately" {
        value 2;
        description
          "Immediate switchback.";
      }
      enum "never" {
        value 3;
        description
          "Never switchback.";
      }
    }
    description
      "L2VPN reroute mode.";
  }

  typedef pw-redundancy-mode {
    type enumeration {
      enum "frr" {
        value 0;
        description
          "The PW redundancy mode is FRR.";
      }
      enum "independent" {
        value 1;
        description
          "The PW redundancy mode is independent.";
      }
      enum "master" {
        value 2;
        description
          "The PW redundancy mode is master.";
      }
      enum "none" {
        value 3;
        description
          "The PW redundancy mode is not configured.";
      }
    }
    description
      "PW redundancy mode.";
  }

  typedef vpls-redundancy-mode {
    type enumeration {
      enum "independent" {
        value 1;
        description
          "The PW redundancy mode is independent.";
      }
      enum "master" {
        value 2;
        description
          "The PW redundancy mode is master.";
      }
      enum "none" {
        value 3;
        description
          "The PW redundancy mode is not configured.";
      }
    }
    description
      "PW redundancy mode.";
  }

  typedef l2vpn-vpls-vsi-mem-disc-type {
    type enumeration {
      enum "default" {
        value 0;
        description
          "The member discovery type is composite.";
      }
      enum "auto" {
        value 1;
        description
          "The member discovery type is automatic.";
      }
      enum "static" {
        value 2;
        description
          "The member discovery type is static.";
      }
    }
    description
      "L2VPN VPLS VSI member discovery type.";
  }

  typedef l2vpn-vpls-unknow-frame-act {
    type enumeration {
      enum "broadcast" {
        value 0;
        description
          "Broadcast unknown frames.";
      }
      enum "drop" {
        value 1;
        description
          "Drop unknown frames.";
      }
      enum "local-handle" {
        value 2;
        description
          "Locally handle unknown frames.";
      }
      enum "drop-learn" {
        value 3;
        description
          "Drop unknown frames but learn the MAC addresses of these frames.";
      }
    }
    description
      "L2VPN VPLS unknown frame act.";
  }

  typedef l2vpn-vpls-pw-type {
    type enumeration {
      enum "label" {
        value 0;
        description
          "The PW type is label.";
      }
      enum "qinq" {
        value 1;
        description
          "The PW type is QinQ.";
      }
      enum "mehvpls" {
        value 2;
        description
          "The PW type is MEHVPLS. An AC interface is an interface bound to a VSI. On a LDP VPLS network, if the peer is a UPE, the PW connecting the UPE is processed as an AC in internal processing. The detailed VSI information shows that the PW type of the UPE is MEHVPLS.";
      }
    }
    description
      "L2VPN VPLS PW type.";
  }

  typedef l2vpn-vpls-traffic-statistics-enable-type {
    type enumeration {
      enum "default" {
        value 0;
        description
          "VSI traffic statistics collection configurations are inherited.";
      }
      enum "disable" {
        value 1;
        description
          "The function to collect VPLS traffic statistics is disabled.";
      }
      enum "enable" {
        value 2;
        description
          "The function to collect VPLS traffic statistics is enabled.";
      }
    }
    description
      "L2VPN VPLS traffic statistics enable type.";
  }

  typedef l2vpn-vpls-ldp-pw-state-code {
    type enumeration {
      enum "forward" {
        value 0;
        description
          "Forwarding is supported.";
      }
      enum "standby" {
        value 1;
        description
          "The PW is a secondary PW.";
      }
      enum "ac-fault" {
        value 2;
        description
          "The peer AC interface is faulty.";
      }
      enum "psn-fault" {
        value 3;
        description
          "A fault occurs on the public network between the local end and peer end.";
      }
      enum "not-forward" {
        value 4;
        description
          "Forwarding is not supported.";
      }
    }
    description
      "L2VPN VPLS LDP PW state code.";
  }

  typedef l2vpn-vpws-vrrp-state {
    type enumeration {
      enum "initialize" {
        value 0;
        description
          "The VRRP state is initializing.";
      }
      enum "backup" {
        value 1;
        description
          "The VRRP state is backup.";
      }
      enum "master" {
        value 2;
        description
          "The VRRP state is master.";
      }
    }
    description
      "L2VPN VPWS VRRP state.";
  }

  typedef l2vpn-vpws-bfd-state {
    type enumeration {
      enum "invalid" {
        value 0;
        description
          "The state of BFD is invalid. The status code is 0.";
      }
      enum "down" {
        value 1;
        description
          "The state of BFD is down.";
      }
      enum "up" {
        value 2;
        description
          "The state of BFD is up.";
      }
      enum "admin-down" {
        value 3;
        description
          "The state of BFD is administratively down.";
      }
    }
    description
      "L2VPN VPWS BFD state.";
  }

  typedef l2vpn-aps-bind-type {
    type enumeration {
      enum "admin" {
        value 1;
        description
          "The APS bind type is admin.";
      }
      enum "reference" {
        value 2;
        description
          "The APS bind type is reference.";
      }
    }
    description
      "L2VPN APS bind type.";
  }

  typedef oam-protocal {
    type enumeration {
      enum "mpls-oam" {
        value 3;
        description
          "MPLS OAM is used to monitor the link status.";
      }
      enum "tp-oam" {
        value 4;
        description
          "MPLS-TP OAM is used to monitor the link status.";
      }
      enum "none" {
        value 5;
        description
          "No link detection protocol is used to detect the link status, or the packet receiving function of a configured link detection protocol is not enabled.";
      }
    }
    description
      "L2VPN OAM protocol.";
  }

  typedef oam-status {
    type enumeration {
      enum "nondefect" {
        value 1;
        description
          "The link status is normal.";
      }
      enum "defect" {
        value 2;
        description
          "The link is faulty.";
      }
      enum "detect-stop" {
        value 3;
        description
          "Link detection stops.";
      }
      enum "invalid" {
        value 4;
        description
          "No link detection protocol is used to detect the link status, or the packet receiving function of a configured link detection protocol is not enabled.";
      }
    }
    description
      "L2VPN OAM status.";
  }

  typedef l2vpn-aps-status {
    type enumeration {
      enum "LO" {
        value 1;
        description
          "Services are locked to the primary PW.";
      }
      enum "SF-P" {
        value 2;
        description
          "The secondary or bypass PW becomes faulty.";
      }
      enum "FS" {
        value 3;
        description
          "Services are forcibly switched from the primary PW to the secondary or bypass PW.";
      }
      enum "SF" {
        value 4;
        description
          "The primary PW becomes faulty.";
      }
      enum "SD-P" {
        value 5;
        description
          "Signals degrade on the secondary or bypass PW.";
      }
      enum "SD" {
        value 6;
        description
          "Signals degrade on the primary PW.";
      }
      enum "MS" {
        value 7;
        description
          "Services are manually switched from the primary PW to the secondary or bypass PW.";
      }
      enum "WTR" {
        value 8;
        description
          "The system is waiting to switch traffic back from the secondary or bypass PW to the primary PW.";
      }
      enum "EXER" {
        value 9;
        description
          "The status is exercise.";
      }
      enum "RR" {
        value 10;
        description
          "Revertive switching request.";
      }
      enum "DNR" {
        value 11;
        description
          "Do not revert.";
      }
      enum "NR" {
        value 12;
        description
          "The primary, secondary, or bypass PW is normal.";
      }
      enum "MS-P" {
        value 13;
        description
          "Services are manually switched from the primary PW to the secondary or bypass PW.";
      }
      enum "MS-W" {
        value 14;
        description
          "Services are manually switched from the secondary or bypass PW to the primary PW.";
      }
      enum "EXER-P" {
        value 15;
        description
          "The secondary or bypass PW exercises traffic switching.";
      }
      enum "EXER-W" {
        value 16;
        description
          "The primary PW exercises traffic switching.";
      }
      enum "RR-P" {
        value 17;
        description
          "Services are requested to switch from the primary PW to the secondary or bypass PW.";
      }
      enum "RR-W" {
        value 18;
        description
          "Services are requested to switch from the secondary or bypass PW to the primary PW.";
      }
      enum "NR-P" {
        value 19;
        description
          "Services are not requested to switch from the primary PW to the secondary or bypass PW.";
      }
      enum "NR-W" {
        value 20;
        description
          "Services are not requested to switch from the secondary or bypass PW to the primary PW.";
      }
    }
    description
      "L2VPN APS status.";
  }

  typedef l2vpn-aps-path-status {
    type enumeration {
      enum "no-defect" {
        value 0;
        description
          "No fault exists.";
      }
      enum "defect" {
        value 1;
        description
          "A fault exists.";
      }
      enum "defect-sd" {
        value 2;
        description
          "Signals attenuated.";
      }
      enum "invalid" {
        value 3;
        description
          "The working path status cannot be detected because the PW APS instance is in the slave state.";
      }
    }
    description
      "L2VPN APS path status.";
  }

  typedef l2vpn-aps-result {
    type enumeration {
      enum "work" {
        value 0;
        description
          "The traffic in the PW protection group is transmitted over the primary PW.";
      }
      enum "protect" {
        value 1;
        description
          "The traffic in the PW protection group is transmitted over the secondary or bypass PW.";
      }
    }
    description
      "L2VPN APS result.";
  }

  typedef l2vpn-protect-group-name {
    type string {
      length "1..15";
    }
    description
      "L2VPN protect group name.";
  }

  typedef vpn-rt-type {
    type enumeration {
      enum "export-extcommunity" {
        value 2;
        description
          "Extended community attribute of the route from an outbound interface to the destination VPN.";
      }
      enum "import-extcommunity" {
        value 3;
        description
          "Receive routes that carry the specified extended community attribute.";
      }
    }
    description
      "L2VPN common VPN RT type.";
  }

  typedef vpls-split-horizon-mode-type {
    type enumeration {
      enum "spoke" {
        value 1;
        description
          "The split horizon mode type is spoke.";
      }
      enum "hub" {
        value 2;
        description
          "The split horizon mode type is hub.";
      }
    }
    description
      "L2VPN VPLS split horizon mode type.";
  }

  typedef pw-signal-type {
    type enumeration {
      enum "ldp" {
        value 1;
        description
          "The PW signal type is LDP.";
      }
      enum "static" {
        value 2;
        description
          "The PW signal type is static.";
      }
    }
    description
      "L2VPN PW signal type.";
  }

  typedef l2vpn-rtp-header-type {
    type enumeration {
      enum "false" {
        value 0;
        description
          "The function to add RTP headers to packets is disabled.";
      }
      enum "standard" {
        value 1;
        description
          "Add standard RTP headers to packets.";
      }
      enum "private" {
        value 2;
        description
          "Add vendor-specific RTP headers to packets.";
      }
    }
    description
      "L2VPN RT header type.";
  }

  typedef l2vpn-payload-comp {
    type enumeration {
      enum "disable" {
        value 0;
        description
          "Disable payload compression.";
      }
      enum "uneq" {
        value 1;
        description
          "Send DBA packets when the unequipped circuit indication is detected.";
      }
    }
    description
      "L2VPN payload compression.";
  }

  typedef l2vpn-route-status {
    type enumeration {
      enum "reachable" {
        value 1;
        description
          "The route status is reachable.";
      }
      enum "unreachable" {
        value 2;
        description
          "The route status is unreachable.";
      }
    }
    description
      "L2VPN route status.";
  }

  typedef ac-oam-mapping-type {
    type enumeration {
      enum "default" {
        value 1;
        description
          "The AC OAM mapping type is default.";
      }
      enum "1ag" {
        value 2;
        description
          "The AC OAM mapping type is 1ag.";
      }
      enum "3ah" {
        value 3;
        description
          "The AC OAM mapping type is 3ah.";
      }
    }
    description
      "L2VPN AC OAM mapping type.";
  }

  typedef oam-state {
    type enumeration {
      enum "down" {
        value 0;
        description
          "The MC OAM state is down.";
      }
      enum "up" {
        value 1;
        description
          "The MC OAM state is up.";
      }
      enum "invalid" {
        value 2;
        description
          "The MC OAM state is invalid.";
      }
    }
    description
      "L2VPN MC OAM state.";
  }

  typedef flow-label-ability {
    type enumeration {
      enum "default" {
        value 0;
        description
          "The flow label ability is default.";
      }
      enum "send" {
        value 1;
        description
          "Ability to send flow labels.";
      }
      enum "receive" {
        value 2;
        description
          "Ability to receive flow labels.";
      }
      enum "both" {
        value 3;
        description
          "Ability to both send and receive flow labels.";
      }
      enum "disable" {
        value 4;
        description
          "Ability to disable flow labels.";
      }
    }
    description
      "L2VPN flow label ability.";
  }

  typedef l2vpn-load-balance-type {
    type enumeration {
      enum "packet" {
        value 1;
        description
          "Per-packet load balancing.";
      }
      enum "flow" {
        value 2;
        description
          "Per-flow load balancing.";
      }
    }
    description
      "L2VPN load balance type.";
  }

  typedef bgp-encap-type {
    type enumeration {
      enum "vpls" {
        value 19;
        description
          "The encapsulation type is BGP VPLS.";
      }
    }
    description
      "L2VPN BGP encapsulation type.";
  }

  typedef vsi-work-mode {
    type enumeration {
      enum "normal" {
        value 0;
        description
          "The VSI work mode is normal.";
      }
      enum "bd-mode" {
        value 1;
        description
          "The VSI work mode is bd-mode.";
      }
      enum "b-vsi" {
        value 3;
        description
          "Used to process B-MAC addresses and determine a PW's remote PE based on the configured peer address.";
      }
      enum "i-vsi" {
        value 4;
        description
          "I-VSI with no service type specified.";
      }
      enum "i-vsi-p2p" {
        value 5;
        description
          "The VSI work mode is P2P I-VSI.";
      }
      enum "i-vsi-b-evpn-interworking" {
        value 7;
        description
          "The VSI work mode is I-VSI accessing B-EVPN.";
      }
    }
    description
      "L2VPN VPLS VSI work mode.";
  }

  typedef send-receive-active-status {
    type enumeration {
      enum "send-receive-inactive" {
        value 0;
        description
          "Send inactive and receive inactive.";
      }
      enum "send-active-receive-inactive" {
        value 2;
        description
          "Send active and receive inactive.";
      }
      enum "send-inactive-receive-active" {
        value 4;
        description
          "Send inactive and receive active.";
      }
      enum "send-receive-active" {
        value 6;
        description
          "Send active and receive active.";
      }
    }
    description
      "L2VPN sernd recv active status.";
  }

  typedef ac-block-status {
    type enumeration {
      enum "unblocked" {
        value 0;
        description
          "The block status of AC is unblocked.";
      }
      enum "blocked" {
        value 1;
        description
          "The block status of AC is blocked.";
      }
    }
    description
      "L2VPN AC block status.";
  }

  typedef vpws-bgp-ce-name-type {
    type string {
      length "1..20";
    }
    description
      "L2VPN VPWS BGP CE name.";
  }

  typedef vpls-multi-homing-site-name {
    type string {
      length "1..19";
      pattern '[a-zA-Z][a-zA-Z0-9_-]*';
    }
    description
      "L2VPN VPLS multi-homing site name.";
  }

  typedef bfd-vccv-cv-type {
    type enumeration {
      enum "cv-linkage-bfd" {
        value 0;
        description
          "IP/UDP encapsulation supports fault detection and status signaling.";
      }
      enum "cv-bfd" {
        value 1;
        description
          "Fault Detection Only.";
      }
      enum "cv-pw-ach-bfd" {
        value 2;
        description
          "PW-ACH encapsulation supports only fault detection.";
      }
    }
    description
      "L2VPN BFD VCCV CV type.";
  }

  typedef l2vpn-common-enable-type {
    type enumeration {
      enum "disable" {
        value 1;
        description
          "The setting is disabled.";
      }
      enum "enable" {
        value 2;
        description
          "The setting is enabled.";
      }
    }
    description
      "L2VPN common enable.";
  }

  typedef interface-change-withdraw-type {
    type enumeration {
      enum "all" {
        value 0;
        description
          "The interface change withdraw type is all.";
      }
      enum "up" {
        value 1;
        description
          "The interface change withdraw type is up.";
      }
      enum "down" {
        value 2;
        description
          "The interface change withdraw type is down.";
      }
    }
    description
      "Interface change withdraw type.";
  }

  typedef suppression-type {
    type enumeration {
      enum "broadcast" {
        value 0;
        description
          "The suppression type is broadcast.";
      }
      enum "multicast" {
        value 1;
        description
          "The suppression type is multicast.";
      }
      enum "unknown-unicast" {
        value 2;
        description
          "The suppression type is unknown-unicast.";
      }
    }
    description
      "L2VPN suppression type.";
  }

  typedef mac-remove-type {
    type enumeration {
      enum "invalid" {
        value 0;
        description
          "The MAC remove type is invalid.";
      }
      enum "all-but-mine" {
        value 1;
        description
          "The MAC remove type is all-but-mine.";
      }
      enum "all-from-me" {
        value 2;
        description
          "The MAC remove type is all-from-me.";
      }
    }
    description
      "L2VPN MAC remove type.";
  }

  typedef l2vpn-arp-send-type {
    type enumeration {
      enum "dual-send" {
        value 1;
        description
          "The ARP send type is dual send.";
      }
      enum "single-send" {
        value 2;
        description
          "The ARP send type is single send.";
      }
    }
    description
      "L2VPN ARP send type.";
  }

  typedef l2vpn-nd-send-type {
    type enumeration {
      enum "dual-send" {
        value 1;
        description
          "The ND send type is dual send.";
      }
    }
    description
      "L2VPN ND send type.";
  }

  typedef l2vpn-pw-aps-ps-type {
    type enumeration {
      enum "manual" {
        value 1;
        description
          "Traffic is switched to the protection path manually. If the protection path is down, traffic cannot be switched and an error message will be displayed.";
      }
      enum "force" {
        value 2;
        description
          "Traffic is forced to switch to the protection path regardless of whether the protection path is up.";
      }
      enum "lock" {
        value 3;
        description
          "Traffic is locked to the working path, and is not switched to the protection path even if the working path becomes faulty.";
      }
      enum "clear" {
        value 4;
        description
          "Clear the manual switch request configured.";
      }
      enum "manual-to-work" {
        value 5;
        description
          "Traffic is switched to the working path manually. If the working path is down, traffic cannot be switched and an error message will be displayed.";
      }
      enum "manual-to-protect" {
        value 6;
        description
          "Traffic is switched to the protection path manually. If the protection path is down, traffic cannot be switched and an error message will be displayed.";
      }
      enum "exercise" {
        value 7;
        description
          "Switching exercise mode.";
      }
    }
    description
      "L2VPN PW APS PS type.";
  }

  typedef l2vpn-protect-group-ps-type {
    type enumeration {
      enum "manual" {
        value 1;
        description
          "The switching type of the PW protection group is manual switching.";
      }
      enum "clear" {
        value 2;
        description
          "The switching type of the PW protection group is clear.";
      }
    }
    description
      "L2VPN protect group PS type.";
  }

  typedef multicast-tunnel-type {
    type enumeration {
      enum "invalid" {
        value 0;
        description
          "The MC tunnel type is invalid.";
      }
      enum "mldp-p2mp" {
        value 1;
        description
          "The MC tunnel type is mLDP P2MP.";
      }
      enum "te-p2mp" {
        value 3;
        description
          "The MC tunnel type is TE P2MP.";
      }
    }
    description
      "L2VPN MC tunnel type.";
  }

  typedef pw-block-status {
    type enumeration {
      enum "default" {
        value 0;
        description
          "The block status of PW is default.";
      }
      enum "blocked" {
        value 1;
        description
          "The block status of PW is blocked.";
      }
      enum "unblocked" {
        value 2;
        description
          "The block status of PW is unblocked.";
      }
      enum "temp-blocked" {
        value 3;
        description
          "The block status of PW is temp blocked.";
      }
    }
    description
      "L2VPN PW block status.";
  }

  typedef vpws-bgp-vpn-encap {
    type enumeration {
      enum "atm-aal5-sdu" {
        value 2;
        description
          "The encapsulation type is ATM-AAL5-SDU.";
      }
      enum "atm-trans-cell" {
        value 3;
        description
          "The encapsulation type is ATM-TRANS-CELL.";
      }
      enum "vlan" {
        value 4;
        description
          "The encapsulation type is VLAN.";
      }
      enum "ethernet" {
        value 5;
        description
          "The encapsulation type is ethernet.";
      }
      enum "hdlc" {
        value 6;
        description
          "The encapsulation type is HDLC.";
      }
      enum "ppp" {
        value 7;
        description
          "The encapsulation type is PPP.";
      }
      enum "atm-nto1-vcc" {
        value 9;
        description
          "The encapsulation type is ATM-Nto1-VCC.";
      }
      enum "atm-nto1-vpc" {
        value 10;
        description
          "The encapsulation type is ATM-Nto1-VPC.";
      }
      enum "ip-layer2" {
        value 11;
        description
          "The encapsulation type is IP-Layer2.";
      }
      enum "atm-1to1-vcc" {
        value 12;
        description
          "The encapsulation type is ATM-1to1-VCC.";
      }
      enum "atm-1to1-vpc" {
        value 13;
        description
          "The encapsulation type is ATM-1to1-VPC.";
      }
      enum "ip-interworking" {
        value 64;
        description
          "The encapsulation type is IP interworking.";
      }
    }
    description
      "Encapsulation type for a VPWS BGP VPN instance.";
  }

  typedef l2vpn-vpls-pw-bfd-state {
    type enumeration {
      enum "invalid" {
        value 0;
        description
          "The state of BFD is invalid.";
      }
      enum "down" {
        value 1;
        description
          "The state of BFD is down.";
      }
      enum "up" {
        value 2;
        description
          "The state of BFD is up.";
      }
      enum "admin-down" {
        value 3;
        description
          "The state of BFD is administratively down.";
      }
      enum "remote-ac-error" {
        value 4;
        description
          "The state of BFD is remote AC error.";
      }
      enum "remote-ac-error-resume" {
        value 5;
        description
          "The state of BFD is remote AC error resume.";
      }
    }
    description
      "BFD for VPLS PW state.";
  }

  typedef vpws-bgp-pw-type {
    type enumeration {
      enum "local" {
        value 0;
        description
          "The BGP PW type is local.";
      }
      enum "remote" {
        value 1;
        description
          "The BGP PW type is remote.";
      }
      enum "unknown" {
        value 2;
        description
          "The BGP PW type is unknown.";
      }
    }
    description
      "L2VPN VPWS BGP PW type.";
  }

  typedef vpws-bgp-ac-oam-state {
    type enumeration {
      enum "down" {
        value 0;
        description
          "The AC OAM state is down.";
      }
      enum "up" {
        value 1;
        description
          "The AC OAM state is up.";
      }
      enum "invalid" {
        value 2;
        description
          "The AC OAM state is invalid.";
      }
    }
    description
      "L2VPN VPWS BGP AC OAM state.";
  }

  typedef vpls-ldp-peer-type {
    type enumeration {
      enum "static" {
        value 0;
        description
          "The peer type is static.";
      }
      enum "dynamic" {
        value 1;
        description
          "The peer type is dynamic.";
      }
    }
    description
      "L2VPN VPLS LDP peer type.";
  }

  typedef vpls-loop-detect-type {
    type enumeration {
      enum "detect-loop" {
        value 1;
        description
          "A loop is detected before the maximum number of hops is reached.";
      }
      enum "exceed-max-hop" {
        value 2;
        description
          "The maximum number of hops for loop detection has been exceeded.";
      }
    }
    description
      "L2VPN VPLS loop detect type.";
  }

  typedef vpls-bgp-encapsulation-type {
    type enumeration {
      enum "vpls" {
        value 19;
        description
          "The encapsulation type is BGP VPLS.";
      }
    }
    description
      "L2VPN BGP encapsulation type.";
  }

  typedef control-flag-bits-type {
    type bits {
      bit sbit {
        position 0;
        description
          "S bit.";
      }
      bit local-cbit {
        position 1;
        description
          "Local C bit.";
      }
      bit fbit {
        position 2;
        description
          "F bit.";
      }
      bit qbit {
        position 3;
        description
          "Q bit.";
      }
      bit remote-c-bit {
        position 4;
        description
          "Remote C bit.";
      }
    }
    description
      "Indicates the control flag.";
  }

  typedef vsi-pbb-instance-type {
    type enumeration {
      enum "normal" {
        value 0;
        description
          "Normal mode.";
      }
      enum "b-vsi" {
        value 1;
        description
          "Used to process B-MAC addresses and determine a PW's remote PE based on the configured peer address.";
      }
      enum "i-vsi" {
        value 2;
        description
          "Used to encapsulate packets into PBB frames and is bound to an AC interface for local CE identification.";
      }
    }
    description
      "L2VPN VSI PBB instance style.";
  }

  typedef vsi-pbb-learned-flag {
    type enumeration {
      enum "no-mac" {
        value 1;
        description
          "No B-MAC outbound interface has been learned.";
      }
      enum "first" {
        value 2;
        description
          "This B-MAC outbound interface was learned first.";
      }
      enum "master" {
        value 3;
        description
          "Primary B-MAC outbound interface learned.";
      }
      enum "backup" {
        value 4;
        description
          "Secondary B-MAC outbound interface learned.";
      }
    }
    description
      "L2VPN VSI PBB learned flag.";
  }

  typedef multicast-active-state {
    type enumeration {
      enum "default" {
        value 0;
        description
          "The MC active state is none.";
      }
      enum "inactive" {
        value 1;
        description
          "The MC active state is inactive.";
      }
      enum "active" {
        value 2;
        description
          "The MC active state is active.";
      }
    }
    description
      "L2VPN MC active state.";
  }

  typedef multicast-oam-type {
    type enumeration {
      enum "none" {
        value 0;
        description
          "The MC OAM type is none.";
      }
      enum "static-bfd" {
        value 1;
        description
          "The MC OAM type is static BFD.";
      }
      enum "bfd" {
        value 2;
        description
          "The MC OAM type is dynamic BFD.";
      }
      enum "mpls-oam" {
        value 3;
        description
          "MPLS OAM is used to detect the link status.";
      }
      enum "tp-oam" {
        value 4;
        description
          "MPLS-TP OAM is used to detect the link status.";
      }
    }
    description
      "L2VPN MC OAM type.";
  }

  typedef suppression-direction {
    type enumeration {
      enum "both" {
        value 0;
        description
          "The suppression direction is both.";
      }
      enum "in-bound" {
        value 1;
        description
          "The suppression direction is inbound.";
      }
      enum "out-bound" {
        value 2;
        description
          "The suppression direction is outbound.";
      }
    }
    description
      "L2VPN suppression direction.";
  }

  typedef etree-work-mode {
    type enumeration {
      enum "default" {
        value 0;
        description
          "The e-tree work mode of the PW is not specified.";
      }
      enum "optimized" {
        value 1;
        description
          "The e-tree work mode of the PW is optimized.";
      }
      enum "compatible" {
        value 2;
        description
          "The e-tree work mode of the PW is compatible.";
      }
    }
    description
      "The e-tree work mode of the PW.";
  }

  typedef etree-access-role {
    type enumeration {
      enum "root" {
        value 1;
        description
          "The e-tree access role of the AC is root.";
      }
      enum "leaf" {
        value 2;
        description
          "The e-tree access role of the AC is leaf.";
      }
    }
    description
      "The e-tree access role of the AC.";
  }

  grouping ncs_template_spe-infos-type {
    description
      "Indicates the query list of the SPE information.";
    list spe {
      // NCS patched for predictable order
      ordered-by user;
      key "spe-pw-id spe-peer-ip";
      description
        "Operational data of the SPE on the path to the peer.";
      leaf spe-pw-id {
        type string;
        description
          "List of PW IDs on the path traveled by a label mapping message.";
      }
      leaf spe-peer-ip {
        type string;
        description
          "IP address of an SPE in the path to the peer.";
      }
    }
  }

  grouping ncs_template_l2vpn-reroute-policy-type {
    description
      "L2VPN protect group reroute policy class.";
    leaf policy {
      type ncs_template_l2vpn-reroute-mode;
      // NCS drop default statement
      description
        "Switchback policy.";
    }
    leaf delay-time {
      // NCS drop when statement
      type string;
      units "s";
      // NCS drop default statement
      description
        "Delay for switching traffic back to the primary PW.";
    }
    // NCS drop config false leaf 'last-switchback-time'
    // NCS drop config false leaf 'last-reroute-action'
    // NCS drop config false leaf 'last-switchback-reason'
  }

  grouping ncs_template_l2vpn-dyn-bfd-para-type {
    description
      "Dynamic BFD parameters.";
    leaf min-rx-interval {
      type string;
      units "ms";
      // NCS drop default statement
      description
        "Minimum receive interval.";
    }
    leaf min-tx-interval {
      type string;
      units "ms";
      // NCS drop default statement
      description
        "Minimum transmit interval.";
    }
    leaf detect-multiplier {
      type string;
      // NCS drop default statement
      description
        "Detection multiplier.";
    }
  }

  grouping ncs_template_l2vpn-label-stacks-type {
    description
      "Label stack.";
    list label-stack {
      // NCS patched for predictable order
      ordered-by user;
      key "label-stack level";
      description
        "Operational data of the PW label stack.";
      leaf label-stack {
        type string;
        description
          "Label stack.";
      }
      leaf level {
        type string;
        description
          "Label level.";
      }
      leaf type {
        type string;
        description
          "Label type.";
      }
      leaf label {
        type string;
        description
          "Label value.";
      }
      leaf out-interface {
        type string;
        description
          "Outbound interface name.";
      }
    }
  }

  grouping ncs_template_l2vpn-pw-down-causes-type {
    description
      "Indicates the down causes of the PW.";
    list down-cause {
      // NCS patched for predictable order
      ordered-by user;
      key "down-cause-index";
      description
        "Statistics of the down causes of PWs.";
      leaf down-cause-index {
        type string;
        description
          "Sequence number of the PW down cause.";
      }
      leaf down-cause {
        type string;
        description
          "Indicates the down causes of the PW.";
      }
    }
  }

  grouping ncs_template_l2vpn-pw-status-changes-type {
    description
      "Indicates the reason and the time of the PW status that has changed.";
    list status-change {
      // NCS patched for predictable order
      ordered-by user;
      key "index";
      description
        "Statistics of the reason and the time of the PW status that has changed.";
      leaf index {
        type string;
        description
          "Sequence number of reasons that the PW status has changed.";
      }
      leaf timestamp {
        type string;
        description
          "Indicates the time of the PW status has changed.";
      }
      leaf reason {
        type string;
        description
          "Indicates the reason of the PW status has changed.";
      }
    }
  }

  grouping ncs_template_l2vpn-ccc-tdm-type {
    description
      "Tdm parameters of CCC instance.";
    leaf tdm-encapsulate-number {
      ext:dynamic-default;
      type string;
      description
        "Number of TDM frames encapsulated in a CESoPSN or SAToP packet in the TDMoPSN application.";
    }
    leaf jitter-buffer {
      ext:dynamic-default;
      type string;
      units "us";
      description
        "Depth of the jitter buffer in the application of TDMoPSN.";
    }
    leaf rtp-header {
      type string;
      // NCS drop default statement
      description
        "Enable/disable the RTP header of transparently transmitted TDM frames.";
    }
    leaf idle-code {
      type string;
      // NCS drop default statement
      description
        "Idle code that is filled when the jitter buffer underflow occurs.";
    }
  }

  grouping ncs_template_l2vpn-ccc-atm-type {
    description
      "L2VPN ATM class.";
    leaf max-atm-cells {
      type string;
      ext:dynamic-default;
      description
        "Maximum number of ATM cells to be encapsulated into a packet that can be received by a device.";
    }
    leaf atm-pack-overtime {
      type string;
      units "us";
      ext:dynamic-default;
      description
        "Delay in encapsulating ATM cells into a packet.";
    }
  }

  grouping ncs_template_vpws-localccc-instance-grp {
    description
      "VPWS local CCC instance.";
    leaf encapsulation-type {
      ext:operation-exclude "update";
      type ncs_template_encapsulation-type;
      // NCS drop must statement
      // NCS drop mandatory statement
      description
        "Encapsulation type of a VPWS instance.";
    }
    container tdm-parameter {
      // NCS drop when statement
      description
        "Configure TDM parameters.";
      leaf tdm-encapsulate-number {
        type string;
        ext:dynamic-default;
        description
          "Number of TDM frames encapsulated in a CESoPSN or SAToP packet in the TDMoPSN application.";
      }
      leaf jitter-buffer {
        type string;
        units "us";
        ext:dynamic-default;
        description
          "Depth of the jitter buffer in the application of TDMoPSN.";
      }
      leaf rtp-header {
        type string;
        // NCS drop default statement
        description
          "Enable/disable transparently transmission of TDM frames.";
      }
      leaf idle-code {
        type string;
        // NCS drop default statement
        description
          "Idle code that is filled when the jitter buffer underflow occurs.";
      }
    }
    container atm-parameter {
      // NCS drop when statement
      description
        "Configure ATM parameters.";
      leaf max-atm-cells {
        type string;
        ext:dynamic-default;
        description
          "Maximum number of ATM cells to be encapsulated into a packet that can be received by a device.";
      }
      leaf atm-pack-overtime {
        type string;
        units "us";
        ext:dynamic-default;
        description
          "Delay in encapsulating ATM cells into a packet.";
      }
    }
    container acs {
      description
        "List of information about all ACs.";
      list ac {
        // NCS patched for predictable order
        ordered-by user;
        ext:operation-exclude "update|delete";
        // NCS drop must statement
        key "interface-name";
        // NCS drop min-elements statement
        // NCS drop max-elements statement
        description
          "Configure information about an AC. AC information is displayed in a configuration order.";
        leaf interface-name {
          type string;
          description
            "Name of an AC interface.";
        }
        leaf tagged {
          ext:operation-exclude "update|delete";
          // NCS drop when statement
          type string;
          ext:dynamic-default {
            ext:default-value "false" {
              // NCS drop when statement
              description
                "The default value is false when encapsulation-type is ethernet.";
            }
            ext:default-value "true" {
              // NCS drop when statement
              description
                "The default value is true when encapsulation-type is VLAN.";
            }
          }
          // NCS drop must statement
          description
            "Enable/disable the VLAN tag setting.";
        }
        leaf access-port {
          ext:operation-exclude "update|delete";
          // NCS drop when statement
          type string;
          // NCS drop must statement
          // NCS drop default statement
          description
            "Enable/disable the attribute that allows only untagged packets to pass through an interface.";
        }
        leaf trigger-interface-down {
          type string;
          // NCS drop must statement
          // NCS drop default statement
          description
            "Enable/disable remote interface shutdown-based association between the PW status and interface status.";
        }
        // NCS drop config false leaf state
        // NCS drop config false leaf 'token-exceed'
        container arp-entry {
          presence "Enable the ARP entry for AC.";
          description
            "Configure the ARP entry attribute used for IP interworking between PEs.";
          leaf local-ce-mac {
            type pub-type:ncs_template_mac-address;
            description
              "MAC address of the ethernet interface or sub-interface on a CE connected to the local AC interface. If MAC, IP, and broadcast addresses are all configured, these addresses take effect in the sequence of MAC address, IP address, and broadcast address.";
          }
          leaf local-ce-ip {
            type string;
            description
              "IP address of the ethernet interface or sub-interface on a CE connected to the local AC interface.";
          }
          leaf local-ce-broadcast {
            type string;
            // NCS drop must statement
            // NCS drop default statement
            description
              "Enable/disable the broadcast function on a PE Ethernet interface connected to a CE.";
          }
          leaf remote-ce-ip {
            type string;
            description
              "IP address of the remote CE connected to the local AC interface.";
          }
        }
        // NCS drop config false container 'ac-arps'
      }
    }
  }

  grouping ncs_template_vpws-remoteccc-instance-grp {
    description
      "VPWS remote CCC instance.";
    leaf encapsulation-type {
      ext:operation-exclude "update";
      ext:support-filter "true";
      type ncs_template_encapsulation-type;
      // NCS drop must statement
      // NCS drop mandatory statement
      description
        "Encapsulation type of a VPWS instance.";
    }
    container acs {
      description
        "List of information about all ACs.";
      list ac {
        // NCS patched for predictable order
        ordered-by user;
        ext:operation-exclude "update|delete";
        // NCS drop must statement
        key "interface-name";
        // NCS drop min-elements statement
        // NCS drop max-elements statement
        description
          "Configure information about an AC.";
        leaf interface-name {
          type string;
          description
            "Name of an AC interface.";
        }
        leaf tagged {
          ext:operation-exclude "update|delete";
          // NCS drop when statement
          type string;
          ext:dynamic-default {
            ext:default-value "false" {
              // NCS drop when statement
              description
                "The default value is false when encapsulation-type is ethernet.";
            }
            ext:default-value "true" {
              // NCS drop when statement
              description
                "The default value is true when encapsulation-type is VLAN.";
            }
          }
          // NCS drop must statement
          description
            "Enable/disable the VLAN tag setting.";
        }
        // NCS drop config false leaf state
        // NCS drop config false leaf 'token-exceed'
        container arp-entry {
          presence "Enable the ARP entry for AC.";
          description
            "Configure the ARP entry attribute used for IP interworking between PEs.";
          leaf local-ce-mac {
            type pub-type:ncs_template_mac-address;
            description
              "MAC address of the Ethernet interface or sub-interface on a CE connected to the local AC interface. If MAC, IP, and broadcast addresses are all configured, these addresses take effect in the sequence of MAC address, IP address, and broadcast address.";
          }
          leaf local-ce-ip {
            type string;
            description
              "IP address of the Ethernet interface or sub-interface on a CE connected to the local AC interface.";
          }
          leaf local-ce-broadcast {
            type string;
            // NCS drop must statement
            // NCS drop default statement
            description
              "Enable/disable broadcast on a PE Ethernet interface connected to a CE.";
          }
          leaf remote-ce-ip {
            type string;
            description
              "IP address of the remote CE connected to the local AC interface.";
          }
        }
        // NCS drop config false container 'ac-arps'
      }
    }
    container pw {
      ext:operation-exclude "update|delete";
      // NCS drop must statement
      description
        "Configure a VPWS remote CCC PW.";
      leaf out-label {
        ext:operation-exclude "update";
        type string;
        // NCS drop mandatory statement
        description
          "Label for sending packets.";
      }
      leaf in-label {
        ext:operation-exclude "update";
        type string;
        // NCS drop mandatory statement
        description
          "Label for receiving packets.";
      }
      leaf control-word {
        ext:operation-exclude "update|delete";
        type ncs_template_l2vpn-control-word;
        // NCS drop must statement
        // NCS drop default statement
        description
          "Enable the control word function. The control word is usually used for TDM, ATM, and FR PWs.";
      }
      leaf out-interface-name {
        ext:operation-exclude "update|delete";
        type string;
        description
          "Outbound interface.";
      }
      leaf next-hop {
        ext:operation-exclude "update|delete";
        type string;
        description
          "Next hop.";
      }
    }
  }

  grouping ncs_template_vpws-swtich-instance-grp {
    description
      "VPWS switch instance.";
    leaf switch-type {
      ext:operation-exclude "update";
      type ncs_template_l2vpn-switch-type;
      // NCS drop mandatory statement
      description
        "Switch type of a VPWS switch instance.";
    }
    leaf encapsulation-type {
      type ncs_template_encapsulation-type;
      // NCS drop must statement
      // NCS drop mandatory statement
      description
        "Encapsulation type of a VPWS switch instance.";
    }
    leaf control-word-trans {
      type string;
      // NCS drop default statement
      description
        "Enable/disable the control word of a VPWS switching instance to be transparently transmitted.";
    }
    leaf control-word {
      // NCS drop when statement
      type ncs_template_l2vpn-control-word;
      // NCS drop must statement
      // NCS drop default statement
      description
        "Enable the control word function. The control word function is usually used for TDM, ATM, and FR PWs.";
    }
    leaf mtu {
      // NCS drop when statement
      type string;
      // NCS drop default statement
      description
        "MTU of a VPWS switch instance.";
    }
    leaf bit-error-detection {
      // NCS drop when statement
      type string;
      // NCS drop default statement
      description
        "Enable/disable bit error detection on SPEs for an LDP MS-PW.";
    }
    // NCS drop config false leaf 'create-time'
    // NCS drop config false leaf 'up-time'
    // NCS drop config false leaf 'last-change-time'
    container pws {
      description
        "List of VPWS PWs.";
      list pw {
        // NCS patched for predictable order
        ordered-by user;
        ext:operation-exclude "update|delete";
        // NCS drop must statement
        // NCS drop must statement
        key "role";
        unique "peer-ip";
        // NCS drop min-elements statement
        // NCS drop max-elements statement
        description
          "Configure a PW in a VPWS switching instance.";
        leaf role {
          type ncs_template_ms-pw-role-type;
          description
            "Role of a PW.";
        }
        leaf pw-id {
          ext:operation-exclude "update|delete";
          type string;
          description
            "PW ID.";
        }
        leaf peer-ip {
          ext:operation-exclude "update|delete";
          type ncs_template_l2vpn-peer-address-type;
          description
            "IP address of a peer.";
        }
        leaf transmit-label {
          ext:operation-exclude "update|delete";
          // NCS drop when statement
          type string;
          description
            "Static label for sending packets.";
        }
        leaf receive-label {
          ext:operation-exclude "update|delete";
          // NCS drop when statement
          type string;
          description
            "Static label for receiving packets.";
        }
        leaf tunnel-policy {
          type string;
          description
            "Name of a tunnel policy. If the tunnel policy name is not specified, the system uses the default tunnel policy. The default tunnel policy preferentially selects LSPs for packet transmission and the number of load-balancing tunnels is 1. If the tunnel policy name is specified but the corresponding tunnel policy does not exist, the system still uses the default tunnel policy.";
        }
        container flow-label {
          // NCS drop must statement
          presence "enbale flow label for pw";
          description
            "Enable/disable the flow label of a PW.";
          leaf ability {
            ext:operation-exclude "delete";
            // NCS drop when statement
            type ncs_template_flow-label-ability;
            // NCS drop must statement
            description
              "Flow label capability. The values of the ability node at both ends of a PW must be consistent.";
          }
          leaf oam-packet-pop {
            type string;
            // NCS drop default statement
            description
              "Enable/disable the function of popping out flow labels in the OAM packets.";
          }
        }
        container hard-pipe {
          // NCS drop when statement
          presence "Enable hard pipe for pw.";
          description
            "Enable/disable hard pipe.";
          leaf bandwidth {
            // NCS drop when statement
            type string;
            units "kbit/s";
            // NCS drop mandatory statement
            description
              "Specify bandwidth value.";
          }
          leaf expand-ratio {
            type string;
            // NCS drop default statement
            description
              "Specify the value of bandwidth expand ratio (%). As to CES service, expand ratio ranges from 0 to 10000. The other service, expand ratio ranges from 0 to 100.";
          }
        }
        container tdm-parameter {
          // NCS drop when statement
          description
            "Configure TDM parameters.";
          leaf tdm-encapsulate-number {
            // NCS drop when statement
            type string;
            ext:dynamic-default;
            description
              "Number of TDM frames encapsulated in a CESoPSN or SAToP packet in the TDMoPSN application.";
          }
          leaf rtp-header {
            type ncs_template_l2vpn-rtp-header-type;
            // NCS drop default statement
            description
              "Add the RTP header to transparently transmitted TDM frames.";
          }
          leaf time-slot {
            // NCS drop when statement
            type string;
            description
              "Number of time slots on an interface.";
          }
        }
        // NCS drop config false container 'pw-info'
      }
    }
    container reliability {
      // NCS drop when statement
      description
        "Configure PW reliability.";
      leaf redundancy-mode {
        type ncs_template_pw-redundancy-mode;
        // NCS drop must statement
        // NCS drop default statement
        description
          "PW redundancy mode.";
      }
      leaf switchover {
        type string;
        // NCS drop default statement
        description
          "Enable/disable the PW switchover.";
      }
      container reroute {
        description
          "Configure a switchback policy list.";
        leaf reroute-policy {
          type ncs_template_l2vpn-reroute-mode;
          // NCS drop default statement
          description
            "Switchback policy.";
        }
        leaf delay-time {
          // NCS drop when statement
          type string;
          units "s";
          // NCS drop default statement
          description
            "Delay for switching traffic back to the primary PW.";
        }
        // NCS drop config false leaf 'last-switchback-reason'
        // NCS drop config false leaf 'last-switchback-time'
        // NCS drop config false leaf 'delay-residual'
      }
    }
  }

  grouping ncs_template_vpws-bgp-instance-grp {
    description
      "VPWS BGP VPN instance connection.";
    leaf vpn-instance {
      type string;
      // NCS drop mandatory statement
      description
        "VPWS BGP instance.";
    }
    leaf local-site {
      type string;
      // NCS drop mandatory statement
      description
        "Local site name.";
    }
    container acs {
      description
        "List of attachment circuits in a VPWS BGP VPN instance.";
      list ac {
        // NCS patched for predictable order
        ordered-by user;
        key "interface-name";
        // NCS drop min-elements statement
        // NCS drop max-elements statement
        description
          "Configure a connection attachment circuit.";
        leaf interface-name {
          type string;
          description
            "VPWS BGP VPN instance connection attachment circuit interface name. The encapsulation type of this interface must be the same as that of the VPN instance. Otherwise, the PW cannot go Up.";
        }
        leaf tagged {
          // NCS drop when statement
          ext:operation-exclude "update|delete";
          type string;
          description
            "Enable/disable the attachment circuit tag of the VPWS BGP instance.";
          ext:dynamic-default;
        }
        leaf trigger-interface-down {
          type string;
          // NCS drop must statement
          // NCS drop default statement
          description
            "Enable/disable remote interface shutdown-based association between the PW status and interface status.";
        }
        // NCS drop config false leaf state
        // NCS drop config false leaf 'token-exceed'
      }
    }
    container pws {
      description
        "List of PWs.";
      list pw {
        // NCS patched for predictable order
        ordered-by user;
        key "remote-site-id";
        unique "role";
        // NCS drop min-elements statement
        description
          "Configure a PW.";
        leaf remote-site-id {
          type string;
          // NCS drop must statement
          description
            "VPWS BGP VPN instance connection remote customer edge identifier.";
        }
        leaf role {
          ext:operation-exclude "update|delete";
          type ncs_template_pw-role-type;
          // NCS drop must statement
          // NCS drop default statement
          description
            "VPWS BGP VPN instance connection pseudo wire role. Configure a primary PW first. The PW role canot be changed.";
        }
        leaf tunnel-policy {
          type string;
          description
            "VPWS BGP VPN instance connection tunnel policy name.";
        }
        leaf traffic-statistics-collection {
          type string;
          // NCS drop default statement
          description
            "Enable/disable connection traffic statistics collection of a VPWS BGP VPN instance.";
        }
        leaf manual-set-fault {
          type string;
          // NCS drop default statement
          description
            "Enable/disable the manual setting of faults in a VPWS BGP VPN instance connection.";
        }
        container bfd {
          // NCS drop when statement
          // NCS drop must statement
          presence "enable pw bfd.";
          description
            "Enable/disable BFD for PW in a VPWS BGP VPN instance.";
          uses ncs_template_l2vpn-dyn-bfd-para-type;
          leaf track-interface {
            type string;
            // NCS drop default statement
            description
              "Enable/disable BFD track interface state.";
          }
        }
        // NCS drop config false container 'pw-info'
        // NCS drop config false container tunnels
        // NCS drop config false container 'traffic-statistics'
      }
    }
    container reliability {
      // NCS drop when statement
      description
        "Configure PW reliability.";
      leaf redundancy-mode {
        type ncs_template_pw-redundancy-mode;
        // NCS drop must statement
        // NCS drop default statement
        description
          "PW redundancy mode.";
      }
      leaf dual-receive {
        type string;
        // NCS drop default statement
        description
          "Enable/disable the receipt of both the primary and secondary PWs to receive packets.";
      }
      container reroute {
        description
          "Configure a switchback policy list.";
        leaf reroute-policy {
          type ncs_template_l2vpn-reroute-mode;
          // NCS drop default statement
          description
            "Switchback policy.";
        }
        leaf delay-time {
          // NCS drop when statement
          type string;
          units "s";
          // NCS drop default statement
          description
            "Delay for switching traffic back to the primary PW.";
        }
        leaf resume-time {
          // NCS drop when statement
          type string;
          units "s";
          // NCS drop default statement
          description
            "Time after which the peer PE on the secondary PW is notified that the local PE has recovered. This parameter can be configured only in FRR mode.";
        }
        // NCS drop config false leaf 'last-switchback-reason'
        // NCS drop config false leaf 'last-switchback-time'
        // NCS drop config false leaf 'delay-residual'
        // NCS drop config false leaf 'resume-residual'
      }
    }
    container oam-mapping {
      presence "enable AC OAM mapping";
      description
        "Enable/disable OAM mapping.";
      leaf type {
        type ncs_template_ac-oam-mapping-type;
        // NCS drop must statement
        // NCS drop mandatory statement
        description
          "VPWS attachment circuit OAM mapping type.";
      }
      leaf md-name {
        ext:operation-exclude "update|delete";
        // NCS drop when statement
        type string;
        description
          "VPWS OAM mapping parameter md name.";
      }
      leaf ma-name {
        ext:operation-exclude "update|delete";
        // NCS drop when statement
        type string;
        description
          "VPWS OAM mapping parameter ma name.";
      }
    }
  }

  grouping ncs_template_vpls-instance-grp {
    description
      "VPLS instance.";
    leaf member-discovery-mode {
      type ncs_template_l2vpn-vpls-vsi-mem-disc-type;
      // NCS drop default statement
      description
        "VPLS member discovery mode for a specified VSI.";
    }
    leaf work-mode {
      ext:operation-exclude "update";
      type ncs_template_vsi-work-mode;
      // NCS drop default statement
      description
        "Workmode of a VSI.";
    }
    leaf encapsulation-type {
      type ncs_template_l2vpn-vpls-encap-type;
      // NCS drop must statement
      // NCS drop default statement
      description
        "Encapsulation type of a VSI.";
    }
    leaf mtu {
      type string;
      // NCS drop default statement
      description
        "VPLS MTU.";
    }
    leaf tunnel-policy {
      type string;
      description
        "Name of a tunnel policy for a VSI. If the tunnel policy name is not specified, the system uses the default tunnel policy. The default tunnel policy preferentially selects LSPs for packet transmission and the number of load-balancing tunnels is 1. If the tunnel policy name is specified but the corresponding tunnel policy does not exist, the system still uses the default tunnel policy.";
    }
    leaf shutdown {
      type string;
      // NCS drop default statement
      description
        "Enable/disable the function of shutting down a specified VSI.";
    }
    leaf isolate-spoken {
      // NCS drop when statement
      type string;
      // NCS drop must statement
      // NCS drop default statement
      description
        "Enable/disable forwarding isolation between AC interfaces, between UPE PWs, and between ACs and UPE PWs in a VSI.";
    }
    leaf isolate-spoken-include-multicast {
      // NCS drop when statement
      type string;
      // NCS drop must statement
      // NCS drop default statement
      description
        "Enable/disable isolating forwarding between AC interfaces, between UPE PWs, and between ACs and UPE PWs in a VSI.";
    }
    leaf ignore-ac-state {
      type string;
      // NCS drop default statement
      description
        "Enable/disable the function for the VSI status not to be affected by changes in the AC status.";
    }
    leaf response-ac-state {
      // NCS drop when statement
      type string;
      // NCS drop default statement
      description
        "Enable/disable the function for the BD VSI status to be affected by changes in the BD AC status.";
    }
    leaf admin-vsi {
      type string;
      // NCS drop must statement
      // NCS drop default statement
      description
        "Enable/disable the function for the current service VSI to be configured as the mVSI.";
    }
    leaf track-admin-vsi {
      ext:operation-exclude "update|delete";
      // NCS drop when statement
      type string;
      // NCS drop must statement
      description
        "Name of the mVSI to which a service VSI is bound.";
    }
    leaf unknown-unicast-action {
      // NCS drop when statement
      type ncs_template_l2vpn-vpls-unknow-frame-act;
      // NCS drop default statement
      description
        "Action taken to process unknown unicast frames.";
    }
    leaf unknown-multicast-action {
      // NCS drop when statement
      type ncs_template_l2vpn-vpls-unknow-frame-act;
      // NCS drop must statement
      // NCS drop default statement
      description
        "Action taken to process unknown multicast frames.";
    }
    leaf isolate-hub-ac-pw {
      // NCS drop when statement
      type string;
      // NCS drop must statement
      // NCS drop default statement
      description
        "Enable/disable forwarding isolation between hub ACs and PWs in a VSI.";
    }
    leaf p2p-vsi {
      // NCS drop when statement
      type string;
      // NCS drop must statement
      // NCS drop default statement
      description
        "Enable/disable the P2P VSI.";
    }
    leaf traffic-statistics-collection {
      // NCS drop when statement
      type string;
      // NCS drop default statement
      description
        "Enable/disable VSI QoS traffic statistics collection.";
    }
    leaf mac-remove-mode {
      type ncs_template_mac-remove-type;
      // NCS drop must statement
      // NCS drop default statement
      description
        "Local MAC remove mode.";
    }
    leaf mac-learn {
      // NCS drop when statement
      type string;
      // NCS drop must statement
      // NCS drop default statement
      description
        "Enable/disable the function for a VSI to learn MAC addresses.";
    }
    leaf mac-learn-style {
      // NCS drop when statement
      type ncs_template_l2vpn-mac-learn-style;
      // NCS drop must statement
      // NCS drop default statement
      description
        "MAC address learning style of PWs.";
    }
    leaf mac-age-time {
      // NCS drop when statement
      type string;
      units "s";
      description
        "MAC address aging timer that sets the aging time of MAC addresses.";
    }
    leaf local-mac-age-time {
      // NCS drop when statement
      type string;
      units "s";
      description
        "Local MAC address aging timer that sets the aging time of MAC addresses.";
    }
    leaf remote-mac-age-time {
      // NCS drop when statement
      type string;
      units "s";
      description
        "Remote MAC address aging timer that sets the aging time of MAC addresses.";
    }
    leaf mac-withdraw {
      type string;
      // NCS drop default statement
      description
        "Enable/disable the function for a VSI to delete the local MAC address and notifies all remote peers of the deletion when an AC or a UPE fault occurs and the VSI remains up.";
    }
    leaf interface-change-mac-withdraw {
      // NCS drop when statement
      type string;
      // NCS drop default statement
      description
        "Enable/disable the function for PEs to send LDP MAC withdraw messages to all peers when the status of the AC interface bound to the VSI changes.";
    }
    leaf interface-change-mac-withdraw-type {
      type ncs_template_interface-change-withdraw-type;
      // NCS drop must statement
      // NCS drop default statement
      description
        "Specify the status change type for a VSI AC interface.";
    }
    leaf bd-pwtag-mac-withdraw {
      // NCS drop when statement
      type string;
      // NCS drop default statement
      description
        "Enable/disable the function for LDP MAC withdraw messages to carry PW tag corresponding to the VSI bound to the bridge domain. This node can be configured only when the VSI works in BD mode.";
    }
    leaf bd-down-mac-withdraw {
      // NCS drop when statement
      type string;
      // NCS drop default statement
      description
        "Enable/disable the function for PEs to send LDP MAC withdraw messages to all peers when BD goes down. This node can be configured only when the VSI works in BD mode.";
    }
    leaf propagate-mac-withdraw {
      // NCS drop when statement
      type string;
      // NCS drop default statement
      description
        "Enable/disable the function for a PE to propagate LDP MAC withdraw messages to other peers after receiving the message from a remote peer.";
    }
    leaf mac-flush-rfc-compatible {
      // NCS drop when statement
      type string;
      // NCS drop default statement
      description
        "Enable/disable the transmission of standard MAC-flush message when the PW status changes.";
    }
    leaf vrrp-mac-withdraw-retry {
      type string;
      // NCS drop default statement
      description
        "VRRP backup Mac withdraw retry.";
    }
    // NCS drop config false leaf 'token-exceed'
    // NCS drop config false leaf 'ac-count'
    // NCS drop config false leaf 'create-time'
    // NCS drop config false leaf 'ignore-ac-state-effect'
    container etree {
      // NCS drop when statement
      // NCS drop must statement
      presence "Enable ethernet tree.";
      description
        "Enable/disable vpls ethernet tree.";
      leaf static {
        type string;
        // NCS drop must statement
        // NCS drop default statement
        description
          "Enable/disable static mode.";
      }
      leaf root-vlan {
        type string;
        description
          "Specify root VLAN id.";
      }
      leaf leaf-vlan {
        type string;
        description
          "Specify leaf VLAN id.";
      }
    }
    container ldp-signaling {
      presence "Label Distribution Protocol (LDP) signaling.";
      description
        "Enable/disable Label Distribution Protocol (LDP) signaling.";
      leaf vsi-id {
        ext:operation-exclude "update";
        type string;
        // NCS drop must statement
        // NCS drop must statement
        // NCS drop must statement
        description
          "VPLS LDP VSI ID. Can not be modified after configuration.";
      }
      leaf traffic-statistics-collection {
        // NCS drop when statement
        type string;
        // NCS drop must statement
        // NCS drop default statement
        description
          "Enable/disable traffic statistics collection.";
      }
      leaf control-word {
        type ncs_template_l2vpn-control-word;
        // NCS drop must statement
        // NCS drop default statement
        description
          "Enable the control word feature. The control word feature is usually used for TDM, ATM, and FR PWs.";
      }
      leaf hard-pipe {
        type string;
        // NCS drop must statement
        // NCS drop default statement
        description
          "Enable/disable hard pipe.";
      }
      leaf mac-withdraw {
        type string;
        // NCS drop must statement
        // NCS drop default statement
        description
          "Enable/disable the function for a VSI to delete the local MAC address and notify all remote peers of the deletion when an AC or a UPE fault occurs and the VSI remains up.";
      }
      leaf interface-change-mac-withdraw {
        type string;
        // NCS drop must statement
        // NCS drop default statement
        description
          "Enable/disable the function for PEs to send LDP MAC withdraw messages to all peers when the status of the AC interface bound to the VSI changes.";
      }
      leaf interface-change-mac-withdraw-type {
        type ncs_template_interface-change-withdraw-type;
        // NCS drop must statement
        // NCS drop default statement
        description
          "Specify the status change type for a VSI AC interface.";
      }
      leaf upe-upe-mac-withdraw {
        type string;
        // NCS drop must statement
        // NCS drop default statement
        description
          "Enable/disable the function for an NPE to forward the LDP MAC withdraw messages received from a UPE to other UPEs.";
      }
      leaf upe-npe-mac-withdraw {
        type string;
        // NCS drop must statement
        // NCS drop default statement
        description
          "Enable/disable the function for an NPE to forward the LDP MAC withdraw messages received from a UPE to other NPEs.";
      }
      leaf npe-upe-mac-withdraw {
        type string;
        // NCS drop must statement
        // NCS drop default statement
        description
          "Enable/disable the function for an NPE to forward the LDP MAC withdraw messages received from another NPE to UPEs.";
      }
      container flow-label {
        presence "enable flow-label for ldp signaling pws.";
        description
          "Enable/disable flow label capability of a PW.";
        leaf ability {
          type ncs_template_flow-label-ability;
          // NCS drop must statement
          // NCS drop mandatory statement
          description
            "Enable/disable flow label capability.";
        }
        leaf static {
          type string;
          // NCS drop default statement
          description
            "Enable/disable the static flow label function.";
        }
      }
      container pws {
        // NCS drop when statement
        description
          "List of VPLS PWs.";
        list pw {
          // NCS patched for predictable order
          ordered-by user;
          key "peer-ip negotiation-vc-id encapsulation-type";
          description
            "Configure VPLS PWs.";
          leaf peer-ip {
            type string;
            description
              "Peer IP address. The loopback IP address of a peer is usually used as the peer IP address.";
          }
          leaf negotiation-vc-id {
            type string;
            description
              "PW ID used to uniquely identify a VC. The PW ID is usually used when both ends need to communicate but the VSI IDs on both ends are different.";
          }
          leaf encapsulation-type {
            type ncs_template_l2vpn-vpls-ldp-pw-encap-type;
            description
              "Encapsulation type of a VPLS PW. 'unsupport' indicates that the encapsulation type of a VSI is inherited.";
          }
          leaf role {
            ext:operation-exclude "update|delete";
            type ncs_template_vpls-pw-role-type;
            // NCS drop must statement
            // NCS drop default statement
            description
              "Role of a PW, either primary or secondary. Configure a primary PW first.";
          }
          leaf name {
            ext:operation-exclude "update";
            type string;
            description
              "PW name.";
          }
          leaf signal-type {
            ext:operation-exclude "update|delete";
            type ncs_template_pw-signal-type;
            // NCS drop must statement
            // NCS drop must statement
            // NCS drop must statement
            // NCS drop must statement
            // NCS drop default statement
            description
              "PW type, either dynamic or static.";
          }
          leaf transmit-label {
            ext:operation-exclude "update|delete";
            // NCS drop when statement
            type string;
            description
              "Label for sending packets.";
          }
          leaf receive-label {
            ext:operation-exclude "update|delete";
            // NCS drop when statement
            type string;
            description
              "Label for receiving packets.";
          }
          leaf control-word {
            // NCS drop when statement
            type ncs_template_l2vpn-control-word;
            // NCS drop default statement
            description
              "Enable the control word function.";
          }
          leaf vccv {
            // NCS drop when statement
            type string;
            // NCS drop default statement
            description
              "Enable/disable virtual circuit connectivity verification capability. VCCV supports two modes: control word and label alert.";
          }
          leaf ignore-standby {
            ext:operation-exclude "update|delete";
            type string;
            // NCS drop default statement
            description
              "Enable/disable the function for the created PW to ignore the standby state sent from the peer device.";
          }
          leaf upe {
            ext:operation-exclude "update|delete";
            type string;
            // NCS drop default statement
            description
              "Enable/disable the peer device as a UPE.";
          }
          leaf tunnel-policy {
            type string;
            description
              "Name of the tunnel policy for a PW.";
          }
          leaf traffic-statistics-collection {
            type ncs_template_l2vpn-vpls-traffic-statistics-enable-type;
            // NCS drop must statement
            // NCS drop default statement
            description
              "Enable the function to collect traffic statistics.";
          }
          leaf track-hub-pw {
            // NCS drop when statement
            type string;
            // NCS drop must statement
            // NCS drop default statement
            description
              "Enable/disable the function for the spoke PW to track the hub PW. If a PW is not a spoke PW, it cannot track the hub PW.";
          }
          leaf ignore-stp-loop-check {
            // NCS drop when statement
            type string;
            // NCS drop default statement
            description
              "Enable/disable the function of ignoring STP loops.";
          }
          leaf hard-pipe-bandwidth {
            ext:operation-exclude "delete";
            // NCS drop when statement
            type string;
            units "kbit/s";
            description
              "Specify bandwidth value.";
          }
          leaf hard-pipe-burst-time {
            ext:operation-exclude "delete";
            // NCS drop when statement
            type string;
            units "us";
            // NCS drop default statement
            description
              "Burst time.";
          }
          leaf status-code-change-flush-mac-disable {
            // NCS drop when statement
            type string;
            // NCS drop default statement
            description
              "Enable/disable the function of flushing MAC when status code change.";
          }
          leaf ac-mode {
            ext:operation-exclude "update|delete";
            // NCS drop when statement
            type string;
            // NCS drop default statement
            description
              "Enable/disable the AC mode.";
          }
          leaf etree-mode {
            // NCS drop when statement
            type ncs_template_etree-work-mode;
            // NCS drop default statement
            description
              "Specify e-tree work mode.";
          }
          leaf etree-leaf {
            // NCS drop when statement
            type string;
            // NCS drop default statement
            description
              "Enable/disable e-tree leaf.";
          }
          container flow-label {
            // NCS drop when statement
            presence "enable flow label";
            description
              "Enable/disable the flow label capability of a PW.";
            leaf ability {
              type ncs_template_flow-label-ability;
              // NCS drop must statement
              // NCS drop mandatory statement
              description
                "Flow label capability.";
            }
            leaf static {
              type string;
              // NCS drop must statement
              // NCS drop default statement
              description
                "Enable/disable the static flow label function.";
            }
          }
          container bfd {
            // NCS drop when statement
            presence "enable vpls ldp pw bfd.";
            description
              "Enable/disable BFD.";
            leaf min-rx-interval {
              type string;
              units "ms";
              // NCS drop default statement
              description
                "Minimum receive interval.";
            }
            leaf min-tx-interval {
              type string;
              units "ms";
              // NCS drop default statement
              description
                "Minimum transmit interval.";
            }
            leaf detect-multiplier {
              type string;
              // NCS drop default statement
              description
                "Detection multiplier.";
            }
            leaf option-tlv {
              type string;
              // NCS drop default statement
              description
                "Enable/disable BFD detection with options.";
            }
          }
          // NCS drop config false container 'pw-info'
          uses l2vpn:ncs_template_suppression-statisticss-grp;
          uses l2vpn:ncs_template_pw-traffic-statisticss-grp;
          // NCS drop config false container 'hard-pipe-traffic-statistics'
        }
      }
      container redundancy-protect-groups {
        // NCS drop when statement
        description
          "List of VPLS PW protection groups.";
        list redundancy-protect-group {
          // NCS patched for predictable order
          ordered-by user;
          key "name";
          // NCS drop max-elements statement
          description
            "Configure VPLS PW protection groups.";
          leaf name {
            type ncs_template_l2vpn-protect-group-name;
            description
              "Name of a PW protection group. The name is a string of case-sensitive characters.";
          }
          leaf protect-mode {
            type ncs_template_vpls-redundancy-mode;
            // NCS drop default statement
            description
              "Switching mode of the PW protection group.";
          }
          leaf dual-receive {
            // NCS drop when statement
            type string;
            // NCS drop default statement
            description
              "Enable/disable the receipt of both the primary and secondary PWs.";
          }
          leaf holdoff {
            // NCS drop when statement
            type string;
            units "s";
            description
              "Hold time for traffic switching.";
          }
          container reroute-policy {
            // NCS drop when statement
            description
              "Configure a switchback policy.";
            uses l2vpn:ncs_template_l2vpn-reroute-policy-type;
          }
          container pw-members {
            // NCS drop when statement
            description
              "List of PW members in a protection group.";
            list pw-member {
              // NCS patched for predictable order
              ordered-by user;
              // NCS drop must statement
              key "peer-ip negotiation-vc-id encapsulation-type";
              unique "preference";
              // NCS drop max-elements statement
              description
                "Configure PW members in a protection group.";
              leaf peer-ip {
                type string;
                description
                  "Peer IP address. The loopback IP address of a peer is usually used as the peer IP address.";
              }
              leaf negotiation-vc-id {
                type string;
                description
                  "PW ID used to uniquely identify a VC. The PW ID is usually used when both ends need to communicate but the VSI IDs on both ends are different.";
              }
              leaf encapsulation-type {
                type ncs_template_l2vpn-vpls-ldp-pw-encap-type;
                description
                  "Encapsulate type.";
              }
              leaf preference {
                type string;
                // NCS drop mandatory statement
                description
                  "Priority of a PW in the PW protection group.";
              }
              // NCS drop config false leaf role
              // NCS drop config false leaf 'active-state'
            }
          }
          // NCS drop config false container historys
        }
      }
      // NCS drop config false container 'traffic-statistics'
    }
    container bgp-signaling {
      // NCS drop when statement
      // NCS drop must statement
      // NCS drop must statement
      presence "Container for bgp protocol vpls instance.";
      description
        "Enable/disable BGP VSIs.";
      leaf route-distinguisher {
        type string;
        description
          "Route distinguisher.";
      }
      leaf encapsulation-rfc4761-compatible {
        type string;
        // NCS drop default statement
        description
          "Enable/disable the function of changing an encapsulation type.";
      }
      leaf encapsulation-vpls-family-compatible {
        type string;
        // NCS drop default statement
        description
          "Enable/disable the function of changing an encapsulation type to private mode.";
      }
      leaf mtu-negotiate-disable {
        type string;
        // NCS drop default statement
        description
          "Enable/disable the function of ignoring MTU match between local VSI and remote VSI. The default implementation is match.";
      }
      leaf control-word {
        type ncs_template_l2vpn-control-word;
        // NCS drop must statement
        // NCS drop default statement
        description
          "Enable the control word feature. The control word feature is usually used for TDM, ATM, and FR PWs.";
      }
      // NCS drop config false leaf 'auto-route-distinguisher'
      container sites {
        description
          "List of BGP sites.";
        list site {
          // NCS patched for predictable order
          ordered-by user;
          // NCS drop must statement
          key "site-id";
          // NCS drop max-elements statement
          description
            "Configure BGP sites.";
          leaf site-id {
            type string;
            description
              "BGP site ID.";
          }
          leaf range {
            type string;
            // NCS drop default statement
            description
              "BGP site range. Cannot decrease site range.";
          }
          leaf default-offset {
            ext:operation-exclude "update|delete";
            type string;
            // NCS drop default statement
            description
              "The default offset of BGP site. The value of this node cannot be modified or deleted after being set.";
          }
        }
      }
      container vpn-targets {
        description
          "List of VPN targets.";
        list vpn-target {
          // NCS patched for predictable order
          ordered-by user;
          key "rt-value rt-type";
          // NCS drop max-elements statement
          description
            "Configure VPN targets.";
          leaf rt-value {
            type string;
            description
              "Route target. The format of an RT can be:
               - 16-bit AS number:32-bit user-defined number, for example, 1:3. An AS number ranges from 0 to 65535, and a user-defined number ranges from 0 to 4294967295. The AS number and user-defined number cannot be both 0s. This means that the RT cannot be 0:0.
               - Integral 4-byte AS number:2-byte user-defined number, for example, 65537:3. An AS number ranges from 65536 to 4294967295. A user-defined number ranges from 0 to 65535. The AS number and user-defined number cannot be both 0s. This means that the RT cannot be 0:0.
               - 32-bit IP address:16-bit user-defined number, for example: 192.168.122.15:1. The IP address ranges from 0.0.0.0 to 255.255.255.255, and the user-defined number ranges from 0 to 65535.
               - 32-bit AS number:16-bit user-defined number, for example, 10.11:3. An AS number ranges from 0.0 to 65535.65535, and a user-defined number ranges from 0 to 65535. The AS number and user-defined number cannot be both 0s. This means that the RT cannot be 0.0:0.";
          }
          leaf rt-type {
            type ncs_template_vpn-rt-type;
            description
              "RT type, which can be:
               - export-extcommunity: specifies the value of the extended community attribute of the route from an outbound interface to the destination VPN.
               - import-extcommunity: receives routes that carry the specified extended community attribute value.";
          }
        }
      }
      container flow-label {
        presence "enable flow-label for bgp signaling pws.";
        description
          "Enable/disable flow label capability of a PW.";
        leaf ability {
          type ncs_template_flow-label-ability;
          // NCS drop must statement
          // NCS drop mandatory statement
          description
            "Flow label capability.";
        }
        leaf static {
          type string;
          // NCS drop default statement
          description
            "Enable/disable the static flow label function.";
        }
      }
      container pws {
        description
          "List of VPLS BGP PWs.";
        list pw {
          // NCS patched for predictable order
          ordered-by user;
          // NCS drop must statement
          key "peer-ip remote-site-id";
          unique "name";
          description
            "Configure VPLS BGP PWs.";
          leaf peer-ip {
            type string;
            description
              "Peer IP address.";
          }
          leaf remote-site-id {
            type string;
            description
              "Remote BGP site ID.";
          }
          leaf name {
            type string;
            description
              "PW name.";
          }
          leaf traffic-statistics-collection {
            type string;
            // NCS drop must statement
            // NCS drop default statement
            description
              "Enable/disable the function to collect traffic statistics.";
          }
          uses l2vpn:ncs_template_suppression-statisticss-grp;
        }
      }
      // NCS drop config false container 'local-label-blocks'
      // NCS drop config false container 'remote-label-blocks'
      // NCS drop config false container 'pw-infos'
    }
    container bgp-multi-homing-signaling {
      // NCS drop when statement
      // NCS drop must statement
      // NCS drop must statement
      presence "Container for bgp protocol vpls instance.";
      description
        "Configure BGP VSIs.";
      leaf route-distinguisher {
        type string;
        description
          "Route distinguisher.";
      }
      leaf encapsulation-rfc4761-compatible {
        type string;
        // NCS drop default statement
        description
          "Enable/disable the setting of an encapsulation type.";
      }
      leaf encapsulation-vpls-family-compatible {
        type string;
        // NCS drop default statement
        description
          "Enable/disable the setting of an encapsulation type to private mode.";
      }
      leaf mtu-negotiate-disable {
        type string;
        // NCS drop default statement
        description
          "Enable/disable the function of ignoring MTU match between local VSI and remote VSI. The default implementation is match.";
      }
      leaf site-range {
        type string;
        description
          "BGP site range. Cannot decrease site range.";
      }
      leaf default-offset {
        ext:operation-exclude "update|delete";
        // NCS drop when statement
        type string;
        // NCS drop default statement
        description
          "BGP site offset. The value of this node cannot be modified after being set.";
      }
      leaf control-word {
        type ncs_template_l2vpn-control-word;
        // NCS drop must statement
        // NCS drop default statement
        description
          "Enable the control word feature. The control word feature is usually used for TDM, ATM, and FR PWs.";
      }
      // NCS drop config false leaf 'auto-route-distinguisher'
      container default-site {
        description
          "Configure the default BGP multi-homing site.";
        leaf name {
          type ncs_template_vpls-multi-homing-site-name;
          // NCS drop must statement
          // NCS drop default statement
          description
            "BGP multi-homing default site name.";
        }
        leaf site-id {
          type string;
          description
            "BGP multi-homing default site ID.";
        }
        leaf preference {
          // NCS drop when statement
          type string;
          // NCS drop default statement
          description
            "BGP multi-homing default site preference.";
        }
        // NCS drop config false leaf selected
        // NCS drop config false container 'remote-sites'
      }
      container sites {
        description
          "List of BGP multi-homing sites.";
        list site {
          // NCS patched for predictable order
          ordered-by user;
          key "name";
          // NCS drop max-elements statement
          description
            "Configure BGP multi-homing sites.";
          leaf name {
            type ncs_template_vpls-multi-homing-site-name;
            // NCS drop must statement
            description
              "BGP multi-homing site name.";
          }
          leaf site-id {
            type string;
            description
              "BGP multi-homing site ID.";
          }
          leaf preference {
            // NCS drop when statement
            type string;
            // NCS drop default statement
            description
              "BGP multi-homing site preference.";
          }
          leaf active-delay-time {
            // NCS drop when statement
            type string;
            units "s";
            // NCS drop default statement
            description
              "BGP multi-homing site active delay time.";
          }
          leaf recover-delay-time {
            // NCS drop when statement
            type string;
            units "s";
            // NCS drop default statement
            description
              "BGP multi-homing site recover delay time.";
          }
          leaf best-site {
            // NCS drop when statement
            type empty;
            description
              "BGP multi-homing best site.";
          }
          // NCS drop config false leaf selected
          // NCS drop config false container 'remote-sites'
          // NCS drop config false container 'ac-infos'
        }
      }
      container vpn-targets {
        description
          "List of VPN targets.";
        list vpn-target {
          // NCS patched for predictable order
          ordered-by user;
          key "rt-value rt-type";
          // NCS drop max-elements statement
          description
            "Configure VPN targets.";
          leaf rt-value {
            type string;
            description
              "Route target. The format of an RT can be:
               - 16-bit AS number:32-bit user-defined number, for example, 1:3. An AS number ranges from 0 to 65535, and a user-defined number ranges from 0 to 4294967295. The AS number and user-defined number cannot be both 0s. This means that the RT cannot be 0:0.
               - Integral 4-byte AS number:2-byte user-defined number, for example, 65537:3. An AS number ranges from 65536 to 4294967295. A user-defined number ranges from 0 to 65535. The AS number and user-defined number cannot be both 0s. This means that the RT cannot be 0:0.
               - 32-bit IP address:16-bit user-defined number, for example: 192.168.122.15:1. The IP address ranges from 0.0.0.0 to 255.255.255.255, and the user-defined number ranges from 0 to 65535.
               - 32-bit AS number:16-bit user-defined number, for example, 10.11:3. An AS number ranges from 0.0 to 65535.65535, and a user-defined number ranges from 0 to 65535. The AS number and user-defined number cannot be both 0s. This means that the RT cannot be 0.0:0.";
          }
          leaf rt-type {
            type ncs_template_vpn-rt-type;
            description
              "RT type, which can be:
               - export-extcommunity: specifies the value of the extended community attribute of the route from an outbound interface to the destination VPN.
               - import-extcommunity: receives routes that carry the specified extended community attribute value.";
          }
        }
      }
      container pws {
        description
          "List of VPLS BGP multi-homing PWs.";
        list pw {
          // NCS patched for predictable order
          ordered-by user;
          // NCS drop must statement
          key "peer-ip";
          unique "name";
          description
            "Configure a VPLS BGP multi-homing PW.";
          leaf peer-ip {
            type string;
            description
              "Peer IP address.";
          }
          leaf name {
            type string;
            description
              "PW name.";
          }
          leaf traffic-statistics-collection {
            type string;
            // NCS drop must statement
            // NCS drop default statement
            description
              "Enable/disable the function to collect traffic statistics.";
          }
          uses l2vpn:ncs_template_suppression-statisticss-grp;
        }
      }
      // NCS drop config false container 'pw-infos'
      // NCS drop config false container 'local-label-blocks'
      // NCS drop config false container 'remote-sites'
    }
    container bgpad-signaling {
      // NCS drop when statement
      // NCS drop must statement
      // NCS drop must statement
      presence "Container for bgpad protocol vpls instance.";
      description
        "Enable/disable BGP AD VSI.";
      leaf vpls-id {
        type string;
        description
          "VPLS domain ID. The format of a VPLS domain ID can be:
           - 16-bit AS number:32-bit user-defined number, for example, 1:3. An AS number ranges from 0 to 65535, and a user-defined number ranges from 0 to 4294967295. The AS number and user-defined number cannot be both 0s. This means that the VPLS domain ID cannot be 0:0.
           - Integral 4-byte AS number:2-byte user-defined number, for example, 65537:3. An AS number ranges from 65536 to 4294967295. A user-defined number ranges from 0 to 65535. The AS number and user-defined number cannot be both 0s. This means that the VPLS domain ID cannot be 0:0.
           - 32-bit IP address:16-bit user-defined number, for example: 192.168.122.15:1. The IP address ranges from 0.0.0.0 to 255.255.255.255, and the user-defined number ranges from 0 to 65535.
           - 32-bit AS number:16-bit user-defined number, for example, 10.11:3. An AS number ranges from 0.0 to 65535.65535, and a user-defined number ranges from 0 to 65535. The AS number and user-defined number cannot be both 0s. This means that the VPLS domain ID cannot be 0.0:0.";
      }
      leaf split-horizon {
        // NCS drop when statement
        type ncs_template_vpls-split-horizon-mode-type;
        // NCS drop default statement
        description
          "PW split horizon mode.";
      }
      leaf traffic-statistics-collection {
        // NCS drop when statement
        type string;
        // NCS drop must statement
        // NCS drop default statement
        description
          "Enable/disable traffic statistics collection.";
      }
      // NCS drop config false leaf 'route-distinguisher'
      // NCS drop config false leaf 'vsi-id'
      container vpn-targets {
        // NCS drop when statement
        description
          "List of VPN targets.";
        list vpn-target {
          // NCS patched for predictable order
          ordered-by user;
          key "rt-value rt-type";
          // NCS drop max-elements statement
          description
            "Configure VPN targets.";
          leaf rt-value {
            type string;
            description
              "Route target. The format of an RT can be:
               - 16-bit AS number:32-bit user-defined number, for example, 1:3. An AS number ranges from 0 to 65535, and a user-defined number ranges from 0 to 4294967295. The AS number and user-defined number cannot be both 0s. This means that the RT cannot be 0:0.
               - Integral 4-byte AS number:2-byte user-defined number, for example, 65537:3. An AS number ranges from 65536 to 4294967295. A user-defined number ranges from 0 to 65535. The AS number and user-defined number cannot be both 0s. This means that the RT cannot be 0:0.
               - 32-bit IP address:16-bit user-defined number, for example: 192.168.122.15:1. The IP address ranges from 0.0.0.0 to 255.255.255.255, and the user-defined number ranges from 0 to 65535.
               - 32-bit AS number:16-bit user-defined number, for example, 10.11:3. An AS number ranges from 0.0 to 65535.65535, and a user-defined number ranges from 0 to 65535. The AS number and user-defined number cannot be both 0s. This means that the RT cannot be 0.0:0.";
          }
          leaf rt-type {
            type ncs_template_vpn-rt-type;
            description
              "RT type, which can be:
               - export-extcommunity: specifies the value of the extended community attribute of the route from an outbound interface to the destination VPN.
               - import-extcommunity: receives routes that carry the specified extended community attribute value.";
          }
        }
      }
      container pws {
        // NCS drop when statement
        description
          "List of BGP AD PWs.";
        list pw {
          // NCS patched for predictable order
          ordered-by user;
          // NCS drop must statement
          key "peer-ip";
          description
            "Configure a BGP AD PW.";
          leaf peer-ip {
            type string;
            description
              "Peer IP address.";
          }
          leaf name {
            type string;
            description
              "PW name.";
          }
          leaf traffic-statistics-collection {
            type string;
            // NCS drop must statement
            // NCS drop must statement
            // NCS drop must statement
            description
              "Enable/disable the function to collect traffic statistics.";
          }
          uses l2vpn:ncs_template_suppression-statisticss-grp;
        }
      }
      // NCS drop config false container peers
    }
    container acs {
      // NCS drop when statement
      description
        "List of VPLS ACs.";
      list ac {
        // NCS patched for predictable order
        ordered-by user;
        key "interface-name";
        description
          "Configure a VPLS AC.";
        leaf interface-name {
          type string;
          // NCS drop must statement
          description
            "Name of the AC interface bound to a VSI.";
        }
        leaf site-name {
          // NCS drop when statement
          type ncs_template_vpls-multi-homing-site-name;
          description
            "BGP multi-homing site name. The value of this node cannot be changed after being configured.";
        }
        leaf hub-mode {
          type string;
          // NCS drop default statement
          description
            "Enable/disable an interface's support for the hub mode.";
        }
        leaf access-port {
          ext:operation-exclude "update|delete";
          type string;
          // NCS drop must statement
          // NCS drop default statement
          description
            "Enable/disable the attribute that allows only untagged packets to pass through an interface.";
        }
        leaf etree-leaf {
          // NCS drop when statement
          type string;
          // NCS drop must statement
          // NCS drop default statement
          description
            "Enable/disable e-tree leaf.";
        }
        // NCS drop config false leaf state
        // NCS drop config false leaf 'block-state'
        // NCS drop config false leaf 'last-up-time'
        // NCS drop config false leaf 'total-up-time'
        // NCS drop config false leaf 'token-exceed'
        // NCS drop config false leaf 'oam-state'
      }
    }
    container bds {
      // NCS drop when statement
      // NCS drop must statement
      description
        "List of VPLS BD ACs.";
      list bd {
        // NCS patched for predictable order
        ordered-by user;
        // NCS drop must statement
        key "id";
        unique "pw-tag";
        description
          "Configure VPLS BD ACs.";
        leaf id {
          type string;
          description
            "BD ID.";
        }
        leaf pw-tag {
          type string;
          description
            "PW tag.";
        }
        // NCS drop config false leaf state
        // NCS drop config false leaf 'last-up-time'
        // NCS drop config false leaf 'total-up-time'
      }
    }
    container pbb {
      // NCS drop when statement
      // NCS drop must statement
      description
        "Configure PBB VPLS.";
      leaf i-tag {
        // NCS drop when statement
        type string;
        description
          "Tag defined in 802.1ah to identify a service instance.";
      }
      leaf backbone-source-mac {
        // NCS drop when statement
        type pub-type:ncs_template_mac-address;
        description
          "B-SMAC address.";
      }
      leaf backbone-destination-mac {
        // NCS drop when statement
        type pub-type:ncs_template_mac-address;
        description
          "B-DMAC address.";
      }
      leaf mac-withdraw-rfc7361-compatible {
        // NCS drop when statement
        type string;
        // NCS drop default statement
        description
          "Enable/disable MAC withdraw messages that carry PBB B-MAC and I-tag TLVs in accordance with RFC 7361.";
      }
      leaf b-vsi {
        type string;
        // NCS drop must statement
        description
          "Name of the B-VSI instance to which the I-VSI is bound.";
      }
      leaf b-evpn {
        type string;
        // NCS drop must statement
        description
          "Name of the B-EVPN instance to which the I-VSI is bound.";
      }
      // NCS drop config false leaf 'learned-flag'
      // NCS drop config false leaf 'learned-in-label'
      // NCS drop config false leaf 'learned-out-label'
      // NCS drop config false container 'i-vsis'
    }
    container ipmsi {
      // NCS drop when statement
      // NCS drop must statement
      // NCS drop must statement
      presence "enable ipmsi.";
      description
        "Enable/disable multicast VPLS.";
      container root {
        presence "root";
        description
          "Enable/disable the P2MP tunnel root.";
        leaf data-switch-disable {
          type string;
          // NCS drop default statement
          description
            "Enable/disable broadcast, unknown unicast, and multicast traffic's switching to a PW when a P2MP tunnel goes down.";
        }
        leaf mc-tunnel-type {
          type ncs_template_multicast-tunnel-type;
          // NCS drop default statement
          description
            "P2MP tunnel type.";
        }
        leaf root-ip {
          // NCS drop when statement
          type string;
          description
            "Root IP address of a P2MP tunnel.";
        }
        leaf te-p2mp-dynamic {
          // NCS drop when statement
          type string;
          // NCS drop default statement
          description
            "Enable/disable P2MP dynamic TE.";
        }
        leaf p2mp-template-name {
          // NCS drop when statement
          type string;
          description
            "P2MP template name.";
        }
        leaf bfd-track-if-name {
          // NCS drop when statement
          type string;
          description
            "Name of the interface bound to a BFD session.";
        }
        // NCS drop config false leaf 'leaf-count'
        // NCS drop config false container tunnel
        // NCS drop config false container leafs
      }
      container leaf {
        presence "leaf";
        description
          "Enable/disable the leaf of a P2MP tunnel.";
        // NCS drop config false leaf 'egress-count'
        container pw-protect-groups {
          description
            "List of PW protection groups.";
          list pw-protect-group {
            // NCS patched for predictable order
            ordered-by user;
            key "primary-root-ip backup-root-ip";
            description
              "Configure a PW protection group.";
            leaf primary-root-ip {
              type string;
              description
                "IP address of the primary root.";
            }
            leaf backup-root-ip {
              type string;
              description
                "IP address of the backup root.";
            }
            leaf wtr {
              type string;
              units "min";
              // NCS drop default statement
              description
                "Wait-to-Restore time.";
            }
            leaf primary-track-bfd {
              type string;
              // NCS drop default statement
              description
                "Enable/disable the association between the primary root and a BFD session.";
            }
            leaf backup-track-bfd {
              type string;
              // NCS drop default statement
              description
                "Enable/disable the association between the backup root and a BFD session.";
            }
            // NCS drop config false container primary
            // NCS drop config false container backup
          }
        }
        // NCS drop config false container 'mldp-p2mp-tunnels'
        // NCS drop config false container 'te-p2mp-tunnels'
      }
    }
    // NCS drop config false container 'mac-withdraw-loop-detect'
    // NCS drop config false container 'down-causes'
    // NCS drop config false container statistic
    // NCS drop config false container 'ac-suppression-statisticss'
  }

  grouping ncs_template_l2vpn-protect-group-historys-type {
    description
      "List of L2VPN protect group histroy info container.";
    list history {
      // NCS patched for predictable order
      ordered-by user;
      key "num";
      // NCS drop max-elements statement
      description
        "Operational data of historical switching information of a PW protection group.";
      leaf num {
        type string;
        description
          "Sequence number.";
      }
      leaf reroute-time {
        type string;
        description
          "Switchback time.";
      }
      leaf reroute-action {
        type string;
        description
          "Switchback action.";
      }
      leaf reroute-reason {
        type string;
        description
          "Switchback reason.";
      }
    }
  }

  grouping ncs_template_bgp-local-label-block-grp {
    description
      "List of a local label blocks.";
    list local-label-block {
      // NCS patched for predictable order
      ordered-by user;
      key "offset";
      description
        "Operational data of local label blocks.";
      leaf offset {
        type string;
        description
          "BGP site offset.";
      }
      leaf label-start {
        type string;
        description
          "Start of the label.";
      }
      leaf add-range {
        type string;
        description
          "BGP site range.";
      }
      leaf site-base {
        type string;
        description
          "Base of the site.";
      }
    }
  }

  grouping ncs_template_bgp-remote-label-block-grp {
    description
      "List of remote label blocks.";
    list remote-label-block {
      // NCS patched for predictable order
      ordered-by user;
      key "route-distinguisher site-id offset";
      description
        "Operational data of remote label blocks.";
      leaf route-distinguisher {
        type string;
        description
          "Route distinguisher.";
      }
      leaf site-id {
        type string;
        description
          "BGP site ID.";
      }
      leaf offset {
        type string;
        description
          "BGP site offset.";
      }
      leaf label-start {
        type string;
        description
          "Start of the label.";
      }
      leaf add-range {
        type string;
        description
          "BGP site range.";
      }
    }
  }

  grouping ncs_template_ac-arp-grp {
    description
      "List of ARP information about all ACs.";
    list ac-arp {
      // NCS patched for predictable order
      ordered-by user;
      key "mac-type";
      // NCS drop max-elements statement
      description
        "Operational data of ARP information about an AC.";
      leaf mac-type {
        type ncs_template_l2vpn-mac-type;
        description
          "MAC address learning type.";
      }
      leaf mac-address {
        type pub-type:ncs_template_mac-address;
        description
          "MAC address of the local CE.";
      }
      leaf expire-time {
        type string;
        units "min";
        description
          "Aging time.";
      }
      leaf vlan-id {
        type string;
        description
          "VLAN ID corresponding to a MAC address.";
      }
      leaf ip-address {
        type string;
        description
          "Dynamically learned IP address of the local CE.";
      }
    }
  }

  grouping ncs_template_ipmsi-leaf-protect-group-parameter {
    description
      "Operational data of Ipmsi leaf protect group parameters.";
    leaf valid {
      type string;
      // NCS drop default statement
      description
        "The root is valid.";
    }
    leaf active-state {
      type ncs_template_multicast-active-state;
      description
        "The root is active.";
    }
    leaf oam-protocol {
      type ncs_template_multicast-oam-type;
      description
        "Root OAM protocol.";
    }
    leaf oam-state {
      type ncs_template_oam-state;
      description
        "Root OAM status.";
    }
  }

  grouping ncs_template_mldp-p2mp-tunnel-grp {
    description
      "Operational data of Ipmsi mLDP P2MP tunnel.";
    list mldp-p2mp-tunnel {
      // NCS patched for predictable order
      ordered-by user;
      key "root-ip opaque-value";
      // NCS drop max-elements statement
      description
        "Operational data of tunnel information on a leaf node.";
      leaf root-ip {
        type string;
        description
          "Root IP address of a P2MP tunnel.";
      }
      leaf opaque-value {
        type string;
        description
          "Original opaque value in a message. The value is displayed in the format of TLV.";
      }
      leaf state {
        type ncs_template_l2vpn-state;
        description
          "P2MP tunnel status.";
      }
    }
  }

  grouping ncs_template_te-p2mp-tunnel-grp {
    description
      "Operational data of Ipmsi te P2MP tunnel.";
    list te-p2mp-tunnel {
      // NCS patched for predictable order
      ordered-by user;
      key "ingress-lsr-id session-id p2mp-id";
      // NCS drop max-elements statement
      description
        "Operational data of tunnel information on a leaf node.";
      leaf ingress-lsr-id {
        type string;
        description
          "Ingress LSR ID.";
      }
      leaf session-id {
        type string;
        description
          "RSVP session ID.";
      }
      leaf p2mp-id {
        type string;
        description
          "P2MP session ID.";
      }
      leaf state {
        type ncs_template_l2vpn-state;
        description
          "P2MP tunnel status.";
      }
    }
  }

  grouping ncs_template_bgp-mh-remote-site-grp {
    description
      "Operational data of BGP multi-homing remote site information.";
    list remote-site {
      // NCS patched for predictable order
      ordered-by user;
      key "remote-site-id peer-ip";
      description
        "Operational data of BGP multi-homing remote site information.";
      leaf remote-site-id {
        type string;
        description
          "BGP multi-homing remote site ID.";
      }
      leaf peer-ip {
        type string;
        description
          "BGP multi-homing peer IP.";
      }
    }
  }

  grouping ncs_template_suppression-statistics-grp {
    description
      "Suppression statistics.";
    leaf suppression-type {
      type ncs_template_suppression-type;
      description
        "Suppression statistics type.";
    }
    leaf cir {
      type string;
      description
        "CIR value.";
    }
    leaf pir {
      type string;
      description
        "PIR value.";
    }
    leaf cbs {
      type string;
      description
        "CBS value.";
    }
    leaf pbs {
      type string;
      description
        "PBS value.";
    }
    leaf passed-packets {
      type string;
      description
        "Passed packets.";
    }
    leaf passed-bytes {
      type string;
      description
        "Passed bytes.";
    }
    leaf discard-packets {
      type string;
      description
        "Discard packets.";
    }
    leaf discard-bytes {
      type string;
      description
        "Discard bytes.";
    }
    leaf passed-packet-rate {
      type string;
      units "pps";
      description
        "Passed packet rate.";
    }
    leaf passed-bit-rate {
      type string;
      units "bit/s";
      description
        "Passed bit rate.";
    }
    leaf discard-packet-rate {
      type string;
      units "pps";
      description
        "Discard packet rate.";
    }
    leaf discard-bit-rate {
      type string;
      units "bit/s";
      description
        "Discard bit rate.";
    }
  }

  grouping ncs_template_suppression-statisticss-grp {
    description
      "Suppression statistics.";
    // NCS drop config false container 'suppression-statisticss'
  }

  grouping ncs_template_pw-traffic-statisticss-grp {
    description
      "Traffic statistics of PW.";
    // NCS drop config false container 'traffic-statistics'
  }

  grouping ncs_rpc_notif_spe-infos-type {
    description
      "Indicates the query list of the SPE information.";
    list spe {
      key "spe-pw-id spe-peer-ip";
      description
        "Operational data of the SPE on the path to the peer.";
      leaf spe-pw-id {
        type uint32 {
          range "0..4294967295";
        }
        description
          "List of PW IDs on the path traveled by a label mapping message.";
      }
      leaf spe-peer-ip {
        type inet:ipv4-address-no-zone;
        description
          "IP address of an SPE in the path to the peer.";
      }
    }
  }

  grouping ncs_rpc_notif_l2vpn-reroute-policy-type {
    description
      "L2VPN protect group reroute policy class.";
    leaf policy {
      type ncs_rpc_notif_l2vpn-reroute-mode;
      default "delay";
      description
        "Switchback policy.";
    }
    leaf delay-time {
      when "../policy='delay'" {
        tailf:xpath-root 3;
      }
      type uint32 {
        range "10..10800";
      }
      units "s";
      default "30";
      description
        "Delay for switching traffic back to the primary PW.";
    }
    leaf last-switchback-time {
      type string {
        length "1..60";
      }
      config false;
      description
        "Last switchback time.";
    }
    leaf last-reroute-action {
      type string {
        length "1..100";
      }
      config false;
      description
        "Last switchback action.";
    }
    leaf last-switchback-reason {
      type string {
        length "0..100";
      }
      config false;
      description
        "Last switchback reason.";
    }
  }

  grouping ncs_rpc_notif_l2vpn-dyn-bfd-para-type {
    description
      "Dynamic BFD parameters.";
    leaf min-rx-interval {
      type uint16 {
        range "0..65535";
      }
      units "ms";
      default "10";
      description
        "Minimum receive interval.";
    }
    leaf min-tx-interval {
      type uint16 {
        range "0..65535";
      }
      units "ms";
      default "10";
      description
        "Minimum transmit interval.";
    }
    leaf detect-multiplier {
      type uint16 {
        range "3..50";
      }
      default "3";
      description
        "Detection multiplier.";
    }
  }

  grouping ncs_rpc_notif_l2vpn-label-stacks-type {
    description
      "Label stack.";
    list label-stack {
      key "label-stack level";
      description
        "Operational data of the PW label stack.";
      leaf label-stack {
        type uint32 {
          range "1..4294967295";
        }
        description
          "Label stack.";
      }
      leaf level {
        type uint32 {
          range "1..4294967295";
        }
        description
          "Label level.";
      }
      leaf type {
        type string {
          length "0..20";
        }
        description
          "Label type.";
      }
      leaf label {
        type string {
          length "0..20";
        }
        description
          "Label value.";
      }
      leaf out-interface {
        type string;
        description
          "Outbound interface name.";
      }
    }
  }

  grouping ncs_rpc_notif_l2vpn-pw-down-causes-type {
    description
      "Indicates the down causes of the PW.";
    list down-cause {
      key "down-cause-index";
      description
        "Statistics of the down causes of PWs.";
      leaf down-cause-index {
        type uint32;
        description
          "Sequence number of the PW down cause.";
      }
      leaf down-cause {
        type string {
          length "0..100";
        }
        description
          "Indicates the down causes of the PW.";
      }
    }
  }

  grouping ncs_rpc_notif_l2vpn-pw-status-changes-type {
    description
      "Indicates the reason and the time of the PW status that has changed.";
    list status-change {
      key "index";
      description
        "Statistics of the reason and the time of the PW status that has changed.";
      leaf index {
        type uint32;
        description
          "Sequence number of reasons that the PW status has changed.";
      }
      leaf timestamp {
        type string {
          length "0..60";
        }
        description
          "Indicates the time of the PW status has changed.";
      }
      leaf reason {
        type string {
          length "0..100";
        }
        description
          "Indicates the reason of the PW status has changed.";
      }
    }
  }

  grouping ncs_rpc_notif_l2vpn-ccc-tdm-type {
    description
      "Tdm parameters of CCC instance.";
    leaf tdm-encapsulate-number {
      ext:dynamic-default;
      type uint32 {
        range "1..40";
      }
      description
        "Number of TDM frames encapsulated in a CESoPSN or SAToP packet in the TDMoPSN application.";
    }
    leaf jitter-buffer {
      ext:dynamic-default;
      type uint32 {
        range "1..64000";
      }
      units "us";
      description
        "Depth of the jitter buffer in the application of TDMoPSN.";
    }
    leaf rtp-header {
      type boolean;
      default "false";
      description
        "Enable/disable the RTP header of transparently transmitted TDM frames.";
    }
    leaf idle-code {
      type yang:hex-string {
        length "1..2";
      }
      default "ff";
      description
        "Idle code that is filled when the jitter buffer underflow occurs.";
    }
  }

  grouping ncs_rpc_notif_l2vpn-ccc-atm-type {
    description
      "L2VPN ATM class.";
    leaf max-atm-cells {
      type uint32 {
        range "1..28";
      }
      ext:dynamic-default;
      description
        "Maximum number of ATM cells to be encapsulated into a packet that can be received by a device.";
    }
    leaf atm-pack-overtime {
      type uint32 {
        range "100..10000";
      }
      units "us";
      ext:dynamic-default;
      description
        "Delay in encapsulating ATM cells into a packet.";
    }
  }

  grouping ncs_rpc_notif_vpws-localccc-instance-grp {
    description
      "VPWS local CCC instance.";
    leaf encapsulation-type {
      ext:operation-exclude "update";
      type ncs_rpc_notif_encapsulation-type;
      must "../encapsulation-type='vlan' or
../encapsulation-type='ethernet' or
../encapsulation-type='hdlc' or
../encapsulation-type='ppp' or
../encapsulation-type='atm-nto1-vcc' or
../encapsulation-type='atm-nto1-vpc' or
../encapsulation-type='atm-1to1-vcc' or
../encapsulation-type='atm-1to1-vpc' or
../encapsulation-type='atm-trans-cell' or
../encapsulation-type='cep' or
../encapsulation-type='satop-e1' or
../encapsulation-type='cesopsn-basic' or
../encapsulation-type='ip-interworking' or
../encapsulation-type='unsupport'" {
        tailf:xpath-root 3;
      }
      mandatory true;
      description
        "Encapsulation type of a VPWS instance.";
    }
    container tdm-parameter {
      when "../encapsulation-type='satop-e1' or
../encapsulation-type='cesopsn-basic' or
../encapsulation-type='cep' or
../encapsulation-type='satop-t1' or
../encapsulation-type='satop-e3'" {
        tailf:xpath-root 3;
      }
      description
        "Configure TDM parameters.";
      leaf tdm-encapsulate-number {
        type uint32 {
          range "1..40";
        }
        ext:dynamic-default;
        description
          "Number of TDM frames encapsulated in a CESoPSN or SAToP packet in the TDMoPSN application.";
      }
      leaf jitter-buffer {
        type uint32 {
          range "1..64000";
        }
        units "us";
        ext:dynamic-default;
        description
          "Depth of the jitter buffer in the application of TDMoPSN.";
      }
      leaf rtp-header {
        type boolean;
        default "false";
        description
          "Enable/disable transparently transmission of TDM frames.";
      }
      leaf idle-code {
        type yang:hex-string {
          length "1..2";
        }
        default "ff";
        description
          "Idle code that is filled when the jitter buffer underflow occurs.";
      }
    }
    container atm-parameter {
      when "../encapsulation-type='atm-aal5-sdu' or
../encapsulation-type='atm-trans-cell' or
../encapsulation-type='atm-nto1-vcc' or
../encapsulation-type='atm-nto1-vpc' or
../encapsulation-type='atm-1to1-vcc' or
../encapsulation-type='atm-1to1-vpc' or
../encapsulation-type='atm-aal5-pdu'" {
        tailf:xpath-root 3;
      }
      description
        "Configure ATM parameters.";
      leaf max-atm-cells {
        type uint32 {
          range "1..28";
        }
        ext:dynamic-default;
        description
          "Maximum number of ATM cells to be encapsulated into a packet that can be received by a device.";
      }
      leaf atm-pack-overtime {
        type uint32 {
          range "100..10000";
        }
        units "us";
        ext:dynamic-default;
        description
          "Delay in encapsulating ATM cells into a packet.";
      }
    }
    container acs {
      description
        "List of information about all ACs.";
      list ac {
        ext:operation-exclude "update|delete";
        must "(not(arp-entry)) or (arp-entry and (/ifm:ifm/ifm:interfaces/ifm:interface[ifm:name=current()/interface-name]/ifm:link-protocol='ethernet'))" {
          tailf:xpath-root 3;
        }
        key "interface-name";
        min-elements 2;
        max-elements 2;
        description
          "Configure information about an AC. AC information is displayed in a configuration order.";
        leaf interface-name {
          type string;
          description
            "Name of an AC interface.";
        }
        leaf tagged {
          ext:operation-exclude "update|delete";
          when "../../../encapsulation-type='ethernet' or
../../../encapsulation-type='vlan'" {
            tailf:xpath-root 3;
          }
          type boolean;
          ext:dynamic-default {
            ext:default-value "false" {
              when "../../../encapsulation-type='ethernet'" {
                tailf:xpath-root 3;
              }
              description
                "The default value is false when encapsulation-type is ethernet.";
            }
            ext:default-value "true" {
              when "../../../encapsulation-type='vlan'" {
                tailf:xpath-root 3;
              }
              description
                "The default value is true when encapsulation-type is VLAN.";
            }
          }
          must "(../../../encapsulation-type='ethernet' and ../tagged='false') or
(../../../encapsulation-type='vlan' and ../tagged='true')" {
            tailf:xpath-root 3;
          }
          description
            "Enable/disable the VLAN tag setting.";
        }
        leaf access-port {
          ext:operation-exclude "update|delete";
          when "../../../encapsulation-type='ethernet' or
../../../encapsulation-type='ip-interworking' or
../../../encapsulation-type='ip-layer2' or
../../../encapsulation-type='vlan'" {
            tailf:xpath-root 3;
          }
          type boolean;
          must "/ifm:ifm/ifm:interfaces/ifm:interface[ifm:name=current()/../interface-name]/ifm:class='main-interface' or (/ifm:ifm/ifm:interfaces/ifm:interface[ifm:name=current()/../interface-name]/ifm:class='sub-interface' and ../access-port = 'false')" {
            tailf:xpath-root 3;
          }
          default "false";
          description
            "Enable/disable the attribute that allows only untagged packets to pass through an interface.";
        }
        leaf trigger-interface-down {
          type boolean;
          must "(/ifm:ifm/ifm:interfaces/ifm:interface[ifm:name=current()/../interface-name]/ifm:class='main-interface' and /ifm:ifm/ifm:interfaces/ifm:interface[ifm:name=current()/../interface-name]/ifm:link-protocol='ethernet' and . = 'true') or (. = 'false')" {
            tailf:xpath-root 3;
          }
          default "false";
          description
            "Enable/disable remote interface shutdown-based association between the PW status and interface status.";
        }
        leaf state {
          type ncs_rpc_notif_l2vpn-state;
          config false;
          description
            "Status of an AC.";
        }
        leaf token-exceed {
          type boolean;
          default "false";
          config false;
          description
            "Indicates whether the number of AC tokens exceeds the maximum limit.";
        }
        container arp-entry {
          presence "Enable the ARP entry for AC.";
          description
            "Configure the ARP entry attribute used for IP interworking between PEs.";
          leaf local-ce-mac {
            type pub-type:ncs_rpc_notif_mac-address;
            description
              "MAC address of the ethernet interface or sub-interface on a CE connected to the local AC interface. If MAC, IP, and broadcast addresses are all configured, these addresses take effect in the sequence of MAC address, IP address, and broadcast address.";
          }
          leaf local-ce-ip {
            type inet:ipv4-address-no-zone;
            description
              "IP address of the ethernet interface or sub-interface on a CE connected to the local AC interface.";
          }
          leaf local-ce-broadcast {
            type boolean;
            must "((.='false' and (../local-ce-mac or ../local-ce-ip or ../remote-ce-ip)) or (.='true'))" {
              tailf:xpath-root 3;
            }
            default "false";
            description
              "Enable/disable the broadcast function on a PE Ethernet interface connected to a CE.";
          }
          leaf remote-ce-ip {
            type inet:ipv4-address-no-zone;
            description
              "IP address of the remote CE connected to the local AC interface.";
          }
        }
        container ac-arps {
          config false;
          description
            "Operational data of ARP information about all ACs.";
          uses ncs_rpc_notif_ac-arp-grp;
        }
      }
    }
  }

  grouping ncs_rpc_notif_vpws-remoteccc-instance-grp {
    description
      "VPWS remote CCC instance.";
    leaf encapsulation-type {
      ext:operation-exclude "update";
      ext:support-filter "true";
      type ncs_rpc_notif_encapsulation-type;
      must "../encapsulation-type='vlan' or
../encapsulation-type='ethernet' or
../encapsulation-type='hdlc' or
../encapsulation-type='ppp' or
../encapsulation-type='atm-nto1-vcc' or
../encapsulation-type='atm-nto1-vpc' or
../encapsulation-type='atm-1to1-vcc' or
../encapsulation-type='atm-1to1-vpc' or
../encapsulation-type='cep' or
../encapsulation-type='satop-e1' or
../encapsulation-type='cesopsn-basic' or
../encapsulation-type='ip-interworking' or
../encapsulation-type='unsupport'" {
        tailf:xpath-root 3;
      }
      mandatory true;
      description
        "Encapsulation type of a VPWS instance.";
    }
    container acs {
      description
        "List of information about all ACs.";
      list ac {
        ext:operation-exclude "update|delete";
        must "(not(arp-entry)) or (arp-entry and (/ifm:ifm/ifm:interfaces/ifm:interface[ifm:name=current()/interface-name]/ifm:link-protocol='ethernet'))" {
          tailf:xpath-root 3;
        }
        key "interface-name";
        min-elements 1;
        max-elements 1;
        description
          "Configure information about an AC.";
        leaf interface-name {
          type string;
          description
            "Name of an AC interface.";
        }
        leaf tagged {
          ext:operation-exclude "update|delete";
          when "../../../encapsulation-type='ethernet' or
../../../encapsulation-type='vlan'" {
            tailf:xpath-root 3;
          }
          type boolean;
          ext:dynamic-default {
            ext:default-value "false" {
              when "../../../encapsulation-type='ethernet'" {
                tailf:xpath-root 3;
              }
              description
                "The default value is false when encapsulation-type is ethernet.";
            }
            ext:default-value "true" {
              when "../../../encapsulation-type='vlan'" {
                tailf:xpath-root 3;
              }
              description
                "The default value is true when encapsulation-type is VLAN.";
            }
          }
          must "(../../../encapsulation-type='ethernet' and ../tagged='false') or
(../../../encapsulation-type='vlan' and ../tagged='true')" {
            tailf:xpath-root 3;
          }
          description
            "Enable/disable the VLAN tag setting.";
        }
        leaf state {
          type ncs_rpc_notif_l2vpn-state;
          config false;
          description
            "Status of an AC.";
        }
        leaf token-exceed {
          type boolean;
          default "false";
          config false;
          description
            "Indicates whether the number of AC tokens exceeds the maximum limit.";
        }
        container arp-entry {
          presence "Enable the ARP entry for AC.";
          description
            "Configure the ARP entry attribute used for IP interworking between PEs.";
          leaf local-ce-mac {
            type pub-type:ncs_rpc_notif_mac-address;
            description
              "MAC address of the Ethernet interface or sub-interface on a CE connected to the local AC interface. If MAC, IP, and broadcast addresses are all configured, these addresses take effect in the sequence of MAC address, IP address, and broadcast address.";
          }
          leaf local-ce-ip {
            type inet:ipv4-address-no-zone;
            description
              "IP address of the Ethernet interface or sub-interface on a CE connected to the local AC interface.";
          }
          leaf local-ce-broadcast {
            type boolean;
            must "((.='false' and (../local-ce-mac or ../local-ce-ip or ../remote-ce-ip)) or (.='true'))" {
              tailf:xpath-root 3;
            }
            default "false";
            description
              "Enable/disable broadcast on a PE Ethernet interface connected to a CE.";
          }
          leaf remote-ce-ip {
            type inet:ipv4-address-no-zone;
            description
              "IP address of the remote CE connected to the local AC interface.";
          }
        }
        container ac-arps {
          config false;
          description
            "Operational data of ARP information about all ACs.";
          uses ncs_rpc_notif_ac-arp-grp;
        }
      }
    }
    container pw {
      ext:operation-exclude "update|delete";
      must '(out-interface-name and not(next-hop)) or (not(out-interface-name) and next-hop)' {
        tailf:xpath-root 3;
      }
      description
        "Configure a VPWS remote CCC PW.";
      leaf out-label {
        ext:operation-exclude "update";
        type uint32 {
          range "0..1048575";
        }
        mandatory true;
        description
          "Label for sending packets.";
      }
      leaf in-label {
        ext:operation-exclude "update";
        type uint32 {
          range "16..1048575";
        }
        mandatory true;
        description
          "Label for receiving packets.";
      }
      leaf control-word {
        ext:operation-exclude "update|delete";
        type ncs_rpc_notif_l2vpn-control-word;
        must ".!='prefer'" {
          tailf:xpath-root 3;
        }
        default "default";
        description
          "Enable the control word function. The control word is usually used for TDM, ATM, and FR PWs.";
      }
      leaf out-interface-name {
        ext:operation-exclude "update|delete";
        type string;
        description
          "Outbound interface.";
      }
      leaf next-hop {
        ext:operation-exclude "update|delete";
        type inet:ipv4-address-no-zone;
        description
          "Next hop.";
      }
    }
  }

  grouping ncs_rpc_notif_vpws-swtich-instance-grp {
    description
      "VPWS switch instance.";
    leaf switch-type {
      ext:operation-exclude "update";
      type ncs_rpc_notif_l2vpn-switch-type;
      mandatory true;
      description
        "Switch type of a VPWS switch instance.";
    }
    leaf encapsulation-type {
      type ncs_rpc_notif_encapsulation-type;
      must "../encapsulation-type='fr' or
../encapsulation-type='atm-aal5-sdu' or
../encapsulation-type='atm-trans-cell' or
../encapsulation-type='vlan' or
../encapsulation-type='ethernet' or
../encapsulation-type='hdlc' or
../encapsulation-type='ppp' or
../encapsulation-type='atm-nto1-vcc' or
../encapsulation-type='atm-nto1-vpc' or
../encapsulation-type='ip-layer2' or
../encapsulation-type='atm-1to1-vcc' or
../encapsulation-type='atm-1to1-vpc' or
../encapsulation-type='atm-aal5-pdu' or
../encapsulation-type='cep' or
../encapsulation-type='satop-e1' or
../encapsulation-type='satop-t1' or
../encapsulation-type='satop-e3' or
../encapsulation-type='cesopsn-basic' or
../encapsulation-type='ip-interworking'" {
        tailf:xpath-root 3;
      }
      mandatory true;
      description
        "Encapsulation type of a VPWS switch instance.";
    }
    leaf control-word-trans {
      type boolean;
      default "false";
      description
        "Enable/disable the control word of a VPWS switching instance to be transparently transmitted.";
    }
    leaf control-word {
      when "not(../switch-type='ldp-ldp' or ../switch-type='ldp-ldp-bak')" {
        tailf:xpath-root 3;
      }
      type ncs_rpc_notif_l2vpn-control-word;
      must ".!='prefer'" {
        tailf:xpath-root 3;
      }
      default "default";
      description
        "Enable the control word function. The control word function is usually used for TDM, ATM, and FR PWs.";
    }
    leaf mtu {
      when "../switch-type='ldp-svc' and (../encapsulation-type='vlan' or ../encapsulation-type='ethernet')" {
        tailf:xpath-root 3;
      }
      type uint16 {
        range "46..9600";
      }
      default "1500";
      description
        "MTU of a VPWS switch instance.";
    }
    leaf bit-error-detection {
      when "../switch-type='ldp-ldp'" {
        tailf:xpath-root 3;
      }
      type boolean;
      default "false";
      description
        "Enable/disable bit error detection on SPEs for an LDP MS-PW.";
    }
    leaf create-time {
      type string {
        length "1..80";
      }
      config false;
      description
        "How long a VPWS switch instance has been created.";
    }
    leaf up-time {
      type string {
        length "1..80";
      }
      config false;
      description
        "How long a VPWS switch instance has been in the up state. If a VPWS instance is in the down state, its VPWS instance up duration is 0.";
    }
    leaf last-change-time {
      type string {
        length "1..80";
      }
      config false;
      description
        "How long the status of a VPWS switch instance stays unchanged since the last change time.";
    }
    container pws {
      description
        "List of VPWS PWs.";
      list pw {
        ext:operation-exclude "update|delete";
        must 'pw-id and peer-ip' {
          tailf:xpath-root 3;
        }
        must "(((../../switch-type='ldp-svc' and role='right-primary') or ../../switch-type='svc-svc') and transmit-label and receive-label) or not((../../switch-type='ldp-svc' and role='right-primary') or ../../switch-type='svc-svc')" {
          tailf:xpath-root 3;
        }
        key "role";
        unique "peer-ip";
        min-elements 2;
        max-elements 3;
        description
          "Configure a PW in a VPWS switching instance.";
        leaf role {
          type ncs_rpc_notif_ms-pw-role-type;
          description
            "Role of a PW.";
        }
        leaf pw-id {
          ext:operation-exclude "update|delete";
          type uint32 {
            range "1..4294967295";
          }
          description
            "PW ID.";
        }
        leaf peer-ip {
          ext:operation-exclude "update|delete";
          type ncs_rpc_notif_l2vpn-peer-address-type;
          description
            "IP address of a peer.";
        }
        leaf transmit-label {
          ext:operation-exclude "update|delete";
          when "(../../../switch-type='ldp-svc' and ../role='right-primary') or ../../../switch-type='svc-svc'" {
            tailf:xpath-root 3;
          }
          type uint32 {
            range "0..1048575";
          }
          description
            "Static label for sending packets.";
        }
        leaf receive-label {
          ext:operation-exclude "update|delete";
          when "(../../../switch-type='ldp-svc' and ../role='right-primary') or ../../../switch-type='svc-svc'" {
            tailf:xpath-root 3;
          }
          type uint32 {
            range "16..1048575";
          }
          description
            "Static label for receiving packets.";
        }
        leaf tunnel-policy {
          type string {
            length "1..39";
          }
          description
            "Name of a tunnel policy. If the tunnel policy name is not specified, the system uses the default tunnel policy. The default tunnel policy preferentially selects LSPs for packet transmission and the number of load-balancing tunnels is 1. If the tunnel policy name is specified but the corresponding tunnel policy does not exist, the system still uses the default tunnel policy.";
        }
        container flow-label {
          must "ability or oam-packet-pop='true'" {
            tailf:xpath-root 3;
          }
          presence "enbale flow label for pw";
          description
            "Enable/disable the flow label of a PW.";
          leaf ability {
            ext:operation-exclude "delete";
            when "../../../../switch-type='ldp-svc' and ../oam-packet-pop ='false'" {
              tailf:xpath-root 3;
            }
            type ncs_rpc_notif_flow-label-ability;
            must ".!='default' and .!='disable'" {
              tailf:xpath-root 3;
            }
            description
              "Flow label capability. The values of the ability node at both ends of a PW must be consistent.";
          }
          leaf oam-packet-pop {
            type boolean;
            default "false";
            description
              "Enable/disable the function of popping out flow labels in the OAM packets.";
          }
        }
        container hard-pipe {
          when "../../../switch-type='svc-svc' or (../../../switch-type='ldp-svc' and ../role='right-primary')" {
            tailf:xpath-root 3;
          }
          presence "Enable hard pipe for pw.";
          description
            "Enable/disable hard pipe.";
          leaf bandwidth {
            when "../../../../encapsulation-type='ethernet' or ../../../../encapsulation-type='vlan'" {
              tailf:xpath-root 3;
            }
            type uint32 {
              range "16..4294967294";
            }
            units "kbit/s";
            mandatory true;
            description
              "Specify bandwidth value.";
          }
          leaf expand-ratio {
            type uint16 {
              range "0..10000";
            }
            default "10";
            description
              "Specify the value of bandwidth expand ratio (%). As to CES service, expand ratio ranges from 0 to 10000. The other service, expand ratio ranges from 0 to 100.";
          }
        }
        container tdm-parameter {
          when "../../../switch-type='ldp-svc' and
(../../../encapsulation-type='cep' or
../../../encapsulation-type='cesopsn-basic' or
../../../encapsulation-type='satop-e1' or
../../../encapsulation-type='satop-t1' or
../../../encapsulation-type='satop-e3') and
(../role='left-primary')" {
            tailf:xpath-root 3;
          }
          description
            "Configure TDM parameters.";
          leaf tdm-encapsulate-number {
            when "../../../../encapsulation-type='cesopsn-basic' or
../../../../encapsulation-type='satop-e1' or
../../../../encapsulation-type='satop-t1' or
../../../../encapsulation-type='satop-e3'" {
              tailf:xpath-root 3;
            }
            type uint32 {
              range "1..5000";
            }
            ext:dynamic-default;
            description
              "Number of TDM frames encapsulated in a CESoPSN or SAToP packet in the TDMoPSN application.";
          }
          leaf rtp-header {
            type ncs_rpc_notif_l2vpn-rtp-header-type;
            default "false";
            description
              "Add the RTP header to transparently transmitted TDM frames.";
          }
          leaf time-slot {
            when "../../../../encapsulation-type='cesopsn-basic'" {
              tailf:xpath-root 3;
            }
            type uint32 {
              range "1..32";
            }
            description
              "Number of time slots on an interface.";
          }
        }
        container pw-info {
          config false;
          description
            "Operational data of VPWS PW information.";
          leaf session-state {
            type ncs_rpc_notif_l2vpn-state;
            description
              "Status of an LDP session between the endpoint devices of a VC.";
          }
          leaf pw-state {
            type ncs_rpc_notif_l2vpn-pw-state;
            description
              "Status of a PW.";
          }
          leaf pw-id {
            type uint32;
            description
              "PW ID.";
          }
          leaf encapsulation-type {
            type ncs_rpc_notif_encapsulation-type;
            description
              "Encapsulation type of a PW.";
          }
          leaf destination {
            type inet:ip-address-no-zone;
            description
              "Destination address, usually the LSR ID of a peer.";
          }
          leaf local-vc-label {
            type uint32;
            description
              "Local VC label.";
          }
          leaf remote-vc-label {
            type uint32;
            description
              "VC label on the remote end.";
          }
          leaf local-ac-oam {
            type ncs_rpc_notif_l2vpn-state;
            description
              "OAM status of a local AC.";
          }
          leaf local-psn-oam {
            type ncs_rpc_notif_l2vpn-state;
            description
              "PSN OAM status on the local end.";
          }
          leaf local-forward-state {
            type ncs_rpc_notif_l2vpn-forward-state;
            description
              "Forwarding status of the local end.";
          }
          leaf remote-ac-oam {
            type ncs_rpc_notif_l2vpn-state;
            description
              "OAM status on the remote end.";
          }
          leaf remote-psn-oam {
            type ncs_rpc_notif_l2vpn-state;
            description
              "PSN OAM status on the remote end.";
          }
          leaf remote-forward-state {
            type ncs_rpc_notif_l2vpn-forward-state;
            description
              "Forwarding status of the remote end.";
          }
          leaf local-vc-mtu {
            type uint32;
            description
              "MTU for a local VC.";
          }
          leaf remote-vc-mtu {
            type uint32;
            description
              "VC MTU on the remote end.";
          }
          leaf local-vccv {
            type string {
              length "0..40";
            }
            description
              "VCCV capability supported by the local end. By default, the LSP ping and BFD for the label alert mode can be used if the control word function is disabled. If the control word function is enabled, the LSP ping and BFD for both the label alert mode and control word mode can be used.";
          }
          leaf remote-vccv {
            type string {
              length "0..40";
            }
            description
              "VCCV capability supported by the remote end. By default, the LSP ping and BFD for the label alert mode can be used if the control word function is disabled. If the control word function is enabled, the LSP ping and BFD for both the label alert mode and control word mode can be used.";
          }
          leaf local-control-word {
            type ncs_rpc_notif_l2vpn-control-word;
            description
              "Enable the control word function on the local end.";
          }
          leaf remote-control-word {
            type ncs_rpc_notif_l2vpn-control-word;
            description
              "Enable the control word function on the remote end.";
          }
          leaf tunnel-policy {
            type string {
              length "1..39";
            }
            description
              "Name of a tunnel policy.";
          }
          leaf tunnel-count {
            type uint16;
            default "0";
            description
              "Number of effective tunnels.";
          }
          leaf spe-count {
            type uint32 {
              range "0..4294967295";
            }
            default "0";
            description
              "Number of SPEs in the path to the peer.";
          }
          leaf create-time {
            type string {
              length "1..80";
            }
            description
              "How long a PW has been created.";
          }
          leaf up-time {
            type string {
              length "1..80";
            }
            description
              "How long a PW has been in the up state. If a PW is in the down state, its PW up duration is 0.";
          }
          leaf last-change-time {
            type string {
              length "1..80";
            }
            description
              "How long the status of a PW has stayed unchanged since the last change time.";
          }
          leaf last-up-time {
            type string {
              length "1..80";
            }
            description
              "Date and time when a PW was up for the last time, for example, 2012/07/20 02:30:46.";
          }
          leaf total-up-time {
            type string {
              length "1..80";
            }
            description
              "Total up time of a PW.";
          }
          leaf c-key {
            type uint32;
            description
              "Customer key. Each CKey corresponds to a PW.";
          }
          leaf n-key {
            type uint32;
            description
              "Network key. Each NKey corresponds to a combination of the peer and tunnel policy.";
          }
          leaf remote-vccv-code {
            type pub-type:ncs_rpc_notif_hex-binary;
            description
              "Remote VCCV code.";
          }
          leaf hard-pipe-bandwidth {
            type uint32 {
              range "16..4294967294";
            }
            units "kbit/s";
            description
              "Specify bandwidth value.";
          }
          leaf hard-pipe-expand-ratio {
            type string {
              length "0..7";
            }
            description
              "Specify the value of bandwidth expand ratio (%).";
          }
          leaf pw-token-exceed {
            type boolean;
            default "false";
            description
              "Indicates whether the number of PW tokens exceeds the maximum limit.";
          }
          container spes {
            config false;
            description
              "Operational data of SPEs on the path to the peer.";
            uses l2vpn:ncs_rpc_notif_spe-infos-type;
          }
          container tunnels {
            config false;
            description
              "List of VPWS PW tunnels.";
            list tunnel {
              key "tunnel-key";
              max-elements 32;
              description
                "Operational data of tunnels.";
              leaf tunnel-key {
                type string {
                  length "0..21";
                }
                description
                  "Index of a public network tunnel.";
              }
              leaf tunnel-type {
                type ncs_rpc_notif_l2vpn-tunnel-type;
                description
                  "Type of the tunnel used by the PW.";
              }
              leaf tunnel-name {
                type string {
                  length "0..64";
                }
                description
                  "Name of the tunnel used by the PW.";
              }
              leaf public-next-hop {
                type inet:ipv4-address-no-zone;
                description
                  "Next hop of a PW on the public network.";
              }
            }
          }
          container down-causes {
            description
              "Operational data of the down causes.";
            uses l2vpn:ncs_rpc_notif_l2vpn-pw-down-causes-type;
          }
          container status-changes {
            description
              "Operational data of the reason and time.";
            uses l2vpn:ncs_rpc_notif_l2vpn-pw-status-changes-type;
          }
        }
      }
    }
    container reliability {
      when "../switch-type='ldp-ldp-bak'" {
        tailf:xpath-root 3;
      }
      description
        "Configure PW reliability.";
      leaf redundancy-mode {
        type ncs_rpc_notif_pw-redundancy-mode;
        must "../redundancy-mode='master'" {
          tailf:xpath-root 3;
        }
        default "master";
        description
          "PW redundancy mode.";
      }
      leaf switchover {
        type boolean;
        default "false";
        description
          "Enable/disable the PW switchover.";
      }
      container reroute {
        description
          "Configure a switchback policy list.";
        leaf reroute-policy {
          type ncs_rpc_notif_l2vpn-reroute-mode;
          default "delay";
          description
            "Switchback policy.";
        }
        leaf delay-time {
          when "../reroute-policy='delay'" {
            tailf:xpath-root 3;
          }
          type uint32 {
            range "10..10800";
          }
          units "s";
          default "30";
          description
            "Delay for switching traffic back to the primary PW.";
        }
        leaf last-switchback-reason {
          type string {
            length "0..100";
          }
          config false;
          description
            "Last switchback reason.";
        }
        leaf last-switchback-time {
          type string {
            length "1..60";
          }
          config false;
          description
            "Last switchback time.";
        }
        leaf delay-residual {
          type uint32;
          units "s";
          config false;
          description
            "Remaining delay time.";
        }
      }
    }
  }

  grouping ncs_rpc_notif_vpws-bgp-instance-grp {
    description
      "VPWS BGP VPN instance connection.";
    leaf vpn-instance {
      type string;
      mandatory true;
      description
        "VPWS BGP instance.";
    }
    leaf local-site {
      type string;
      mandatory true;
      description
        "Local site name.";
    }
    container acs {
      description
        "List of attachment circuits in a VPWS BGP VPN instance.";
      list ac {
        key "interface-name";
        min-elements 1;
        max-elements 1;
        description
          "Configure a connection attachment circuit.";
        leaf interface-name {
          type string;
          description
            "VPWS BGP VPN instance connection attachment circuit interface name. The encapsulation type of this interface must be the same as that of the VPN instance. Otherwise, the PW cannot go Up.";
        }
        leaf tagged {
          when "/l2vpn:l2vpn/l2vpn:common/l2vpn:vpws-bgp-vpns/l2vpn:vpws-bgp-vpn[l2vpn:name=current()/../../../l2vpn:vpn-instance]/l2vpn:encapsulation-type !='ip-interworking' and /l2vpn:l2vpn/l2vpn:common/l2vpn:vpws-bgp-vpns/l2vpn:vpws-bgp-vpn[l2vpn:name=current()/../../../l2vpn:vpn-instance]/l2vpn:encapsulation-type !='ip-layer2'" {
            tailf:xpath-root 3;
          }
          ext:operation-exclude "update|delete";
          type boolean;
          description
            "Enable/disable the attachment circuit tag of the VPWS BGP instance.";
          ext:dynamic-default;
        }
        leaf trigger-interface-down {
          type boolean;
          must "(/ifm:ifm/ifm:interfaces/ifm:interface[ifm:name=current()/../interface-name]/ifm:class='main-interface' and /ifm:ifm/ifm:interfaces/ifm:interface[ifm:name=current()/../interface-name]/ifm:link-protocol='ethernet' and . = 'true') or (. = 'false')" {
            tailf:xpath-root 3;
          }
          default "false";
          description
            "Enable/disable remote interface shutdown-based association between the PW status and interface status.";
        }
        leaf state {
          type ncs_rpc_notif_l2vpn-state;
          config false;
          description
            "Status of an AC interface.";
        }
        leaf token-exceed {
          type boolean;
          default "false";
          config false;
          description
            "Indicates whether the number of AC tokens exceeds the maximum limit.";
        }
      }
    }
    container pws {
      description
        "List of PWs.";
      list pw {
        key "remote-site-id";
        unique "role";
        min-elements 1;
        description
          "Configure a PW.";
        leaf remote-site-id {
          type uint16 {
            range "0..65534";
          }
          must '../l2vpn:remote-site-id < (/l2vpn:l2vpn/l2vpn:common/l2vpn:vpws-bgp-vpns/l2vpn:vpws-bgp-vpn[l2vpn:name=current()/../../../l2vpn:vpn-instance]/l2vpn:sites/l2vpn:site[l2vpn:name = current()/../../../l2vpn:local-site]/range + /l2vpn:l2vpn/l2vpn:common/l2vpn:vpws-bgp-vpns/l2vpn:vpws-bgp-vpn[l2vpn:name = current()/../../../l2vpn:vpn-instance]/l2vpn:sites/l2vpn:site[l2vpn:name = current()/../../../l2vpn:local-site]/default-offset) and ../l2vpn:remote-site-id >= /l2vpn:l2vpn/l2vpn:common/l2vpn:vpws-bgp-vpns/l2vpn:vpws-bgp-vpn[l2vpn:name = current()/../../../l2vpn:vpn-instance]/l2vpn:sites/l2vpn:site[l2vpn:name = current()/../../../l2vpn:local-site]/default-offset' {
            tailf:xpath-root 3;
          }
          description
            "VPWS BGP VPN instance connection remote customer edge identifier.";
        }
        leaf role {
          ext:operation-exclude "update|delete";
          type ncs_rpc_notif_pw-role-type;
          must "(.='primary') or (.='backup' and ../../pw[role='primary'])" {
            tailf:xpath-root 3;
          }
          default "primary";
          description
            "VPWS BGP VPN instance connection pseudo wire role. Configure a primary PW first. The PW role canot be changed.";
        }
        leaf tunnel-policy {
          type string {
            length "1..39";
          }
          description
            "VPWS BGP VPN instance connection tunnel policy name.";
        }
        leaf traffic-statistics-collection {
          type boolean;
          default "false";
          description
            "Enable/disable connection traffic statistics collection of a VPWS BGP VPN instance.";
        }
        leaf manual-set-fault {
          type boolean;
          default "false";
          description
            "Enable/disable the manual setting of faults in a VPWS BGP VPN instance connection.";
        }
        container bfd {
          when '/bfd:bfd' {
            tailf:xpath-root 3;
          }
          must "/l2vpn:l2vpn/l2vpn:common/l2vpn:vpws-bgp-vpns/l2vpn:vpws-bgp-vpn[l2vpn:name=current()/../../../l2vpn:vpn-instance]/l2vpn:control-word='enable'" {
            tailf:xpath-root 3;
          }
          presence "enable pw bfd.";
          description
            "Enable/disable BFD for PW in a VPWS BGP VPN instance.";
          uses ncs_rpc_notif_l2vpn-dyn-bfd-para-type;
          leaf track-interface {
            type boolean;
            default "false";
            description
              "Enable/disable BFD track interface state.";
          }
        }
        container pw-info {
          config false;
          description
            "Operational data of VPWS BGP PW information.";
          leaf type {
            type ncs_rpc_notif_vpws-bgp-pw-type;
            description
              "Indicates the type of the pw.";
          }
          leaf local-vc-state {
            type ncs_rpc_notif_l2vpn-pw-state;
            description
              "Indicates the status of the local PW.";
          }
          leaf remote-vc-state {
            type ncs_rpc_notif_l2vpn-pw-state;
            description
              "Indicates the status of the remote PW.";
          }
          leaf peer-ip {
            type inet:ipv4-address-no-zone;
            description
              "Indicates the LSR ID of the VC peer device.";
          }
          leaf local-vc-label {
            type uint32;
            description
              "Indicates the local VC label.";
          }
          leaf remote-vc-label {
            type uint32;
            description
              "Indicates the remote VC label.";
          }
          leaf ac-oam-state {
            type ncs_rpc_notif_vpws-bgp-ac-oam-state;
            description
              "Indicates the OAM status of the AC.";
          }
          leaf bfd-state {
            type ncs_rpc_notif_l2vpn-vpws-bfd-state;
            description
              "Indicates the status of the BFD for PW.";
          }
          leaf control-flag-bit {
            type ncs_rpc_notif_control-flag-bits-type;
            description
              "Indicates the control flag.";
          }
          leaf pw-token-exceed {
            type boolean;
            default "false";
            description
              "Indicates whether the number of PW tokens exceeds the maximum limit.";
          }
          container down-causes {
            config false;
            description
              "Operational data of the down causes.";
            uses l2vpn:ncs_rpc_notif_l2vpn-pw-down-causes-type;
          }
        }
        container tunnels {
          config false;
          description
            "List of VPWS BGP PW tunnel info.";
          list tunnel {
            key "tunnel-key";
            max-elements 32;
            description
              "Operational data of tunnels.";
            leaf tunnel-key {
              type string {
                length "0..21";
              }
              description
                "Index of a public network tunnel.";
            }
            leaf tunnel-type {
              type ncs_rpc_notif_l2vpn-tunnel-type;
              description
                "Type of the tunnel used by the PW.";
            }
            leaf tunnel-name {
              type string {
                length "0..64";
              }
              description
                "Name of the tunnel used by the PW.";
            }
            leaf public-next-hop {
              type inet:ipv4-address-no-zone;
              description
                "Next hop of a PW on the public network.";
            }
          }
        }
        container traffic-statistics {
          config false;
          description
            "Operational data of VPWS BGP PW traffic statistics.";
          leaf interface-name {
            type string;
            description
              "The name of interface.";
          }
          leaf last-clear-time {
            type string {
              length "1..60";
            }
            description
              "Time when statistics are cleared for the last time.";
          }
          leaf input-bytes-rate {
            type uint64;
            description
              "Rate of traffic received on the PW.";
          }
          leaf input-packets-rate {
            type uint64;
            description
              "Rate of frames received on the PW.";
          }
          leaf output-bytes-rate {
            type uint64;
            description
              "Rate of traffic transmitted out of the PW.";
          }
          leaf output-packets-rate {
            type uint64;
            description
              "Rate of frames transmitted out of the PW.";
          }
          leaf input-bytes {
            type uint64;
            description
              "Number of bytes received on the PW.";
          }
          leaf input-packets {
            type uint64;
            description
              "Number of frames received on the PW.";
          }
          leaf output-bytes {
            type uint64;
            description
              "Number of bytes transmitted out of the PW.";
          }
          leaf output-packets {
            type uint64;
            description
              "Number of frames transmitted out of the PW.";
          }
        }
      }
    }
    container reliability {
      when 'count(../pws/pw)=2' {
        tailf:xpath-root 3;
      }
      description
        "Configure PW reliability.";
      leaf redundancy-mode {
        type ncs_rpc_notif_pw-redundancy-mode;
        must "../redundancy-mode='frr'" {
          tailf:xpath-root 3;
        }
        default "frr";
        description
          "PW redundancy mode.";
      }
      leaf dual-receive {
        type boolean;
        default "false";
        description
          "Enable/disable the receipt of both the primary and secondary PWs to receive packets.";
      }
      container reroute {
        description
          "Configure a switchback policy list.";
        leaf reroute-policy {
          type ncs_rpc_notif_l2vpn-reroute-mode;
          default "delay";
          description
            "Switchback policy.";
        }
        leaf delay-time {
          when "../reroute-policy='delay'" {
            tailf:xpath-root 3;
          }
          type uint32 {
            range "10..10800";
          }
          units "s";
          default "30";
          description
            "Delay for switching traffic back to the primary PW.";
        }
        leaf resume-time {
          when "not(../reroute-policy='never')" {
            tailf:xpath-root 3;
          }
          type uint32 {
            range "0..600";
          }
          units "s";
          default "10";
          description
            "Time after which the peer PE on the secondary PW is notified that the local PE has recovered. This parameter can be configured only in FRR mode.";
        }
        leaf last-switchback-reason {
          type string {
            length "0..100";
          }
          config false;
          description
            "Last switchback reason.";
        }
        leaf last-switchback-time {
          type string {
            length "1..60";
          }
          config false;
          description
            "Last switchback time.";
        }
        leaf delay-residual {
          type uint32;
          units "s";
          config false;
          description
            "Remaining delay time.";
        }
        leaf resume-residual {
          type uint32;
          units "s";
          config false;
          description
            "Remaining resume time.";
        }
      }
    }
    container oam-mapping {
      presence "enable AC OAM mapping";
      description
        "Enable/disable OAM mapping.";
      leaf type {
        type ncs_rpc_notif_ac-oam-mapping-type;
        must "(../type='1ag' and ../md-name and ../ma-name) or ../type!='1ag'" {
          tailf:xpath-root 3;
        }
        mandatory true;
        description
          "VPWS attachment circuit OAM mapping type.";
      }
      leaf md-name {
        ext:operation-exclude "update|delete";
        when "../type='1ag'" {
          tailf:xpath-root 3;
        }
        type string {
          length "1..43";
        }
        description
          "VPWS OAM mapping parameter md name.";
      }
      leaf ma-name {
        ext:operation-exclude "update|delete";
        when "../type='1ag'" {
          tailf:xpath-root 3;
        }
        type string {
          length "1..43";
        }
        description
          "VPWS OAM mapping parameter ma name.";
      }
    }
  }

  grouping ncs_rpc_notif_vpls-instance-grp {
    description
      "VPLS instance.";
    leaf member-discovery-mode {
      type ncs_rpc_notif_l2vpn-vpls-vsi-mem-disc-type;
      default "default";
      description
        "VPLS member discovery mode for a specified VSI.";
    }
    leaf work-mode {
      ext:operation-exclude "update";
      type ncs_rpc_notif_vsi-work-mode;
      default "normal";
      description
        "Workmode of a VSI.";
    }
    leaf encapsulation-type {
      type ncs_rpc_notif_l2vpn-vpls-encap-type;
      must ".='vlan' or not(../etree)" {
        tailf:xpath-root 3;
      }
      default "vlan";
      description
        "Encapsulation type of a VSI.";
    }
    leaf mtu {
      type uint16 {
        range "46..65535";
      }
      default "1500";
      description
        "VPLS MTU.";
    }
    leaf tunnel-policy {
      type string {
        length "1..39";
      }
      description
        "Name of a tunnel policy for a VSI. If the tunnel policy name is not specified, the system uses the default tunnel policy. The default tunnel policy preferentially selects LSPs for packet transmission and the number of load-balancing tunnels is 1. If the tunnel policy name is specified but the corresponding tunnel policy does not exist, the system still uses the default tunnel policy.";
    }
    leaf shutdown {
      type boolean;
      default "false";
      description
        "Enable/disable the function of shutting down a specified VSI.";
    }
    leaf isolate-spoken {
      when "../work-mode='normal'" {
        tailf:xpath-root 3;
      }
      type boolean;
      must ".='false' or not(../etree)" {
        tailf:xpath-root 3;
      }
      default "false";
      description
        "Enable/disable forwarding isolation between AC interfaces, between UPE PWs, and between ACs and UPE PWs in a VSI.";
    }
    leaf isolate-spoken-include-multicast {
      when "../isolate-spoken='true'" {
        tailf:xpath-root 3;
      }
      type boolean;
      must ".='false' or not(../etree)" {
        tailf:xpath-root 3;
      }
      default "false";
      description
        "Enable/disable isolating forwarding between AC interfaces, between UPE PWs, and between ACs and UPE PWs in a VSI.";
    }
    leaf ignore-ac-state {
      type boolean;
      default "false";
      description
        "Enable/disable the function for the VSI status not to be affected by changes in the AC status.";
    }
    leaf response-ac-state {
      when "../work-mode='bd-mode'" {
        tailf:xpath-root 3;
      }
      type boolean;
      default "false";
      description
        "Enable/disable the function for the BD VSI status to be affected by changes in the BD AC status.";
    }
    leaf admin-vsi {
      type boolean;
      must "(.='false') or (.='true' and ../isolate-spoken='false' and not(../etree))" {
        tailf:xpath-root 3;
      }
      default "false";
      description
        "Enable/disable the function for the current service VSI to be configured as the mVSI.";
    }
    leaf track-admin-vsi {
      ext:operation-exclude "update|delete";
      when "../work-mode='normal' or ../work-mode='b-vsi'" {
        tailf:xpath-root 3;
      }
      type string {
        length "1..31";
      }
      must "(../admin-vsi='false' and /l2vpn:l2vpn/l2vpn:instances/l2vpn:instance[l2vpn:name=current()][l2vpn:type='vpls']/l2vpn:vpls/l2vpn:admin-vsi='true')" {
        tailf:xpath-root 3;
      }
      description
        "Name of the mVSI to which a service VSI is bound.";
    }
    leaf unknown-unicast-action {
      when "not(../work-mode='bd-mode')" {
        tailf:xpath-root 3;
      }
      type ncs_rpc_notif_l2vpn-vpls-unknow-frame-act;
      default "broadcast";
      description
        "Action taken to process unknown unicast frames.";
    }
    leaf unknown-multicast-action {
      when "not(../work-mode='bd-mode')" {
        tailf:xpath-root 3;
      }
      type ncs_rpc_notif_l2vpn-vpls-unknow-frame-act;
      must "((.='broadcast' or .='drop'))" {
        tailf:xpath-root 3;
      }
      default "broadcast";
      description
        "Action taken to process unknown multicast frames.";
    }
    leaf isolate-hub-ac-pw {
      when "../work-mode='normal'" {
        tailf:xpath-root 3;
      }
      type boolean;
      must ".='false' or not(../etree)" {
        tailf:xpath-root 3;
      }
      default "false";
      description
        "Enable/disable forwarding isolation between hub ACs and PWs in a VSI.";
    }
    leaf p2p-vsi {
      when "../work-mode='normal'" {
        tailf:xpath-root 3;
      }
      type boolean;
      must ".='false' or (.='true' and ../admin-vsi='false' and ../mac-learn='false' and ../mac-learn-style='unqualify' and not(../etree))" {
        tailf:xpath-root 3;
      }
      default "false";
      description
        "Enable/disable the P2P VSI.";
    }
    leaf traffic-statistics-collection {
      when "../work-mode='normal' or ../work-mode='bd-mode'" {
        tailf:xpath-root 3;
      }
      type boolean;
      default "false";
      description
        "Enable/disable VSI QoS traffic statistics collection.";
    }
    leaf mac-remove-mode {
      type ncs_rpc_notif_mac-remove-type;
      must "((not(.='all-from-me')) or ((.='all-from-me') and (not(../work-mode='bd-mode')) and (not(../work-mode='b-vsi')) and (not(../work-mode='i-vsi')) and (not(../work-mode='i-vsi-p2p')) and (not(../work-mode='i-vsi-b-evpn-interworking'))))" {
        tailf:xpath-root 3;
      }
      default "invalid";
      description
        "Local MAC remove mode.";
    }
    leaf mac-learn {
      when "not(../work-mode='bd-mode')" {
        tailf:xpath-root 3;
      }
      type boolean;
      must ".='false' or (.='true' and ../p2p-vsi='false')" {
        tailf:xpath-root 3;
      }
      default "true";
      description
        "Enable/disable the function for a VSI to learn MAC addresses.";
    }
    leaf mac-learn-style {
      when "../work-mode='normal'" {
        tailf:xpath-root 3;
      }
      type ncs_rpc_notif_l2vpn-mac-learn-style;
      must ".='unqualify' or not(../etree)" {
        tailf:xpath-root 3;
      }
      default "unqualify";
      description
        "MAC address learning style of PWs.";
    }
    leaf mac-age-time {
      when "not(../work-mode='bd-mode')" {
        tailf:xpath-root 3;
      }
      type uint32 {
        range "0 | 60..1000000";
      }
      units "s";
      description
        "MAC address aging timer that sets the aging time of MAC addresses.";
    }
    leaf local-mac-age-time {
      when "../work-mode='normal'" {
        tailf:xpath-root 3;
      }
      type uint32 {
        range "0 | 60..1000000";
      }
      units "s";
      description
        "Local MAC address aging timer that sets the aging time of MAC addresses.";
    }
    leaf remote-mac-age-time {
      when "../work-mode='normal'" {
        tailf:xpath-root 3;
      }
      type uint32 {
        range "0 | 60..1000000";
      }
      units "s";
      description
        "Remote MAC address aging timer that sets the aging time of MAC addresses.";
    }
    leaf mac-withdraw {
      type boolean;
      default "false";
      description
        "Enable/disable the function for a VSI to delete the local MAC address and notifies all remote peers of the deletion when an AC or a UPE fault occurs and the VSI remains up.";
    }
    leaf interface-change-mac-withdraw {
      when "not(../work-mode='i-vsi-b-evpn-interworking')" {
        tailf:xpath-root 3;
      }
      type boolean;
      default "false";
      description
        "Enable/disable the function for PEs to send LDP MAC withdraw messages to all peers when the status of the AC interface bound to the VSI changes.";
    }
    leaf interface-change-mac-withdraw-type {
      type ncs_rpc_notif_interface-change-withdraw-type;
      must ".='all' or ../interface-change-mac-withdraw='true'" {
        tailf:xpath-root 3;
      }
      default "all";
      description
        "Specify the status change type for a VSI AC interface.";
    }
    leaf bd-pwtag-mac-withdraw {
      when "../work-mode='bd-mode'" {
        tailf:xpath-root 3;
      }
      type boolean;
      default "false";
      description
        "Enable/disable the function for LDP MAC withdraw messages to carry PW tag corresponding to the VSI bound to the bridge domain. This node can be configured only when the VSI works in BD mode.";
    }
    leaf bd-down-mac-withdraw {
      when "../work-mode='bd-mode'" {
        tailf:xpath-root 3;
      }
      type boolean;
      default "true";
      description
        "Enable/disable the function for PEs to send LDP MAC withdraw messages to all peers when BD goes down. This node can be configured only when the VSI works in BD mode.";
    }
    leaf propagate-mac-withdraw {
      when "not(../work-mode='i-vsi-b-evpn-interworking')" {
        tailf:xpath-root 3;
      }
      type boolean;
      default "false";
      description
        "Enable/disable the function for a PE to propagate LDP MAC withdraw messages to other peers after receiving the message from a remote peer.";
    }
    leaf mac-flush-rfc-compatible {
      when "../work-mode='normal' or ../work-mode='bd-mode'" {
        tailf:xpath-root 3;
      }
      type boolean;
      default "false";
      description
        "Enable/disable the transmission of standard MAC-flush message when the PW status changes.";
    }
    leaf vrrp-mac-withdraw-retry {
      type uint16 {
        range "0..60";
      }
      default "0";
      description
        "VRRP backup Mac withdraw retry.";
    }
    leaf token-exceed {
      type boolean;
      default "false";
      config false;
      description
        "Indicates whether the number of VSI tokens exceeds the maximum limit.";
    }
    leaf ac-count {
      type uint32;
      config false;
      description
        "Total number of ACs in a VSI.";
    }
    leaf create-time {
      type string {
        length "1..60";
      }
      config false;
      description
        "Time when a VSI was created.";
    }
    leaf ignore-ac-state-effect {
      type boolean;
      default "false";
      config false;
      description
        "Configure the VSI status not to be affected by changes in the AC status. By default, the VSI status changes according to the AC status.";
    }
    container etree {
      when "../work-mode='normal'" {
        tailf:xpath-root 3;
      }
      must '(root-vlan and leaf-vlan) or ((not(root-vlan)) and (not(leaf-vlan)))' {
        tailf:xpath-root 3;
      }
      presence "Enable ethernet tree.";
      description
        "Enable/disable vpls ethernet tree.";
      leaf static {
        type boolean;
        must "../static='true'" {
          tailf:xpath-root 3;
        }
        default "true";
        description
          "Enable/disable static mode.";
      }
      leaf root-vlan {
        type uint16 {
          range "1..4094";
        }
        description
          "Specify root VLAN id.";
      }
      leaf leaf-vlan {
        type uint16 {
          range "1..4094";
        }
        description
          "Specify leaf VLAN id.";
      }
    }
    container ldp-signaling {
      presence "Label Distribution Protocol (LDP) signaling.";
      description
        "Enable/disable Label Distribution Protocol (LDP) signaling.";
      leaf vsi-id {
        ext:operation-exclude "update";
        type uint64 {
          range "1..4294967295";
        }
        must 'count(/l2vpn:l2vpn/l2vpn:instances/l2vpn:instance/l2vpn:vpls/l2vpn:ldp-signaling/l2vpn:vsi-id[.=current()])<=1' {
          tailf:xpath-root 3;
        }
        must 'count(/l2vpn:l2vpn/l2vpn:instances/l2vpn:instance/l2vpn:vpws-ldp/l2vpn:pws/l2vpn:pw/l2vpn:pw-id[.=current()])=0' {
          tailf:xpath-root 3;
        }
        must 'count(/l2vpn:l2vpn/l2vpn:instances/l2vpn:instance/l2vpn:vpws-switch/l2vpn:pws/l2vpn:pw/l2vpn:pw-id[.=current()])=0' {
          tailf:xpath-root 3;
        }
        description
          "VPLS LDP VSI ID. Can not be modified after configuration.";
      }
      leaf traffic-statistics-collection {
        when '../vsi-id' {
          tailf:xpath-root 3;
        }
        type boolean;
        must ". = 'false' or not(../../traffic-statistics-collection='true')" {
          tailf:xpath-root 3;
        }
        default "false";
        description
          "Enable/disable traffic statistics collection.";
      }
      leaf control-word {
        type ncs_rpc_notif_l2vpn-control-word;
        must ".='disable' or .='enable'" {
          tailf:xpath-root 3;
        }
        default "disable";
        description
          "Enable the control word feature. The control word feature is usually used for TDM, ATM, and FR PWs.";
      }
      leaf hard-pipe {
        type boolean;
        must ".='false' or (../../work-mode='normal' and not(../../bgp-signaling) and not(../../bgpad-signaling) and ../../p2p-vsi='false')" {
          tailf:xpath-root 3;
        }
        default "false";
        description
          "Enable/disable hard pipe.";
      }
      leaf mac-withdraw {
        type boolean;
        must ".='false' or (../../mac-withdraw='false' and ../../propagate-mac-withdraw='false' and ../../interface-change-mac-withdraw='false')" {
          tailf:xpath-root 3;
        }
        default "false";
        description
          "Enable/disable the function for a VSI to delete the local MAC address and notify all remote peers of the deletion when an AC or a UPE fault occurs and the VSI remains up.";
      }
      leaf interface-change-mac-withdraw {
        type boolean;
        must ".='false' or  (.='true' and ../../mac-withdraw='false' and ../../propagate-mac-withdraw='false' and ../../interface-change-mac-withdraw='false' and ../../work-mode!='i-vsi-b-evpn-interworking')" {
          tailf:xpath-root 3;
        }
        default "false";
        description
          "Enable/disable the function for PEs to send LDP MAC withdraw messages to all peers when the status of the AC interface bound to the VSI changes.";
      }
      leaf interface-change-mac-withdraw-type {
        type ncs_rpc_notif_interface-change-withdraw-type;
        must ".='all' or ../interface-change-mac-withdraw='true'" {
          tailf:xpath-root 3;
        }
        default "all";
        description
          "Specify the status change type for a VSI AC interface.";
      }
      leaf upe-upe-mac-withdraw {
        type boolean;
        must ".='false' or (../../mac-withdraw='false' and ../../propagate-mac-withdraw='false' and ../../interface-change-mac-withdraw='false' and ../../work-mode!='i-vsi')" {
          tailf:xpath-root 3;
        }
        default "false";
        description
          "Enable/disable the function for an NPE to forward the LDP MAC withdraw messages received from a UPE to other UPEs.";
      }
      leaf upe-npe-mac-withdraw {
        type boolean;
        must ".='false' or (../../mac-withdraw='false' and ../../propagate-mac-withdraw='false' and ../../interface-change-mac-withdraw='false' and ../../work-mode!='i-vsi')" {
          tailf:xpath-root 3;
        }
        default "false";
        description
          "Enable/disable the function for an NPE to forward the LDP MAC withdraw messages received from a UPE to other NPEs.";
      }
      leaf npe-upe-mac-withdraw {
        type boolean;
        must ".='false' or (../../mac-withdraw='false' and ../../propagate-mac-withdraw='false' and ../../interface-change-mac-withdraw='false' and ../../work-mode!='i-vsi')" {
          tailf:xpath-root 3;
        }
        default "false";
        description
          "Enable/disable the function for an NPE to forward the LDP MAC withdraw messages received from another NPE to UPEs.";
      }
      container flow-label {
        presence "enable flow-label for ldp signaling pws.";
        description
          "Enable/disable flow label capability of a PW.";
        leaf ability {
          type ncs_rpc_notif_flow-label-ability;
          must ".!='default' and .!='disable'" {
            tailf:xpath-root 3;
          }
          mandatory true;
          description
            "Enable/disable flow label capability.";
        }
        leaf static {
          type boolean;
          default "false";
          description
            "Enable/disable the static flow label function.";
        }
      }
      container pws {
        when '../vsi-id' {
          tailf:xpath-root 3;
        }
        description
          "List of VPLS PWs.";
        list pw {
          key "peer-ip negotiation-vc-id encapsulation-type";
          description
            "Configure VPLS PWs.";
          leaf peer-ip {
            type inet:ipv4-address-no-zone;
            description
              "Peer IP address. The loopback IP address of a peer is usually used as the peer IP address.";
          }
          leaf negotiation-vc-id {
            type uint32 {
              range "1..4294967295";
            }
            description
              "PW ID used to uniquely identify a VC. The PW ID is usually used when both ends need to communicate but the VSI IDs on both ends are different.";
          }
          leaf encapsulation-type {
            type ncs_rpc_notif_l2vpn-vpls-ldp-pw-encap-type;
            description
              "Encapsulation type of a VPLS PW. 'unsupport' indicates that the encapsulation type of a VSI is inherited.";
          }
          leaf role {
            ext:operation-exclude "update|delete";
            type ncs_rpc_notif_vpls-pw-role-type;
            must "../role='primary' or (../role='backup' and  ../../pw[role='primary'])" {
              tailf:xpath-root 3;
            }
            default "primary";
            description
              "Role of a PW, either primary or secondary. Configure a primary PW first.";
          }
          leaf name {
            ext:operation-exclude "update";
            type string {
              length "1..15";
            }
            description
              "PW name.";
          }
          leaf signal-type {
            ext:operation-exclude "update|delete";
            type ncs_rpc_notif_pw-signal-type;
            must "(../signal-type='ldp') or ../role!='backup'" {
              tailf:xpath-root 3;
            }
            must "(../signal-type='static' and ../tunnel-policy) or ../../../hard-pipe='false'" {
              tailf:xpath-root 3;
            }
            must "(../signal-type='static' and ../transmit-label and ../receive-label) or ../signal-type='ldp'" {
              tailf:xpath-root 3;
            }
            must "(.='static' and ../ignore-standby='false') or .!='static'" {
              tailf:xpath-root 3;
            }
            default "ldp";
            description
              "PW type, either dynamic or static.";
          }
          leaf transmit-label {
            ext:operation-exclude "update|delete";
            when "../signal-type='static'" {
              tailf:xpath-root 3;
            }
            type uint32 {
              range "0..1048575";
            }
            description
              "Label for sending packets.";
          }
          leaf receive-label {
            ext:operation-exclude "update|delete";
            when "../signal-type='static'" {
              tailf:xpath-root 3;
            }
            type uint32 {
              range "16..1048575";
            }
            description
              "Label for receiving packets.";
          }
          leaf control-word {
            when '../name' {
              tailf:xpath-root 3;
            }
            type ncs_rpc_notif_l2vpn-control-word;
            default "default";
            description
              "Enable the control word function.";
          }
          leaf vccv {
            when '../name' {
              tailf:xpath-root 3;
            }
            type boolean;
            default "true";
            description
              "Enable/disable virtual circuit connectivity verification capability. VCCV supports two modes: control word and label alert.";
          }
          leaf ignore-standby {
            ext:operation-exclude "update|delete";
            type boolean;
            default "false";
            description
              "Enable/disable the function for the created PW to ignore the standby state sent from the peer device.";
          }
          leaf upe {
            ext:operation-exclude "update|delete";
            type boolean;
            default "false";
            description
              "Enable/disable the peer device as a UPE.";
          }
          leaf tunnel-policy {
            type string {
              length "1..39";
            }
            description
              "Name of the tunnel policy for a PW.";
          }
          leaf traffic-statistics-collection {
            type ncs_rpc_notif_l2vpn-vpls-traffic-statistics-enable-type;
            must ". = 'default' or not(../../../../traffic-statistics-collection = 'true')" {
              tailf:xpath-root 3;
            }
            default "default";
            description
              "Enable the function to collect traffic statistics.";
          }
          leaf track-hub-pw {
            when '../name' {
              tailf:xpath-root 3;
            }
            type boolean;
            must "../track-hub-pw='false' or (../track-hub-pw='true' and ../upe='true' and ../../../../work-mode!='i-vsi-b-evpn-interworking')" {
              tailf:xpath-root 3;
            }
            default "false";
            description
              "Enable/disable the function for the spoke PW to track the hub PW. If a PW is not a spoke PW, it cannot track the hub PW.";
          }
          leaf ignore-stp-loop-check {
            when '../name' {
              tailf:xpath-root 3;
            }
            type boolean;
            default "false";
            description
              "Enable/disable the function of ignoring STP loops.";
          }
          leaf hard-pipe-bandwidth {
            ext:operation-exclude "delete";
            when "../../../hard-pipe='true'" {
              tailf:xpath-root 3;
            }
            type uint32 {
              range "16..4294967294";
            }
            units "kbit/s";
            description
              "Specify bandwidth value.";
          }
          leaf hard-pipe-burst-time {
            ext:operation-exclude "delete";
            when '../hard-pipe-bandwidth' {
              tailf:xpath-root 3;
            }
            type uint32 {
              range "100..5000";
            }
            units "us";
            default "100";
            description
              "Burst time.";
          }
          leaf status-code-change-flush-mac-disable {
            when '../name' {
              tailf:xpath-root 3;
            }
            type boolean;
            default "false";
            description
              "Enable/disable the function of flushing MAC when status code change.";
          }
          leaf ac-mode {
            ext:operation-exclude "update|delete";
            when "../../../../work-mode='bd-mode'" {
              tailf:xpath-root 3;
            }
            type boolean;
            default "false";
            description
              "Enable/disable the AC mode.";
          }
          leaf etree-mode {
            when '../../../../etree and ../name' {
              tailf:xpath-root 3;
            }
            type ncs_rpc_notif_etree-work-mode;
            default "default";
            description
              "Specify e-tree work mode.";
          }
          leaf etree-leaf {
            when "../etree-mode = 'compatible'" {
              tailf:xpath-root 3;
            }
            type boolean;
            default "false";
            description
              "Enable/disable e-tree leaf.";
          }
          container flow-label {
            when '../name' {
              tailf:xpath-root 3;
            }
            presence "enable flow label";
            description
              "Enable/disable the flow label capability of a PW.";
            leaf ability {
              type ncs_rpc_notif_flow-label-ability;
              must ".!='default'" {
                tailf:xpath-root 3;
              }
              mandatory true;
              description
                "Flow label capability.";
            }
            leaf static {
              type boolean;
              must ".='false' or ../ability!='disable'" {
                tailf:xpath-root 3;
              }
              default "false";
              description
                "Enable/disable the static flow label function.";
            }
          }
          container bfd {
            when '../name and /bfd:bfd' {
              tailf:xpath-root 3;
            }
            presence "enable vpls ldp pw bfd.";
            description
              "Enable/disable BFD.";
            leaf min-rx-interval {
              type uint16 {
                range "0..65535";
              }
              units "ms";
              default "10";
              description
                "Minimum receive interval.";
            }
            leaf min-tx-interval {
              type uint16 {
                range "0..65535";
              }
              units "ms";
              default "10";
              description
                "Minimum transmit interval.";
            }
            leaf detect-multiplier {
              type uint16 {
                range "3..50";
              }
              default "3";
              description
                "Detection multiplier.";
            }
            leaf option-tlv {
              type boolean;
              default "false";
              description
                "Enable/disable BFD detection with options.";
            }
          }
          container pw-info {
            config false;
            description
              "Operational data of VPLS LDP PW information.";
            leaf peer-ip {
              type inet:ipv4-address-no-zone;
              description
                "Peer IP address.";
            }
            leaf negotiation-vc-id {
              type uint32;
              description
                "PW ID used to uniquely identify a VC. The PW ID is usually used when both ends need to communicate but the VSI IDs on both ends are different.";
            }
            leaf pw-type {
              type ncs_rpc_notif_l2vpn-vpls-pw-type;
              description
                "PW type, which can be label, QinQ, or MEHVPLS.";
            }
            leaf session-state {
              type ncs_rpc_notif_l2vpn-state;
              description
                "Status of the session between the local end and its peer. The value is either up or down. This item is displayed only when the VPLS type is Martini.";
            }
            leaf pw-state {
              type ncs_rpc_notif_l2vpn-pw-state;
              description
                "Current PW status.";
            }
            leaf local-vc-label {
              type uint32;
              description
                "VC label allocated by the local device.";
            }
            leaf remote-vc-label {
              type uint32;
              description
                "VC label allocated by the peer.";
            }
            leaf remote-control-word {
              type ncs_rpc_notif_l2vpn-control-word;
              description
                "Enable the control word function on the remote end.";
            }
            leaf tunnel-policy {
              type string {
                length "1..39";
              }
              description
                "Name of the tunnel policy for a PW.";
            }
            leaf last-up-time {
              type string {
                length "1..80";
              }
              description
                "Date and time when a PW was up for the last time, for example, 2012/07/20 02:30:46.";
            }
            leaf total-up-time {
              type string {
                length "1..80";
              }
              description
                "Total up time of the PW.";
            }
            leaf c-key {
              type uint32;
              description
                "Customer key. Each CKey corresponds to a PW.";
            }
            leaf n-key {
              type uint32;
              description
                "Network key. Each NKey corresponds to a combination of the peer and tunnel policy.";
            }
            leaf spe-count {
              type uint32 {
                range "0..4294967295";
              }
              description
                "Number of SPEs in the path to the peer.";
            }
            leaf stp-enable {
              type boolean;
              description
                "Enable STP for PW.";
            }
            leaf mac-flapping-state {
              type ncs_rpc_notif_pw-block-status;
              description
                "MAC flapping information.";
            }
            leaf pw-index {
              type uint32;
              description
                "PW index.";
            }
            leaf remote-group-id {
              type uint32;
              description
                "ID of a remote PW group.";
            }
            leaf remote-mtu {
              type uint32;
              description
                "MTU of the remote VSI.";
            }
            leaf remote-state-code {
              type ncs_rpc_notif_l2vpn-vpls-ldp-pw-state-code;
              description
                "Status code information on the remote end.";
            }
            leaf received-flow-label {
              type ncs_rpc_notif_flow-label-ability;
              description
                "Received flow label.";
            }
            leaf negotiated-flow-label {
              type ncs_rpc_notif_flow-label-ability;
              description
                "Negotiated flow label.";
            }
            leaf remote-vccv-code {
              type pub-type:ncs_rpc_notif_hex-binary;
              description
                "Remote VCCV code.";
            }
            leaf bfd-enable {
              type boolean;
              description
                "Enable BFD.";
            }
            leaf bfd-state {
              type ncs_rpc_notif_l2vpn-vpls-pw-bfd-state;
              description
                "BFD status.";
            }
            leaf bfd-session-index {
              when "../dynamic-bfd-session='false'" {
                tailf:xpath-root 3;
              }
              type uint32;
              description
                "BFD index.";
            }
            leaf dynamic-bfd-session {
              type boolean;
              description
                "Enable dynamic BFD.";
            }
            leaf bfd-for-pw {
              when "../dynamic-bfd-session='true'" {
                tailf:xpath-root 3;
              }
              type boolean;
              description
                "Dynamic BFD session status.";
            }
            leaf block-status {
              type ncs_rpc_notif_pw-block-status;
              description
                "Specifies whether a PW is blocked. If the PW is blocked, it cannot receive or transmit services.";
            }
            leaf pw-token-exceed {
              type boolean;
              default "false";
              description
                "Indicates whether the number of PW tokens exceeds the maximum limit.";
            }
            container tunnels {
              config false;
              description
                "List of VPLS LDP PW tunnels.";
              list tunnel {
                key "tunnel-key";
                max-elements 32;
                description
                  "Operational data of VPLS LDP PW tunnels.";
                leaf tunnel-key {
                  type string {
                    length "0..21";
                  }
                  description
                    "Tunnel ID in hexadecimal notation that is assigned by the system.";
                }
                leaf tunnel-type {
                  type ncs_rpc_notif_l2vpn-tunnel-type;
                  description
                    "Type of a tunnel.";
                }
                leaf out-interface {
                  type string {
                    length "0..257";
                  }
                  description
                    "Outbound interface of a PW.";
                }
                leaf tunnel-name {
                  type string {
                    length "0..64";
                  }
                  description
                    "Name of the tunnel used by the PW.";
                }
                leaf public-next-hop {
                  type inet:ipv4-address-no-zone;
                  description
                    "Public next hop of a PW.";
                }
              }
            }
            container spes {
              description
                "Operational data of SPEs on the path to the peer.";
              uses l2vpn:ncs_rpc_notif_spe-infos-type;
            }
            container label-stacks {
              description
                "Operational data of PW label stacks.";
              uses l2vpn:ncs_rpc_notif_l2vpn-label-stacks-type;
            }
            container down-causes {
              description
                "Operational data of the down causes.";
              uses l2vpn:ncs_rpc_notif_l2vpn-pw-down-causes-type;
            }
            container status-changes {
              description
                "Operational data of the reason and time.";
              uses l2vpn:ncs_rpc_notif_l2vpn-pw-status-changes-type;
            }
          }
          uses l2vpn:ncs_rpc_notif_suppression-statisticss-grp;
          uses l2vpn:ncs_rpc_notif_pw-traffic-statisticss-grp;
          container hard-pipe-traffic-statistics {
            config false;
            description
              "Operational data of traffic statistics about VPLS LDP PW HardPipe.";
            leaf last-clear-time {
              type string {
                length "1..60";
              }
              description
                "Time when statistics are cleared for the last time.";
            }
            leaf pass-packets-rate {
              type uint64;
              description
                "The last 300 seconds pass packets rate.";
            }
            leaf pass-bytes-rate {
              type uint64;
              description
                "The last 300 seconds pass bytes rate.";
            }
            leaf discard-packets-rate {
              type uint64;
              description
                "The last 300 seconds discard packets rate.";
            }
            leaf discard-bytes-rate {
              type uint64;
              description
                "The last 300 seconds discard bytes rate.";
            }
            leaf pass-packets {
              type uint64;
              description
                "Number of pass packets in the last 300 seconds.";
            }
            leaf pass-bytes {
              type uint64;
              description
                "Number of pass bytes in the last 300 seconds.";
            }
            leaf drop-packets {
              type uint64;
              description
                "Number of discard packets in the last 300 seconds.";
            }
            leaf drop-bytes {
              type uint64;
              description
                "Number of discard bytes in the last 300 seconds.";
            }
          }
        }
      }
      container redundancy-protect-groups {
        when '../vsi-id' {
          tailf:xpath-root 3;
        }
        description
          "List of VPLS PW protection groups.";
        list redundancy-protect-group {
          key "name";
          max-elements 32;
          description
            "Configure VPLS PW protection groups.";
          leaf name {
            type ncs_rpc_notif_l2vpn-protect-group-name;
            description
              "Name of a PW protection group. The name is a string of case-sensitive characters.";
          }
          leaf protect-mode {
            type ncs_rpc_notif_vpls-redundancy-mode;
            default "none";
            description
              "Switching mode of the PW protection group.";
          }
          leaf dual-receive {
            when "../protect-mode!='none'" {
              tailf:xpath-root 3;
            }
            type boolean;
            default "false";
            description
              "Enable/disable the receipt of both the primary and secondary PWs.";
          }
          leaf holdoff {
            when "../protect-mode='master'" {
              tailf:xpath-root 3;
            }
            type uint16 {
              range "1..180";
            }
            units "s";
            description
              "Hold time for traffic switching.";
          }
          container reroute-policy {
            when "../protect-mode='master'" {
              tailf:xpath-root 3;
            }
            description
              "Configure a switchback policy.";
            uses l2vpn:ncs_rpc_notif_l2vpn-reroute-policy-type;
          }
          container pw-members {
            when "not(../protect-mode='none')" {
              tailf:xpath-root 3;
            }
            description
              "List of PW members in a protection group.";
            list pw-member {
              must '../../../../pws/pw[peer-ip=current()/peer-ip][negotiation-vc-id=current()/negotiation-vc-id][encapsulation-type=current()/encapsulation-type]' {
                tailf:xpath-root 3;
              }
              key "peer-ip negotiation-vc-id encapsulation-type";
              unique "preference";
              max-elements 2;
              description
                "Configure PW members in a protection group.";
              leaf peer-ip {
                type inet:ipv4-address-no-zone;
                description
                  "Peer IP address. The loopback IP address of a peer is usually used as the peer IP address.";
              }
              leaf negotiation-vc-id {
                type uint32 {
                  range "1..4294967295";
                }
                description
                  "PW ID used to uniquely identify a VC. The PW ID is usually used when both ends need to communicate but the VSI IDs on both ends are different.";
              }
              leaf encapsulation-type {
                type ncs_rpc_notif_l2vpn-vpls-ldp-pw-encap-type;
                description
                  "Encapsulate type.";
              }
              leaf preference {
                type uint32 {
                  range "1..32";
                }
                mandatory true;
                description
                  "Priority of a PW in the PW protection group.";
              }
              leaf role {
                type ncs_rpc_notif_l2vpn-backup-mode;
                config false;
                description
                  "Primary/secondary status of a PW.";
              }
              leaf active-state {
                type boolean;
                default "false";
                config false;
                description
                  "Whether an interface is active.";
              }
            }
          }
          container historys {
            config false;
            description
              "Operational data of historical switching information of PW protection groups.";
            uses l2vpn:ncs_rpc_notif_l2vpn-protect-group-historys-type;
          }
        }
      }
      container traffic-statistics {
        config false;
        description
          "Operational data of traffic statistics.";
        leaf last-cleared {
          type string {
            length "1..60";
          }
          description
            "Time when traffic statistics were cleared the last time.";
        }
        leaf in-packets-rate {
          type uint64;
          description
            "Rate of packets received.";
        }
        leaf out-packets-rate {
          type uint64;
          description
            "Rate of packets sent.";
        }
        leaf in-packets {
          type uint64;
          description
            "Number of packets received.";
        }
        leaf out-packets {
          type uint64;
          description
            "Number of packets sent.";
        }
        leaf in-unicast-packets {
          type uint64;
          description
            "Number of unicast packets received.";
        }
        leaf in-multicast-packets {
          type uint64;
          description
            "Number of multicast packets received.";
        }
        leaf in-drop-packets {
          type uint64;
          description
            "Number of packets received and then discarded.";
        }
        leaf out-unicast-packets {
          type uint64;
          description
            "Number of unicast packets sent.";
        }
        leaf out-multicast-packets {
          type uint64;
          description
            "Number of multicast packets sent.";
        }
      }
    }
    container bgp-signaling {
      when "../work-mode='normal' or ../work-mode='bd-mode'" {
        tailf:xpath-root 3;
      }
      must "../admin-vsi!='true' and ../track-admin-vsi!='true' and ../p2p-vsi!='true' and (../mac-remove-mode='invalid' or (../mac-remove-mode!='invalid' and ../ldp-signaling))" {
        tailf:xpath-root 3;
      }
      must 'not(../etree)' {
        tailf:xpath-root 3;
      }
      presence "Container for bgp protocol vpls instance.";
      description
        "Enable/disable BGP VSIs.";
      leaf route-distinguisher {
        type string {
          length "3..21";
        }
        description
          "Route distinguisher.";
      }
      leaf encapsulation-rfc4761-compatible {
        type boolean;
        default "false";
        description
          "Enable/disable the function of changing an encapsulation type.";
      }
      leaf encapsulation-vpls-family-compatible {
        type boolean;
        default "false";
        description
          "Enable/disable the function of changing an encapsulation type to private mode.";
      }
      leaf mtu-negotiate-disable {
        type boolean;
        default "false";
        description
          "Enable/disable the function of ignoring MTU match between local VSI and remote VSI. The default implementation is match.";
      }
      leaf control-word {
        type ncs_rpc_notif_l2vpn-control-word;
        must "((../control-word='disable' or ../control-word='enable' ) )" {
          tailf:xpath-root 3;
        }
        default "disable";
        description
          "Enable the control word feature. The control word feature is usually used for TDM, ATM, and FR PWs.";
      }
      leaf auto-route-distinguisher {
        type string {
          length "3..21";
        }
        config false;
        description
          "Automatic route distinguisher (RD). If no RD is configured for an L2VPN instance, you can specify an IPv4 address using the rd-ip parameter, based on which an RD is automatically generated in the format of 32-bit prefix IP address:index, for example, 192.168.122.15:1. An index is an integer automatically allocated by the system and ranges from 1 to 65535.Each L2VPN instance must use a unique RD.";
      }
      container sites {
        description
          "List of BGP sites.";
        list site {
          must 'not(site-id=0 and default-offset=1)' {
            tailf:xpath-root 3;
          }
          key "site-id";
          max-elements 1;
          description
            "Configure BGP sites.";
          leaf site-id {
            type uint32 {
              range "0..65534";
            }
            description
              "BGP site ID.";
          }
          leaf range {
            type uint32 {
              range "1..65535";
            }
            default "10";
            description
              "BGP site range. Cannot decrease site range.";
          }
          leaf default-offset {
            ext:operation-exclude "update|delete";
            type uint16 {
              range "0..1";
            }
            default "0";
            description
              "The default offset of BGP site. The value of this node cannot be modified or deleted after being set.";
          }
        }
      }
      container vpn-targets {
        description
          "List of VPN targets.";
        list vpn-target {
          key "rt-value rt-type";
          max-elements 32;
          description
            "Configure VPN targets.";
          leaf rt-value {
            type string {
              length "3..21";
            }
            description
              "Route target. The format of an RT can be:
               - 16-bit AS number:32-bit user-defined number, for example, 1:3. An AS number ranges from 0 to 65535, and a user-defined number ranges from 0 to 4294967295. The AS number and user-defined number cannot be both 0s. This means that the RT cannot be 0:0.
               - Integral 4-byte AS number:2-byte user-defined number, for example, 65537:3. An AS number ranges from 65536 to 4294967295. A user-defined number ranges from 0 to 65535. The AS number and user-defined number cannot be both 0s. This means that the RT cannot be 0:0.
               - 32-bit IP address:16-bit user-defined number, for example: 192.168.122.15:1. The IP address ranges from 0.0.0.0 to 255.255.255.255, and the user-defined number ranges from 0 to 65535.
               - 32-bit AS number:16-bit user-defined number, for example, 10.11:3. An AS number ranges from 0.0 to 65535.65535, and a user-defined number ranges from 0 to 65535. The AS number and user-defined number cannot be both 0s. This means that the RT cannot be 0.0:0.";
          }
          leaf rt-type {
            type ncs_rpc_notif_vpn-rt-type;
            description
              "RT type, which can be:
               - export-extcommunity: specifies the value of the extended community attribute of the route from an outbound interface to the destination VPN.
               - import-extcommunity: receives routes that carry the specified extended community attribute value.";
          }
        }
      }
      container flow-label {
        presence "enable flow-label for bgp signaling pws.";
        description
          "Enable/disable flow label capability of a PW.";
        leaf ability {
          type ncs_rpc_notif_flow-label-ability;
          must ".!='default' and .!='disable'" {
            tailf:xpath-root 3;
          }
          mandatory true;
          description
            "Flow label capability.";
        }
        leaf static {
          type boolean;
          default "false";
          description
            "Enable/disable the static flow label function.";
        }
      }
      container pws {
        description
          "List of VPLS BGP PWs.";
        list pw {
          must "name or traffic-statistics-collection='true'" {
            tailf:xpath-root 3;
          }
          key "peer-ip remote-site-id";
          unique "name";
          description
            "Configure VPLS BGP PWs.";
          leaf peer-ip {
            type inet:ipv4-address-no-zone;
            description
              "Peer IP address.";
          }
          leaf remote-site-id {
            type uint32 {
              range "0..65534";
            }
            description
              "Remote BGP site ID.";
          }
          leaf name {
            type string {
              length "1..15";
            }
            description
              "PW name.";
          }
          leaf traffic-statistics-collection {
            type boolean;
            must ". = 'false' or not(../../../../traffic-statistics-collection = 'true' or ../../../../ldp-signaling/traffic-statistics-collection = 'true' or ../../../../ldp-signaling/pws/pw[traffic-statistics-collection != 'default'])" {
              tailf:xpath-root 3;
            }
            default "false";
            description
              "Enable/disable the function to collect traffic statistics.";
          }
          uses l2vpn:ncs_rpc_notif_suppression-statisticss-grp;
        }
      }
      container local-label-blocks {
        config false;
        description
          "Operational data of local label blocks.";
        uses ncs_rpc_notif_bgp-local-label-block-grp;
      }
      container remote-label-blocks {
        config false;
        description
          "Operational data of remote label blocks.";
        uses ncs_rpc_notif_bgp-remote-label-block-grp;
      }
      container pw-infos {
        config false;
        description
          "List of BGP PWs.";
        list pw-info {
          key "site-id offset";
          description
            "Operational data of the BGP PW list.";
          leaf site-id {
            type uint32 {
              range "0..65534";
            }
            description
              "BGP site ID.";
          }
          leaf offset {
            type uint16;
            description
              "BGP site offset.";
          }
          leaf peer-ip {
            type inet:ipv4-address-no-zone;
            description
              "BGP peer IP address.";
          }
          leaf pw-type {
            type ncs_rpc_notif_l2vpn-vpls-pw-type;
            description
              "PW type, which can be label, QinQ, or MEHVPLS.";
          }
          leaf pw-state {
            type ncs_rpc_notif_l2vpn-pw-state;
            description
              "PW status.";
          }
          leaf local-vc-label {
            type uint32;
            description
              "VC label allocated by the local device.";
          }
          leaf remote-vc-label {
            type uint32;
            description
              "VC label allocated by the peer.";
          }
          leaf last-up-time {
            type yang:date-and-time;
            description
              "Date and time when a PW was up for the last time, for example, 2012/07/20 02:30:46.";
          }
          leaf total-up-time {
            type string {
              length "1..80";
            }
            description
              "Total duration when the PW is up.";
          }
          leaf c-key {
            type uint32;
            description
              "Customer key. Each CKey corresponds to a PW.";
          }
          leaf n-key {
            type uint32;
            description
              "Network key. Each NKey corresponds to a combination of the peer and tunnel policy.";
          }
          leaf broadcast-tunnel-key {
            type string {
              length "0..21";
            }
            description
              "Tunnel ID used by a PW for broadcast.";
          }
          leaf stp-enable {
            type boolean;
            description
              "Enable STP for PW.";
          }
          leaf mac-flapping-enable {
            type ncs_rpc_notif_pw-block-status;
            description
              "MAC flapping information.";
          }
          leaf main-pw-token {
            type pub-type:ncs_rpc_notif_hex-binary;
            description
              "Token of the primary PW.";
          }
          leaf backup-pw-token {
            type pub-type:ncs_rpc_notif_hex-binary;
            description
              "Token of the secondary PW.";
          }
          leaf receive-flow-label {
            type ncs_rpc_notif_flow-label-ability;
            description
              "Received flow label.";
          }
          leaf negotiate-flow-label {
            type ncs_rpc_notif_flow-label-ability;
            description
              "Negotiated flow label.";
          }
          leaf remote-control-word {
            type ncs_rpc_notif_l2vpn-control-word;
            description
              "Remote control word capability.";
          }
          leaf negotiate-control-word {
            type ncs_rpc_notif_l2vpn-control-word;
            description
              "Negotiated control word capability.";
          }
          container tunnels {
            description
              "List of VPLS PW tunnels.";
            list tunnel {
              key "tunnel-key";
              max-elements 32;
              description
                "Operational data of VPLS PW tunnels.";
              leaf tunnel-key {
                type string {
                  length "0..21";
                }
                description
                  "Tunnel ID in hexadecimal notation that is assigned by the system.";
              }
              leaf tunnel-type {
                type ncs_rpc_notif_l2vpn-tunnel-type;
                description
                  "Type of a tunnel.";
              }
              leaf out-interface {
                type pub-type:ncs_rpc_notif_if-name;
                description
                  "Outbound interface of a PW.";
              }
              leaf tunnel-name {
                type string {
                  length "0..64";
                }
                description
                  "Name of the tunnel used by the PW.";
              }
              leaf public-next-hop {
                type inet:ipv4-address-no-zone;
                description
                  "Public next hop of a PW.";
              }
            }
          }
          container traffic-statistics {
            description
              "Peer traffic statistics.";
            leaf in-traffic-rate {
              type uint64;
              units "bit/s";
              description
                "Rate of traffic received by the PW.";
            }
            leaf out-traffic-rate {
              type uint64;
              units "bit/s";
              description
                "Rate of traffic sent by the PW.";
            }
            leaf in-frame-rate {
              type uint64;
              units "pps";
              description
                "Rate of frames received by the PW.";
            }
            leaf out-frame-rate {
              type uint64;
              units "pps";
              description
                "Rate of frames sent by the PW.";
            }
            leaf in-bytes {
              type uint64;
              units "Byte";
              description
                "Number of bytes received by the PW.";
            }
            leaf out-bytes {
              type uint64;
              units "Byte";
              description
                "Number of bytes sent by the PW.";
            }
            leaf in-frames {
              type uint64;
              units "packet";
              description
                "Number of frames received by the PW.";
            }
            leaf out-frames {
              type uint64;
              units "packet";
              description
                "Number of frames sent by the PW.";
            }
            leaf in-unicast-frames {
              type uint64;
              units "packet";
              description
                "Number of unicast frames received by the PW.";
            }
            leaf in-unicast-bytes {
              type uint64;
              units "Byte";
              description
                "Number of unicast bytes received by the PW.";
            }
            leaf in-multicast-frames {
              type uint64;
              units "packet";
              description
                "Number of multicast frames received by the PW.";
            }
            leaf in-multicast-bytes {
              type uint64;
              units "Byte";
              description
                "Number of multicast bytes received by the PW.";
            }
            leaf in-broadcast-frames {
              type uint64;
              units "packet";
              description
                "Number of broadcast frames received by the PW.";
            }
            leaf in-broadcast-bytes {
              type uint64;
              units "Byte";
              description
                "Number of broadcast bytes received by the PW.";
            }
            leaf out-unicast-frames {
              type uint64;
              units "packet";
              description
                "Number of unicast frames sent by the PW.";
            }
            leaf out-unicast-bytes {
              type uint64;
              units "Byte";
              description
                "Number of unicast bytes sent by the PW.";
            }
            leaf out-multicast-frames {
              type uint64;
              units "packet";
              description
                "Number of multicast frames sent by the PW.";
            }
            leaf out-multicast-bytes {
              type uint64;
              units "Byte";
              description
                "Number of multicast bytes sent by the PW.";
            }
            leaf out-broadcast-frames {
              type uint64;
              units "packet";
              description
                "Number of broadcast frames sent by the PW.";
            }
            leaf out-broadcast-bytes {
              type uint64;
              units "Byte";
              description
                "Number of broadcast bytes sent by the PW.";
            }
            leaf in-discard-frames {
              type uint64;
              units "packet";
              description
                "Number of frames received and then dropped by the PW.";
            }
            leaf reset-time {
              type yang:date-and-time;
              description
                "Time when statistics were cleared the last time.";
            }
          }
        }
      }
    }
    container bgp-multi-homing-signaling {
      when "../work-mode='normal'" {
        tailf:xpath-root 3;
      }
      must "../admin-vsi!='true' and ../track-admin-vsi!='true' and ../p2p-vsi!='true' and ../mac-remove-mode='invalid'" {
        tailf:xpath-root 3;
      }
      must 'not(../etree)' {
        tailf:xpath-root 3;
      }
      presence "Container for bgp protocol vpls instance.";
      description
        "Configure BGP VSIs.";
      leaf route-distinguisher {
        type string {
          length "3..21";
        }
        description
          "Route distinguisher.";
      }
      leaf encapsulation-rfc4761-compatible {
        type boolean;
        default "false";
        description
          "Enable/disable the setting of an encapsulation type.";
      }
      leaf encapsulation-vpls-family-compatible {
        type boolean;
        default "false";
        description
          "Enable/disable the setting of an encapsulation type to private mode.";
      }
      leaf mtu-negotiate-disable {
        type boolean;
        default "false";
        description
          "Enable/disable the function of ignoring MTU match between local VSI and remote VSI. The default implementation is match.";
      }
      leaf site-range {
        type uint32 {
          range "1..65535";
        }
        description
          "BGP site range. Cannot decrease site range.";
      }
      leaf default-offset {
        ext:operation-exclude "update|delete";
        when '../site-range' {
          tailf:xpath-root 3;
        }
        type uint16 {
          range "0..1";
        }
        default "0";
        description
          "BGP site offset. The value of this node cannot be modified after being set.";
      }
      leaf control-word {
        type ncs_rpc_notif_l2vpn-control-word;
        must "(../control-word='disable' or ../control-word='enable')" {
          tailf:xpath-root 3;
        }
        default "disable";
        description
          "Enable the control word feature. The control word feature is usually used for TDM, ATM, and FR PWs.";
      }
      leaf auto-route-distinguisher {
        type string {
          length "3..21";
        }
        config false;
        description
          "Automatic route distinguisher (RD). If no RD is configured for an L2VPN instance, you can specify an IPv4 address using the rd-ip parameter, based on which an RD is automatically generated in the format of 32-bit prefix IP address:index, for example, 192.168.122.15:1. An index is an integer automatically allocated by the system and ranges from 1 to 65535.Each L2VPN instance must use a unique RD.";
      }
      container default-site {
        description
          "Configure the default BGP multi-homing site.";
        leaf name {
          type ncs_rpc_notif_vpls-multi-homing-site-name;
          must "../name='default'" {
            tailf:xpath-root 3;
          }
          default "default";
          description
            "BGP multi-homing default site name.";
        }
        leaf site-id {
          type uint32 {
            range "0..65534";
          }
          description
            "BGP multi-homing default site ID.";
        }
        leaf preference {
          when '../site-id' {
            tailf:xpath-root 3;
          }
          type uint32 {
            range "1..65535";
          }
          default "100";
          description
            "BGP multi-homing default site preference.";
        }
        leaf selected {
          type boolean;
          config false;
          description
            "BGP multi-homing default site selected flag.";
        }
        container remote-sites {
          config false;
          description
            "Operational data of BGP multi-homing remote site information.";
          uses ncs_rpc_notif_bgp-mh-remote-site-grp;
        }
      }
      container sites {
        description
          "List of BGP multi-homing sites.";
        list site {
          key "name";
          max-elements 512;
          description
            "Configure BGP multi-homing sites.";
          leaf name {
            type ncs_rpc_notif_vpls-multi-homing-site-name;
            must "not(../name='default')" {
              tailf:xpath-root 3;
            }
            description
              "BGP multi-homing site name.";
          }
          leaf site-id {
            type uint32 {
              range "0..65534";
            }
            description
              "BGP multi-homing site ID.";
          }
          leaf preference {
            when '../site-id' {
              tailf:xpath-root 3;
            }
            type uint32 {
              range "1..65535";
            }
            default "100";
            description
              "BGP multi-homing site preference.";
          }
          leaf active-delay-time {
            when "../name!='default' and not(../best-site) and ../site-id" {
              tailf:xpath-root 3;
            }
            type uint16 {
              range "0..256";
            }
            units "s";
            default "30";
            description
              "BGP multi-homing site active delay time.";
          }
          leaf recover-delay-time {
            when "../name!='default' and not(../best-site) and ../site-id" {
              tailf:xpath-root 3;
            }
            type uint16 {
              range "0..3600";
            }
            units "s";
            default "180";
            description
              "BGP multi-homing site recover delay time.";
          }
          leaf best-site {
            when "../name!='default' and ../site-id" {
              tailf:xpath-root 3;
            }
            type empty;
            description
              "BGP multi-homing best site.";
          }
          leaf selected {
            type boolean;
            config false;
            description
              "Selected flag of BGP multi-homing site.";
          }
          container remote-sites {
            config false;
            description
              "Operational data of BGP multi-homing remote site information.";
            uses ncs_rpc_notif_bgp-mh-remote-site-grp;
          }
          container ac-infos {
            config false;
            description
              "List of BGP multi-homing AC information.";
            list ac-info {
              key "interface-name";
              description
                "Operational data of BGP multi-homing AC information.";
              leaf interface-name {
                type string;
                description
                  "BGP multi-homing AC interface name.";
              }
              leaf ac-state {
                type ncs_rpc_notif_ac-state;
                description
                  "BGP multi-homing AC state.";
              }
              leaf mflp-state {
                type ncs_rpc_notif_ac-block-status;
                description
                  "BGP multi-homing MFLP block state.";
              }
              leaf block-state {
                type ncs_rpc_notif_ac-block-status;
                description
                  "BGP multi-homing AC block state.";
              }
            }
          }
        }
      }
      container vpn-targets {
        description
          "List of VPN targets.";
        list vpn-target {
          key "rt-value rt-type";
          max-elements 32;
          description
            "Configure VPN targets.";
          leaf rt-value {
            type string {
              length "3..21";
            }
            description
              "Route target. The format of an RT can be:
               - 16-bit AS number:32-bit user-defined number, for example, 1:3. An AS number ranges from 0 to 65535, and a user-defined number ranges from 0 to 4294967295. The AS number and user-defined number cannot be both 0s. This means that the RT cannot be 0:0.
               - Integral 4-byte AS number:2-byte user-defined number, for example, 65537:3. An AS number ranges from 65536 to 4294967295. A user-defined number ranges from 0 to 65535. The AS number and user-defined number cannot be both 0s. This means that the RT cannot be 0:0.
               - 32-bit IP address:16-bit user-defined number, for example: 192.168.122.15:1. The IP address ranges from 0.0.0.0 to 255.255.255.255, and the user-defined number ranges from 0 to 65535.
               - 32-bit AS number:16-bit user-defined number, for example, 10.11:3. An AS number ranges from 0.0 to 65535.65535, and a user-defined number ranges from 0 to 65535. The AS number and user-defined number cannot be both 0s. This means that the RT cannot be 0.0:0.";
          }
          leaf rt-type {
            type ncs_rpc_notif_vpn-rt-type;
            description
              "RT type, which can be:
               - export-extcommunity: specifies the value of the extended community attribute of the route from an outbound interface to the destination VPN.
               - import-extcommunity: receives routes that carry the specified extended community attribute value.";
          }
        }
      }
      container pws {
        description
          "List of VPLS BGP multi-homing PWs.";
        list pw {
          must "name or traffic-statistics-collection='true'" {
            tailf:xpath-root 3;
          }
          key "peer-ip";
          unique "name";
          description
            "Configure a VPLS BGP multi-homing PW.";
          leaf peer-ip {
            type inet:ipv4-address-no-zone;
            description
              "Peer IP address.";
          }
          leaf name {
            type string {
              length "1..15";
            }
            description
              "PW name.";
          }
          leaf traffic-statistics-collection {
            type boolean;
            must ". = 'false' or not(../../../../traffic-statistics-collection = 'true')" {
              tailf:xpath-root 3;
            }
            default "false";
            description
              "Enable/disable the function to collect traffic statistics.";
          }
          uses l2vpn:ncs_rpc_notif_suppression-statisticss-grp;
        }
      }
      container pw-infos {
        config false;
        description
          "List of BGP multi-homing PWs.";
        list pw-info {
          key "site-id offset";
          description
            "Operational data of BGP multi-homing PWs.";
          leaf site-id {
            type uint32 {
              range "0..65534";
            }
            description
              "BGP site ID.";
          }
          leaf offset {
            type uint16;
            description
              "BGP site offset.";
          }
          leaf peer-ip {
            type inet:ipv4-address-no-zone;
            description
              "BGP peer IP.";
          }
          leaf pw-type {
            type ncs_rpc_notif_l2vpn-vpls-pw-type;
            description
              "PW type, which can be label, QinQ, or MEHVPLS.";
          }
          leaf pw-state {
            type ncs_rpc_notif_l2vpn-pw-state;
            description
              "PW status.";
          }
          leaf local-vc-label {
            type uint32;
            description
              "VC label allocated by the local device.";
          }
          leaf remote-vc-label {
            type uint32;
            description
              "VC label allocated by the peer.";
          }
          leaf last-up-time {
            type yang:date-and-time;
            description
              "Date and time when a PW was up for the last time, for example, 2012/07/20 02:30:46.";
          }
          leaf total-up-time {
            type string {
              length "1..80";
            }
            description
              "Total duration when the PW is up.";
          }
          leaf c-key {
            type uint32;
            description
              "Customer key. Each CKey corresponds to a PW.";
          }
          leaf n-key {
            type uint32;
            description
              "Network key. Each NKey corresponds to a combination of the peer and tunnel policy.";
          }
          leaf broadcast-tunnel-key {
            type string {
              length "0..21";
            }
            description
              "Tunnel ID used by a PW for broadcast.";
          }
          leaf stp-enable {
            type boolean;
            description
              "Enable STP for PW.";
          }
          leaf mac-flapping-enable {
            type ncs_rpc_notif_pw-block-status;
            description
              "MAC flapping information.";
          }
          leaf main-pw-token {
            type pub-type:ncs_rpc_notif_hex-binary;
            description
              "Token of the primary PW.";
          }
          leaf backup-pw-token {
            type pub-type:ncs_rpc_notif_hex-binary;
            description
              "Token of the secondary PW.";
          }
          leaf remote-control-word {
            type ncs_rpc_notif_l2vpn-control-word;
            description
              "Remote control word capability.";
          }
          leaf negotiate-control-word {
            type ncs_rpc_notif_l2vpn-control-word;
            description
              "Negotiated control word capability.";
          }
          container tunnels {
            description
              "List of VPLS PW tunnels.";
            list tunnel {
              key "tunnel-key";
              max-elements 32;
              description
                "Operational data of a VPLS PW tunnel.";
              leaf tunnel-key {
                type string {
                  length "0..21";
                }
                description
                  "Tunnel ID in hexadecimal notation that is assigned by the system.";
              }
              leaf tunnel-type {
                type ncs_rpc_notif_l2vpn-tunnel-type;
                description
                  "Type of a tunnel.";
              }
              leaf out-interface {
                type pub-type:ncs_rpc_notif_if-name;
                description
                  "Outbound interface of a PW.";
              }
              leaf tunnel-name {
                type string {
                  length "0..64";
                }
                description
                  "Name of the tunnel used by the PW.";
              }
              leaf public-next-hop {
                type inet:ipv4-address-no-zone;
                description
                  "Public next hop of a PW.";
              }
            }
          }
          container traffic-statistics {
            description
              "Peer traffic statistics.";
            leaf in-traffic-rate {
              type uint64;
              units "bit/s";
              description
                "Rate of traffic received by the PW.";
            }
            leaf out-traffic-rate {
              type uint64;
              units "bit/s";
              description
                "Rate of traffic sent by the PW.";
            }
            leaf in-frame-rate {
              type uint64;
              units "pps";
              description
                "Rate of frames received by the PW.";
            }
            leaf out-frame-rate {
              type uint64;
              units "pps";
              description
                "Rate of frames sent by the PW.";
            }
            leaf in-bytes {
              type uint64;
              units "Byte";
              description
                "Number of bytes received by the PW.";
            }
            leaf out-bytes {
              type uint64;
              units "Byte";
              description
                "Number of bytes sent by the PW.";
            }
            leaf in-frames {
              type uint64;
              units "packet";
              description
                "Number of frames received by the PW.";
            }
            leaf out-frames {
              type uint64;
              units "packet";
              description
                "Number of frames sent by the PW.";
            }
            leaf in-unicast-frames {
              type uint64;
              units "packet";
              description
                "Number of unicast frames received by the PW.";
            }
            leaf in-unicast-bytes {
              type uint64;
              units "Byte";
              description
                "Number of unicast bytes received by the PW.";
            }
            leaf in-multicast-frames {
              type uint64;
              units "packet";
              description
                "Number of multicast frames received by the PW.";
            }
            leaf in-multicast-bytes {
              type uint64;
              units "Byte";
              description
                "Number of multicast bytes received by the PW.";
            }
            leaf in-broadcast-frames {
              type uint64;
              units "packet";
              description
                "Number of broadcast frames received by the PW.";
            }
            leaf in-broadcast-bytes {
              type uint64;
              units "Byte";
              description
                "Number of broadcast bytes received by the PW.";
            }
            leaf out-unicast-frames {
              type uint64;
              units "packet";
              description
                "Number of unicast frames sent by the PW.";
            }
            leaf out-unicast-bytes {
              type uint64;
              units "Byte";
              description
                "Number of unicast bytes sent by the PW.";
            }
            leaf out-multicast-frames {
              type uint64;
              units "packet";
              description
                "Number of multicast frames sent by the PW.";
            }
            leaf out-multicast-bytes {
              type uint64;
              units "Byte";
              description
                "Number of multicast bytes sent by the PW.";
            }
            leaf out-broadcast-frames {
              type uint64;
              units "packet";
              description
                "Number of broadcast frames sent by the PW.";
            }
            leaf out-broadcast-bytes {
              type uint64;
              units "Byte";
              description
                "Number of broadcast bytes sent by the PW.";
            }
            leaf in-discard-frames {
              type uint64;
              units "packet";
              description
                "Number of frames received and then dropped by the PW.";
            }
            leaf reset-time {
              type yang:date-and-time;
              description
                "Time when statistics were cleared the last time.";
            }
          }
        }
      }
      container local-label-blocks {
        config false;
        description
          "Operational data of local label blocks.";
        uses ncs_rpc_notif_bgp-local-label-block-grp;
      }
      container remote-sites {
        config false;
        description
          "List of BGP multi-homing remote site information.";
        list remote-site {
          key "site-id route-distinguisher offset";
          description
            "Operational data of BGP multi-homing remote site information.";
          leaf site-id {
            type uint32;
            description
              "BGP multi-homing remote site ID.";
          }
          leaf route-distinguisher {
            type string {
              length "3..21";
            }
            description
              "Route distinguisher.";
          }
          leaf offset {
            type uint16;
            description
              "BGP site offset.";
          }
          leaf peer-ip {
            type inet:ipv4-address-no-zone;
            description
              "The IP address of peer.";
          }
          leaf mtu {
            type uint32;
            description
              "Maximum transmission unit.";
          }
          leaf encapsulation-type {
            type ncs_rpc_notif_vpls-bgp-encapsulation-type;
            description
              "The encapsulation type of remote PW.";
          }
          leaf label-start {
            type uint32;
            description
              "Start of the label.";
          }
          leaf add-range {
            type uint16;
            description
              "BGP site range.";
          }
        }
      }
    }
    container bgpad-signaling {
      when "(../work-mode='normal' or ../work-mode='bd-mode')" {
        tailf:xpath-root 3;
      }
      must "../admin-vsi!='true' and ../track-admin-vsi!='true' and ../p2p-vsi !='true'" {
        tailf:xpath-root 3;
      }
      must 'not(../etree)' {
        tailf:xpath-root 3;
      }
      presence "Container for bgpad protocol vpls instance.";
      description
        "Enable/disable BGP AD VSI.";
      leaf vpls-id {
        type string {
          length "3..21";
        }
        description
          "VPLS domain ID. The format of a VPLS domain ID can be:
           - 16-bit AS number:32-bit user-defined number, for example, 1:3. An AS number ranges from 0 to 65535, and a user-defined number ranges from 0 to 4294967295. The AS number and user-defined number cannot be both 0s. This means that the VPLS domain ID cannot be 0:0.
           - Integral 4-byte AS number:2-byte user-defined number, for example, 65537:3. An AS number ranges from 65536 to 4294967295. A user-defined number ranges from 0 to 65535. The AS number and user-defined number cannot be both 0s. This means that the VPLS domain ID cannot be 0:0.
           - 32-bit IP address:16-bit user-defined number, for example: 192.168.122.15:1. The IP address ranges from 0.0.0.0 to 255.255.255.255, and the user-defined number ranges from 0 to 65535.
           - 32-bit AS number:16-bit user-defined number, for example, 10.11:3. An AS number ranges from 0.0 to 65535.65535, and a user-defined number ranges from 0 to 65535. The AS number and user-defined number cannot be both 0s. This means that the VPLS domain ID cannot be 0.0:0.";
      }
      leaf split-horizon {
        when '../vpls-id' {
          tailf:xpath-root 3;
        }
        type ncs_rpc_notif_vpls-split-horizon-mode-type;
        default "hub";
        description
          "PW split horizon mode.";
      }
      leaf traffic-statistics-collection {
        when '../vpls-id' {
          tailf:xpath-root 3;
        }
        type boolean;
        must ". ='false' or not(../../traffic-statistics-collection='true' or ../../ldp-signaling/traffic-statistics-collection='true' or ../../ldp-signaling/pws/pw/traffic-statistics-collection!='default')" {
          tailf:xpath-root 3;
        }
        default "false";
        description
          "Enable/disable traffic statistics collection.";
      }
      leaf route-distinguisher {
        type string {
          length "3..21";
        }
        config false;
        description
          "Route distinguisher.";
      }
      leaf vsi-id {
        type inet:ipv4-address-no-zone;
        config false;
        description
          "VSI ID. For a BGP AD VSI, the VSI ID is the IP address used by the local PE for signaling negotiation.";
      }
      container vpn-targets {
        when '../vpls-id' {
          tailf:xpath-root 3;
        }
        description
          "List of VPN targets.";
        list vpn-target {
          key "rt-value rt-type";
          max-elements 32;
          description
            "Configure VPN targets.";
          leaf rt-value {
            type string {
              length "3..21";
            }
            description
              "Route target. The format of an RT can be:
               - 16-bit AS number:32-bit user-defined number, for example, 1:3. An AS number ranges from 0 to 65535, and a user-defined number ranges from 0 to 4294967295. The AS number and user-defined number cannot be both 0s. This means that the RT cannot be 0:0.
               - Integral 4-byte AS number:2-byte user-defined number, for example, 65537:3. An AS number ranges from 65536 to 4294967295. A user-defined number ranges from 0 to 65535. The AS number and user-defined number cannot be both 0s. This means that the RT cannot be 0:0.
               - 32-bit IP address:16-bit user-defined number, for example: 192.168.122.15:1. The IP address ranges from 0.0.0.0 to 255.255.255.255, and the user-defined number ranges from 0 to 65535.
               - 32-bit AS number:16-bit user-defined number, for example, 10.11:3. An AS number ranges from 0.0 to 65535.65535, and a user-defined number ranges from 0 to 65535. The AS number and user-defined number cannot be both 0s. This means that the RT cannot be 0.0:0.";
          }
          leaf rt-type {
            type ncs_rpc_notif_vpn-rt-type;
            description
              "RT type, which can be:
               - export-extcommunity: specifies the value of the extended community attribute of the route from an outbound interface to the destination VPN.
               - import-extcommunity: receives routes that carry the specified extended community attribute value.";
          }
        }
      }
      container pws {
        when '../vpls-id' {
          tailf:xpath-root 3;
        }
        description
          "List of BGP AD PWs.";
        list pw {
          must 'name or traffic-statistics-collection' {
            tailf:xpath-root 3;
          }
          key "peer-ip";
          description
            "Configure a BGP AD PW.";
          leaf peer-ip {
            type inet:ipv4-address-no-zone;
            description
              "Peer IP address.";
          }
          leaf name {
            type string {
              length "1..15";
            }
            description
              "PW name.";
          }
          leaf traffic-statistics-collection {
            type boolean;
            must "not(../../../../ldp-signaling/traffic-statistics-collection = 'true')" {
              tailf:xpath-root 3;
            }
            must "not(../../../../ldp-signaling/pws/pw[traffic-statistics-collection != 'default'])" {
              tailf:xpath-root 3;
            }
            must ". != 'true' or (../../../../traffic-statistics-collection = 'false')" {
              tailf:xpath-root 3;
            }
            description
              "Enable/disable the function to collect traffic statistics.";
          }
          uses l2vpn:ncs_rpc_notif_suppression-statisticss-grp;
        }
      }
      container peers {
        config false;
        description
          "List of BGP AD peer.";
        list peer {
          key "peer-router-id";
          max-elements 65536;
          description
            "Operational data of BGP AD peer.";
          leaf peer-router-id {
            type inet:ipv4-address-no-zone;
            description
              "Peer IP address.";
          }
          leaf vpls-id {
            type string {
              length "3..21";
            }
            description
              "VPLS domain ID.";
          }
          leaf saii {
            type inet:ipv4-address-no-zone;
            description
              "Source attachment individual identifier.";
          }
          leaf taii {
            type inet:ipv4-address-no-zone;
            description
              "Target attachment individual identifier.";
          }
          leaf peer-type {
            type ncs_rpc_notif_vpls-ldp-peer-type;
            description
              "Remote peer type, either dynamic or static.";
          }
          container pw-info {
            config false;
            description
              "Operational data of BGP AD PW.";
            leaf peer-ip {
              type inet:ipv4-address-no-zone;
              description
                "BGP AD PW.";
            }
            leaf pw-type {
              type ncs_rpc_notif_l2vpn-vpls-pw-type;
              description
                "PW type, which can be label, QinQ, or MEHVPLS.";
            }
            leaf session-state {
              type ncs_rpc_notif_l2vpn-state;
              description
                "Status of the session between the local end and its peer. The value can be up or down. This item is displayed only when the VPLS type is Martini.";
            }
            leaf pw-state {
              type ncs_rpc_notif_l2vpn-pw-state;
              description
                "PW status.";
            }
            leaf local-vc-label {
              type uint32;
              description
                "VC label allocated by the local device.";
            }
            leaf remote-vc-label {
              type uint32;
              description
                "VC label allocated by the peer.";
            }
            leaf last-up-time {
              type string {
                length "1..80";
              }
              description
                "Date and time when a PW was up for the last time, for example, 2012/07/20 02:30:46.";
            }
            leaf total-up-time {
              type string {
                length "1..80";
              }
              description
                "Total duration when the PW is up.";
            }
            leaf c-key {
              type uint32;
              description
                "Customer key. Each CKey corresponds to a PW.";
            }
            leaf n-key {
              type uint32;
              description
                "Network key. Each NKey corresponds to a combination of the peer and tunnel policy.";
            }
            leaf broadcast-tunnel-key {
              type string {
                length "0..21";
              }
              description
                "Tunnel ID used by a PW for broadcast.";
            }
            leaf stp-enable {
              type boolean;
              description
                "Enable STP for PW.";
            }
            leaf mac-flapping-enable {
              type ncs_rpc_notif_pw-block-status;
              description
                "MAC flapping information.";
            }
            leaf main-pw-token {
              type pub-type:ncs_rpc_notif_hex-binary;
              description
                "Token of the primary PW.";
            }
            leaf backup-pw-token {
              type pub-type:ncs_rpc_notif_hex-binary;
              description
                "Token of the secondary PW.";
            }
            leaf remote-vccv-code {
              type pub-type:ncs_rpc_notif_hex-binary;
              description
                "Remote VCCV code.";
            }
            leaf pw-token-exceed {
              type boolean;
              default "false";
              description
                "Indicates whether the number of PW tokens exceeds the maximum limit.";
            }
            container tunnels {
              config false;
              description
                "List of VPLS PW tunnel.";
              list tunnel {
                key "tunnel-key";
                max-elements 32;
                description
                  "Operational data of VPLS PW tunnel.";
                leaf tunnel-key {
                  type string {
                    length "0..21";
                  }
                  description
                    "Tunnel ID in hexadecimal notation that is assigned by the system.";
                }
                leaf tunnel-type {
                  type ncs_rpc_notif_l2vpn-tunnel-type;
                  description
                    "Type of a tunnel.";
                }
                leaf out-interface {
                  type string {
                    length "0..256";
                  }
                  description
                    "Outbound interface of a PW.";
                }
                leaf tunnel-name {
                  type string {
                    length "0..64";
                  }
                  description
                    "Name of the tunnel used by the PW.";
                }
                leaf public-next-hop {
                  type inet:ipv4-address-no-zone;
                  description
                    "Public next hop of a PW.";
                }
              }
            }
          }
          uses l2vpn:ncs_rpc_notif_pw-traffic-statisticss-grp;
        }
      }
    }
    container acs {
      when "../work-mode!='bd-mode'" {
        tailf:xpath-root 3;
      }
      description
        "List of VPLS ACs.";
      list ac {
        key "interface-name";
        description
          "Configure a VPLS AC.";
        leaf interface-name {
          type string;
          must "/ifm:ifm/ifm:interfaces/ifm:interface[ifm:name=current()]/ifm:link-protocol='ethernet'" {
            tailf:xpath-root 3;
          }
          description
            "Name of the AC interface bound to a VSI.";
        }
        leaf site-name {
          when '../../../bgp-multi-homing-signaling/sites/site/site-id' {
            tailf:xpath-root 3;
          }
          type ncs_rpc_notif_vpls-multi-homing-site-name;
          description
            "BGP multi-homing site name. The value of this node cannot be changed after being configured.";
        }
        leaf hub-mode {
          type boolean;
          default "false";
          description
            "Enable/disable an interface's support for the hub mode.";
        }
        leaf access-port {
          ext:operation-exclude "update|delete";
          type boolean;
          must "/ifm:ifm/ifm:interfaces/ifm:interface[ifm:name=current()/../interface-name]/ifm:class='main-interface' or (/ifm:ifm/ifm:interfaces/ifm:interface[ifm:name=current()/../interface-name]/ifm:class='sub-interface' and ../access-port = 'false')" {
            tailf:xpath-root 3;
          }
          default "false";
          description
            "Enable/disable the attribute that allows only untagged packets to pass through an interface.";
        }
        leaf etree-leaf {
          when '../../../etree' {
            tailf:xpath-root 3;
          }
          type boolean;
          must ".='false' or ../../../ldp-signaling" {
            tailf:xpath-root 3;
          }
          default "false";
          description
            "Enable/disable e-tree leaf.";
        }
        leaf state {
          type ncs_rpc_notif_ac-state;
          config false;
          description
            "Status of the AC interface bound to a VSI.";
        }
        leaf block-state {
          type ncs_rpc_notif_ac-block-status;
          config false;
          description
            "AC block state.";
        }
        leaf last-up-time {
          type string {
            length "1..60";
          }
          config false;
          description
            "Date and time when the AC interface was up for the last time, for example, 2012/07/20 02:30:46.";
        }
        leaf total-up-time {
          type string {
            length "1..60";
          }
          config false;
          description
            "Total up time of the AC interface.";
        }
        leaf token-exceed {
          type boolean;
          default "false";
          config false;
          description
            "Indicates whether the number of AC tokens exceeds the maximum limit.";
        }
        leaf oam-state {
          type ncs_rpc_notif_oam-state;
          config false;
          description
            "OAM Status of the AC interface bound to a VSI.";
        }
      }
    }
    container bds {
      when "../work-mode='bd-mode' and (../ldp-signaling/vsi-id or ../bgp-signaling or ../bgpad-signaling/vpls-id)" {
        tailf:xpath-root 3;
      }
      must 'not(../etree)' {
        tailf:xpath-root 3;
      }
      description
        "List of VPLS BD ACs.";
      list bd {
        must '(pw-tag and count(.)>1) or (not(count(.)>1))' {
          tailf:xpath-root 3;
        }
        key "id";
        unique "pw-tag";
        description
          "Configure VPLS BD ACs.";
        leaf id {
          type string;
          description
            "BD ID.";
        }
        leaf pw-tag {
          type uint16 {
            range "1..4094";
          }
          description
            "PW tag.";
        }
        leaf state {
          type ncs_rpc_notif_ac-state;
          config false;
          description
            "Status of the AC interface bound to a VSI.";
        }
        leaf last-up-time {
          type string {
            length "1..60";
          }
          config false;
          description
            "Date and time when the AC interface was up for the last time, for example, 2012/07/20 02:30:46.";
        }
        leaf total-up-time {
          type string {
            length "1..60";
          }
          config false;
          description
            "Total up time of the AC interface.";
        }
      }
    }
    container pbb {
      when "../work-mode='b-vsi' or ../work-mode='i-vsi' or ../work-mode='i-vsi-p2p' or ../work-mode='i-vsi-b-evpn-interworking'" {
        tailf:xpath-root 3;
      }
      must "../admin-vsi!='true'" {
        tailf:xpath-root 3;
      }
      description
        "Configure PBB VPLS.";
      leaf i-tag {
        when "../../work-mode='i-vsi-b-evpn-interworking' or ../../work-mode='i-vsi' or ../../work-mode='i-vsi-p2p'" {
          tailf:xpath-root 3;
        }
        type uint32 {
          range "0..16777215";
        }
        description
          "Tag defined in 802.1ah to identify a service instance.";
      }
      leaf backbone-source-mac {
        when "../../work-mode='b-vsi' or ../../work-mode='i-vsi' or ../../work-mode='i-vsi-p2p'" {
          tailf:xpath-root 3;
        }
        type pub-type:ncs_rpc_notif_mac-address;
        description
          "B-SMAC address.";
      }
      leaf backbone-destination-mac {
        when "../../work-mode='i-vsi' or ../../work-mode='i-vsi-p2p'" {
          tailf:xpath-root 3;
        }
        type pub-type:ncs_rpc_notif_mac-address;
        description
          "B-DMAC address.";
      }
      leaf mac-withdraw-rfc7361-compatible {
        when "../../work-mode='b-vsi'" {
          tailf:xpath-root 3;
        }
        type boolean;
        default "false";
        description
          "Enable/disable MAC withdraw messages that carry PBB B-MAC and I-tag TLVs in accordance with RFC 7361.";
      }
      leaf b-vsi {
        type string;
        must "/l2vpn:l2vpn/l2vpn:instances/l2vpn:instance[l2vpn:name=current()][l2vpn:type='vpls']/l2vpn:vpls/l2vpn:work-mode='b-vsi' and ../../work-mode='i-vsi-p2p' and ../i-tag and ../backbone-destination-mac and ../backbone-source-mac" {
          tailf:xpath-root 3;
        }
        description
          "Name of the B-VSI instance to which the I-VSI is bound.";
      }
      leaf b-evpn {
        type string {
          length "1..31";
        }
        must "../../work-mode='i-vsi-b-evpn-interworking' and ../i-tag" {
          tailf:xpath-root 3;
        }
        description
          "Name of the B-EVPN instance to which the I-VSI is bound.";
      }
      leaf learned-flag {
        type ncs_rpc_notif_vsi-pbb-learned-flag;
        config false;
        description
          "B-MAC address learning result.";
      }
      leaf learned-in-label {
        type uint32;
        config false;
        description
          "Learned in-label.";
      }
      leaf learned-out-label {
        type uint32;
        config false;
        description
          "Learned out-label.";
      }
      container i-vsis {
        config false;
        description
          "List of I-VSI.";
        list i-vsi {
          key "vsi-name";
          description
            "Operational data of I-VSI.";
          leaf vsi-name {
            type string {
              length "1..31";
            }
            description
              "I-VSI name.";
          }
        }
      }
    }
    container ipmsi {
      when "../work-mode!='bd-mode'" {
        tailf:xpath-root 3;
      }
      must '../bgpad-signaling/vpls-id or ../bgp-multi-homing-signaling' {
        tailf:xpath-root 3;
      }
      must 'not(../etree)' {
        tailf:xpath-root 3;
      }
      presence "enable ipmsi.";
      description
        "Enable/disable multicast VPLS.";
      container root {
        presence "root";
        description
          "Enable/disable the P2MP tunnel root.";
        leaf data-switch-disable {
          type boolean;
          default "false";
          description
            "Enable/disable broadcast, unknown unicast, and multicast traffic's switching to a PW when a P2MP tunnel goes down.";
        }
        leaf mc-tunnel-type {
          type ncs_rpc_notif_multicast-tunnel-type;
          default "invalid";
          description
            "P2MP tunnel type.";
        }
        leaf root-ip {
          when "../mc-tunnel-type!='invalid' and ../mc-tunnel-type!='te-p2mp'" {
            tailf:xpath-root 3;
          }
          type inet:ipv4-address-no-zone;
          description
            "Root IP address of a P2MP tunnel.";
        }
        leaf te-p2mp-dynamic {
          when "../mc-tunnel-type!='invalid' and ../mc-tunnel-type!='mldp-p2mp'" {
            tailf:xpath-root 3;
          }
          type boolean;
          default "false";
          description
            "Enable/disable P2MP dynamic TE.";
        }
        leaf p2mp-template-name {
          when "../te-p2mp-dynamic='false' and ../mc-tunnel-type='te-p2mp'" {
            tailf:xpath-root 3;
          }
          type string {
            length "1..31";
          }
          description
            "P2MP template name.";
        }
        leaf bfd-track-if-name {
          when '../../../acs/ac' {
            tailf:xpath-root 3;
          }
          type string;
          description
            "Name of the interface bound to a BFD session.";
        }
        leaf leaf-count {
          type uint32 {
            range "0..65535";
          }
          config false;
          description
            "Number of leaves.";
        }
        container tunnel {
          config false;
          description
            "Operational data of tunnels.";
          leaf ingress-lsr-id {
            type inet:ipv4-address-no-zone;
            description
              "Ingress LSR ID.";
          }
          leaf state {
            type ncs_rpc_notif_l2vpn-state;
            description
              "P2MP tunnel status.";
          }
          leaf session-id {
            type uint32 {
              range "0..4294967295";
            }
            description
              "RSVP session ID.";
          }
          leaf p2mp-id {
            type string {
              length "0..10";
            }
            description
              "P2MP session ID.";
          }
          leaf opaque-value {
            type string {
              length "0..4096";
            }
            description
              "Original opaque value in a message. The value is displayed in the format of TLV.";
          }
        }
        container leafs {
          config false;
          description
            "List of Leaf.";
          list leaf {
            key "peer-ip";
            description
              "Operational data of leafs.";
            leaf peer-ip {
              type inet:ipv4-address-no-zone;
              description
                "LSR ID of the remote device.";
            }
          }
        }
      }
      container leaf {
        presence "leaf";
        description
          "Enable/disable the leaf of a P2MP tunnel.";
        leaf egress-count {
          type uint64 {
            range "0..65534";
          }
          config false;
          description
            "Number of P2MP tunnel egresses.";
        }
        container pw-protect-groups {
          description
            "List of PW protection groups.";
          list pw-protect-group {
            key "primary-root-ip backup-root-ip";
            description
              "Configure a PW protection group.";
            leaf primary-root-ip {
              type inet:ipv4-address-no-zone;
              description
                "IP address of the primary root.";
            }
            leaf backup-root-ip {
              type inet:ipv4-address-no-zone;
              description
                "IP address of the backup root.";
            }
            leaf wtr {
              type uint32 {
                range "0..600";
              }
              units "min";
              default "30";
              description
                "Wait-to-Restore time.";
            }
            leaf primary-track-bfd {
              type boolean;
              default "false";
              description
                "Enable/disable the association between the primary root and a BFD session.";
            }
            leaf backup-track-bfd {
              type boolean;
              default "false";
              description
                "Enable/disable the association between the backup root and a BFD session.";
            }
            container primary {
              config false;
              description
                "Operational data of primary root node.";
              uses ncs_rpc_notif_ipmsi-leaf-protect-group-parameter;
            }
            container backup {
              config false;
              description
                "Operational data of backup root node.";
              uses ncs_rpc_notif_ipmsi-leaf-protect-group-parameter;
            }
          }
        }
        container mldp-p2mp-tunnels {
          config false;
          description
            "Operational data of mLDP P2MP tunnel.";
          uses ncs_rpc_notif_mldp-p2mp-tunnel-grp;
        }
        container te-p2mp-tunnels {
          config false;
          description
            "Operational data of te P2MP tunnel.";
          uses ncs_rpc_notif_te-p2mp-tunnel-grp;
        }
      }
    }
    container mac-withdraw-loop-detect {
      config false;
      description
        "Operational data of MAC withdraw loop detection information.";
      leaf last-loop-type {
        type ncs_rpc_notif_vpls-loop-detect-type;
        description
          "Type of the last loop detected by MAC withdraw loop detection.";
      }
      leaf send-peer {
        type inet:ipv4-address-no-zone;
        description
          "Transmit peer for MAC withdraw loop detection.";
      }
      leaf receive-peer {
        type inet:ipv4-address-no-zone;
        description
          "Receive peer for MAC withdraw loop detection.";
      }
      leaf last-loop-time {
        type string {
          length "1..80";
        }
        description
          "Time when MAC withdraw loop detection detected the last loop.";
      }
    }
    container down-causes {
      config false;
      description
        "Operational data of the down causes of the VSI.";
      uses l2vpn:ncs_rpc_notif_l2vpn-pw-down-causes-type;
    }
    container statistic {
      config false;
      description
        "Operational data of L2VPN VPLS statistic.";
      leaf up-pw-num {
        type uint32;
        description
          "Number of the up state PW.";
      }
      leaf down-pw-num {
        type uint32;
        description
          "Number of the down state PW.";
      }
      leaf backup-pw-num {
        type uint32;
        description
          "Number of the backup state PW.";
      }
      leaf up-bfd-num {
        type uint32;
        description
          "Number of the BFD notify up state PW.";
      }
      leaf down-bfd-num {
        type uint32;
        description
          "Number of the BFD notify down state PW.";
      }
      leaf up-ac-num {
        type uint32;
        description
          "Number of the up state AC.";
      }
      leaf down-ac-num {
        type uint32;
        description
          "Number of the down state AC.";
      }
      leaf down-acoam-num {
        type uint32;
        description
          "Number of the down state AC because of OAM.";
      }
    }
    container ac-suppression-statisticss {
      config false;
      description
        "List of VPLS AC Suppression statistics.";
      list ac-suppression-statistics {
        key "direction suppression-type";
        description
          "Operational data of suppression statistics about VPLS ACs.";
        leaf direction {
          type ncs_rpc_notif_suppression-direction;
          description
            "Suppression statistics direction.";
        }
        uses l2vpn:ncs_rpc_notif_suppression-statistics-grp;
      }
    }
  }

  grouping ncs_rpc_notif_l2vpn-protect-group-historys-type {
    description
      "List of L2VPN protect group histroy info container.";
    list history {
      key "num";
      max-elements 5;
      description
        "Operational data of historical switching information of a PW protection group.";
      leaf num {
        type uint32 {
          range "1..5";
        }
        description
          "Sequence number.";
      }
      leaf reroute-time {
        type string {
          length "1..60";
        }
        description
          "Switchback time.";
      }
      leaf reroute-action {
        type string {
          length "1..100";
        }
        description
          "Switchback action.";
      }
      leaf reroute-reason {
        type string {
          length "0..100";
        }
        description
          "Switchback reason.";
      }
    }
  }

  grouping ncs_rpc_notif_bgp-local-label-block-grp {
    description
      "List of a local label blocks.";
    list local-label-block {
      key "offset";
      description
        "Operational data of local label blocks.";
      leaf offset {
        type uint16;
        description
          "BGP site offset.";
      }
      leaf label-start {
        type uint32;
        description
          "Start of the label.";
      }
      leaf add-range {
        type uint32;
        description
          "BGP site range.";
      }
      leaf site-base {
        type uint32;
        description
          "Base of the site.";
      }
    }
  }

  grouping ncs_rpc_notif_bgp-remote-label-block-grp {
    description
      "List of remote label blocks.";
    list remote-label-block {
      key "route-distinguisher site-id offset";
      description
        "Operational data of remote label blocks.";
      leaf route-distinguisher {
        type string {
          length "3..21";
        }
        description
          "Route distinguisher.";
      }
      leaf site-id {
        type uint32 {
          range "0..65534";
        }
        description
          "BGP site ID.";
      }
      leaf offset {
        type uint16;
        description
          "BGP site offset.";
      }
      leaf label-start {
        type uint32;
        description
          "Start of the label.";
      }
      leaf add-range {
        type uint32;
        description
          "BGP site range.";
      }
    }
  }

  grouping ncs_rpc_notif_ac-arp-grp {
    description
      "List of ARP information about all ACs.";
    list ac-arp {
      key "mac-type";
      max-elements 3;
      description
        "Operational data of ARP information about an AC.";
      leaf mac-type {
        type ncs_rpc_notif_l2vpn-mac-type;
        description
          "MAC address learning type.";
      }
      leaf mac-address {
        type pub-type:ncs_rpc_notif_mac-address;
        description
          "MAC address of the local CE.";
      }
      leaf expire-time {
        type uint32;
        units "min";
        description
          "Aging time.";
      }
      leaf vlan-id {
        type uint32;
        description
          "VLAN ID corresponding to a MAC address.";
      }
      leaf ip-address {
        type inet:ipv4-address-no-zone;
        description
          "Dynamically learned IP address of the local CE.";
      }
    }
  }

  grouping ncs_rpc_notif_ipmsi-leaf-protect-group-parameter {
    description
      "Operational data of Ipmsi leaf protect group parameters.";
    leaf valid {
      type boolean;
      default "false";
      description
        "The root is valid.";
    }
    leaf active-state {
      type ncs_rpc_notif_multicast-active-state;
      description
        "The root is active.";
    }
    leaf oam-protocol {
      type ncs_rpc_notif_multicast-oam-type;
      description
        "Root OAM protocol.";
    }
    leaf oam-state {
      type ncs_rpc_notif_oam-state;
      description
        "Root OAM status.";
    }
  }

  grouping ncs_rpc_notif_mldp-p2mp-tunnel-grp {
    description
      "Operational data of Ipmsi mLDP P2MP tunnel.";
    list mldp-p2mp-tunnel {
      key "root-ip opaque-value";
      max-elements 65536;
      description
        "Operational data of tunnel information on a leaf node.";
      leaf root-ip {
        type inet:ipv4-address-no-zone;
        description
          "Root IP address of a P2MP tunnel.";
      }
      leaf opaque-value {
        type string {
          length "0..21";
        }
        description
          "Original opaque value in a message. The value is displayed in the format of TLV.";
      }
      leaf state {
        type ncs_rpc_notif_l2vpn-state;
        description
          "P2MP tunnel status.";
      }
    }
  }

  grouping ncs_rpc_notif_te-p2mp-tunnel-grp {
    description
      "Operational data of Ipmsi te P2MP tunnel.";
    list te-p2mp-tunnel {
      key "ingress-lsr-id session-id p2mp-id";
      max-elements 65536;
      description
        "Operational data of tunnel information on a leaf node.";
      leaf ingress-lsr-id {
        type inet:ipv4-address-no-zone;
        description
          "Ingress LSR ID.";
      }
      leaf session-id {
        type uint32 {
          range "0..4294967295";
        }
        description
          "RSVP session ID.";
      }
      leaf p2mp-id {
        type string {
          length "0..14";
        }
        description
          "P2MP session ID.";
      }
      leaf state {
        type ncs_rpc_notif_l2vpn-state;
        description
          "P2MP tunnel status.";
      }
    }
  }

  grouping ncs_rpc_notif_bgp-mh-remote-site-grp {
    description
      "Operational data of BGP multi-homing remote site information.";
    list remote-site {
      key "remote-site-id peer-ip";
      description
        "Operational data of BGP multi-homing remote site information.";
      leaf remote-site-id {
        type uint32;
        description
          "BGP multi-homing remote site ID.";
      }
      leaf peer-ip {
        type inet:ipv4-address-no-zone;
        description
          "BGP multi-homing peer IP.";
      }
    }
  }

  grouping ncs_rpc_notif_suppression-statistics-grp {
    description
      "Suppression statistics.";
    leaf suppression-type {
      type ncs_rpc_notif_suppression-type;
      description
        "Suppression statistics type.";
    }
    leaf cir {
      type uint32;
      description
        "CIR value.";
    }
    leaf pir {
      type uint32;
      description
        "PIR value.";
    }
    leaf cbs {
      type uint32;
      description
        "CBS value.";
    }
    leaf pbs {
      type uint32;
      description
        "PBS value.";
    }
    leaf passed-packets {
      type uint64;
      description
        "Passed packets.";
    }
    leaf passed-bytes {
      type uint64;
      description
        "Passed bytes.";
    }
    leaf discard-packets {
      type uint64;
      description
        "Discard packets.";
    }
    leaf discard-bytes {
      type uint64;
      description
        "Discard bytes.";
    }
    leaf passed-packet-rate {
      type uint64;
      units "pps";
      description
        "Passed packet rate.";
    }
    leaf passed-bit-rate {
      type uint64;
      units "bit/s";
      description
        "Passed bit rate.";
    }
    leaf discard-packet-rate {
      type uint64;
      units "pps";
      description
        "Discard packet rate.";
    }
    leaf discard-bit-rate {
      type uint64;
      units "bit/s";
      description
        "Discard bit rate.";
    }
  }

  grouping ncs_rpc_notif_suppression-statisticss-grp {
    description
      "Suppression statistics.";
    container suppression-statisticss {
      config false;
      description
        "List of suppression statistics.";
      list suppression-statistics {
        key "suppression-type";
        description
          "Operational data of suppression statistics.";
        uses l2vpn:ncs_rpc_notif_suppression-statistics-grp;
      }
    }
  }

  grouping ncs_rpc_notif_pw-traffic-statisticss-grp {
    description
      "Traffic statistics of PW.";
    container traffic-statistics {
      config false;
      description
        "Operational data of traffic statistics about PWs.";
      leaf in-traffic-rate {
        type uint64;
        description
          "Rate of traffic received by the PW.";
      }
      leaf out-traffic-rate {
        type uint64;
        description
          "Rate of traffic sent by the PW.";
      }
      leaf in-frame-rate {
        type uint64;
        description
          "Rate of frames received by the PW.";
      }
      leaf out-frame-rate {
        type uint64;
        description
          "Rate of frames sent by the PW.";
      }
      leaf in-bytes {
        type uint64;
        description
          "Number of bytes received by the PW.";
      }
      leaf out-bytes {
        type uint64;
        description
          "Number of bytes sent by the PW.";
      }
      leaf in-frames {
        type uint64;
        description
          "Number of frames received by the PW.";
      }
      leaf out-frames {
        type uint64;
        description
          "Number of frames sent by the PW.";
      }
      leaf in-unicast-frames {
        type uint64;
        description
          "Number of unicast frames received by the PW.";
      }
      leaf in-unicast-bytes {
        type uint64;
        description
          "Number of unicast bytes received by the PW.";
      }
      leaf in-multicast-frames {
        type uint64;
        description
          "Number of multicast frames received by the PW.";
      }
      leaf in-multicast-bytes {
        type uint64;
        description
          "Number of multicast bytes received by the PW.";
      }
      leaf in-broadcast-frames {
        type uint64;
        description
          "Number of broadcast frames received by the PW.";
      }
      leaf in-broadcast-bytes {
        type uint64;
        description
          "Number of broadcast bytes received by the PW.";
      }
      leaf out-unicast-frames {
        type uint64;
        description
          "Number of unicast frames sent by the PW.";
      }
      leaf out-unicast-bytes {
        type uint64;
        description
          "Number of unicast bytes sent by the PW.";
      }
      leaf out-multicast-frames {
        type uint64;
        description
          "Number of multicast frames sent by the PW.";
      }
      leaf out-multicast-bytes {
        type uint64;
        description
          "Number of multicast bytes sent by the PW.";
      }
      leaf out-broadcast-frames {
        type uint64;
        description
          "Number of broadcast frames sent by the PW.";
      }
      leaf out-broadcast-bytes {
        type uint64;
        description
          "Number of broadcast bytes sent by the PW.";
      }
      leaf in-discard-frames {
        type uint64;
        description
          "Number of frames received and then dropped by the PW.";
      }
      leaf reset-time {
        type string {
          length "1..60";
        }
        description
          "Time when statistics were cleared the last time.";
      }
    }
  }

  grouping live_ncs_spe-infos-type {
    description
      "Indicates the query list of the SPE information.";
    list spe {
      key "spe-pw-id spe-peer-ip";
      description
        "Operational data of the SPE on the path to the peer.";
      leaf spe-pw-id {
        type uint32 {
          range "0..4294967295";
        }
        description
          "List of PW IDs on the path traveled by a label mapping message.";
      }
      leaf spe-peer-ip {
        type inet:ipv4-address-no-zone;
        description
          "IP address of an SPE in the path to the peer.";
      }
    }
  }

  grouping live_ncs_l2vpn-reroute-policy-type {
    description
      "L2VPN protect group reroute policy class.";
    leaf policy {
      type live_ncs_l2vpn-reroute-mode;
      // NCS drop default statement
      description
        "Switchback policy.";
    }
    leaf delay-time {
      // NCS drop when statement
      type uint32 {
        range "10..10800";
      }
      units "s";
      // NCS drop default statement
      description
        "Delay for switching traffic back to the primary PW.";
    }
    leaf last-switchback-time {
      type string {
        length "1..60";
      }
      description
        "Last switchback time.";
    }
    leaf last-reroute-action {
      type string {
        length "1..100";
      }
      description
        "Last switchback action.";
    }
    leaf last-switchback-reason {
      type string {
        length "0..100";
      }
      description
        "Last switchback reason.";
    }
  }

  grouping live_ncs_l2vpn-dyn-bfd-para-type {
    description
      "Dynamic BFD parameters.";
    leaf min-rx-interval {
      type uint16 {
        range "0..65535";
      }
      units "ms";
      // NCS drop default statement
      description
        "Minimum receive interval.";
    }
    leaf min-tx-interval {
      type uint16 {
        range "0..65535";
      }
      units "ms";
      // NCS drop default statement
      description
        "Minimum transmit interval.";
    }
    leaf detect-multiplier {
      type uint16 {
        range "3..50";
      }
      // NCS drop default statement
      description
        "Detection multiplier.";
    }
  }

  grouping live_ncs_l2vpn-label-stacks-type {
    description
      "Label stack.";
    list label-stack {
      key "label-stack level";
      description
        "Operational data of the PW label stack.";
      leaf label-stack {
        type uint32 {
          range "1..4294967295";
        }
        description
          "Label stack.";
      }
      leaf level {
        type uint32 {
          range "1..4294967295";
        }
        description
          "Label level.";
      }
      leaf type {
        type string {
          length "0..20";
        }
        description
          "Label type.";
      }
      leaf label {
        type string {
          length "0..20";
        }
        description
          "Label value.";
      }
      leaf out-interface {
        type leafref {
          path "/ncs:devices/ncs:device/ncs:live-status/ifm:ifm/ifm:interfaces/ifm:interface/ifm:name" {
            tailf:xpath-root 3;
          }
        }
        description
          "Outbound interface name.";
      }
    }
  }

  grouping live_ncs_l2vpn-pw-down-causes-type {
    description
      "Indicates the down causes of the PW.";
    list down-cause {
      key "down-cause-index";
      description
        "Statistics of the down causes of PWs.";
      leaf down-cause-index {
        type uint32;
        description
          "Sequence number of the PW down cause.";
      }
      leaf down-cause {
        type string {
          length "0..100";
        }
        description
          "Indicates the down causes of the PW.";
      }
    }
  }

  grouping live_ncs_l2vpn-pw-status-changes-type {
    description
      "Indicates the reason and the time of the PW status that has changed.";
    list status-change {
      key "index";
      description
        "Statistics of the reason and the time of the PW status that has changed.";
      leaf index {
        type uint32;
        description
          "Sequence number of reasons that the PW status has changed.";
      }
      leaf timestamp {
        type string {
          length "0..60";
        }
        description
          "Indicates the time of the PW status has changed.";
      }
      leaf reason {
        type string {
          length "0..100";
        }
        description
          "Indicates the reason of the PW status has changed.";
      }
    }
  }

  grouping live_ncs_l2vpn-ccc-tdm-type {
    description
      "Tdm parameters of CCC instance.";
    leaf tdm-encapsulate-number {
      ext:dynamic-default;
      type uint32 {
        range "1..40";
      }
      description
        "Number of TDM frames encapsulated in a CESoPSN or SAToP packet in the TDMoPSN application.";
    }
    leaf jitter-buffer {
      ext:dynamic-default;
      type uint32 {
        range "1..64000";
      }
      units "us";
      description
        "Depth of the jitter buffer in the application of TDMoPSN.";
    }
    leaf rtp-header {
      type boolean;
      // NCS drop default statement
      description
        "Enable/disable the RTP header of transparently transmitted TDM frames.";
    }
    leaf idle-code {
      type yang:hex-string {
        length "1..2";
      }
      // NCS drop default statement
      description
        "Idle code that is filled when the jitter buffer underflow occurs.";
    }
  }

  grouping live_ncs_l2vpn-ccc-atm-type {
    description
      "L2VPN ATM class.";
    leaf max-atm-cells {
      type uint32 {
        range "1..28";
      }
      ext:dynamic-default;
      description
        "Maximum number of ATM cells to be encapsulated into a packet that can be received by a device.";
    }
    leaf atm-pack-overtime {
      type uint32 {
        range "100..10000";
      }
      units "us";
      ext:dynamic-default;
      description
        "Delay in encapsulating ATM cells into a packet.";
    }
  }

  grouping live_ncs_vpws-localccc-instance-grp {
    description
      "VPWS local CCC instance.";
    leaf encapsulation-type {
      ext:operation-exclude "update";
      type live_ncs_encapsulation-type;
      // NCS drop must statement
      // NCS drop mandatory statement
      description
        "Encapsulation type of a VPWS instance.";
    }
    container tdm-parameter {
      // NCS drop when statement
      description
        "Configure TDM parameters.";
      leaf tdm-encapsulate-number {
        type uint32 {
          range "1..40";
        }
        ext:dynamic-default;
        description
          "Number of TDM frames encapsulated in a CESoPSN or SAToP packet in the TDMoPSN application.";
      }
      leaf jitter-buffer {
        type uint32 {
          range "1..64000";
        }
        units "us";
        ext:dynamic-default;
        description
          "Depth of the jitter buffer in the application of TDMoPSN.";
      }
      leaf rtp-header {
        type boolean;
        // NCS drop default statement
        description
          "Enable/disable transparently transmission of TDM frames.";
      }
      leaf idle-code {
        type yang:hex-string {
          length "1..2";
        }
        // NCS drop default statement
        description
          "Idle code that is filled when the jitter buffer underflow occurs.";
      }
    }
    container atm-parameter {
      // NCS drop when statement
      description
        "Configure ATM parameters.";
      leaf max-atm-cells {
        type uint32 {
          range "1..28";
        }
        ext:dynamic-default;
        description
          "Maximum number of ATM cells to be encapsulated into a packet that can be received by a device.";
      }
      leaf atm-pack-overtime {
        type uint32 {
          range "100..10000";
        }
        units "us";
        ext:dynamic-default;
        description
          "Delay in encapsulating ATM cells into a packet.";
      }
    }
    container acs {
      description
        "List of information about all ACs.";
      list ac {
        ext:operation-exclude "update|delete";
        // NCS drop must statement
        key "interface-name";
        // NCS drop min-elements statement
        // NCS drop max-elements statement
        description
          "Configure information about an AC. AC information is displayed in a configuration order.";
        leaf interface-name {
          type leafref {
            path "/ncs:devices/ncs:device/ncs:live-status/ifm:ifm/ifm:interfaces/ifm:interface/ifm:name" {
              tailf:xpath-root 3;
            }
          }
          description
            "Name of an AC interface.";
        }
        leaf tagged {
          ext:operation-exclude "update|delete";
          // NCS drop when statement
          type boolean;
          ext:dynamic-default {
            ext:default-value "false" {
              // NCS drop when statement
              description
                "The default value is false when encapsulation-type is ethernet.";
            }
            ext:default-value "true" {
              // NCS drop when statement
              description
                "The default value is true when encapsulation-type is VLAN.";
            }
          }
          // NCS drop must statement
          description
            "Enable/disable the VLAN tag setting.";
        }
        leaf access-port {
          ext:operation-exclude "update|delete";
          // NCS drop when statement
          type boolean;
          // NCS drop must statement
          // NCS drop default statement
          description
            "Enable/disable the attribute that allows only untagged packets to pass through an interface.";
        }
        leaf trigger-interface-down {
          type boolean;
          // NCS drop must statement
          // NCS drop default statement
          description
            "Enable/disable remote interface shutdown-based association between the PW status and interface status.";
        }
        leaf state {
          type live_ncs_l2vpn-state;
          description
            "Status of an AC.";
        }
        leaf token-exceed {
          type boolean;
          // NCS drop default statement
          description
            "Indicates whether the number of AC tokens exceeds the maximum limit.";
        }
        container arp-entry {
          presence "Enable the ARP entry for AC.";
          description
            "Configure the ARP entry attribute used for IP interworking between PEs.";
          leaf local-ce-mac {
            type pub-type:live_ncs_mac-address;
            description
              "MAC address of the ethernet interface or sub-interface on a CE connected to the local AC interface. If MAC, IP, and broadcast addresses are all configured, these addresses take effect in the sequence of MAC address, IP address, and broadcast address.";
          }
          leaf local-ce-ip {
            type inet:ipv4-address-no-zone;
            description
              "IP address of the ethernet interface or sub-interface on a CE connected to the local AC interface.";
          }
          leaf local-ce-broadcast {
            type boolean;
            // NCS drop must statement
            // NCS drop default statement
            description
              "Enable/disable the broadcast function on a PE Ethernet interface connected to a CE.";
          }
          leaf remote-ce-ip {
            type inet:ipv4-address-no-zone;
            description
              "IP address of the remote CE connected to the local AC interface.";
          }
        }
        container ac-arps {
          description
            "Operational data of ARP information about all ACs.";
          uses live_ncs_ac-arp-grp;
        }
      }
    }
  }

  grouping live_ncs_vpws-remoteccc-instance-grp {
    description
      "VPWS remote CCC instance.";
    leaf encapsulation-type {
      ext:operation-exclude "update";
      ext:support-filter "true";
      type live_ncs_encapsulation-type;
      // NCS drop must statement
      // NCS drop mandatory statement
      description
        "Encapsulation type of a VPWS instance.";
    }
    container acs {
      description
        "List of information about all ACs.";
      list ac {
        ext:operation-exclude "update|delete";
        // NCS drop must statement
        key "interface-name";
        // NCS drop min-elements statement
        // NCS drop max-elements statement
        description
          "Configure information about an AC.";
        leaf interface-name {
          type leafref {
            path "/ncs:devices/ncs:device/ncs:live-status/ifm:ifm/ifm:interfaces/ifm:interface/ifm:name" {
              tailf:xpath-root 3;
            }
          }
          description
            "Name of an AC interface.";
        }
        leaf tagged {
          ext:operation-exclude "update|delete";
          // NCS drop when statement
          type boolean;
          ext:dynamic-default {
            ext:default-value "false" {
              // NCS drop when statement
              description
                "The default value is false when encapsulation-type is ethernet.";
            }
            ext:default-value "true" {
              // NCS drop when statement
              description
                "The default value is true when encapsulation-type is VLAN.";
            }
          }
          // NCS drop must statement
          description
            "Enable/disable the VLAN tag setting.";
        }
        leaf state {
          type live_ncs_l2vpn-state;
          description
            "Status of an AC.";
        }
        leaf token-exceed {
          type boolean;
          // NCS drop default statement
          description
            "Indicates whether the number of AC tokens exceeds the maximum limit.";
        }
        container arp-entry {
          presence "Enable the ARP entry for AC.";
          description
            "Configure the ARP entry attribute used for IP interworking between PEs.";
          leaf local-ce-mac {
            type pub-type:live_ncs_mac-address;
            description
              "MAC address of the Ethernet interface or sub-interface on a CE connected to the local AC interface. If MAC, IP, and broadcast addresses are all configured, these addresses take effect in the sequence of MAC address, IP address, and broadcast address.";
          }
          leaf local-ce-ip {
            type inet:ipv4-address-no-zone;
            description
              "IP address of the Ethernet interface or sub-interface on a CE connected to the local AC interface.";
          }
          leaf local-ce-broadcast {
            type boolean;
            // NCS drop must statement
            // NCS drop default statement
            description
              "Enable/disable broadcast on a PE Ethernet interface connected to a CE.";
          }
          leaf remote-ce-ip {
            type inet:ipv4-address-no-zone;
            description
              "IP address of the remote CE connected to the local AC interface.";
          }
        }
        container ac-arps {
          description
            "Operational data of ARP information about all ACs.";
          uses live_ncs_ac-arp-grp;
        }
      }
    }
    container pw {
      ext:operation-exclude "update|delete";
      // NCS drop must statement
      description
        "Configure a VPWS remote CCC PW.";
      leaf out-label {
        ext:operation-exclude "update";
        type uint32 {
          range "0..1048575";
        }
        // NCS drop mandatory statement
        description
          "Label for sending packets.";
      }
      leaf in-label {
        ext:operation-exclude "update";
        type uint32 {
          range "16..1048575";
        }
        // NCS drop mandatory statement
        description
          "Label for receiving packets.";
      }
      leaf control-word {
        ext:operation-exclude "update|delete";
        type live_ncs_l2vpn-control-word;
        // NCS drop must statement
        // NCS drop default statement
        description
          "Enable the control word function. The control word is usually used for TDM, ATM, and FR PWs.";
      }
      leaf out-interface-name {
        ext:operation-exclude "update|delete";
        type leafref {
          path "/ncs:devices/ncs:device/ncs:live-status/ifm:ifm/ifm:interfaces/ifm:interface/ifm:name" {
            tailf:xpath-root 3;
          }
        }
        description
          "Outbound interface.";
      }
      leaf next-hop {
        ext:operation-exclude "update|delete";
        type inet:ipv4-address-no-zone;
        description
          "Next hop.";
      }
    }
  }

  grouping live_ncs_vpws-swtich-instance-grp {
    description
      "VPWS switch instance.";
    leaf switch-type {
      ext:operation-exclude "update";
      type live_ncs_l2vpn-switch-type;
      // NCS drop mandatory statement
      description
        "Switch type of a VPWS switch instance.";
    }
    leaf encapsulation-type {
      type live_ncs_encapsulation-type;
      // NCS drop must statement
      // NCS drop mandatory statement
      description
        "Encapsulation type of a VPWS switch instance.";
    }
    leaf control-word-trans {
      type boolean;
      // NCS drop default statement
      description
        "Enable/disable the control word of a VPWS switching instance to be transparently transmitted.";
    }
    leaf control-word {
      // NCS drop when statement
      type live_ncs_l2vpn-control-word;
      // NCS drop must statement
      // NCS drop default statement
      description
        "Enable the control word function. The control word function is usually used for TDM, ATM, and FR PWs.";
    }
    leaf mtu {
      // NCS drop when statement
      type uint16 {
        range "46..9600";
      }
      // NCS drop default statement
      description
        "MTU of a VPWS switch instance.";
    }
    leaf bit-error-detection {
      // NCS drop when statement
      type boolean;
      // NCS drop default statement
      description
        "Enable/disable bit error detection on SPEs for an LDP MS-PW.";
    }
    leaf create-time {
      type string {
        length "1..80";
      }
      description
        "How long a VPWS switch instance has been created.";
    }
    leaf up-time {
      type string {
        length "1..80";
      }
      description
        "How long a VPWS switch instance has been in the up state. If a VPWS instance is in the down state, its VPWS instance up duration is 0.";
    }
    leaf last-change-time {
      type string {
        length "1..80";
      }
      description
        "How long the status of a VPWS switch instance stays unchanged since the last change time.";
    }
    container pws {
      description
        "List of VPWS PWs.";
      list pw {
        ext:operation-exclude "update|delete";
        // NCS drop must statement
        // NCS drop must statement
        key "role";
        unique "peer-ip";
        // NCS drop min-elements statement
        // NCS drop max-elements statement
        description
          "Configure a PW in a VPWS switching instance.";
        leaf role {
          type live_ncs_ms-pw-role-type;
          description
            "Role of a PW.";
        }
        leaf pw-id {
          ext:operation-exclude "update|delete";
          type uint32 {
            range "1..4294967295";
          }
          description
            "PW ID.";
        }
        leaf peer-ip {
          ext:operation-exclude "update|delete";
          type live_ncs_l2vpn-peer-address-type;
          description
            "IP address of a peer.";
        }
        leaf transmit-label {
          ext:operation-exclude "update|delete";
          // NCS drop when statement
          type uint32 {
            range "0..1048575";
          }
          description
            "Static label for sending packets.";
        }
        leaf receive-label {
          ext:operation-exclude "update|delete";
          // NCS drop when statement
          type uint32 {
            range "16..1048575";
          }
          description
            "Static label for receiving packets.";
        }
        leaf tunnel-policy {
          type string {
            length "1..39";
          }
          description
            "Name of a tunnel policy. If the tunnel policy name is not specified, the system uses the default tunnel policy. The default tunnel policy preferentially selects LSPs for packet transmission and the number of load-balancing tunnels is 1. If the tunnel policy name is specified but the corresponding tunnel policy does not exist, the system still uses the default tunnel policy.";
        }
        container flow-label {
          // NCS drop must statement
          presence "enbale flow label for pw";
          description
            "Enable/disable the flow label of a PW.";
          leaf ability {
            ext:operation-exclude "delete";
            // NCS drop when statement
            type live_ncs_flow-label-ability;
            // NCS drop must statement
            description
              "Flow label capability. The values of the ability node at both ends of a PW must be consistent.";
          }
          leaf oam-packet-pop {
            type boolean;
            // NCS drop default statement
            description
              "Enable/disable the function of popping out flow labels in the OAM packets.";
          }
        }
        container hard-pipe {
          // NCS drop when statement
          presence "Enable hard pipe for pw.";
          description
            "Enable/disable hard pipe.";
          leaf bandwidth {
            // NCS drop when statement
            type uint32 {
              range "16..4294967294";
            }
            units "kbit/s";
            // NCS drop mandatory statement
            description
              "Specify bandwidth value.";
          }
          leaf expand-ratio {
            type uint16 {
              range "0..10000";
            }
            // NCS drop default statement
            description
              "Specify the value of bandwidth expand ratio (%). As to CES service, expand ratio ranges from 0 to 10000. The other service, expand ratio ranges from 0 to 100.";
          }
        }
        container tdm-parameter {
          // NCS drop when statement
          description
            "Configure TDM parameters.";
          leaf tdm-encapsulate-number {
            // NCS drop when statement
            type uint32 {
              range "1..5000";
            }
            ext:dynamic-default;
            description
              "Number of TDM frames encapsulated in a CESoPSN or SAToP packet in the TDMoPSN application.";
          }
          leaf rtp-header {
            type live_ncs_l2vpn-rtp-header-type;
            // NCS drop default statement
            description
              "Add the RTP header to transparently transmitted TDM frames.";
          }
          leaf time-slot {
            // NCS drop when statement
            type uint32 {
              range "1..32";
            }
            description
              "Number of time slots on an interface.";
          }
        }
        container pw-info {
          description
            "Operational data of VPWS PW information.";
          leaf session-state {
            type live_ncs_l2vpn-state;
            description
              "Status of an LDP session between the endpoint devices of a VC.";
          }
          leaf pw-state {
            type live_ncs_l2vpn-pw-state;
            description
              "Status of a PW.";
          }
          leaf pw-id {
            type uint32;
            description
              "PW ID.";
          }
          leaf encapsulation-type {
            type live_ncs_encapsulation-type;
            description
              "Encapsulation type of a PW.";
          }
          leaf destination {
            type inet:ip-address-no-zone;
            description
              "Destination address, usually the LSR ID of a peer.";
          }
          leaf local-vc-label {
            type uint32;
            description
              "Local VC label.";
          }
          leaf remote-vc-label {
            type uint32;
            description
              "VC label on the remote end.";
          }
          leaf local-ac-oam {
            type live_ncs_l2vpn-state;
            description
              "OAM status of a local AC.";
          }
          leaf local-psn-oam {
            type live_ncs_l2vpn-state;
            description
              "PSN OAM status on the local end.";
          }
          leaf local-forward-state {
            type live_ncs_l2vpn-forward-state;
            description
              "Forwarding status of the local end.";
          }
          leaf remote-ac-oam {
            type live_ncs_l2vpn-state;
            description
              "OAM status on the remote end.";
          }
          leaf remote-psn-oam {
            type live_ncs_l2vpn-state;
            description
              "PSN OAM status on the remote end.";
          }
          leaf remote-forward-state {
            type live_ncs_l2vpn-forward-state;
            description
              "Forwarding status of the remote end.";
          }
          leaf local-vc-mtu {
            type uint32;
            description
              "MTU for a local VC.";
          }
          leaf remote-vc-mtu {
            type uint32;
            description
              "VC MTU on the remote end.";
          }
          leaf local-vccv {
            type string {
              length "0..40";
            }
            description
              "VCCV capability supported by the local end. By default, the LSP ping and BFD for the label alert mode can be used if the control word function is disabled. If the control word function is enabled, the LSP ping and BFD for both the label alert mode and control word mode can be used.";
          }
          leaf remote-vccv {
            type string {
              length "0..40";
            }
            description
              "VCCV capability supported by the remote end. By default, the LSP ping and BFD for the label alert mode can be used if the control word function is disabled. If the control word function is enabled, the LSP ping and BFD for both the label alert mode and control word mode can be used.";
          }
          leaf local-control-word {
            type live_ncs_l2vpn-control-word;
            description
              "Enable the control word function on the local end.";
          }
          leaf remote-control-word {
            type live_ncs_l2vpn-control-word;
            description
              "Enable the control word function on the remote end.";
          }
          leaf tunnel-policy {
            type string {
              length "1..39";
            }
            description
              "Name of a tunnel policy.";
          }
          leaf tunnel-count {
            type uint16;
            // NCS drop default statement
            description
              "Number of effective tunnels.";
          }
          leaf spe-count {
            type uint32 {
              range "0..4294967295";
            }
            // NCS drop default statement
            description
              "Number of SPEs in the path to the peer.";
          }
          leaf create-time {
            type string {
              length "1..80";
            }
            description
              "How long a PW has been created.";
          }
          leaf up-time {
            type string {
              length "1..80";
            }
            description
              "How long a PW has been in the up state. If a PW is in the down state, its PW up duration is 0.";
          }
          leaf last-change-time {
            type string {
              length "1..80";
            }
            description
              "How long the status of a PW has stayed unchanged since the last change time.";
          }
          leaf last-up-time {
            type string {
              length "1..80";
            }
            description
              "Date and time when a PW was up for the last time, for example, 2012/07/20 02:30:46.";
          }
          leaf total-up-time {
            type string {
              length "1..80";
            }
            description
              "Total up time of a PW.";
          }
          leaf c-key {
            type uint32;
            description
              "Customer key. Each CKey corresponds to a PW.";
          }
          leaf n-key {
            type uint32;
            description
              "Network key. Each NKey corresponds to a combination of the peer and tunnel policy.";
          }
          leaf remote-vccv-code {
            type pub-type:live_ncs_hex-binary;
            description
              "Remote VCCV code.";
          }
          leaf hard-pipe-bandwidth {
            type uint32 {
              range "16..4294967294";
            }
            units "kbit/s";
            description
              "Specify bandwidth value.";
          }
          leaf hard-pipe-expand-ratio {
            type string {
              length "0..7";
            }
            description
              "Specify the value of bandwidth expand ratio (%).";
          }
          leaf pw-token-exceed {
            type boolean;
            // NCS drop default statement
            description
              "Indicates whether the number of PW tokens exceeds the maximum limit.";
          }
          container spes {
            description
              "Operational data of SPEs on the path to the peer.";
            uses l2vpn:live_ncs_spe-infos-type;
          }
          container tunnels {
            description
              "List of VPWS PW tunnels.";
            list tunnel {
              key "tunnel-key";
              // NCS drop max-elements statement
              description
                "Operational data of tunnels.";
              leaf tunnel-key {
                type string {
                  length "0..21";
                }
                description
                  "Index of a public network tunnel.";
              }
              leaf tunnel-type {
                type live_ncs_l2vpn-tunnel-type;
                description
                  "Type of the tunnel used by the PW.";
              }
              leaf tunnel-name {
                type string {
                  length "0..64";
                }
                description
                  "Name of the tunnel used by the PW.";
              }
              leaf public-next-hop {
                type inet:ipv4-address-no-zone;
                description
                  "Next hop of a PW on the public network.";
              }
            }
          }
          container down-causes {
            description
              "Operational data of the down causes.";
            uses l2vpn:live_ncs_l2vpn-pw-down-causes-type;
          }
          container status-changes {
            description
              "Operational data of the reason and time.";
            uses l2vpn:live_ncs_l2vpn-pw-status-changes-type;
          }
        }
      }
    }
    container reliability {
      // NCS drop when statement
      description
        "Configure PW reliability.";
      leaf redundancy-mode {
        type live_ncs_pw-redundancy-mode;
        // NCS drop must statement
        // NCS drop default statement
        description
          "PW redundancy mode.";
      }
      leaf switchover {
        type boolean;
        // NCS drop default statement
        description
          "Enable/disable the PW switchover.";
      }
      container reroute {
        description
          "Configure a switchback policy list.";
        leaf reroute-policy {
          type live_ncs_l2vpn-reroute-mode;
          // NCS drop default statement
          description
            "Switchback policy.";
        }
        leaf delay-time {
          // NCS drop when statement
          type uint32 {
            range "10..10800";
          }
          units "s";
          // NCS drop default statement
          description
            "Delay for switching traffic back to the primary PW.";
        }
        leaf last-switchback-reason {
          type string {
            length "0..100";
          }
          description
            "Last switchback reason.";
        }
        leaf last-switchback-time {
          type string {
            length "1..60";
          }
          description
            "Last switchback time.";
        }
        leaf delay-residual {
          type uint32;
          units "s";
          description
            "Remaining delay time.";
        }
      }
    }
  }

  grouping live_ncs_vpws-bgp-instance-grp {
    description
      "VPWS BGP VPN instance connection.";
    leaf vpn-instance {
      type leafref {
        path "/ncs:devices/ncs:device/ncs:live-status/l2vpn/common/vpws-bgp-vpns/vpws-bgp-vpn/name" {
          tailf:xpath-root 3;
        }
      }
      // NCS drop mandatory statement
      description
        "VPWS BGP instance.";
    }
    leaf local-site {
      type leafref {
        path "/ncs:devices/ncs:device/ncs:live-status/l2vpn/common/vpws-bgp-vpns/vpws-bgp-vpn/sites/site/name" {
          tailf:xpath-root 3;
        }
      }
      // NCS drop mandatory statement
      description
        "Local site name.";
    }
    container acs {
      description
        "List of attachment circuits in a VPWS BGP VPN instance.";
      list ac {
        key "interface-name";
        // NCS drop min-elements statement
        // NCS drop max-elements statement
        description
          "Configure a connection attachment circuit.";
        leaf interface-name {
          type leafref {
            path "/ncs:devices/ncs:device/ncs:live-status/ifm:ifm/ifm:interfaces/ifm:interface/ifm:name" {
              tailf:xpath-root 3;
            }
          }
          description
            "VPWS BGP VPN instance connection attachment circuit interface name. The encapsulation type of this interface must be the same as that of the VPN instance. Otherwise, the PW cannot go Up.";
        }
        leaf tagged {
          // NCS drop when statement
          ext:operation-exclude "update|delete";
          type boolean;
          description
            "Enable/disable the attachment circuit tag of the VPWS BGP instance.";
          ext:dynamic-default;
        }
        leaf trigger-interface-down {
          type boolean;
          // NCS drop must statement
          // NCS drop default statement
          description
            "Enable/disable remote interface shutdown-based association between the PW status and interface status.";
        }
        leaf state {
          type live_ncs_l2vpn-state;
          description
            "Status of an AC interface.";
        }
        leaf token-exceed {
          type boolean;
          // NCS drop default statement
          description
            "Indicates whether the number of AC tokens exceeds the maximum limit.";
        }
      }
    }
    container pws {
      description
        "List of PWs.";
      list pw {
        key "remote-site-id";
        unique "role";
        // NCS drop min-elements statement
        description
          "Configure a PW.";
        leaf remote-site-id {
          type uint16 {
            range "0..65534";
          }
          // NCS drop must statement
          description
            "VPWS BGP VPN instance connection remote customer edge identifier.";
        }
        leaf role {
          ext:operation-exclude "update|delete";
          type live_ncs_pw-role-type;
          // NCS drop must statement
          // NCS drop default statement
          description
            "VPWS BGP VPN instance connection pseudo wire role. Configure a primary PW first. The PW role canot be changed.";
        }
        leaf tunnel-policy {
          type string {
            length "1..39";
          }
          description
            "VPWS BGP VPN instance connection tunnel policy name.";
        }
        leaf traffic-statistics-collection {
          type boolean;
          // NCS drop default statement
          description
            "Enable/disable connection traffic statistics collection of a VPWS BGP VPN instance.";
        }
        leaf manual-set-fault {
          type boolean;
          // NCS drop default statement
          description
            "Enable/disable the manual setting of faults in a VPWS BGP VPN instance connection.";
        }
        container bfd {
          // NCS drop when statement
          // NCS drop must statement
          presence "enable pw bfd.";
          description
            "Enable/disable BFD for PW in a VPWS BGP VPN instance.";
          uses live_ncs_l2vpn-dyn-bfd-para-type;
          leaf track-interface {
            type boolean;
            // NCS drop default statement
            description
              "Enable/disable BFD track interface state.";
          }
        }
        container pw-info {
          description
            "Operational data of VPWS BGP PW information.";
          leaf type {
            type live_ncs_vpws-bgp-pw-type;
            description
              "Indicates the type of the pw.";
          }
          leaf local-vc-state {
            type live_ncs_l2vpn-pw-state;
            description
              "Indicates the status of the local PW.";
          }
          leaf remote-vc-state {
            type live_ncs_l2vpn-pw-state;
            description
              "Indicates the status of the remote PW.";
          }
          leaf peer-ip {
            type inet:ipv4-address-no-zone;
            description
              "Indicates the LSR ID of the VC peer device.";
          }
          leaf local-vc-label {
            type uint32;
            description
              "Indicates the local VC label.";
          }
          leaf remote-vc-label {
            type uint32;
            description
              "Indicates the remote VC label.";
          }
          leaf ac-oam-state {
            type live_ncs_vpws-bgp-ac-oam-state;
            description
              "Indicates the OAM status of the AC.";
          }
          leaf bfd-state {
            type live_ncs_l2vpn-vpws-bfd-state;
            description
              "Indicates the status of the BFD for PW.";
          }
          leaf control-flag-bit {
            type live_ncs_control-flag-bits-type;
            description
              "Indicates the control flag.";
          }
          leaf pw-token-exceed {
            type boolean;
            // NCS drop default statement
            description
              "Indicates whether the number of PW tokens exceeds the maximum limit.";
          }
          container down-causes {
            description
              "Operational data of the down causes.";
            uses l2vpn:live_ncs_l2vpn-pw-down-causes-type;
          }
        }
        container tunnels {
          description
            "List of VPWS BGP PW tunnel info.";
          list tunnel {
            key "tunnel-key";
            // NCS drop max-elements statement
            description
              "Operational data of tunnels.";
            leaf tunnel-key {
              type string {
                length "0..21";
              }
              description
                "Index of a public network tunnel.";
            }
            leaf tunnel-type {
              type live_ncs_l2vpn-tunnel-type;
              description
                "Type of the tunnel used by the PW.";
            }
            leaf tunnel-name {
              type string {
                length "0..64";
              }
              description
                "Name of the tunnel used by the PW.";
            }
            leaf public-next-hop {
              type inet:ipv4-address-no-zone;
              description
                "Next hop of a PW on the public network.";
            }
          }
        }
        container traffic-statistics {
          description
            "Operational data of VPWS BGP PW traffic statistics.";
          leaf interface-name {
            type leafref {
              path "/ncs:devices/ncs:device/ncs:live-status/ifm:ifm/ifm:interfaces/ifm:interface/ifm:name" {
                tailf:xpath-root 3;
              }
            }
            description
              "The name of interface.";
          }
          leaf last-clear-time {
            type string {
              length "1..60";
            }
            description
              "Time when statistics are cleared for the last time.";
          }
          leaf input-bytes-rate {
            type uint64;
            description
              "Rate of traffic received on the PW.";
          }
          leaf input-packets-rate {
            type uint64;
            description
              "Rate of frames received on the PW.";
          }
          leaf output-bytes-rate {
            type uint64;
            description
              "Rate of traffic transmitted out of the PW.";
          }
          leaf output-packets-rate {
            type uint64;
            description
              "Rate of frames transmitted out of the PW.";
          }
          leaf input-bytes {
            type uint64;
            description
              "Number of bytes received on the PW.";
          }
          leaf input-packets {
            type uint64;
            description
              "Number of frames received on the PW.";
          }
          leaf output-bytes {
            type uint64;
            description
              "Number of bytes transmitted out of the PW.";
          }
          leaf output-packets {
            type uint64;
            description
              "Number of frames transmitted out of the PW.";
          }
        }
      }
    }
    container reliability {
      // NCS drop when statement
      description
        "Configure PW reliability.";
      leaf redundancy-mode {
        type live_ncs_pw-redundancy-mode;
        // NCS drop must statement
        // NCS drop default statement
        description
          "PW redundancy mode.";
      }
      leaf dual-receive {
        type boolean;
        // NCS drop default statement
        description
          "Enable/disable the receipt of both the primary and secondary PWs to receive packets.";
      }
      container reroute {
        description
          "Configure a switchback policy list.";
        leaf reroute-policy {
          type live_ncs_l2vpn-reroute-mode;
          // NCS drop default statement
          description
            "Switchback policy.";
        }
        leaf delay-time {
          // NCS drop when statement
          type uint32 {
            range "10..10800";
          }
          units "s";
          // NCS drop default statement
          description
            "Delay for switching traffic back to the primary PW.";
        }
        leaf resume-time {
          // NCS drop when statement
          type uint32 {
            range "0..600";
          }
          units "s";
          // NCS drop default statement
          description
            "Time after which the peer PE on the secondary PW is notified that the local PE has recovered. This parameter can be configured only in FRR mode.";
        }
        leaf last-switchback-reason {
          type string {
            length "0..100";
          }
          description
            "Last switchback reason.";
        }
        leaf last-switchback-time {
          type string {
            length "1..60";
          }
          description
            "Last switchback time.";
        }
        leaf delay-residual {
          type uint32;
          units "s";
          description
            "Remaining delay time.";
        }
        leaf resume-residual {
          type uint32;
          units "s";
          description
            "Remaining resume time.";
        }
      }
    }
    container oam-mapping {
      presence "enable AC OAM mapping";
      description
        "Enable/disable OAM mapping.";
      leaf type {
        type live_ncs_ac-oam-mapping-type;
        // NCS drop must statement
        // NCS drop mandatory statement
        description
          "VPWS attachment circuit OAM mapping type.";
      }
      leaf md-name {
        ext:operation-exclude "update|delete";
        // NCS drop when statement
        type string {
          length "1..43";
        }
        description
          "VPWS OAM mapping parameter md name.";
      }
      leaf ma-name {
        ext:operation-exclude "update|delete";
        // NCS drop when statement
        type string {
          length "1..43";
        }
        description
          "VPWS OAM mapping parameter ma name.";
      }
    }
  }

  grouping live_ncs_vpls-instance-grp {
    description
      "VPLS instance.";
    leaf member-discovery-mode {
      type live_ncs_l2vpn-vpls-vsi-mem-disc-type;
      // NCS drop default statement
      description
        "VPLS member discovery mode for a specified VSI.";
    }
    leaf work-mode {
      ext:operation-exclude "update";
      type live_ncs_vsi-work-mode;
      // NCS drop default statement
      description
        "Workmode of a VSI.";
    }
    leaf encapsulation-type {
      type live_ncs_l2vpn-vpls-encap-type;
      // NCS drop must statement
      // NCS drop default statement
      description
        "Encapsulation type of a VSI.";
    }
    leaf mtu {
      type uint16 {
        range "46..65535";
      }
      // NCS drop default statement
      description
        "VPLS MTU.";
    }
    leaf tunnel-policy {
      type string {
        length "1..39";
      }
      description
        "Name of a tunnel policy for a VSI. If the tunnel policy name is not specified, the system uses the default tunnel policy. The default tunnel policy preferentially selects LSPs for packet transmission and the number of load-balancing tunnels is 1. If the tunnel policy name is specified but the corresponding tunnel policy does not exist, the system still uses the default tunnel policy.";
    }
    leaf shutdown {
      type boolean;
      // NCS drop default statement
      description
        "Enable/disable the function of shutting down a specified VSI.";
    }
    leaf isolate-spoken {
      // NCS drop when statement
      type boolean;
      // NCS drop must statement
      // NCS drop default statement
      description
        "Enable/disable forwarding isolation between AC interfaces, between UPE PWs, and between ACs and UPE PWs in a VSI.";
    }
    leaf isolate-spoken-include-multicast {
      // NCS drop when statement
      type boolean;
      // NCS drop must statement
      // NCS drop default statement
      description
        "Enable/disable isolating forwarding between AC interfaces, between UPE PWs, and between ACs and UPE PWs in a VSI.";
    }
    leaf ignore-ac-state {
      type boolean;
      // NCS drop default statement
      description
        "Enable/disable the function for the VSI status not to be affected by changes in the AC status.";
    }
    leaf response-ac-state {
      // NCS drop when statement
      type boolean;
      // NCS drop default statement
      description
        "Enable/disable the function for the BD VSI status to be affected by changes in the BD AC status.";
    }
    leaf admin-vsi {
      type boolean;
      // NCS drop must statement
      // NCS drop default statement
      description
        "Enable/disable the function for the current service VSI to be configured as the mVSI.";
    }
    leaf track-admin-vsi {
      ext:operation-exclude "update|delete";
      // NCS drop when statement
      type string {
        length "1..31";
      }
      // NCS drop must statement
      description
        "Name of the mVSI to which a service VSI is bound.";
    }
    leaf unknown-unicast-action {
      // NCS drop when statement
      type live_ncs_l2vpn-vpls-unknow-frame-act;
      // NCS drop default statement
      description
        "Action taken to process unknown unicast frames.";
    }
    leaf unknown-multicast-action {
      // NCS drop when statement
      type live_ncs_l2vpn-vpls-unknow-frame-act;
      // NCS drop must statement
      // NCS drop default statement
      description
        "Action taken to process unknown multicast frames.";
    }
    leaf isolate-hub-ac-pw {
      // NCS drop when statement
      type boolean;
      // NCS drop must statement
      // NCS drop default statement
      description
        "Enable/disable forwarding isolation between hub ACs and PWs in a VSI.";
    }
    leaf p2p-vsi {
      // NCS drop when statement
      type boolean;
      // NCS drop must statement
      // NCS drop default statement
      description
        "Enable/disable the P2P VSI.";
    }
    leaf traffic-statistics-collection {
      // NCS drop when statement
      type boolean;
      // NCS drop default statement
      description
        "Enable/disable VSI QoS traffic statistics collection.";
    }
    leaf mac-remove-mode {
      type live_ncs_mac-remove-type;
      // NCS drop must statement
      // NCS drop default statement
      description
        "Local MAC remove mode.";
    }
    leaf mac-learn {
      // NCS drop when statement
      type boolean;
      // NCS drop must statement
      // NCS drop default statement
      description
        "Enable/disable the function for a VSI to learn MAC addresses.";
    }
    leaf mac-learn-style {
      // NCS drop when statement
      type live_ncs_l2vpn-mac-learn-style;
      // NCS drop must statement
      // NCS drop default statement
      description
        "MAC address learning style of PWs.";
    }
    leaf mac-age-time {
      // NCS drop when statement
      type uint32 {
        range "0 | 60..1000000";
      }
      units "s";
      description
        "MAC address aging timer that sets the aging time of MAC addresses.";
    }
    leaf local-mac-age-time {
      // NCS drop when statement
      type uint32 {
        range "0 | 60..1000000";
      }
      units "s";
      description
        "Local MAC address aging timer that sets the aging time of MAC addresses.";
    }
    leaf remote-mac-age-time {
      // NCS drop when statement
      type uint32 {
        range "0 | 60..1000000";
      }
      units "s";
      description
        "Remote MAC address aging timer that sets the aging time of MAC addresses.";
    }
    leaf mac-withdraw {
      type boolean;
      // NCS drop default statement
      description
        "Enable/disable the function for a VSI to delete the local MAC address and notifies all remote peers of the deletion when an AC or a UPE fault occurs and the VSI remains up.";
    }
    leaf interface-change-mac-withdraw {
      // NCS drop when statement
      type boolean;
      // NCS drop default statement
      description
        "Enable/disable the function for PEs to send LDP MAC withdraw messages to all peers when the status of the AC interface bound to the VSI changes.";
    }
    leaf interface-change-mac-withdraw-type {
      type live_ncs_interface-change-withdraw-type;
      // NCS drop must statement
      // NCS drop default statement
      description
        "Specify the status change type for a VSI AC interface.";
    }
    leaf bd-pwtag-mac-withdraw {
      // NCS drop when statement
      type boolean;
      // NCS drop default statement
      description
        "Enable/disable the function for LDP MAC withdraw messages to carry PW tag corresponding to the VSI bound to the bridge domain. This node can be configured only when the VSI works in BD mode.";
    }
    leaf bd-down-mac-withdraw {
      // NCS drop when statement
      type boolean;
      // NCS drop default statement
      description
        "Enable/disable the function for PEs to send LDP MAC withdraw messages to all peers when BD goes down. This node can be configured only when the VSI works in BD mode.";
    }
    leaf propagate-mac-withdraw {
      // NCS drop when statement
      type boolean;
      // NCS drop default statement
      description
        "Enable/disable the function for a PE to propagate LDP MAC withdraw messages to other peers after receiving the message from a remote peer.";
    }
    leaf mac-flush-rfc-compatible {
      // NCS drop when statement
      type boolean;
      // NCS drop default statement
      description
        "Enable/disable the transmission of standard MAC-flush message when the PW status changes.";
    }
    leaf vrrp-mac-withdraw-retry {
      type uint16 {
        range "0..60";
      }
      // NCS drop default statement
      description
        "VRRP backup Mac withdraw retry.";
    }
    leaf token-exceed {
      type boolean;
      // NCS drop default statement
      description
        "Indicates whether the number of VSI tokens exceeds the maximum limit.";
    }
    leaf ac-count {
      type uint32;
      description
        "Total number of ACs in a VSI.";
    }
    leaf create-time {
      type string {
        length "1..60";
      }
      description
        "Time when a VSI was created.";
    }
    leaf ignore-ac-state-effect {
      type boolean;
      // NCS drop default statement
      description
        "Configure the VSI status not to be affected by changes in the AC status. By default, the VSI status changes according to the AC status.";
    }
    container etree {
      // NCS drop when statement
      // NCS drop must statement
      presence "Enable ethernet tree.";
      description
        "Enable/disable vpls ethernet tree.";
      leaf static {
        type boolean;
        // NCS drop must statement
        // NCS drop default statement
        description
          "Enable/disable static mode.";
      }
      leaf root-vlan {
        type uint16 {
          range "1..4094";
        }
        description
          "Specify root VLAN id.";
      }
      leaf leaf-vlan {
        type uint16 {
          range "1..4094";
        }
        description
          "Specify leaf VLAN id.";
      }
    }
    container ldp-signaling {
      presence "Label Distribution Protocol (LDP) signaling.";
      description
        "Enable/disable Label Distribution Protocol (LDP) signaling.";
      leaf vsi-id {
        ext:operation-exclude "update";
        type uint64 {
          range "1..4294967295";
        }
        // NCS drop must statement
        // NCS drop must statement
        // NCS drop must statement
        description
          "VPLS LDP VSI ID. Can not be modified after configuration.";
      }
      leaf traffic-statistics-collection {
        // NCS drop when statement
        type boolean;
        // NCS drop must statement
        // NCS drop default statement
        description
          "Enable/disable traffic statistics collection.";
      }
      leaf control-word {
        type live_ncs_l2vpn-control-word;
        // NCS drop must statement
        // NCS drop default statement
        description
          "Enable the control word feature. The control word feature is usually used for TDM, ATM, and FR PWs.";
      }
      leaf hard-pipe {
        type boolean;
        // NCS drop must statement
        // NCS drop default statement
        description
          "Enable/disable hard pipe.";
      }
      leaf mac-withdraw {
        type boolean;
        // NCS drop must statement
        // NCS drop default statement
        description
          "Enable/disable the function for a VSI to delete the local MAC address and notify all remote peers of the deletion when an AC or a UPE fault occurs and the VSI remains up.";
      }
      leaf interface-change-mac-withdraw {
        type boolean;
        // NCS drop must statement
        // NCS drop default statement
        description
          "Enable/disable the function for PEs to send LDP MAC withdraw messages to all peers when the status of the AC interface bound to the VSI changes.";
      }
      leaf interface-change-mac-withdraw-type {
        type live_ncs_interface-change-withdraw-type;
        // NCS drop must statement
        // NCS drop default statement
        description
          "Specify the status change type for a VSI AC interface.";
      }
      leaf upe-upe-mac-withdraw {
        type boolean;
        // NCS drop must statement
        // NCS drop default statement
        description
          "Enable/disable the function for an NPE to forward the LDP MAC withdraw messages received from a UPE to other UPEs.";
      }
      leaf upe-npe-mac-withdraw {
        type boolean;
        // NCS drop must statement
        // NCS drop default statement
        description
          "Enable/disable the function for an NPE to forward the LDP MAC withdraw messages received from a UPE to other NPEs.";
      }
      leaf npe-upe-mac-withdraw {
        type boolean;
        // NCS drop must statement
        // NCS drop default statement
        description
          "Enable/disable the function for an NPE to forward the LDP MAC withdraw messages received from another NPE to UPEs.";
      }
      container flow-label {
        presence "enable flow-label for ldp signaling pws.";
        description
          "Enable/disable flow label capability of a PW.";
        leaf ability {
          type live_ncs_flow-label-ability;
          // NCS drop must statement
          // NCS drop mandatory statement
          description
            "Enable/disable flow label capability.";
        }
        leaf static {
          type boolean;
          // NCS drop default statement
          description
            "Enable/disable the static flow label function.";
        }
      }
      container pws {
        // NCS drop when statement
        description
          "List of VPLS PWs.";
        list pw {
          key "peer-ip negotiation-vc-id encapsulation-type";
          description
            "Configure VPLS PWs.";
          leaf peer-ip {
            type inet:ipv4-address-no-zone;
            description
              "Peer IP address. The loopback IP address of a peer is usually used as the peer IP address.";
          }
          leaf negotiation-vc-id {
            type uint32 {
              range "1..4294967295";
            }
            description
              "PW ID used to uniquely identify a VC. The PW ID is usually used when both ends need to communicate but the VSI IDs on both ends are different.";
          }
          leaf encapsulation-type {
            type live_ncs_l2vpn-vpls-ldp-pw-encap-type;
            description
              "Encapsulation type of a VPLS PW. 'unsupport' indicates that the encapsulation type of a VSI is inherited.";
          }
          leaf role {
            ext:operation-exclude "update|delete";
            type live_ncs_vpls-pw-role-type;
            // NCS drop must statement
            // NCS drop default statement
            description
              "Role of a PW, either primary or secondary. Configure a primary PW first.";
          }
          leaf name {
            ext:operation-exclude "update";
            type string {
              length "1..15";
            }
            description
              "PW name.";
          }
          leaf signal-type {
            ext:operation-exclude "update|delete";
            type live_ncs_pw-signal-type;
            // NCS drop must statement
            // NCS drop must statement
            // NCS drop must statement
            // NCS drop must statement
            // NCS drop default statement
            description
              "PW type, either dynamic or static.";
          }
          leaf transmit-label {
            ext:operation-exclude "update|delete";
            // NCS drop when statement
            type uint32 {
              range "0..1048575";
            }
            description
              "Label for sending packets.";
          }
          leaf receive-label {
            ext:operation-exclude "update|delete";
            // NCS drop when statement
            type uint32 {
              range "16..1048575";
            }
            description
              "Label for receiving packets.";
          }
          leaf control-word {
            // NCS drop when statement
            type live_ncs_l2vpn-control-word;
            // NCS drop default statement
            description
              "Enable the control word function.";
          }
          leaf vccv {
            // NCS drop when statement
            type boolean;
            // NCS drop default statement
            description
              "Enable/disable virtual circuit connectivity verification capability. VCCV supports two modes: control word and label alert.";
          }
          leaf ignore-standby {
            ext:operation-exclude "update|delete";
            type boolean;
            // NCS drop default statement
            description
              "Enable/disable the function for the created PW to ignore the standby state sent from the peer device.";
          }
          leaf upe {
            ext:operation-exclude "update|delete";
            type boolean;
            // NCS drop default statement
            description
              "Enable/disable the peer device as a UPE.";
          }
          leaf tunnel-policy {
            type string {
              length "1..39";
            }
            description
              "Name of the tunnel policy for a PW.";
          }
          leaf traffic-statistics-collection {
            type live_ncs_l2vpn-vpls-traffic-statistics-enable-type;
            // NCS drop must statement
            // NCS drop default statement
            description
              "Enable the function to collect traffic statistics.";
          }
          leaf track-hub-pw {
            // NCS drop when statement
            type boolean;
            // NCS drop must statement
            // NCS drop default statement
            description
              "Enable/disable the function for the spoke PW to track the hub PW. If a PW is not a spoke PW, it cannot track the hub PW.";
          }
          leaf ignore-stp-loop-check {
            // NCS drop when statement
            type boolean;
            // NCS drop default statement
            description
              "Enable/disable the function of ignoring STP loops.";
          }
          leaf hard-pipe-bandwidth {
            ext:operation-exclude "delete";
            // NCS drop when statement
            type uint32 {
              range "16..4294967294";
            }
            units "kbit/s";
            description
              "Specify bandwidth value.";
          }
          leaf hard-pipe-burst-time {
            ext:operation-exclude "delete";
            // NCS drop when statement
            type uint32 {
              range "100..5000";
            }
            units "us";
            // NCS drop default statement
            description
              "Burst time.";
          }
          leaf status-code-change-flush-mac-disable {
            // NCS drop when statement
            type boolean;
            // NCS drop default statement
            description
              "Enable/disable the function of flushing MAC when status code change.";
          }
          leaf ac-mode {
            ext:operation-exclude "update|delete";
            // NCS drop when statement
            type boolean;
            // NCS drop default statement
            description
              "Enable/disable the AC mode.";
          }
          leaf etree-mode {
            // NCS drop when statement
            type live_ncs_etree-work-mode;
            // NCS drop default statement
            description
              "Specify e-tree work mode.";
          }
          leaf etree-leaf {
            // NCS drop when statement
            type boolean;
            // NCS drop default statement
            description
              "Enable/disable e-tree leaf.";
          }
          container flow-label {
            // NCS drop when statement
            presence "enable flow label";
            description
              "Enable/disable the flow label capability of a PW.";
            leaf ability {
              type live_ncs_flow-label-ability;
              // NCS drop must statement
              // NCS drop mandatory statement
              description
                "Flow label capability.";
            }
            leaf static {
              type boolean;
              // NCS drop must statement
              // NCS drop default statement
              description
                "Enable/disable the static flow label function.";
            }
          }
          container bfd {
            // NCS drop when statement
            presence "enable vpls ldp pw bfd.";
            description
              "Enable/disable BFD.";
            leaf min-rx-interval {
              type uint16 {
                range "0..65535";
              }
              units "ms";
              // NCS drop default statement
              description
                "Minimum receive interval.";
            }
            leaf min-tx-interval {
              type uint16 {
                range "0..65535";
              }
              units "ms";
              // NCS drop default statement
              description
                "Minimum transmit interval.";
            }
            leaf detect-multiplier {
              type uint16 {
                range "3..50";
              }
              // NCS drop default statement
              description
                "Detection multiplier.";
            }
            leaf option-tlv {
              type boolean;
              // NCS drop default statement
              description
                "Enable/disable BFD detection with options.";
            }
          }
          container pw-info {
            description
              "Operational data of VPLS LDP PW information.";
            leaf peer-ip {
              type inet:ipv4-address-no-zone;
              description
                "Peer IP address.";
            }
            leaf negotiation-vc-id {
              type uint32;
              description
                "PW ID used to uniquely identify a VC. The PW ID is usually used when both ends need to communicate but the VSI IDs on both ends are different.";
            }
            leaf pw-type {
              type live_ncs_l2vpn-vpls-pw-type;
              description
                "PW type, which can be label, QinQ, or MEHVPLS.";
            }
            leaf session-state {
              type live_ncs_l2vpn-state;
              description
                "Status of the session between the local end and its peer. The value is either up or down. This item is displayed only when the VPLS type is Martini.";
            }
            leaf pw-state {
              type live_ncs_l2vpn-pw-state;
              description
                "Current PW status.";
            }
            leaf local-vc-label {
              type uint32;
              description
                "VC label allocated by the local device.";
            }
            leaf remote-vc-label {
              type uint32;
              description
                "VC label allocated by the peer.";
            }
            leaf remote-control-word {
              type live_ncs_l2vpn-control-word;
              description
                "Enable the control word function on the remote end.";
            }
            leaf tunnel-policy {
              type string {
                length "1..39";
              }
              description
                "Name of the tunnel policy for a PW.";
            }
            leaf last-up-time {
              type string {
                length "1..80";
              }
              description
                "Date and time when a PW was up for the last time, for example, 2012/07/20 02:30:46.";
            }
            leaf total-up-time {
              type string {
                length "1..80";
              }
              description
                "Total up time of the PW.";
            }
            leaf c-key {
              type uint32;
              description
                "Customer key. Each CKey corresponds to a PW.";
            }
            leaf n-key {
              type uint32;
              description
                "Network key. Each NKey corresponds to a combination of the peer and tunnel policy.";
            }
            leaf spe-count {
              type uint32 {
                range "0..4294967295";
              }
              description
                "Number of SPEs in the path to the peer.";
            }
            leaf stp-enable {
              type boolean;
              description
                "Enable STP for PW.";
            }
            leaf mac-flapping-state {
              type live_ncs_pw-block-status;
              description
                "MAC flapping information.";
            }
            leaf pw-index {
              type uint32;
              description
                "PW index.";
            }
            leaf remote-group-id {
              type uint32;
              description
                "ID of a remote PW group.";
            }
            leaf remote-mtu {
              type uint32;
              description
                "MTU of the remote VSI.";
            }
            leaf remote-state-code {
              type live_ncs_l2vpn-vpls-ldp-pw-state-code;
              description
                "Status code information on the remote end.";
            }
            leaf received-flow-label {
              type live_ncs_flow-label-ability;
              description
                "Received flow label.";
            }
            leaf negotiated-flow-label {
              type live_ncs_flow-label-ability;
              description
                "Negotiated flow label.";
            }
            leaf remote-vccv-code {
              type pub-type:live_ncs_hex-binary;
              description
                "Remote VCCV code.";
            }
            leaf bfd-enable {
              type boolean;
              description
                "Enable BFD.";
            }
            leaf bfd-state {
              type live_ncs_l2vpn-vpls-pw-bfd-state;
              description
                "BFD status.";
            }
            leaf bfd-session-index {
              // NCS drop when statement
              type uint32;
              description
                "BFD index.";
            }
            leaf dynamic-bfd-session {
              type boolean;
              description
                "Enable dynamic BFD.";
            }
            leaf bfd-for-pw {
              // NCS drop when statement
              type boolean;
              description
                "Dynamic BFD session status.";
            }
            leaf block-status {
              type live_ncs_pw-block-status;
              description
                "Specifies whether a PW is blocked. If the PW is blocked, it cannot receive or transmit services.";
            }
            leaf pw-token-exceed {
              type boolean;
              // NCS drop default statement
              description
                "Indicates whether the number of PW tokens exceeds the maximum limit.";
            }
            container tunnels {
              description
                "List of VPLS LDP PW tunnels.";
              list tunnel {
                key "tunnel-key";
                // NCS drop max-elements statement
                description
                  "Operational data of VPLS LDP PW tunnels.";
                leaf tunnel-key {
                  type string {
                    length "0..21";
                  }
                  description
                    "Tunnel ID in hexadecimal notation that is assigned by the system.";
                }
                leaf tunnel-type {
                  type live_ncs_l2vpn-tunnel-type;
                  description
                    "Type of a tunnel.";
                }
                leaf out-interface {
                  type string {
                    length "0..257";
                  }
                  description
                    "Outbound interface of a PW.";
                }
                leaf tunnel-name {
                  type string {
                    length "0..64";
                  }
                  description
                    "Name of the tunnel used by the PW.";
                }
                leaf public-next-hop {
                  type inet:ipv4-address-no-zone;
                  description
                    "Public next hop of a PW.";
                }
              }
            }
            container spes {
              description
                "Operational data of SPEs on the path to the peer.";
              uses l2vpn:live_ncs_spe-infos-type;
            }
            container label-stacks {
              description
                "Operational data of PW label stacks.";
              uses l2vpn:live_ncs_l2vpn-label-stacks-type;
            }
            container down-causes {
              description
                "Operational data of the down causes.";
              uses l2vpn:live_ncs_l2vpn-pw-down-causes-type;
            }
            container status-changes {
              description
                "Operational data of the reason and time.";
              uses l2vpn:live_ncs_l2vpn-pw-status-changes-type;
            }
          }
          uses l2vpn:live_ncs_suppression-statisticss-grp;
          uses l2vpn:live_ncs_pw-traffic-statisticss-grp;
          container hard-pipe-traffic-statistics {
            description
              "Operational data of traffic statistics about VPLS LDP PW HardPipe.";
            leaf last-clear-time {
              type string {
                length "1..60";
              }
              description
                "Time when statistics are cleared for the last time.";
            }
            leaf pass-packets-rate {
              type uint64;
              description
                "The last 300 seconds pass packets rate.";
            }
            leaf pass-bytes-rate {
              type uint64;
              description
                "The last 300 seconds pass bytes rate.";
            }
            leaf discard-packets-rate {
              type uint64;
              description
                "The last 300 seconds discard packets rate.";
            }
            leaf discard-bytes-rate {
              type uint64;
              description
                "The last 300 seconds discard bytes rate.";
            }
            leaf pass-packets {
              type uint64;
              description
                "Number of pass packets in the last 300 seconds.";
            }
            leaf pass-bytes {
              type uint64;
              description
                "Number of pass bytes in the last 300 seconds.";
            }
            leaf drop-packets {
              type uint64;
              description
                "Number of discard packets in the last 300 seconds.";
            }
            leaf drop-bytes {
              type uint64;
              description
                "Number of discard bytes in the last 300 seconds.";
            }
          }
        }
      }
      container redundancy-protect-groups {
        // NCS drop when statement
        description
          "List of VPLS PW protection groups.";
        list redundancy-protect-group {
          key "name";
          // NCS drop max-elements statement
          description
            "Configure VPLS PW protection groups.";
          leaf name {
            type live_ncs_l2vpn-protect-group-name;
            description
              "Name of a PW protection group. The name is a string of case-sensitive characters.";
          }
          leaf protect-mode {
            type live_ncs_vpls-redundancy-mode;
            // NCS drop default statement
            description
              "Switching mode of the PW protection group.";
          }
          leaf dual-receive {
            // NCS drop when statement
            type boolean;
            // NCS drop default statement
            description
              "Enable/disable the receipt of both the primary and secondary PWs.";
          }
          leaf holdoff {
            // NCS drop when statement
            type uint16 {
              range "1..180";
            }
            units "s";
            description
              "Hold time for traffic switching.";
          }
          container reroute-policy {
            // NCS drop when statement
            description
              "Configure a switchback policy.";
            uses l2vpn:live_ncs_l2vpn-reroute-policy-type;
          }
          container pw-members {
            // NCS drop when statement
            description
              "List of PW members in a protection group.";
            list pw-member {
              // NCS drop must statement
              key "peer-ip negotiation-vc-id encapsulation-type";
              unique "preference";
              // NCS drop max-elements statement
              description
                "Configure PW members in a protection group.";
              leaf peer-ip {
                type inet:ipv4-address-no-zone;
                description
                  "Peer IP address. The loopback IP address of a peer is usually used as the peer IP address.";
              }
              leaf negotiation-vc-id {
                type uint32 {
                  range "1..4294967295";
                }
                description
                  "PW ID used to uniquely identify a VC. The PW ID is usually used when both ends need to communicate but the VSI IDs on both ends are different.";
              }
              leaf encapsulation-type {
                type live_ncs_l2vpn-vpls-ldp-pw-encap-type;
                description
                  "Encapsulate type.";
              }
              leaf preference {
                type uint32 {
                  range "1..32";
                }
                // NCS drop mandatory statement
                description
                  "Priority of a PW in the PW protection group.";
              }
              leaf role {
                type live_ncs_l2vpn-backup-mode;
                description
                  "Primary/secondary status of a PW.";
              }
              leaf active-state {
                type boolean;
                // NCS drop default statement
                description
                  "Whether an interface is active.";
              }
            }
          }
          container historys {
            description
              "Operational data of historical switching information of PW protection groups.";
            uses l2vpn:live_ncs_l2vpn-protect-group-historys-type;
          }
        }
      }
      container traffic-statistics {
        description
          "Operational data of traffic statistics.";
        leaf last-cleared {
          type string {
            length "1..60";
          }
          description
            "Time when traffic statistics were cleared the last time.";
        }
        leaf in-packets-rate {
          type uint64;
          description
            "Rate of packets received.";
        }
        leaf out-packets-rate {
          type uint64;
          description
            "Rate of packets sent.";
        }
        leaf in-packets {
          type uint64;
          description
            "Number of packets received.";
        }
        leaf out-packets {
          type uint64;
          description
            "Number of packets sent.";
        }
        leaf in-unicast-packets {
          type uint64;
          description
            "Number of unicast packets received.";
        }
        leaf in-multicast-packets {
          type uint64;
          description
            "Number of multicast packets received.";
        }
        leaf in-drop-packets {
          type uint64;
          description
            "Number of packets received and then discarded.";
        }
        leaf out-unicast-packets {
          type uint64;
          description
            "Number of unicast packets sent.";
        }
        leaf out-multicast-packets {
          type uint64;
          description
            "Number of multicast packets sent.";
        }
      }
    }
    container bgp-signaling {
      // NCS drop when statement
      // NCS drop must statement
      // NCS drop must statement
      presence "Container for bgp protocol vpls instance.";
      description
        "Enable/disable BGP VSIs.";
      leaf route-distinguisher {
        type string {
          length "3..21";
        }
        description
          "Route distinguisher.";
      }
      leaf encapsulation-rfc4761-compatible {
        type boolean;
        // NCS drop default statement
        description
          "Enable/disable the function of changing an encapsulation type.";
      }
      leaf encapsulation-vpls-family-compatible {
        type boolean;
        // NCS drop default statement
        description
          "Enable/disable the function of changing an encapsulation type to private mode.";
      }
      leaf mtu-negotiate-disable {
        type boolean;
        // NCS drop default statement
        description
          "Enable/disable the function of ignoring MTU match between local VSI and remote VSI. The default implementation is match.";
      }
      leaf control-word {
        type live_ncs_l2vpn-control-word;
        // NCS drop must statement
        // NCS drop default statement
        description
          "Enable the control word feature. The control word feature is usually used for TDM, ATM, and FR PWs.";
      }
      leaf auto-route-distinguisher {
        type string {
          length "3..21";
        }
        description
          "Automatic route distinguisher (RD). If no RD is configured for an L2VPN instance, you can specify an IPv4 address using the rd-ip parameter, based on which an RD is automatically generated in the format of 32-bit prefix IP address:index, for example, 192.168.122.15:1. An index is an integer automatically allocated by the system and ranges from 1 to 65535.Each L2VPN instance must use a unique RD.";
      }
      container sites {
        description
          "List of BGP sites.";
        list site {
          // NCS drop must statement
          key "site-id";
          // NCS drop max-elements statement
          description
            "Configure BGP sites.";
          leaf site-id {
            type uint32 {
              range "0..65534";
            }
            description
              "BGP site ID.";
          }
          leaf range {
            type uint32 {
              range "1..65535";
            }
            // NCS drop default statement
            description
              "BGP site range. Cannot decrease site range.";
          }
          leaf default-offset {
            ext:operation-exclude "update|delete";
            type uint16 {
              range "0..1";
            }
            // NCS drop default statement
            description
              "The default offset of BGP site. The value of this node cannot be modified or deleted after being set.";
          }
        }
      }
      container vpn-targets {
        description
          "List of VPN targets.";
        list vpn-target {
          key "rt-value rt-type";
          // NCS drop max-elements statement
          description
            "Configure VPN targets.";
          leaf rt-value {
            type string {
              length "3..21";
            }
            description
              "Route target. The format of an RT can be:
               - 16-bit AS number:32-bit user-defined number, for example, 1:3. An AS number ranges from 0 to 65535, and a user-defined number ranges from 0 to 4294967295. The AS number and user-defined number cannot be both 0s. This means that the RT cannot be 0:0.
               - Integral 4-byte AS number:2-byte user-defined number, for example, 65537:3. An AS number ranges from 65536 to 4294967295. A user-defined number ranges from 0 to 65535. The AS number and user-defined number cannot be both 0s. This means that the RT cannot be 0:0.
               - 32-bit IP address:16-bit user-defined number, for example: 192.168.122.15:1. The IP address ranges from 0.0.0.0 to 255.255.255.255, and the user-defined number ranges from 0 to 65535.
               - 32-bit AS number:16-bit user-defined number, for example, 10.11:3. An AS number ranges from 0.0 to 65535.65535, and a user-defined number ranges from 0 to 65535. The AS number and user-defined number cannot be both 0s. This means that the RT cannot be 0.0:0.";
          }
          leaf rt-type {
            type live_ncs_vpn-rt-type;
            description
              "RT type, which can be:
               - export-extcommunity: specifies the value of the extended community attribute of the route from an outbound interface to the destination VPN.
               - import-extcommunity: receives routes that carry the specified extended community attribute value.";
          }
        }
      }
      container flow-label {
        presence "enable flow-label for bgp signaling pws.";
        description
          "Enable/disable flow label capability of a PW.";
        leaf ability {
          type live_ncs_flow-label-ability;
          // NCS drop must statement
          // NCS drop mandatory statement
          description
            "Flow label capability.";
        }
        leaf static {
          type boolean;
          // NCS drop default statement
          description
            "Enable/disable the static flow label function.";
        }
      }
      container pws {
        description
          "List of VPLS BGP PWs.";
        list pw {
          // NCS drop must statement
          key "peer-ip remote-site-id";
          unique "name";
          description
            "Configure VPLS BGP PWs.";
          leaf peer-ip {
            type inet:ipv4-address-no-zone;
            description
              "Peer IP address.";
          }
          leaf remote-site-id {
            type uint32 {
              range "0..65534";
            }
            description
              "Remote BGP site ID.";
          }
          leaf name {
            type string {
              length "1..15";
            }
            description
              "PW name.";
          }
          leaf traffic-statistics-collection {
            type boolean;
            // NCS drop must statement
            // NCS drop default statement
            description
              "Enable/disable the function to collect traffic statistics.";
          }
          uses l2vpn:live_ncs_suppression-statisticss-grp;
        }
      }
      container local-label-blocks {
        description
          "Operational data of local label blocks.";
        uses live_ncs_bgp-local-label-block-grp;
      }
      container remote-label-blocks {
        description
          "Operational data of remote label blocks.";
        uses live_ncs_bgp-remote-label-block-grp;
      }
      container pw-infos {
        description
          "List of BGP PWs.";
        list pw-info {
          key "site-id offset";
          description
            "Operational data of the BGP PW list.";
          leaf site-id {
            type uint32 {
              range "0..65534";
            }
            description
              "BGP site ID.";
          }
          leaf offset {
            type uint16;
            description
              "BGP site offset.";
          }
          leaf peer-ip {
            type inet:ipv4-address-no-zone;
            description
              "BGP peer IP address.";
          }
          leaf pw-type {
            type live_ncs_l2vpn-vpls-pw-type;
            description
              "PW type, which can be label, QinQ, or MEHVPLS.";
          }
          leaf pw-state {
            type live_ncs_l2vpn-pw-state;
            description
              "PW status.";
          }
          leaf local-vc-label {
            type uint32;
            description
              "VC label allocated by the local device.";
          }
          leaf remote-vc-label {
            type uint32;
            description
              "VC label allocated by the peer.";
          }
          leaf last-up-time {
            type yang:date-and-time;
            description
              "Date and time when a PW was up for the last time, for example, 2012/07/20 02:30:46.";
          }
          leaf total-up-time {
            type string {
              length "1..80";
            }
            description
              "Total duration when the PW is up.";
          }
          leaf c-key {
            type uint32;
            description
              "Customer key. Each CKey corresponds to a PW.";
          }
          leaf n-key {
            type uint32;
            description
              "Network key. Each NKey corresponds to a combination of the peer and tunnel policy.";
          }
          leaf broadcast-tunnel-key {
            type string {
              length "0..21";
            }
            description
              "Tunnel ID used by a PW for broadcast.";
          }
          leaf stp-enable {
            type boolean;
            description
              "Enable STP for PW.";
          }
          leaf mac-flapping-enable {
            type live_ncs_pw-block-status;
            description
              "MAC flapping information.";
          }
          leaf main-pw-token {
            type pub-type:live_ncs_hex-binary;
            description
              "Token of the primary PW.";
          }
          leaf backup-pw-token {
            type pub-type:live_ncs_hex-binary;
            description
              "Token of the secondary PW.";
          }
          leaf receive-flow-label {
            type live_ncs_flow-label-ability;
            description
              "Received flow label.";
          }
          leaf negotiate-flow-label {
            type live_ncs_flow-label-ability;
            description
              "Negotiated flow label.";
          }
          leaf remote-control-word {
            type live_ncs_l2vpn-control-word;
            description
              "Remote control word capability.";
          }
          leaf negotiate-control-word {
            type live_ncs_l2vpn-control-word;
            description
              "Negotiated control word capability.";
          }
          container tunnels {
            description
              "List of VPLS PW tunnels.";
            list tunnel {
              key "tunnel-key";
              // NCS drop max-elements statement
              description
                "Operational data of VPLS PW tunnels.";
              leaf tunnel-key {
                type string {
                  length "0..21";
                }
                description
                  "Tunnel ID in hexadecimal notation that is assigned by the system.";
              }
              leaf tunnel-type {
                type live_ncs_l2vpn-tunnel-type;
                description
                  "Type of a tunnel.";
              }
              leaf out-interface {
                type pub-type:live_ncs_if-name;
                description
                  "Outbound interface of a PW.";
              }
              leaf tunnel-name {
                type string {
                  length "0..64";
                }
                description
                  "Name of the tunnel used by the PW.";
              }
              leaf public-next-hop {
                type inet:ipv4-address-no-zone;
                description
                  "Public next hop of a PW.";
              }
            }
          }
          container traffic-statistics {
            description
              "Peer traffic statistics.";
            leaf in-traffic-rate {
              type uint64;
              units "bit/s";
              description
                "Rate of traffic received by the PW.";
            }
            leaf out-traffic-rate {
              type uint64;
              units "bit/s";
              description
                "Rate of traffic sent by the PW.";
            }
            leaf in-frame-rate {
              type uint64;
              units "pps";
              description
                "Rate of frames received by the PW.";
            }
            leaf out-frame-rate {
              type uint64;
              units "pps";
              description
                "Rate of frames sent by the PW.";
            }
            leaf in-bytes {
              type uint64;
              units "Byte";
              description
                "Number of bytes received by the PW.";
            }
            leaf out-bytes {
              type uint64;
              units "Byte";
              description
                "Number of bytes sent by the PW.";
            }
            leaf in-frames {
              type uint64;
              units "packet";
              description
                "Number of frames received by the PW.";
            }
            leaf out-frames {
              type uint64;
              units "packet";
              description
                "Number of frames sent by the PW.";
            }
            leaf in-unicast-frames {
              type uint64;
              units "packet";
              description
                "Number of unicast frames received by the PW.";
            }
            leaf in-unicast-bytes {
              type uint64;
              units "Byte";
              description
                "Number of unicast bytes received by the PW.";
            }
            leaf in-multicast-frames {
              type uint64;
              units "packet";
              description
                "Number of multicast frames received by the PW.";
            }
            leaf in-multicast-bytes {
              type uint64;
              units "Byte";
              description
                "Number of multicast bytes received by the PW.";
            }
            leaf in-broadcast-frames {
              type uint64;
              units "packet";
              description
                "Number of broadcast frames received by the PW.";
            }
            leaf in-broadcast-bytes {
              type uint64;
              units "Byte";
              description
                "Number of broadcast bytes received by the PW.";
            }
            leaf out-unicast-frames {
              type uint64;
              units "packet";
              description
                "Number of unicast frames sent by the PW.";
            }
            leaf out-unicast-bytes {
              type uint64;
              units "Byte";
              description
                "Number of unicast bytes sent by the PW.";
            }
            leaf out-multicast-frames {
              type uint64;
              units "packet";
              description
                "Number of multicast frames sent by the PW.";
            }
            leaf out-multicast-bytes {
              type uint64;
              units "Byte";
              description
                "Number of multicast bytes sent by the PW.";
            }
            leaf out-broadcast-frames {
              type uint64;
              units "packet";
              description
                "Number of broadcast frames sent by the PW.";
            }
            leaf out-broadcast-bytes {
              type uint64;
              units "Byte";
              description
                "Number of broadcast bytes sent by the PW.";
            }
            leaf in-discard-frames {
              type uint64;
              units "packet";
              description
                "Number of frames received and then dropped by the PW.";
            }
            leaf reset-time {
              type yang:date-and-time;
              description
                "Time when statistics were cleared the last time.";
            }
          }
        }
      }
    }
    container bgp-multi-homing-signaling {
      // NCS drop when statement
      // NCS drop must statement
      // NCS drop must statement
      presence "Container for bgp protocol vpls instance.";
      description
        "Configure BGP VSIs.";
      leaf route-distinguisher {
        type string {
          length "3..21";
        }
        description
          "Route distinguisher.";
      }
      leaf encapsulation-rfc4761-compatible {
        type boolean;
        // NCS drop default statement
        description
          "Enable/disable the setting of an encapsulation type.";
      }
      leaf encapsulation-vpls-family-compatible {
        type boolean;
        // NCS drop default statement
        description
          "Enable/disable the setting of an encapsulation type to private mode.";
      }
      leaf mtu-negotiate-disable {
        type boolean;
        // NCS drop default statement
        description
          "Enable/disable the function of ignoring MTU match between local VSI and remote VSI. The default implementation is match.";
      }
      leaf site-range {
        type uint32 {
          range "1..65535";
        }
        description
          "BGP site range. Cannot decrease site range.";
      }
      leaf default-offset {
        ext:operation-exclude "update|delete";
        // NCS drop when statement
        type uint16 {
          range "0..1";
        }
        // NCS drop default statement
        description
          "BGP site offset. The value of this node cannot be modified after being set.";
      }
      leaf control-word {
        type live_ncs_l2vpn-control-word;
        // NCS drop must statement
        // NCS drop default statement
        description
          "Enable the control word feature. The control word feature is usually used for TDM, ATM, and FR PWs.";
      }
      leaf auto-route-distinguisher {
        type string {
          length "3..21";
        }
        description
          "Automatic route distinguisher (RD). If no RD is configured for an L2VPN instance, you can specify an IPv4 address using the rd-ip parameter, based on which an RD is automatically generated in the format of 32-bit prefix IP address:index, for example, 192.168.122.15:1. An index is an integer automatically allocated by the system and ranges from 1 to 65535.Each L2VPN instance must use a unique RD.";
      }
      container default-site {
        description
          "Configure the default BGP multi-homing site.";
        leaf name {
          type live_ncs_vpls-multi-homing-site-name;
          // NCS drop must statement
          // NCS drop default statement
          description
            "BGP multi-homing default site name.";
        }
        leaf site-id {
          type uint32 {
            range "0..65534";
          }
          description
            "BGP multi-homing default site ID.";
        }
        leaf preference {
          // NCS drop when statement
          type uint32 {
            range "1..65535";
          }
          // NCS drop default statement
          description
            "BGP multi-homing default site preference.";
        }
        leaf selected {
          type boolean;
          description
            "BGP multi-homing default site selected flag.";
        }
        container remote-sites {
          description
            "Operational data of BGP multi-homing remote site information.";
          uses live_ncs_bgp-mh-remote-site-grp;
        }
      }
      container sites {
        description
          "List of BGP multi-homing sites.";
        list site {
          key "name";
          // NCS drop max-elements statement
          description
            "Configure BGP multi-homing sites.";
          leaf name {
            type live_ncs_vpls-multi-homing-site-name;
            // NCS drop must statement
            description
              "BGP multi-homing site name.";
          }
          leaf site-id {
            type uint32 {
              range "0..65534";
            }
            description
              "BGP multi-homing site ID.";
          }
          leaf preference {
            // NCS drop when statement
            type uint32 {
              range "1..65535";
            }
            // NCS drop default statement
            description
              "BGP multi-homing site preference.";
          }
          leaf active-delay-time {
            // NCS drop when statement
            type uint16 {
              range "0..256";
            }
            units "s";
            // NCS drop default statement
            description
              "BGP multi-homing site active delay time.";
          }
          leaf recover-delay-time {
            // NCS drop when statement
            type uint16 {
              range "0..3600";
            }
            units "s";
            // NCS drop default statement
            description
              "BGP multi-homing site recover delay time.";
          }
          leaf best-site {
            // NCS drop when statement
            type empty;
            description
              "BGP multi-homing best site.";
          }
          leaf selected {
            type boolean;
            description
              "Selected flag of BGP multi-homing site.";
          }
          container remote-sites {
            description
              "Operational data of BGP multi-homing remote site information.";
            uses live_ncs_bgp-mh-remote-site-grp;
          }
          container ac-infos {
            description
              "List of BGP multi-homing AC information.";
            list ac-info {
              key "interface-name";
              description
                "Operational data of BGP multi-homing AC information.";
              leaf interface-name {
                type leafref {
                  path "/ncs:devices/ncs:device/ncs:live-status/ifm:ifm/ifm:interfaces/ifm:interface/ifm:name" {
                    tailf:xpath-root 3;
                  }
                }
                description
                  "BGP multi-homing AC interface name.";
              }
              leaf ac-state {
                type live_ncs_ac-state;
                description
                  "BGP multi-homing AC state.";
              }
              leaf mflp-state {
                type live_ncs_ac-block-status;
                description
                  "BGP multi-homing MFLP block state.";
              }
              leaf block-state {
                type live_ncs_ac-block-status;
                description
                  "BGP multi-homing AC block state.";
              }
            }
          }
        }
      }
      container vpn-targets {
        description
          "List of VPN targets.";
        list vpn-target {
          key "rt-value rt-type";
          // NCS drop max-elements statement
          description
            "Configure VPN targets.";
          leaf rt-value {
            type string {
              length "3..21";
            }
            description
              "Route target. The format of an RT can be:
               - 16-bit AS number:32-bit user-defined number, for example, 1:3. An AS number ranges from 0 to 65535, and a user-defined number ranges from 0 to 4294967295. The AS number and user-defined number cannot be both 0s. This means that the RT cannot be 0:0.
               - Integral 4-byte AS number:2-byte user-defined number, for example, 65537:3. An AS number ranges from 65536 to 4294967295. A user-defined number ranges from 0 to 65535. The AS number and user-defined number cannot be both 0s. This means that the RT cannot be 0:0.
               - 32-bit IP address:16-bit user-defined number, for example: 192.168.122.15:1. The IP address ranges from 0.0.0.0 to 255.255.255.255, and the user-defined number ranges from 0 to 65535.
               - 32-bit AS number:16-bit user-defined number, for example, 10.11:3. An AS number ranges from 0.0 to 65535.65535, and a user-defined number ranges from 0 to 65535. The AS number and user-defined number cannot be both 0s. This means that the RT cannot be 0.0:0.";
          }
          leaf rt-type {
            type live_ncs_vpn-rt-type;
            description
              "RT type, which can be:
               - export-extcommunity: specifies the value of the extended community attribute of the route from an outbound interface to the destination VPN.
               - import-extcommunity: receives routes that carry the specified extended community attribute value.";
          }
        }
      }
      container pws {
        description
          "List of VPLS BGP multi-homing PWs.";
        list pw {
          // NCS drop must statement
          key "peer-ip";
          unique "name";
          description
            "Configure a VPLS BGP multi-homing PW.";
          leaf peer-ip {
            type inet:ipv4-address-no-zone;
            description
              "Peer IP address.";
          }
          leaf name {
            type string {
              length "1..15";
            }
            description
              "PW name.";
          }
          leaf traffic-statistics-collection {
            type boolean;
            // NCS drop must statement
            // NCS drop default statement
            description
              "Enable/disable the function to collect traffic statistics.";
          }
          uses l2vpn:live_ncs_suppression-statisticss-grp;
        }
      }
      container pw-infos {
        description
          "List of BGP multi-homing PWs.";
        list pw-info {
          key "site-id offset";
          description
            "Operational data of BGP multi-homing PWs.";
          leaf site-id {
            type uint32 {
              range "0..65534";
            }
            description
              "BGP site ID.";
          }
          leaf offset {
            type uint16;
            description
              "BGP site offset.";
          }
          leaf peer-ip {
            type inet:ipv4-address-no-zone;
            description
              "BGP peer IP.";
          }
          leaf pw-type {
            type live_ncs_l2vpn-vpls-pw-type;
            description
              "PW type, which can be label, QinQ, or MEHVPLS.";
          }
          leaf pw-state {
            type live_ncs_l2vpn-pw-state;
            description
              "PW status.";
          }
          leaf local-vc-label {
            type uint32;
            description
              "VC label allocated by the local device.";
          }
          leaf remote-vc-label {
            type uint32;
            description
              "VC label allocated by the peer.";
          }
          leaf last-up-time {
            type yang:date-and-time;
            description
              "Date and time when a PW was up for the last time, for example, 2012/07/20 02:30:46.";
          }
          leaf total-up-time {
            type string {
              length "1..80";
            }
            description
              "Total duration when the PW is up.";
          }
          leaf c-key {
            type uint32;
            description
              "Customer key. Each CKey corresponds to a PW.";
          }
          leaf n-key {
            type uint32;
            description
              "Network key. Each NKey corresponds to a combination of the peer and tunnel policy.";
          }
          leaf broadcast-tunnel-key {
            type string {
              length "0..21";
            }
            description
              "Tunnel ID used by a PW for broadcast.";
          }
          leaf stp-enable {
            type boolean;
            description
              "Enable STP for PW.";
          }
          leaf mac-flapping-enable {
            type live_ncs_pw-block-status;
            description
              "MAC flapping information.";
          }
          leaf main-pw-token {
            type pub-type:live_ncs_hex-binary;
            description
              "Token of the primary PW.";
          }
          leaf backup-pw-token {
            type pub-type:live_ncs_hex-binary;
            description
              "Token of the secondary PW.";
          }
          leaf remote-control-word {
            type live_ncs_l2vpn-control-word;
            description
              "Remote control word capability.";
          }
          leaf negotiate-control-word {
            type live_ncs_l2vpn-control-word;
            description
              "Negotiated control word capability.";
          }
          container tunnels {
            description
              "List of VPLS PW tunnels.";
            list tunnel {
              key "tunnel-key";
              // NCS drop max-elements statement
              description
                "Operational data of a VPLS PW tunnel.";
              leaf tunnel-key {
                type string {
                  length "0..21";
                }
                description
                  "Tunnel ID in hexadecimal notation that is assigned by the system.";
              }
              leaf tunnel-type {
                type live_ncs_l2vpn-tunnel-type;
                description
                  "Type of a tunnel.";
              }
              leaf out-interface {
                type pub-type:live_ncs_if-name;
                description
                  "Outbound interface of a PW.";
              }
              leaf tunnel-name {
                type string {
                  length "0..64";
                }
                description
                  "Name of the tunnel used by the PW.";
              }
              leaf public-next-hop {
                type inet:ipv4-address-no-zone;
                description
                  "Public next hop of a PW.";
              }
            }
          }
          container traffic-statistics {
            description
              "Peer traffic statistics.";
            leaf in-traffic-rate {
              type uint64;
              units "bit/s";
              description
                "Rate of traffic received by the PW.";
            }
            leaf out-traffic-rate {
              type uint64;
              units "bit/s";
              description
                "Rate of traffic sent by the PW.";
            }
            leaf in-frame-rate {
              type uint64;
              units "pps";
              description
                "Rate of frames received by the PW.";
            }
            leaf out-frame-rate {
              type uint64;
              units "pps";
              description
                "Rate of frames sent by the PW.";
            }
            leaf in-bytes {
              type uint64;
              units "Byte";
              description
                "Number of bytes received by the PW.";
            }
            leaf out-bytes {
              type uint64;
              units "Byte";
              description
                "Number of bytes sent by the PW.";
            }
            leaf in-frames {
              type uint64;
              units "packet";
              description
                "Number of frames received by the PW.";
            }
            leaf out-frames {
              type uint64;
              units "packet";
              description
                "Number of frames sent by the PW.";
            }
            leaf in-unicast-frames {
              type uint64;
              units "packet";
              description
                "Number of unicast frames received by the PW.";
            }
            leaf in-unicast-bytes {
              type uint64;
              units "Byte";
              description
                "Number of unicast bytes received by the PW.";
            }
            leaf in-multicast-frames {
              type uint64;
              units "packet";
              description
                "Number of multicast frames received by the PW.";
            }
            leaf in-multicast-bytes {
              type uint64;
              units "Byte";
              description
                "Number of multicast bytes received by the PW.";
            }
            leaf in-broadcast-frames {
              type uint64;
              units "packet";
              description
                "Number of broadcast frames received by the PW.";
            }
            leaf in-broadcast-bytes {
              type uint64;
              units "Byte";
              description
                "Number of broadcast bytes received by the PW.";
            }
            leaf out-unicast-frames {
              type uint64;
              units "packet";
              description
                "Number of unicast frames sent by the PW.";
            }
            leaf out-unicast-bytes {
              type uint64;
              units "Byte";
              description
                "Number of unicast bytes sent by the PW.";
            }
            leaf out-multicast-frames {
              type uint64;
              units "packet";
              description
                "Number of multicast frames sent by the PW.";
            }
            leaf out-multicast-bytes {
              type uint64;
              units "Byte";
              description
                "Number of multicast bytes sent by the PW.";
            }
            leaf out-broadcast-frames {
              type uint64;
              units "packet";
              description
                "Number of broadcast frames sent by the PW.";
            }
            leaf out-broadcast-bytes {
              type uint64;
              units "Byte";
              description
                "Number of broadcast bytes sent by the PW.";
            }
            leaf in-discard-frames {
              type uint64;
              units "packet";
              description
                "Number of frames received and then dropped by the PW.";
            }
            leaf reset-time {
              type yang:date-and-time;
              description
                "Time when statistics were cleared the last time.";
            }
          }
        }
      }
      container local-label-blocks {
        description
          "Operational data of local label blocks.";
        uses live_ncs_bgp-local-label-block-grp;
      }
      container remote-sites {
        description
          "List of BGP multi-homing remote site information.";
        list remote-site {
          key "site-id route-distinguisher offset";
          description
            "Operational data of BGP multi-homing remote site information.";
          leaf site-id {
            type uint32;
            description
              "BGP multi-homing remote site ID.";
          }
          leaf route-distinguisher {
            type string {
              length "3..21";
            }
            description
              "Route distinguisher.";
          }
          leaf offset {
            type uint16;
            description
              "BGP site offset.";
          }
          leaf peer-ip {
            type inet:ipv4-address-no-zone;
            description
              "The IP address of peer.";
          }
          leaf mtu {
            type uint32;
            description
              "Maximum transmission unit.";
          }
          leaf encapsulation-type {
            type live_ncs_vpls-bgp-encapsulation-type;
            description
              "The encapsulation type of remote PW.";
          }
          leaf label-start {
            type uint32;
            description
              "Start of the label.";
          }
          leaf add-range {
            type uint16;
            description
              "BGP site range.";
          }
        }
      }
    }
    container bgpad-signaling {
      // NCS drop when statement
      // NCS drop must statement
      // NCS drop must statement
      presence "Container for bgpad protocol vpls instance.";
      description
        "Enable/disable BGP AD VSI.";
      leaf vpls-id {
        type string {
          length "3..21";
        }
        description
          "VPLS domain ID. The format of a VPLS domain ID can be:
           - 16-bit AS number:32-bit user-defined number, for example, 1:3. An AS number ranges from 0 to 65535, and a user-defined number ranges from 0 to 4294967295. The AS number and user-defined number cannot be both 0s. This means that the VPLS domain ID cannot be 0:0.
           - Integral 4-byte AS number:2-byte user-defined number, for example, 65537:3. An AS number ranges from 65536 to 4294967295. A user-defined number ranges from 0 to 65535. The AS number and user-defined number cannot be both 0s. This means that the VPLS domain ID cannot be 0:0.
           - 32-bit IP address:16-bit user-defined number, for example: 192.168.122.15:1. The IP address ranges from 0.0.0.0 to 255.255.255.255, and the user-defined number ranges from 0 to 65535.
           - 32-bit AS number:16-bit user-defined number, for example, 10.11:3. An AS number ranges from 0.0 to 65535.65535, and a user-defined number ranges from 0 to 65535. The AS number and user-defined number cannot be both 0s. This means that the VPLS domain ID cannot be 0.0:0.";
      }
      leaf split-horizon {
        // NCS drop when statement
        type live_ncs_vpls-split-horizon-mode-type;
        // NCS drop default statement
        description
          "PW split horizon mode.";
      }
      leaf traffic-statistics-collection {
        // NCS drop when statement
        type boolean;
        // NCS drop must statement
        // NCS drop default statement
        description
          "Enable/disable traffic statistics collection.";
      }
      leaf route-distinguisher {
        type string {
          length "3..21";
        }
        description
          "Route distinguisher.";
      }
      leaf vsi-id {
        type inet:ipv4-address-no-zone;
        description
          "VSI ID. For a BGP AD VSI, the VSI ID is the IP address used by the local PE for signaling negotiation.";
      }
      container vpn-targets {
        // NCS drop when statement
        description
          "List of VPN targets.";
        list vpn-target {
          key "rt-value rt-type";
          // NCS drop max-elements statement
          description
            "Configure VPN targets.";
          leaf rt-value {
            type string {
              length "3..21";
            }
            description
              "Route target. The format of an RT can be:
               - 16-bit AS number:32-bit user-defined number, for example, 1:3. An AS number ranges from 0 to 65535, and a user-defined number ranges from 0 to 4294967295. The AS number and user-defined number cannot be both 0s. This means that the RT cannot be 0:0.
               - Integral 4-byte AS number:2-byte user-defined number, for example, 65537:3. An AS number ranges from 65536 to 4294967295. A user-defined number ranges from 0 to 65535. The AS number and user-defined number cannot be both 0s. This means that the RT cannot be 0:0.
               - 32-bit IP address:16-bit user-defined number, for example: 192.168.122.15:1. The IP address ranges from 0.0.0.0 to 255.255.255.255, and the user-defined number ranges from 0 to 65535.
               - 32-bit AS number:16-bit user-defined number, for example, 10.11:3. An AS number ranges from 0.0 to 65535.65535, and a user-defined number ranges from 0 to 65535. The AS number and user-defined number cannot be both 0s. This means that the RT cannot be 0.0:0.";
          }
          leaf rt-type {
            type live_ncs_vpn-rt-type;
            description
              "RT type, which can be:
               - export-extcommunity: specifies the value of the extended community attribute of the route from an outbound interface to the destination VPN.
               - import-extcommunity: receives routes that carry the specified extended community attribute value.";
          }
        }
      }
      container pws {
        // NCS drop when statement
        description
          "List of BGP AD PWs.";
        list pw {
          // NCS drop must statement
          key "peer-ip";
          description
            "Configure a BGP AD PW.";
          leaf peer-ip {
            type inet:ipv4-address-no-zone;
            description
              "Peer IP address.";
          }
          leaf name {
            type string {
              length "1..15";
            }
            description
              "PW name.";
          }
          leaf traffic-statistics-collection {
            type boolean;
            // NCS drop must statement
            // NCS drop must statement
            // NCS drop must statement
            description
              "Enable/disable the function to collect traffic statistics.";
          }
          uses l2vpn:live_ncs_suppression-statisticss-grp;
        }
      }
      container peers {
        description
          "List of BGP AD peer.";
        list peer {
          key "peer-router-id";
          // NCS drop max-elements statement
          description
            "Operational data of BGP AD peer.";
          leaf peer-router-id {
            type inet:ipv4-address-no-zone;
            description
              "Peer IP address.";
          }
          leaf vpls-id {
            type string {
              length "3..21";
            }
            description
              "VPLS domain ID.";
          }
          leaf saii {
            type inet:ipv4-address-no-zone;
            description
              "Source attachment individual identifier.";
          }
          leaf taii {
            type inet:ipv4-address-no-zone;
            description
              "Target attachment individual identifier.";
          }
          leaf peer-type {
            type live_ncs_vpls-ldp-peer-type;
            description
              "Remote peer type, either dynamic or static.";
          }
          container pw-info {
            description
              "Operational data of BGP AD PW.";
            leaf peer-ip {
              type inet:ipv4-address-no-zone;
              description
                "BGP AD PW.";
            }
            leaf pw-type {
              type live_ncs_l2vpn-vpls-pw-type;
              description
                "PW type, which can be label, QinQ, or MEHVPLS.";
            }
            leaf session-state {
              type live_ncs_l2vpn-state;
              description
                "Status of the session between the local end and its peer. The value can be up or down. This item is displayed only when the VPLS type is Martini.";
            }
            leaf pw-state {
              type live_ncs_l2vpn-pw-state;
              description
                "PW status.";
            }
            leaf local-vc-label {
              type uint32;
              description
                "VC label allocated by the local device.";
            }
            leaf remote-vc-label {
              type uint32;
              description
                "VC label allocated by the peer.";
            }
            leaf last-up-time {
              type string {
                length "1..80";
              }
              description
                "Date and time when a PW was up for the last time, for example, 2012/07/20 02:30:46.";
            }
            leaf total-up-time {
              type string {
                length "1..80";
              }
              description
                "Total duration when the PW is up.";
            }
            leaf c-key {
              type uint32;
              description
                "Customer key. Each CKey corresponds to a PW.";
            }
            leaf n-key {
              type uint32;
              description
                "Network key. Each NKey corresponds to a combination of the peer and tunnel policy.";
            }
            leaf broadcast-tunnel-key {
              type string {
                length "0..21";
              }
              description
                "Tunnel ID used by a PW for broadcast.";
            }
            leaf stp-enable {
              type boolean;
              description
                "Enable STP for PW.";
            }
            leaf mac-flapping-enable {
              type live_ncs_pw-block-status;
              description
                "MAC flapping information.";
            }
            leaf main-pw-token {
              type pub-type:live_ncs_hex-binary;
              description
                "Token of the primary PW.";
            }
            leaf backup-pw-token {
              type pub-type:live_ncs_hex-binary;
              description
                "Token of the secondary PW.";
            }
            leaf remote-vccv-code {
              type pub-type:live_ncs_hex-binary;
              description
                "Remote VCCV code.";
            }
            leaf pw-token-exceed {
              type boolean;
              // NCS drop default statement
              description
                "Indicates whether the number of PW tokens exceeds the maximum limit.";
            }
            container tunnels {
              description
                "List of VPLS PW tunnel.";
              list tunnel {
                key "tunnel-key";
                // NCS drop max-elements statement
                description
                  "Operational data of VPLS PW tunnel.";
                leaf tunnel-key {
                  type string {
                    length "0..21";
                  }
                  description
                    "Tunnel ID in hexadecimal notation that is assigned by the system.";
                }
                leaf tunnel-type {
                  type live_ncs_l2vpn-tunnel-type;
                  description
                    "Type of a tunnel.";
                }
                leaf out-interface {
                  type string {
                    length "0..256";
                  }
                  description
                    "Outbound interface of a PW.";
                }
                leaf tunnel-name {
                  type string {
                    length "0..64";
                  }
                  description
                    "Name of the tunnel used by the PW.";
                }
                leaf public-next-hop {
                  type inet:ipv4-address-no-zone;
                  description
                    "Public next hop of a PW.";
                }
              }
            }
          }
          uses l2vpn:live_ncs_pw-traffic-statisticss-grp;
        }
      }
    }
    container acs {
      // NCS drop when statement
      description
        "List of VPLS ACs.";
      list ac {
        key "interface-name";
        description
          "Configure a VPLS AC.";
        leaf interface-name {
          type leafref {
            path "/ncs:devices/ncs:device/ncs:live-status/ifm:ifm/ifm:interfaces/ifm:interface/ifm:name" {
              tailf:xpath-root 3;
            }
          }
          // NCS drop must statement
          description
            "Name of the AC interface bound to a VSI.";
        }
        leaf site-name {
          // NCS drop when statement
          type live_ncs_vpls-multi-homing-site-name;
          description
            "BGP multi-homing site name. The value of this node cannot be changed after being configured.";
        }
        leaf hub-mode {
          type boolean;
          // NCS drop default statement
          description
            "Enable/disable an interface's support for the hub mode.";
        }
        leaf access-port {
          ext:operation-exclude "update|delete";
          type boolean;
          // NCS drop must statement
          // NCS drop default statement
          description
            "Enable/disable the attribute that allows only untagged packets to pass through an interface.";
        }
        leaf etree-leaf {
          // NCS drop when statement
          type boolean;
          // NCS drop must statement
          // NCS drop default statement
          description
            "Enable/disable e-tree leaf.";
        }
        leaf state {
          type live_ncs_ac-state;
          description
            "Status of the AC interface bound to a VSI.";
        }
        leaf block-state {
          type live_ncs_ac-block-status;
          description
            "AC block state.";
        }
        leaf last-up-time {
          type string {
            length "1..60";
          }
          description
            "Date and time when the AC interface was up for the last time, for example, 2012/07/20 02:30:46.";
        }
        leaf total-up-time {
          type string {
            length "1..60";
          }
          description
            "Total up time of the AC interface.";
        }
        leaf token-exceed {
          type boolean;
          // NCS drop default statement
          description
            "Indicates whether the number of AC tokens exceeds the maximum limit.";
        }
        leaf oam-state {
          type live_ncs_oam-state;
          description
            "OAM Status of the AC interface bound to a VSI.";
        }
      }
    }
    container bds {
      // NCS drop when statement
      // NCS drop must statement
      description
        "List of VPLS BD ACs.";
      list bd {
        // NCS drop must statement
        key "id";
        unique "pw-tag";
        description
          "Configure VPLS BD ACs.";
        leaf id {
          type leafref {
            path "/ncs:devices/ncs:device/ncs:live-status/bd:bd/bd:instances/bd:instance/bd:id" {
              tailf:xpath-root 3;
            }
          }
          description
            "BD ID.";
        }
        leaf pw-tag {
          type uint16 {
            range "1..4094";
          }
          description
            "PW tag.";
        }
        leaf state {
          type live_ncs_ac-state;
          description
            "Status of the AC interface bound to a VSI.";
        }
        leaf last-up-time {
          type string {
            length "1..60";
          }
          description
            "Date and time when the AC interface was up for the last time, for example, 2012/07/20 02:30:46.";
        }
        leaf total-up-time {
          type string {
            length "1..60";
          }
          description
            "Total up time of the AC interface.";
        }
      }
    }
    container pbb {
      // NCS drop when statement
      // NCS drop must statement
      description
        "Configure PBB VPLS.";
      leaf i-tag {
        // NCS drop when statement
        type uint32 {
          range "0..16777215";
        }
        description
          "Tag defined in 802.1ah to identify a service instance.";
      }
      leaf backbone-source-mac {
        // NCS drop when statement
        type pub-type:live_ncs_mac-address;
        description
          "B-SMAC address.";
      }
      leaf backbone-destination-mac {
        // NCS drop when statement
        type pub-type:live_ncs_mac-address;
        description
          "B-DMAC address.";
      }
      leaf mac-withdraw-rfc7361-compatible {
        // NCS drop when statement
        type boolean;
        // NCS drop default statement
        description
          "Enable/disable MAC withdraw messages that carry PBB B-MAC and I-tag TLVs in accordance with RFC 7361.";
      }
      leaf b-vsi {
        type leafref {
          path "/ncs:devices/ncs:device/ncs:live-status/l2vpn:l2vpn/l2vpn:instances/l2vpn:instance/l2vpn:name" {
            tailf:xpath-root 3;
          }
        }
        // NCS drop must statement
        description
          "Name of the B-VSI instance to which the I-VSI is bound.";
      }
      leaf b-evpn {
        type string {
          length "1..31";
        }
        // NCS drop must statement
        description
          "Name of the B-EVPN instance to which the I-VSI is bound.";
      }
      leaf learned-flag {
        type live_ncs_vsi-pbb-learned-flag;
        description
          "B-MAC address learning result.";
      }
      leaf learned-in-label {
        type uint32;
        description
          "Learned in-label.";
      }
      leaf learned-out-label {
        type uint32;
        description
          "Learned out-label.";
      }
      container i-vsis {
        description
          "List of I-VSI.";
        list i-vsi {
          key "vsi-name";
          description
            "Operational data of I-VSI.";
          leaf vsi-name {
            type string {
              length "1..31";
            }
            description
              "I-VSI name.";
          }
        }
      }
    }
    container ipmsi {
      // NCS drop when statement
      // NCS drop must statement
      // NCS drop must statement
      presence "enable ipmsi.";
      description
        "Enable/disable multicast VPLS.";
      container root {
        presence "root";
        description
          "Enable/disable the P2MP tunnel root.";
        leaf data-switch-disable {
          type boolean;
          // NCS drop default statement
          description
            "Enable/disable broadcast, unknown unicast, and multicast traffic's switching to a PW when a P2MP tunnel goes down.";
        }
        leaf mc-tunnel-type {
          type live_ncs_multicast-tunnel-type;
          // NCS drop default statement
          description
            "P2MP tunnel type.";
        }
        leaf root-ip {
          // NCS drop when statement
          type inet:ipv4-address-no-zone;
          description
            "Root IP address of a P2MP tunnel.";
        }
        leaf te-p2mp-dynamic {
          // NCS drop when statement
          type boolean;
          // NCS drop default statement
          description
            "Enable/disable P2MP dynamic TE.";
        }
        leaf p2mp-template-name {
          // NCS drop when statement
          type string {
            length "1..31";
          }
          description
            "P2MP template name.";
        }
        leaf bfd-track-if-name {
          // NCS drop when statement
          type leafref {
            path "/ncs:devices/ncs:device/ncs:live-status/ifm:ifm/ifm:interfaces/ifm:interface/ifm:name" {
              tailf:xpath-root 3;
            }
          }
          description
            "Name of the interface bound to a BFD session.";
        }
        leaf leaf-count {
          type uint32 {
            range "0..65535";
          }
          description
            "Number of leaves.";
        }
        container tunnel {
          description
            "Operational data of tunnels.";
          leaf ingress-lsr-id {
            type inet:ipv4-address-no-zone;
            description
              "Ingress LSR ID.";
          }
          leaf state {
            type live_ncs_l2vpn-state;
            description
              "P2MP tunnel status.";
          }
          leaf session-id {
            type uint32 {
              range "0..4294967295";
            }
            description
              "RSVP session ID.";
          }
          leaf p2mp-id {
            type string {
              length "0..10";
            }
            description
              "P2MP session ID.";
          }
          leaf opaque-value {
            type string {
              length "0..4096";
            }
            description
              "Original opaque value in a message. The value is displayed in the format of TLV.";
          }
        }
        container leafs {
          description
            "List of Leaf.";
          list leaf {
            key "peer-ip";
            description
              "Operational data of leafs.";
            leaf peer-ip {
              type inet:ipv4-address-no-zone;
              description
                "LSR ID of the remote device.";
            }
          }
        }
      }
      container leaf {
        presence "leaf";
        description
          "Enable/disable the leaf of a P2MP tunnel.";
        leaf egress-count {
          type uint64 {
            range "0..65534";
          }
          description
            "Number of P2MP tunnel egresses.";
        }
        container pw-protect-groups {
          description
            "List of PW protection groups.";
          list pw-protect-group {
            key "primary-root-ip backup-root-ip";
            description
              "Configure a PW protection group.";
            leaf primary-root-ip {
              type inet:ipv4-address-no-zone;
              description
                "IP address of the primary root.";
            }
            leaf backup-root-ip {
              type inet:ipv4-address-no-zone;
              description
                "IP address of the backup root.";
            }
            leaf wtr {
              type uint32 {
                range "0..600";
              }
              units "min";
              // NCS drop default statement
              description
                "Wait-to-Restore time.";
            }
            leaf primary-track-bfd {
              type boolean;
              // NCS drop default statement
              description
                "Enable/disable the association between the primary root and a BFD session.";
            }
            leaf backup-track-bfd {
              type boolean;
              // NCS drop default statement
              description
                "Enable/disable the association between the backup root and a BFD session.";
            }
            container primary {
              description
                "Operational data of primary root node.";
              uses live_ncs_ipmsi-leaf-protect-group-parameter;
            }
            container backup {
              description
                "Operational data of backup root node.";
              uses live_ncs_ipmsi-leaf-protect-group-parameter;
            }
          }
        }
        container mldp-p2mp-tunnels {
          description
            "Operational data of mLDP P2MP tunnel.";
          uses live_ncs_mldp-p2mp-tunnel-grp;
        }
        container te-p2mp-tunnels {
          description
            "Operational data of te P2MP tunnel.";
          uses live_ncs_te-p2mp-tunnel-grp;
        }
      }
    }
    container mac-withdraw-loop-detect {
      description
        "Operational data of MAC withdraw loop detection information.";
      leaf last-loop-type {
        type live_ncs_vpls-loop-detect-type;
        description
          "Type of the last loop detected by MAC withdraw loop detection.";
      }
      leaf send-peer {
        type inet:ipv4-address-no-zone;
        description
          "Transmit peer for MAC withdraw loop detection.";
      }
      leaf receive-peer {
        type inet:ipv4-address-no-zone;
        description
          "Receive peer for MAC withdraw loop detection.";
      }
      leaf last-loop-time {
        type string {
          length "1..80";
        }
        description
          "Time when MAC withdraw loop detection detected the last loop.";
      }
    }
    container down-causes {
      description
        "Operational data of the down causes of the VSI.";
      uses l2vpn:live_ncs_l2vpn-pw-down-causes-type;
    }
    container statistic {
      description
        "Operational data of L2VPN VPLS statistic.";
      leaf up-pw-num {
        type uint32;
        description
          "Number of the up state PW.";
      }
      leaf down-pw-num {
        type uint32;
        description
          "Number of the down state PW.";
      }
      leaf backup-pw-num {
        type uint32;
        description
          "Number of the backup state PW.";
      }
      leaf up-bfd-num {
        type uint32;
        description
          "Number of the BFD notify up state PW.";
      }
      leaf down-bfd-num {
        type uint32;
        description
          "Number of the BFD notify down state PW.";
      }
      leaf up-ac-num {
        type uint32;
        description
          "Number of the up state AC.";
      }
      leaf down-ac-num {
        type uint32;
        description
          "Number of the down state AC.";
      }
      leaf down-acoam-num {
        type uint32;
        description
          "Number of the down state AC because of OAM.";
      }
    }
    container ac-suppression-statisticss {
      description
        "List of VPLS AC Suppression statistics.";
      list ac-suppression-statistics {
        key "direction suppression-type";
        description
          "Operational data of suppression statistics about VPLS ACs.";
        leaf direction {
          type live_ncs_suppression-direction;
          description
            "Suppression statistics direction.";
        }
        uses l2vpn:live_ncs_suppression-statistics-grp;
      }
    }
  }

  grouping live_ncs_l2vpn-protect-group-historys-type {
    description
      "List of L2VPN protect group histroy info container.";
    list history {
      key "num";
      // NCS drop max-elements statement
      description
        "Operational data of historical switching information of a PW protection group.";
      leaf num {
        type uint32 {
          range "1..5";
        }
        description
          "Sequence number.";
      }
      leaf reroute-time {
        type string {
          length "1..60";
        }
        description
          "Switchback time.";
      }
      leaf reroute-action {
        type string {
          length "1..100";
        }
        description
          "Switchback action.";
      }
      leaf reroute-reason {
        type string {
          length "0..100";
        }
        description
          "Switchback reason.";
      }
    }
  }

  grouping live_ncs_bgp-local-label-block-grp {
    description
      "List of a local label blocks.";
    list local-label-block {
      key "offset";
      description
        "Operational data of local label blocks.";
      leaf offset {
        type uint16;
        description
          "BGP site offset.";
      }
      leaf label-start {
        type uint32;
        description
          "Start of the label.";
      }
      leaf add-range {
        type uint32;
        description
          "BGP site range.";
      }
      leaf site-base {
        type uint32;
        description
          "Base of the site.";
      }
    }
  }

  grouping live_ncs_bgp-remote-label-block-grp {
    description
      "List of remote label blocks.";
    list remote-label-block {
      key "route-distinguisher site-id offset";
      description
        "Operational data of remote label blocks.";
      leaf route-distinguisher {
        type string {
          length "3..21";
        }
        description
          "Route distinguisher.";
      }
      leaf site-id {
        type uint32 {
          range "0..65534";
        }
        description
          "BGP site ID.";
      }
      leaf offset {
        type uint16;
        description
          "BGP site offset.";
      }
      leaf label-start {
        type uint32;
        description
          "Start of the label.";
      }
      leaf add-range {
        type uint32;
        description
          "BGP site range.";
      }
    }
  }

  grouping live_ncs_ac-arp-grp {
    description
      "List of ARP information about all ACs.";
    list ac-arp {
      key "mac-type";
      // NCS drop max-elements statement
      description
        "Operational data of ARP information about an AC.";
      leaf mac-type {
        type live_ncs_l2vpn-mac-type;
        description
          "MAC address learning type.";
      }
      leaf mac-address {
        type pub-type:live_ncs_mac-address;
        description
          "MAC address of the local CE.";
      }
      leaf expire-time {
        type uint32;
        units "min";
        description
          "Aging time.";
      }
      leaf vlan-id {
        type uint32;
        description
          "VLAN ID corresponding to a MAC address.";
      }
      leaf ip-address {
        type inet:ipv4-address-no-zone;
        description
          "Dynamically learned IP address of the local CE.";
      }
    }
  }

  grouping live_ncs_ipmsi-leaf-protect-group-parameter {
    description
      "Operational data of Ipmsi leaf protect group parameters.";
    leaf valid {
      type boolean;
      // NCS drop default statement
      description
        "The root is valid.";
    }
    leaf active-state {
      type live_ncs_multicast-active-state;
      description
        "The root is active.";
    }
    leaf oam-protocol {
      type live_ncs_multicast-oam-type;
      description
        "Root OAM protocol.";
    }
    leaf oam-state {
      type live_ncs_oam-state;
      description
        "Root OAM status.";
    }
  }

  grouping live_ncs_mldp-p2mp-tunnel-grp {
    description
      "Operational data of Ipmsi mLDP P2MP tunnel.";
    list mldp-p2mp-tunnel {
      key "root-ip opaque-value";
      // NCS drop max-elements statement
      description
        "Operational data of tunnel information on a leaf node.";
      leaf root-ip {
        type inet:ipv4-address-no-zone;
        description
          "Root IP address of a P2MP tunnel.";
      }
      leaf opaque-value {
        type string {
          length "0..21";
        }
        description
          "Original opaque value in a message. The value is displayed in the format of TLV.";
      }
      leaf state {
        type live_ncs_l2vpn-state;
        description
          "P2MP tunnel status.";
      }
    }
  }

  grouping live_ncs_te-p2mp-tunnel-grp {
    description
      "Operational data of Ipmsi te P2MP tunnel.";
    list te-p2mp-tunnel {
      key "ingress-lsr-id session-id p2mp-id";
      // NCS drop max-elements statement
      description
        "Operational data of tunnel information on a leaf node.";
      leaf ingress-lsr-id {
        type inet:ipv4-address-no-zone;
        description
          "Ingress LSR ID.";
      }
      leaf session-id {
        type uint32 {
          range "0..4294967295";
        }
        description
          "RSVP session ID.";
      }
      leaf p2mp-id {
        type string {
          length "0..14";
        }
        description
          "P2MP session ID.";
      }
      leaf state {
        type live_ncs_l2vpn-state;
        description
          "P2MP tunnel status.";
      }
    }
  }

  grouping live_ncs_bgp-mh-remote-site-grp {
    description
      "Operational data of BGP multi-homing remote site information.";
    list remote-site {
      key "remote-site-id peer-ip";
      description
        "Operational data of BGP multi-homing remote site information.";
      leaf remote-site-id {
        type uint32;
        description
          "BGP multi-homing remote site ID.";
      }
      leaf peer-ip {
        type inet:ipv4-address-no-zone;
        description
          "BGP multi-homing peer IP.";
      }
    }
  }

  grouping live_ncs_suppression-statistics-grp {
    description
      "Suppression statistics.";
    leaf suppression-type {
      type live_ncs_suppression-type;
      description
        "Suppression statistics type.";
    }
    leaf cir {
      type uint32;
      description
        "CIR value.";
    }
    leaf pir {
      type uint32;
      description
        "PIR value.";
    }
    leaf cbs {
      type uint32;
      description
        "CBS value.";
    }
    leaf pbs {
      type uint32;
      description
        "PBS value.";
    }
    leaf passed-packets {
      type uint64;
      description
        "Passed packets.";
    }
    leaf passed-bytes {
      type uint64;
      description
        "Passed bytes.";
    }
    leaf discard-packets {
      type uint64;
      description
        "Discard packets.";
    }
    leaf discard-bytes {
      type uint64;
      description
        "Discard bytes.";
    }
    leaf passed-packet-rate {
      type uint64;
      units "pps";
      description
        "Passed packet rate.";
    }
    leaf passed-bit-rate {
      type uint64;
      units "bit/s";
      description
        "Passed bit rate.";
    }
    leaf discard-packet-rate {
      type uint64;
      units "pps";
      description
        "Discard packet rate.";
    }
    leaf discard-bit-rate {
      type uint64;
      units "bit/s";
      description
        "Discard bit rate.";
    }
  }

  grouping live_ncs_suppression-statisticss-grp {
    description
      "Suppression statistics.";
    container suppression-statisticss {
      description
        "List of suppression statistics.";
      list suppression-statistics {
        key "suppression-type";
        description
          "Operational data of suppression statistics.";
        uses l2vpn:live_ncs_suppression-statistics-grp;
      }
    }
  }

  grouping live_ncs_pw-traffic-statisticss-grp {
    description
      "Traffic statistics of PW.";
    container traffic-statistics {
      description
        "Operational data of traffic statistics about PWs.";
      leaf in-traffic-rate {
        type uint64;
        description
          "Rate of traffic received by the PW.";
      }
      leaf out-traffic-rate {
        type uint64;
        description
          "Rate of traffic sent by the PW.";
      }
      leaf in-frame-rate {
        type uint64;
        description
          "Rate of frames received by the PW.";
      }
      leaf out-frame-rate {
        type uint64;
        description
          "Rate of frames sent by the PW.";
      }
      leaf in-bytes {
        type uint64;
        description
          "Number of bytes received by the PW.";
      }
      leaf out-bytes {
        type uint64;
        description
          "Number of bytes sent by the PW.";
      }
      leaf in-frames {
        type uint64;
        description
          "Number of frames received by the PW.";
      }
      leaf out-frames {
        type uint64;
        description
          "Number of frames sent by the PW.";
      }
      leaf in-unicast-frames {
        type uint64;
        description
          "Number of unicast frames received by the PW.";
      }
      leaf in-unicast-bytes {
        type uint64;
        description
          "Number of unicast bytes received by the PW.";
      }
      leaf in-multicast-frames {
        type uint64;
        description
          "Number of multicast frames received by the PW.";
      }
      leaf in-multicast-bytes {
        type uint64;
        description
          "Number of multicast bytes received by the PW.";
      }
      leaf in-broadcast-frames {
        type uint64;
        description
          "Number of broadcast frames received by the PW.";
      }
      leaf in-broadcast-bytes {
        type uint64;
        description
          "Number of broadcast bytes received by the PW.";
      }
      leaf out-unicast-frames {
        type uint64;
        description
          "Number of unicast frames sent by the PW.";
      }
      leaf out-unicast-bytes {
        type uint64;
        description
          "Number of unicast bytes sent by the PW.";
      }
      leaf out-multicast-frames {
        type uint64;
        description
          "Number of multicast frames sent by the PW.";
      }
      leaf out-multicast-bytes {
        type uint64;
        description
          "Number of multicast bytes sent by the PW.";
      }
      leaf out-broadcast-frames {
        type uint64;
        description
          "Number of broadcast frames sent by the PW.";
      }
      leaf out-broadcast-bytes {
        type uint64;
        description
          "Number of broadcast bytes sent by the PW.";
      }
      leaf in-discard-frames {
        type uint64;
        description
          "Number of frames received and then dropped by the PW.";
      }
      leaf reset-time {
        type string {
          length "1..60";
        }
        description
          "Time when statistics were cleared the last time.";
      }
    }
  }

  grouping spe-infos-type {
    description
      "Indicates the query list of the SPE information.";
    list spe {
      key "spe-pw-id spe-peer-ip";
      description
        "Operational data of the SPE on the path to the peer.";
      leaf spe-pw-id {
        type uint32 {
          range "0..4294967295";
        }
        description
          "List of PW IDs on the path traveled by a label mapping message.";
      }
      leaf spe-peer-ip {
        type inet:ipv4-address-no-zone;
        description
          "IP address of an SPE in the path to the peer.";
      }
    }
  }

  grouping l2vpn-reroute-policy-type {
    description
      "L2VPN protect group reroute policy class.";
    leaf policy {
      type l2vpn-reroute-mode;
      default "delay";
      description
        "Switchback policy.";
    }
    leaf delay-time {
      when "../policy='delay'" {
        tailf:xpath-root 3;
      }
      type uint32 {
        range "10..10800";
      }
      units "s";
      default "30";
      description
        "Delay for switching traffic back to the primary PW.";
    }
    // NCS drop config false leaf 'last-switchback-time'
    // NCS drop config false leaf 'last-reroute-action'
    // NCS drop config false leaf 'last-switchback-reason'
  }

  grouping l2vpn-dyn-bfd-para-type {
    description
      "Dynamic BFD parameters.";
    leaf min-rx-interval {
      type uint16 {
        range "0..65535";
      }
      units "ms";
      default "10";
      description
        "Minimum receive interval.";
    }
    leaf min-tx-interval {
      type uint16 {
        range "0..65535";
      }
      units "ms";
      default "10";
      description
        "Minimum transmit interval.";
    }
    leaf detect-multiplier {
      type uint16 {
        range "3..50";
      }
      default "3";
      description
        "Detection multiplier.";
    }
  }

  grouping l2vpn-label-stacks-type {
    description
      "Label stack.";
    list label-stack {
      key "label-stack level";
      description
        "Operational data of the PW label stack.";
      leaf label-stack {
        type uint32 {
          range "1..4294967295";
        }
        description
          "Label stack.";
      }
      leaf level {
        type uint32 {
          range "1..4294967295";
        }
        description
          "Label level.";
      }
      leaf type {
        type string {
          length "0..20";
        }
        description
          "Label type.";
      }
      leaf label {
        type string {
          length "0..20";
        }
        description
          "Label value.";
      }
      leaf out-interface {
        type leafref {
          path "/ncs:devices/ncs:device/ncs:config/ifm:ifm/ifm:interfaces/ifm:interface/ifm:name" {
            tailf:xpath-root 3;
          }
        }
        description
          "Outbound interface name.";
      }
    }
  }

  grouping l2vpn-pw-down-causes-type {
    description
      "Indicates the down causes of the PW.";
    list down-cause {
      key "down-cause-index";
      description
        "Statistics of the down causes of PWs.";
      leaf down-cause-index {
        type uint32;
        description
          "Sequence number of the PW down cause.";
      }
      leaf down-cause {
        type string {
          length "0..100";
        }
        description
          "Indicates the down causes of the PW.";
      }
    }
  }

  grouping l2vpn-pw-status-changes-type {
    description
      "Indicates the reason and the time of the PW status that has changed.";
    list status-change {
      key "index";
      description
        "Statistics of the reason and the time of the PW status that has changed.";
      leaf index {
        type uint32;
        description
          "Sequence number of reasons that the PW status has changed.";
      }
      leaf timestamp {
        type string {
          length "0..60";
        }
        description
          "Indicates the time of the PW status has changed.";
      }
      leaf reason {
        type string {
          length "0..100";
        }
        description
          "Indicates the reason of the PW status has changed.";
      }
    }
  }

  grouping l2vpn-ccc-tdm-type {
    description
      "Tdm parameters of CCC instance.";
    leaf tdm-encapsulate-number {
      ext:dynamic-default;
      type uint32 {
        range "1..40";
      }
      description
        "Number of TDM frames encapsulated in a CESoPSN or SAToP packet in the TDMoPSN application.";
    }
    leaf jitter-buffer {
      ext:dynamic-default;
      type uint32 {
        range "1..64000";
      }
      units "us";
      description
        "Depth of the jitter buffer in the application of TDMoPSN.";
    }
    leaf rtp-header {
      type boolean;
      default "false";
      description
        "Enable/disable the RTP header of transparently transmitted TDM frames.";
    }
    leaf idle-code {
      type yang:hex-string {
        length "1..2";
      }
      default "ff";
      description
        "Idle code that is filled when the jitter buffer underflow occurs.";
    }
  }

  grouping l2vpn-ccc-atm-type {
    description
      "L2VPN ATM class.";
    leaf max-atm-cells {
      type uint32 {
        range "1..28";
      }
      ext:dynamic-default;
      description
        "Maximum number of ATM cells to be encapsulated into a packet that can be received by a device.";
    }
    leaf atm-pack-overtime {
      type uint32 {
        range "100..10000";
      }
      units "us";
      ext:dynamic-default;
      description
        "Delay in encapsulating ATM cells into a packet.";
    }
  }

  grouping vpws-localccc-instance-grp {
    description
      "VPWS local CCC instance.";
    leaf encapsulation-type {
      ext:operation-exclude "update";
      type encapsulation-type;
      must "../encapsulation-type='vlan' or
../encapsulation-type='ethernet' or
../encapsulation-type='hdlc' or
../encapsulation-type='ppp' or
../encapsulation-type='atm-nto1-vcc' or
../encapsulation-type='atm-nto1-vpc' or
../encapsulation-type='atm-1to1-vcc' or
../encapsulation-type='atm-1to1-vpc' or
../encapsulation-type='atm-trans-cell' or
../encapsulation-type='cep' or
../encapsulation-type='satop-e1' or
../encapsulation-type='cesopsn-basic' or
../encapsulation-type='ip-interworking' or
../encapsulation-type='unsupport'" {
        tailf:xpath-root 3;
      }
      mandatory true;
      description
        "Encapsulation type of a VPWS instance.";
    }
    container tdm-parameter {
      when "../encapsulation-type='satop-e1' or
../encapsulation-type='cesopsn-basic' or
../encapsulation-type='cep' or
../encapsulation-type='satop-t1' or
../encapsulation-type='satop-e3'" {
        tailf:xpath-root 3;
      }
      description
        "Configure TDM parameters.";
      leaf tdm-encapsulate-number {
        type uint32 {
          range "1..40";
        }
        ext:dynamic-default;
        description
          "Number of TDM frames encapsulated in a CESoPSN or SAToP packet in the TDMoPSN application.";
      }
      leaf jitter-buffer {
        type uint32 {
          range "1..64000";
        }
        units "us";
        ext:dynamic-default;
        description
          "Depth of the jitter buffer in the application of TDMoPSN.";
      }
      leaf rtp-header {
        type boolean;
        default "false";
        description
          "Enable/disable transparently transmission of TDM frames.";
      }
      leaf idle-code {
        type yang:hex-string {
          length "1..2";
        }
        default "ff";
        description
          "Idle code that is filled when the jitter buffer underflow occurs.";
      }
    }
    container atm-parameter {
      when "../encapsulation-type='atm-aal5-sdu' or
../encapsulation-type='atm-trans-cell' or
../encapsulation-type='atm-nto1-vcc' or
../encapsulation-type='atm-nto1-vpc' or
../encapsulation-type='atm-1to1-vcc' or
../encapsulation-type='atm-1to1-vpc' or
../encapsulation-type='atm-aal5-pdu'" {
        tailf:xpath-root 3;
      }
      description
        "Configure ATM parameters.";
      leaf max-atm-cells {
        type uint32 {
          range "1..28";
        }
        ext:dynamic-default;
        description
          "Maximum number of ATM cells to be encapsulated into a packet that can be received by a device.";
      }
      leaf atm-pack-overtime {
        type uint32 {
          range "100..10000";
        }
        units "us";
        ext:dynamic-default;
        description
          "Delay in encapsulating ATM cells into a packet.";
      }
    }
    container acs {
      description
        "List of information about all ACs.";
      list ac {
        ext:operation-exclude "update|delete";
        must "(not(arp-entry)) or (arp-entry and (/ifm:ifm/ifm:interfaces/ifm:interface[ifm:name=current()/interface-name]/ifm:link-protocol='ethernet'))" {
          tailf:xpath-root 3;
        }
        key "interface-name";
        min-elements 2;
        max-elements 2;
        description
          "Configure information about an AC. AC information is displayed in a configuration order.";
        leaf interface-name {
          type leafref {
            path "/ncs:devices/ncs:device/ncs:config/ifm:ifm/ifm:interfaces/ifm:interface/ifm:name" {
              tailf:xpath-root 3;
            }
          }
          description
            "Name of an AC interface.";
        }
        leaf tagged {
          ext:operation-exclude "update|delete";
          when "../../../encapsulation-type='ethernet' or
../../../encapsulation-type='vlan'" {
            tailf:xpath-root 3;
          }
          type boolean;
          ext:dynamic-default {
            ext:default-value "false" {
              when "../../../encapsulation-type='ethernet'" {
                tailf:xpath-root 3;
              }
              description
                "The default value is false when encapsulation-type is ethernet.";
            }
            ext:default-value "true" {
              when "../../../encapsulation-type='vlan'" {
                tailf:xpath-root 3;
              }
              description
                "The default value is true when encapsulation-type is VLAN.";
            }
          }
          must "(../../../encapsulation-type='ethernet' and ../tagged='false') or
(../../../encapsulation-type='vlan' and ../tagged='true')" {
            tailf:xpath-root 3;
          }
          description
            "Enable/disable the VLAN tag setting.";
        }
        leaf access-port {
          ext:operation-exclude "update|delete";
          when "../../../encapsulation-type='ethernet' or
../../../encapsulation-type='ip-interworking' or
../../../encapsulation-type='ip-layer2' or
../../../encapsulation-type='vlan'" {
            tailf:xpath-root 3;
          }
          type boolean;
          must "/ifm:ifm/ifm:interfaces/ifm:interface[ifm:name=current()/../interface-name]/ifm:class='main-interface' or (/ifm:ifm/ifm:interfaces/ifm:interface[ifm:name=current()/../interface-name]/ifm:class='sub-interface' and ../access-port = 'false')" {
            tailf:xpath-root 3;
          }
          default "false";
          description
            "Enable/disable the attribute that allows only untagged packets to pass through an interface.";
        }
        leaf trigger-interface-down {
          type boolean;
          must "(/ifm:ifm/ifm:interfaces/ifm:interface[ifm:name=current()/../interface-name]/ifm:class='main-interface' and /ifm:ifm/ifm:interfaces/ifm:interface[ifm:name=current()/../interface-name]/ifm:link-protocol='ethernet' and . = 'true') or (. = 'false')" {
            tailf:xpath-root 3;
          }
          default "false";
          description
            "Enable/disable remote interface shutdown-based association between the PW status and interface status.";
        }
        // NCS drop config false leaf state
        // NCS drop config false leaf 'token-exceed'
        container arp-entry {
          presence "Enable the ARP entry for AC.";
          description
            "Configure the ARP entry attribute used for IP interworking between PEs.";
          leaf local-ce-mac {
            type pub-type:mac-address;
            description
              "MAC address of the ethernet interface or sub-interface on a CE connected to the local AC interface. If MAC, IP, and broadcast addresses are all configured, these addresses take effect in the sequence of MAC address, IP address, and broadcast address.";
          }
          leaf local-ce-ip {
            type inet:ipv4-address-no-zone;
            description
              "IP address of the ethernet interface or sub-interface on a CE connected to the local AC interface.";
          }
          leaf local-ce-broadcast {
            type boolean;
            must "((.='false' and (../local-ce-mac or ../local-ce-ip or ../remote-ce-ip)) or (.='true'))" {
              tailf:xpath-root 3;
            }
            default "false";
            description
              "Enable/disable the broadcast function on a PE Ethernet interface connected to a CE.";
          }
          leaf remote-ce-ip {
            type inet:ipv4-address-no-zone;
            description
              "IP address of the remote CE connected to the local AC interface.";
          }
        }
        // NCS drop config false container 'ac-arps'
      }
    }
  }

  grouping vpws-remoteccc-instance-grp {
    description
      "VPWS remote CCC instance.";
    leaf encapsulation-type {
      ext:operation-exclude "update";
      ext:support-filter "true";
      type encapsulation-type;
      must "../encapsulation-type='vlan' or
../encapsulation-type='ethernet' or
../encapsulation-type='hdlc' or
../encapsulation-type='ppp' or
../encapsulation-type='atm-nto1-vcc' or
../encapsulation-type='atm-nto1-vpc' or
../encapsulation-type='atm-1to1-vcc' or
../encapsulation-type='atm-1to1-vpc' or
../encapsulation-type='cep' or
../encapsulation-type='satop-e1' or
../encapsulation-type='cesopsn-basic' or
../encapsulation-type='ip-interworking' or
../encapsulation-type='unsupport'" {
        tailf:xpath-root 3;
      }
      mandatory true;
      description
        "Encapsulation type of a VPWS instance.";
    }
    container acs {
      description
        "List of information about all ACs.";
      list ac {
        ext:operation-exclude "update|delete";
        must "(not(arp-entry)) or (arp-entry and (/ifm:ifm/ifm:interfaces/ifm:interface[ifm:name=current()/interface-name]/ifm:link-protocol='ethernet'))" {
          tailf:xpath-root 3;
        }
        key "interface-name";
        min-elements 1;
        max-elements 1;
        description
          "Configure information about an AC.";
        leaf interface-name {
          type leafref {
            path "/ncs:devices/ncs:device/ncs:config/ifm:ifm/ifm:interfaces/ifm:interface/ifm:name" {
              tailf:xpath-root 3;
            }
          }
          description
            "Name of an AC interface.";
        }
        leaf tagged {
          ext:operation-exclude "update|delete";
          when "../../../encapsulation-type='ethernet' or
../../../encapsulation-type='vlan'" {
            tailf:xpath-root 3;
          }
          type boolean;
          ext:dynamic-default {
            ext:default-value "false" {
              when "../../../encapsulation-type='ethernet'" {
                tailf:xpath-root 3;
              }
              description
                "The default value is false when encapsulation-type is ethernet.";
            }
            ext:default-value "true" {
              when "../../../encapsulation-type='vlan'" {
                tailf:xpath-root 3;
              }
              description
                "The default value is true when encapsulation-type is VLAN.";
            }
          }
          must "(../../../encapsulation-type='ethernet' and ../tagged='false') or
(../../../encapsulation-type='vlan' and ../tagged='true')" {
            tailf:xpath-root 3;
          }
          description
            "Enable/disable the VLAN tag setting.";
        }
        // NCS drop config false leaf state
        // NCS drop config false leaf 'token-exceed'
        container arp-entry {
          presence "Enable the ARP entry for AC.";
          description
            "Configure the ARP entry attribute used for IP interworking between PEs.";
          leaf local-ce-mac {
            type pub-type:mac-address;
            description
              "MAC address of the Ethernet interface or sub-interface on a CE connected to the local AC interface. If MAC, IP, and broadcast addresses are all configured, these addresses take effect in the sequence of MAC address, IP address, and broadcast address.";
          }
          leaf local-ce-ip {
            type inet:ipv4-address-no-zone;
            description
              "IP address of the Ethernet interface or sub-interface on a CE connected to the local AC interface.";
          }
          leaf local-ce-broadcast {
            type boolean;
            must "((.='false' and (../local-ce-mac or ../local-ce-ip or ../remote-ce-ip)) or (.='true'))" {
              tailf:xpath-root 3;
            }
            default "false";
            description
              "Enable/disable broadcast on a PE Ethernet interface connected to a CE.";
          }
          leaf remote-ce-ip {
            type inet:ipv4-address-no-zone;
            description
              "IP address of the remote CE connected to the local AC interface.";
          }
        }
        // NCS drop config false container 'ac-arps'
      }
    }
    container pw {
      ext:operation-exclude "update|delete";
      must '(out-interface-name and not(next-hop)) or (not(out-interface-name) and next-hop)' {
        tailf:xpath-root 3;
      }
      description
        "Configure a VPWS remote CCC PW.";
      leaf out-label {
        ext:operation-exclude "update";
        type uint32 {
          range "0..1048575";
        }
        mandatory true;
        description
          "Label for sending packets.";
      }
      leaf in-label {
        ext:operation-exclude "update";
        type uint32 {
          range "16..1048575";
        }
        mandatory true;
        description
          "Label for receiving packets.";
      }
      leaf control-word {
        ext:operation-exclude "update|delete";
        type l2vpn-control-word;
        must ".!='prefer'" {
          tailf:xpath-root 3;
        }
        default "default";
        description
          "Enable the control word function. The control word is usually used for TDM, ATM, and FR PWs.";
      }
      leaf out-interface-name {
        ext:operation-exclude "update|delete";
        type leafref {
          path "/ncs:devices/ncs:device/ncs:config/ifm:ifm/ifm:interfaces/ifm:interface/ifm:name" {
            tailf:xpath-root 3;
          }
        }
        description
          "Outbound interface.";
      }
      leaf next-hop {
        ext:operation-exclude "update|delete";
        type inet:ipv4-address-no-zone;
        description
          "Next hop.";
      }
    }
  }

  grouping vpws-swtich-instance-grp {
    description
      "VPWS switch instance.";
    leaf switch-type {
      ext:operation-exclude "update";
      type l2vpn-switch-type;
      mandatory true;
      description
        "Switch type of a VPWS switch instance.";
    }
    leaf encapsulation-type {
      type encapsulation-type;
      must "../encapsulation-type='fr' or
../encapsulation-type='atm-aal5-sdu' or
../encapsulation-type='atm-trans-cell' or
../encapsulation-type='vlan' or
../encapsulation-type='ethernet' or
../encapsulation-type='hdlc' or
../encapsulation-type='ppp' or
../encapsulation-type='atm-nto1-vcc' or
../encapsulation-type='atm-nto1-vpc' or
../encapsulation-type='ip-layer2' or
../encapsulation-type='atm-1to1-vcc' or
../encapsulation-type='atm-1to1-vpc' or
../encapsulation-type='atm-aal5-pdu' or
../encapsulation-type='cep' or
../encapsulation-type='satop-e1' or
../encapsulation-type='satop-t1' or
../encapsulation-type='satop-e3' or
../encapsulation-type='cesopsn-basic' or
../encapsulation-type='ip-interworking'" {
        tailf:xpath-root 3;
      }
      mandatory true;
      description
        "Encapsulation type of a VPWS switch instance.";
    }
    leaf control-word-trans {
      type boolean;
      default "false";
      description
        "Enable/disable the control word of a VPWS switching instance to be transparently transmitted.";
    }
    leaf control-word {
      when "not(../switch-type='ldp-ldp' or ../switch-type='ldp-ldp-bak')" {
        tailf:xpath-root 3;
      }
      type l2vpn-control-word;
      must ".!='prefer'" {
        tailf:xpath-root 3;
      }
      default "default";
      description
        "Enable the control word function. The control word function is usually used for TDM, ATM, and FR PWs.";
    }
    leaf mtu {
      when "../switch-type='ldp-svc' and (../encapsulation-type='vlan' or ../encapsulation-type='ethernet')" {
        tailf:xpath-root 3;
      }
      type uint16 {
        range "46..9600";
      }
      default "1500";
      description
        "MTU of a VPWS switch instance.";
    }
    leaf bit-error-detection {
      when "../switch-type='ldp-ldp'" {
        tailf:xpath-root 3;
      }
      type boolean;
      default "false";
      description
        "Enable/disable bit error detection on SPEs for an LDP MS-PW.";
    }
    // NCS drop config false leaf 'create-time'
    // NCS drop config false leaf 'up-time'
    // NCS drop config false leaf 'last-change-time'
    container pws {
      description
        "List of VPWS PWs.";
      list pw {
        ext:operation-exclude "update|delete";
        must 'pw-id and peer-ip' {
          tailf:xpath-root 3;
        }
        must "(((../../switch-type='ldp-svc' and role='right-primary') or ../../switch-type='svc-svc') and transmit-label and receive-label) or not((../../switch-type='ldp-svc' and role='right-primary') or ../../switch-type='svc-svc')" {
          tailf:xpath-root 3;
        }
        key "role";
        unique "peer-ip";
        min-elements 2;
        max-elements 3;
        description
          "Configure a PW in a VPWS switching instance.";
        leaf role {
          type ms-pw-role-type;
          description
            "Role of a PW.";
        }
        leaf pw-id {
          ext:operation-exclude "update|delete";
          type uint32 {
            range "1..4294967295";
          }
          description
            "PW ID.";
        }
        leaf peer-ip {
          ext:operation-exclude "update|delete";
          type l2vpn-peer-address-type;
          description
            "IP address of a peer.";
        }
        leaf transmit-label {
          ext:operation-exclude "update|delete";
          when "(../../../switch-type='ldp-svc' and ../role='right-primary') or ../../../switch-type='svc-svc'" {
            tailf:xpath-root 3;
          }
          type uint32 {
            range "0..1048575";
          }
          description
            "Static label for sending packets.";
        }
        leaf receive-label {
          ext:operation-exclude "update|delete";
          when "(../../../switch-type='ldp-svc' and ../role='right-primary') or ../../../switch-type='svc-svc'" {
            tailf:xpath-root 3;
          }
          type uint32 {
            range "16..1048575";
          }
          description
            "Static label for receiving packets.";
        }
        leaf tunnel-policy {
          type string {
            length "1..39";
          }
          description
            "Name of a tunnel policy. If the tunnel policy name is not specified, the system uses the default tunnel policy. The default tunnel policy preferentially selects LSPs for packet transmission and the number of load-balancing tunnels is 1. If the tunnel policy name is specified but the corresponding tunnel policy does not exist, the system still uses the default tunnel policy.";
        }
        container flow-label {
          must "ability or oam-packet-pop='true'" {
            tailf:xpath-root 3;
          }
          presence "enbale flow label for pw";
          description
            "Enable/disable the flow label of a PW.";
          leaf ability {
            ext:operation-exclude "delete";
            when "../../../../switch-type='ldp-svc' and ../oam-packet-pop ='false'" {
              tailf:xpath-root 3;
            }
            type flow-label-ability;
            must ".!='default' and .!='disable'" {
              tailf:xpath-root 3;
            }
            description
              "Flow label capability. The values of the ability node at both ends of a PW must be consistent.";
          }
          leaf oam-packet-pop {
            type boolean;
            default "false";
            description
              "Enable/disable the function of popping out flow labels in the OAM packets.";
          }
        }
        container hard-pipe {
          when "../../../switch-type='svc-svc' or (../../../switch-type='ldp-svc' and ../role='right-primary')" {
            tailf:xpath-root 3;
          }
          presence "Enable hard pipe for pw.";
          description
            "Enable/disable hard pipe.";
          leaf bandwidth {
            when "../../../../encapsulation-type='ethernet' or ../../../../encapsulation-type='vlan'" {
              tailf:xpath-root 3;
            }
            type uint32 {
              range "16..4294967294";
            }
            units "kbit/s";
            mandatory true;
            description
              "Specify bandwidth value.";
          }
          leaf expand-ratio {
            type uint16 {
              range "0..10000";
            }
            default "10";
            description
              "Specify the value of bandwidth expand ratio (%). As to CES service, expand ratio ranges from 0 to 10000. The other service, expand ratio ranges from 0 to 100.";
          }
        }
        container tdm-parameter {
          when "../../../switch-type='ldp-svc' and
(../../../encapsulation-type='cep' or
../../../encapsulation-type='cesopsn-basic' or
../../../encapsulation-type='satop-e1' or
../../../encapsulation-type='satop-t1' or
../../../encapsulation-type='satop-e3') and
(../role='left-primary')" {
            tailf:xpath-root 3;
          }
          description
            "Configure TDM parameters.";
          leaf tdm-encapsulate-number {
            when "../../../../encapsulation-type='cesopsn-basic' or
../../../../encapsulation-type='satop-e1' or
../../../../encapsulation-type='satop-t1' or
../../../../encapsulation-type='satop-e3'" {
              tailf:xpath-root 3;
            }
            type uint32 {
              range "1..5000";
            }
            ext:dynamic-default;
            description
              "Number of TDM frames encapsulated in a CESoPSN or SAToP packet in the TDMoPSN application.";
          }
          leaf rtp-header {
            type l2vpn-rtp-header-type;
            default "false";
            description
              "Add the RTP header to transparently transmitted TDM frames.";
          }
          leaf time-slot {
            when "../../../../encapsulation-type='cesopsn-basic'" {
              tailf:xpath-root 3;
            }
            type uint32 {
              range "1..32";
            }
            description
              "Number of time slots on an interface.";
          }
        }
        // NCS drop config false container 'pw-info'
      }
    }
    container reliability {
      when "../switch-type='ldp-ldp-bak'" {
        tailf:xpath-root 3;
      }
      description
        "Configure PW reliability.";
      leaf redundancy-mode {
        type pw-redundancy-mode;
        must "../redundancy-mode='master'" {
          tailf:xpath-root 3;
        }
        default "master";
        description
          "PW redundancy mode.";
      }
      leaf switchover {
        type boolean;
        default "false";
        description
          "Enable/disable the PW switchover.";
      }
      container reroute {
        description
          "Configure a switchback policy list.";
        leaf reroute-policy {
          type l2vpn-reroute-mode;
          default "delay";
          description
            "Switchback policy.";
        }
        leaf delay-time {
          when "../reroute-policy='delay'" {
            tailf:xpath-root 3;
          }
          type uint32 {
            range "10..10800";
          }
          units "s";
          default "30";
          description
            "Delay for switching traffic back to the primary PW.";
        }
        // NCS drop config false leaf 'last-switchback-reason'
        // NCS drop config false leaf 'last-switchback-time'
        // NCS drop config false leaf 'delay-residual'
      }
    }
  }

  grouping vpws-bgp-instance-grp {
    description
      "VPWS BGP VPN instance connection.";
    leaf vpn-instance {
      type leafref {
        path "/ncs:devices/ncs:device/ncs:config/l2vpn/common/vpws-bgp-vpns/vpws-bgp-vpn/name" {
          tailf:xpath-root 3;
        }
      }
      mandatory true;
      description
        "VPWS BGP instance.";
    }
    leaf local-site {
      type leafref {
        path "/ncs:devices/ncs:device/ncs:config/l2vpn/common/vpws-bgp-vpns/vpws-bgp-vpn/sites/site/name" {
          tailf:xpath-root 3;
        }
      }
      mandatory true;
      description
        "Local site name.";
    }
    container acs {
      description
        "List of attachment circuits in a VPWS BGP VPN instance.";
      list ac {
        key "interface-name";
        min-elements 1;
        max-elements 1;
        description
          "Configure a connection attachment circuit.";
        leaf interface-name {
          type leafref {
            path "/ncs:devices/ncs:device/ncs:config/ifm:ifm/ifm:interfaces/ifm:interface/ifm:name" {
              tailf:xpath-root 3;
            }
          }
          description
            "VPWS BGP VPN instance connection attachment circuit interface name. The encapsulation type of this interface must be the same as that of the VPN instance. Otherwise, the PW cannot go Up.";
        }
        leaf tagged {
          when "/l2vpn:l2vpn/l2vpn:common/l2vpn:vpws-bgp-vpns/l2vpn:vpws-bgp-vpn[l2vpn:name=current()/../../../l2vpn:vpn-instance]/l2vpn:encapsulation-type !='ip-interworking' and /l2vpn:l2vpn/l2vpn:common/l2vpn:vpws-bgp-vpns/l2vpn:vpws-bgp-vpn[l2vpn:name=current()/../../../l2vpn:vpn-instance]/l2vpn:encapsulation-type !='ip-layer2'" {
            tailf:xpath-root 3;
          }
          ext:operation-exclude "update|delete";
          type boolean;
          description
            "Enable/disable the attachment circuit tag of the VPWS BGP instance.";
          ext:dynamic-default;
        }
        leaf trigger-interface-down {
          type boolean;
          must "(/ifm:ifm/ifm:interfaces/ifm:interface[ifm:name=current()/../interface-name]/ifm:class='main-interface' and /ifm:ifm/ifm:interfaces/ifm:interface[ifm:name=current()/../interface-name]/ifm:link-protocol='ethernet' and . = 'true') or (. = 'false')" {
            tailf:xpath-root 3;
          }
          default "false";
          description
            "Enable/disable remote interface shutdown-based association between the PW status and interface status.";
        }
        // NCS drop config false leaf state
        // NCS drop config false leaf 'token-exceed'
      }
    }
    container pws {
      description
        "List of PWs.";
      list pw {
        key "remote-site-id";
        unique "role";
        min-elements 1;
        description
          "Configure a PW.";
        leaf remote-site-id {
          type uint16 {
            range "0..65534";
          }
          must '../l2vpn:remote-site-id < (/l2vpn:l2vpn/l2vpn:common/l2vpn:vpws-bgp-vpns/l2vpn:vpws-bgp-vpn[l2vpn:name=current()/../../../l2vpn:vpn-instance]/l2vpn:sites/l2vpn:site[l2vpn:name = current()/../../../l2vpn:local-site]/range + /l2vpn:l2vpn/l2vpn:common/l2vpn:vpws-bgp-vpns/l2vpn:vpws-bgp-vpn[l2vpn:name = current()/../../../l2vpn:vpn-instance]/l2vpn:sites/l2vpn:site[l2vpn:name = current()/../../../l2vpn:local-site]/default-offset) and ../l2vpn:remote-site-id >= /l2vpn:l2vpn/l2vpn:common/l2vpn:vpws-bgp-vpns/l2vpn:vpws-bgp-vpn[l2vpn:name = current()/../../../l2vpn:vpn-instance]/l2vpn:sites/l2vpn:site[l2vpn:name = current()/../../../l2vpn:local-site]/default-offset' {
            tailf:xpath-root 3;
          }
          description
            "VPWS BGP VPN instance connection remote customer edge identifier.";
        }
        leaf role {
          ext:operation-exclude "update|delete";
          type pw-role-type;
          must "(.='primary') or (.='backup' and ../../pw[role='primary'])" {
            tailf:xpath-root 3;
          }
          default "primary";
          description
            "VPWS BGP VPN instance connection pseudo wire role. Configure a primary PW first. The PW role canot be changed.";
        }
        leaf tunnel-policy {
          type string {
            length "1..39";
          }
          description
            "VPWS BGP VPN instance connection tunnel policy name.";
        }
        leaf traffic-statistics-collection {
          type boolean;
          default "false";
          description
            "Enable/disable connection traffic statistics collection of a VPWS BGP VPN instance.";
        }
        leaf manual-set-fault {
          type boolean;
          default "false";
          description
            "Enable/disable the manual setting of faults in a VPWS BGP VPN instance connection.";
        }
        container bfd {
          when '/bfd:bfd' {
            tailf:xpath-root 3;
          }
          must "/l2vpn:l2vpn/l2vpn:common/l2vpn:vpws-bgp-vpns/l2vpn:vpws-bgp-vpn[l2vpn:name=current()/../../../l2vpn:vpn-instance]/l2vpn:control-word='enable'" {
            tailf:xpath-root 3;
          }
          presence "enable pw bfd.";
          description
            "Enable/disable BFD for PW in a VPWS BGP VPN instance.";
          uses l2vpn-dyn-bfd-para-type;
          leaf track-interface {
            type boolean;
            default "false";
            description
              "Enable/disable BFD track interface state.";
          }
        }
        // NCS drop config false container 'pw-info'
        // NCS drop config false container tunnels
        // NCS drop config false container 'traffic-statistics'
      }
    }
    container reliability {
      when 'count(../pws/pw)=2' {
        tailf:xpath-root 3;
      }
      description
        "Configure PW reliability.";
      leaf redundancy-mode {
        type pw-redundancy-mode;
        must "../redundancy-mode='frr'" {
          tailf:xpath-root 3;
        }
        default "frr";
        description
          "PW redundancy mode.";
      }
      leaf dual-receive {
        type boolean;
        default "false";
        description
          "Enable/disable the receipt of both the primary and secondary PWs to receive packets.";
      }
      container reroute {
        description
          "Configure a switchback policy list.";
        leaf reroute-policy {
          type l2vpn-reroute-mode;
          default "delay";
          description
            "Switchback policy.";
        }
        leaf delay-time {
          when "../reroute-policy='delay'" {
            tailf:xpath-root 3;
          }
          type uint32 {
            range "10..10800";
          }
          units "s";
          default "30";
          description
            "Delay for switching traffic back to the primary PW.";
        }
        leaf resume-time {
          when "not(../reroute-policy='never')" {
            tailf:xpath-root 3;
          }
          type uint32 {
            range "0..600";
          }
          units "s";
          default "10";
          description
            "Time after which the peer PE on the secondary PW is notified that the local PE has recovered. This parameter can be configured only in FRR mode.";
        }
        // NCS drop config false leaf 'last-switchback-reason'
        // NCS drop config false leaf 'last-switchback-time'
        // NCS drop config false leaf 'delay-residual'
        // NCS drop config false leaf 'resume-residual'
      }
    }
    container oam-mapping {
      presence "enable AC OAM mapping";
      description
        "Enable/disable OAM mapping.";
      leaf type {
        type ac-oam-mapping-type;
        must "(../type='1ag' and ../md-name and ../ma-name) or ../type!='1ag'" {
          tailf:xpath-root 3;
        }
        mandatory true;
        description
          "VPWS attachment circuit OAM mapping type.";
      }
      leaf md-name {
        ext:operation-exclude "update|delete";
        when "../type='1ag'" {
          tailf:xpath-root 3;
        }
        type string {
          length "1..43";
        }
        description
          "VPWS OAM mapping parameter md name.";
      }
      leaf ma-name {
        ext:operation-exclude "update|delete";
        when "../type='1ag'" {
          tailf:xpath-root 3;
        }
        type string {
          length "1..43";
        }
        description
          "VPWS OAM mapping parameter ma name.";
      }
    }
  }

  grouping vpls-instance-grp {
    description
      "VPLS instance.";
    leaf member-discovery-mode {
      type l2vpn-vpls-vsi-mem-disc-type;
      default "default";
      description
        "VPLS member discovery mode for a specified VSI.";
    }
    leaf work-mode {
      ext:operation-exclude "update";
      type vsi-work-mode;
      default "normal";
      description
        "Workmode of a VSI.";
    }
    leaf encapsulation-type {
      type l2vpn-vpls-encap-type;
      must ".='vlan' or not(../etree)" {
        tailf:xpath-root 3;
      }
      default "vlan";
      description
        "Encapsulation type of a VSI.";
    }
    leaf mtu {
      type uint16 {
        range "46..65535";
      }
      default "1500";
      description
        "VPLS MTU.";
    }
    leaf tunnel-policy {
      type string {
        length "1..39";
      }
      description
        "Name of a tunnel policy for a VSI. If the tunnel policy name is not specified, the system uses the default tunnel policy. The default tunnel policy preferentially selects LSPs for packet transmission and the number of load-balancing tunnels is 1. If the tunnel policy name is specified but the corresponding tunnel policy does not exist, the system still uses the default tunnel policy.";
    }
    leaf shutdown {
      type boolean;
      default "false";
      description
        "Enable/disable the function of shutting down a specified VSI.";
    }
    leaf isolate-spoken {
      when "../work-mode='normal'" {
        tailf:xpath-root 3;
      }
      type boolean;
      must ".='false' or not(../etree)" {
        tailf:xpath-root 3;
      }
      default "false";
      description
        "Enable/disable forwarding isolation between AC interfaces, between UPE PWs, and between ACs and UPE PWs in a VSI.";
    }
    leaf isolate-spoken-include-multicast {
      when "../isolate-spoken='true'" {
        tailf:xpath-root 3;
      }
      type boolean;
      must ".='false' or not(../etree)" {
        tailf:xpath-root 3;
      }
      default "false";
      description
        "Enable/disable isolating forwarding between AC interfaces, between UPE PWs, and between ACs and UPE PWs in a VSI.";
    }
    leaf ignore-ac-state {
      type boolean;
      default "false";
      description
        "Enable/disable the function for the VSI status not to be affected by changes in the AC status.";
    }
    leaf response-ac-state {
      when "../work-mode='bd-mode'" {
        tailf:xpath-root 3;
      }
      type boolean;
      default "false";
      description
        "Enable/disable the function for the BD VSI status to be affected by changes in the BD AC status.";
    }
    leaf admin-vsi {
      type boolean;
      must "(.='false') or (.='true' and ../isolate-spoken='false' and not(../etree))" {
        tailf:xpath-root 3;
      }
      default "false";
      description
        "Enable/disable the function for the current service VSI to be configured as the mVSI.";
    }
    leaf track-admin-vsi {
      ext:operation-exclude "update|delete";
      when "../work-mode='normal' or ../work-mode='b-vsi'" {
        tailf:xpath-root 3;
      }
      type string {
        length "1..31";
      }
      must "(../admin-vsi='false' and /l2vpn:l2vpn/l2vpn:instances/l2vpn:instance[l2vpn:name=current()][l2vpn:type='vpls']/l2vpn:vpls/l2vpn:admin-vsi='true')" {
        tailf:xpath-root 3;
      }
      description
        "Name of the mVSI to which a service VSI is bound.";
    }
    leaf unknown-unicast-action {
      when "not(../work-mode='bd-mode')" {
        tailf:xpath-root 3;
      }
      type l2vpn-vpls-unknow-frame-act;
      default "broadcast";
      description
        "Action taken to process unknown unicast frames.";
    }
    leaf unknown-multicast-action {
      when "not(../work-mode='bd-mode')" {
        tailf:xpath-root 3;
      }
      type l2vpn-vpls-unknow-frame-act;
      must "((.='broadcast' or .='drop'))" {
        tailf:xpath-root 3;
      }
      default "broadcast";
      description
        "Action taken to process unknown multicast frames.";
    }
    leaf isolate-hub-ac-pw {
      when "../work-mode='normal'" {
        tailf:xpath-root 3;
      }
      type boolean;
      must ".='false' or not(../etree)" {
        tailf:xpath-root 3;
      }
      default "false";
      description
        "Enable/disable forwarding isolation between hub ACs and PWs in a VSI.";
    }
    leaf p2p-vsi {
      when "../work-mode='normal'" {
        tailf:xpath-root 3;
      }
      type boolean;
      must ".='false' or (.='true' and ../admin-vsi='false' and ../mac-learn='false' and ../mac-learn-style='unqualify' and not(../etree))" {
        tailf:xpath-root 3;
      }
      default "false";
      description
        "Enable/disable the P2P VSI.";
    }
    leaf traffic-statistics-collection {
      when "../work-mode='normal' or ../work-mode='bd-mode'" {
        tailf:xpath-root 3;
      }
      type boolean;
      default "false";
      description
        "Enable/disable VSI QoS traffic statistics collection.";
    }
    leaf mac-remove-mode {
      type mac-remove-type;
      must "((not(.='all-from-me')) or ((.='all-from-me') and (not(../work-mode='bd-mode')) and (not(../work-mode='b-vsi')) and (not(../work-mode='i-vsi')) and (not(../work-mode='i-vsi-p2p')) and (not(../work-mode='i-vsi-b-evpn-interworking'))))" {
        tailf:xpath-root 3;
      }
      default "invalid";
      description
        "Local MAC remove mode.";
    }
    leaf mac-learn {
      when "not(../work-mode='bd-mode')" {
        tailf:xpath-root 3;
      }
      type boolean;
      must ".='false' or (.='true' and ../p2p-vsi='false')" {
        tailf:xpath-root 3;
      }
      default "true";
      description
        "Enable/disable the function for a VSI to learn MAC addresses.";
    }
    leaf mac-learn-style {
      when "../work-mode='normal'" {
        tailf:xpath-root 3;
      }
      type l2vpn-mac-learn-style;
      must ".='unqualify' or not(../etree)" {
        tailf:xpath-root 3;
      }
      default "unqualify";
      description
        "MAC address learning style of PWs.";
    }
    leaf mac-age-time {
      when "not(../work-mode='bd-mode')" {
        tailf:xpath-root 3;
      }
      type uint32 {
        range "0 | 60..1000000";
      }
      units "s";
      description
        "MAC address aging timer that sets the aging time of MAC addresses.";
    }
    leaf local-mac-age-time {
      when "../work-mode='normal'" {
        tailf:xpath-root 3;
      }
      type uint32 {
        range "0 | 60..1000000";
      }
      units "s";
      description
        "Local MAC address aging timer that sets the aging time of MAC addresses.";
    }
    leaf remote-mac-age-time {
      when "../work-mode='normal'" {
        tailf:xpath-root 3;
      }
      type uint32 {
        range "0 | 60..1000000";
      }
      units "s";
      description
        "Remote MAC address aging timer that sets the aging time of MAC addresses.";
    }
    leaf mac-withdraw {
      type boolean;
      default "false";
      description
        "Enable/disable the function for a VSI to delete the local MAC address and notifies all remote peers of the deletion when an AC or a UPE fault occurs and the VSI remains up.";
    }
    leaf interface-change-mac-withdraw {
      when "not(../work-mode='i-vsi-b-evpn-interworking')" {
        tailf:xpath-root 3;
      }
      type boolean;
      default "false";
      description
        "Enable/disable the function for PEs to send LDP MAC withdraw messages to all peers when the status of the AC interface bound to the VSI changes.";
    }
    leaf interface-change-mac-withdraw-type {
      type interface-change-withdraw-type;
      must ".='all' or ../interface-change-mac-withdraw='true'" {
        tailf:xpath-root 3;
      }
      default "all";
      description
        "Specify the status change type for a VSI AC interface.";
    }
    leaf bd-pwtag-mac-withdraw {
      when "../work-mode='bd-mode'" {
        tailf:xpath-root 3;
      }
      type boolean;
      default "false";
      description
        "Enable/disable the function for LDP MAC withdraw messages to carry PW tag corresponding to the VSI bound to the bridge domain. This node can be configured only when the VSI works in BD mode.";
    }
    leaf bd-down-mac-withdraw {
      when "../work-mode='bd-mode'" {
        tailf:xpath-root 3;
      }
      type boolean;
      default "true";
      description
        "Enable/disable the function for PEs to send LDP MAC withdraw messages to all peers when BD goes down. This node can be configured only when the VSI works in BD mode.";
    }
    leaf propagate-mac-withdraw {
      when "not(../work-mode='i-vsi-b-evpn-interworking')" {
        tailf:xpath-root 3;
      }
      type boolean;
      default "false";
      description
        "Enable/disable the function for a PE to propagate LDP MAC withdraw messages to other peers after receiving the message from a remote peer.";
    }
    leaf mac-flush-rfc-compatible {
      when "../work-mode='normal' or ../work-mode='bd-mode'" {
        tailf:xpath-root 3;
      }
      type boolean;
      default "false";
      description
        "Enable/disable the transmission of standard MAC-flush message when the PW status changes.";
    }
    leaf vrrp-mac-withdraw-retry {
      type uint16 {
        range "0..60";
      }
      default "0";
      description
        "VRRP backup Mac withdraw retry.";
    }
    // NCS drop config false leaf 'token-exceed'
    // NCS drop config false leaf 'ac-count'
    // NCS drop config false leaf 'create-time'
    // NCS drop config false leaf 'ignore-ac-state-effect'
    container etree {
      when "../work-mode='normal'" {
        tailf:xpath-root 3;
      }
      must '(root-vlan and leaf-vlan) or ((not(root-vlan)) and (not(leaf-vlan)))' {
        tailf:xpath-root 3;
      }
      presence "Enable ethernet tree.";
      description
        "Enable/disable vpls ethernet tree.";
      leaf static {
        type boolean;
        must "../static='true'" {
          tailf:xpath-root 3;
        }
        default "true";
        description
          "Enable/disable static mode.";
      }
      leaf root-vlan {
        type uint16 {
          range "1..4094";
        }
        description
          "Specify root VLAN id.";
      }
      leaf leaf-vlan {
        type uint16 {
          range "1..4094";
        }
        description
          "Specify leaf VLAN id.";
      }
    }
    container ldp-signaling {
      presence "Label Distribution Protocol (LDP) signaling.";
      description
        "Enable/disable Label Distribution Protocol (LDP) signaling.";
      leaf vsi-id {
        ext:operation-exclude "update";
        type uint64 {
          range "1..4294967295";
        }
        must 'count(/l2vpn:l2vpn/l2vpn:instances/l2vpn:instance/l2vpn:vpls/l2vpn:ldp-signaling/l2vpn:vsi-id[.=current()])<=1' {
          tailf:xpath-root 3;
        }
        must 'count(/l2vpn:l2vpn/l2vpn:instances/l2vpn:instance/l2vpn:vpws-ldp/l2vpn:pws/l2vpn:pw/l2vpn:pw-id[.=current()])=0' {
          tailf:xpath-root 3;
        }
        must 'count(/l2vpn:l2vpn/l2vpn:instances/l2vpn:instance/l2vpn:vpws-switch/l2vpn:pws/l2vpn:pw/l2vpn:pw-id[.=current()])=0' {
          tailf:xpath-root 3;
        }
        description
          "VPLS LDP VSI ID. Can not be modified after configuration.";
      }
      leaf traffic-statistics-collection {
        when '../vsi-id' {
          tailf:xpath-root 3;
        }
        type boolean;
        must ". = 'false' or not(../../traffic-statistics-collection='true')" {
          tailf:xpath-root 3;
        }
        default "false";
        description
          "Enable/disable traffic statistics collection.";
      }
      leaf control-word {
        type l2vpn-control-word;
        must ".='disable' or .='enable'" {
          tailf:xpath-root 3;
        }
        default "disable";
        description
          "Enable the control word feature. The control word feature is usually used for TDM, ATM, and FR PWs.";
      }
      leaf hard-pipe {
        type boolean;
        must ".='false' or (../../work-mode='normal' and not(../../bgp-signaling) and not(../../bgpad-signaling) and ../../p2p-vsi='false')" {
          tailf:xpath-root 3;
        }
        default "false";
        description
          "Enable/disable hard pipe.";
      }
      leaf mac-withdraw {
        type boolean;
        must ".='false' or (../../mac-withdraw='false' and ../../propagate-mac-withdraw='false' and ../../interface-change-mac-withdraw='false')" {
          tailf:xpath-root 3;
        }
        default "false";
        description
          "Enable/disable the function for a VSI to delete the local MAC address and notify all remote peers of the deletion when an AC or a UPE fault occurs and the VSI remains up.";
      }
      leaf interface-change-mac-withdraw {
        type boolean;
        must ".='false' or  (.='true' and ../../mac-withdraw='false' and ../../propagate-mac-withdraw='false' and ../../interface-change-mac-withdraw='false' and ../../work-mode!='i-vsi-b-evpn-interworking')" {
          tailf:xpath-root 3;
        }
        default "false";
        description
          "Enable/disable the function for PEs to send LDP MAC withdraw messages to all peers when the status of the AC interface bound to the VSI changes.";
      }
      leaf interface-change-mac-withdraw-type {
        type interface-change-withdraw-type;
        must ".='all' or ../interface-change-mac-withdraw='true'" {
          tailf:xpath-root 3;
        }
        default "all";
        description
          "Specify the status change type for a VSI AC interface.";
      }
      leaf upe-upe-mac-withdraw {
        type boolean;
        must ".='false' or (../../mac-withdraw='false' and ../../propagate-mac-withdraw='false' and ../../interface-change-mac-withdraw='false' and ../../work-mode!='i-vsi')" {
          tailf:xpath-root 3;
        }
        default "false";
        description
          "Enable/disable the function for an NPE to forward the LDP MAC withdraw messages received from a UPE to other UPEs.";
      }
      leaf upe-npe-mac-withdraw {
        type boolean;
        must ".='false' or (../../mac-withdraw='false' and ../../propagate-mac-withdraw='false' and ../../interface-change-mac-withdraw='false' and ../../work-mode!='i-vsi')" {
          tailf:xpath-root 3;
        }
        default "false";
        description
          "Enable/disable the function for an NPE to forward the LDP MAC withdraw messages received from a UPE to other NPEs.";
      }
      leaf npe-upe-mac-withdraw {
        type boolean;
        must ".='false' or (../../mac-withdraw='false' and ../../propagate-mac-withdraw='false' and ../../interface-change-mac-withdraw='false' and ../../work-mode!='i-vsi')" {
          tailf:xpath-root 3;
        }
        default "false";
        description
          "Enable/disable the function for an NPE to forward the LDP MAC withdraw messages received from another NPE to UPEs.";
      }
      container flow-label {
        presence "enable flow-label for ldp signaling pws.";
        description
          "Enable/disable flow label capability of a PW.";
        leaf ability {
          type flow-label-ability;
          must ".!='default' and .!='disable'" {
            tailf:xpath-root 3;
          }
          mandatory true;
          description
            "Enable/disable flow label capability.";
        }
        leaf static {
          type boolean;
          default "false";
          description
            "Enable/disable the static flow label function.";
        }
      }
      container pws {
        when '../vsi-id' {
          tailf:xpath-root 3;
        }
        description
          "List of VPLS PWs.";
        list pw {
          key "peer-ip negotiation-vc-id encapsulation-type";
          description
            "Configure VPLS PWs.";
          leaf peer-ip {
            type inet:ipv4-address-no-zone;
            description
              "Peer IP address. The loopback IP address of a peer is usually used as the peer IP address.";
          }
          leaf negotiation-vc-id {
            type uint32 {
              range "1..4294967295";
            }
            description
              "PW ID used to uniquely identify a VC. The PW ID is usually used when both ends need to communicate but the VSI IDs on both ends are different.";
          }
          leaf encapsulation-type {
            type l2vpn-vpls-ldp-pw-encap-type;
            description
              "Encapsulation type of a VPLS PW. 'unsupport' indicates that the encapsulation type of a VSI is inherited.";
          }
          leaf role {
            ext:operation-exclude "update|delete";
            type vpls-pw-role-type;
            must "../role='primary' or (../role='backup' and  ../../pw[role='primary'])" {
              tailf:xpath-root 3;
            }
            default "primary";
            description
              "Role of a PW, either primary or secondary. Configure a primary PW first.";
          }
          leaf name {
            ext:operation-exclude "update";
            type string {
              length "1..15";
            }
            description
              "PW name.";
          }
          leaf signal-type {
            ext:operation-exclude "update|delete";
            type pw-signal-type;
            must "(../signal-type='ldp') or ../role!='backup'" {
              tailf:xpath-root 3;
            }
            must "(../signal-type='static' and ../tunnel-policy) or ../../../hard-pipe='false'" {
              tailf:xpath-root 3;
            }
            must "(../signal-type='static' and ../transmit-label and ../receive-label) or ../signal-type='ldp'" {
              tailf:xpath-root 3;
            }
            must "(.='static' and ../ignore-standby='false') or .!='static'" {
              tailf:xpath-root 3;
            }
            default "ldp";
            description
              "PW type, either dynamic or static.";
          }
          leaf transmit-label {
            ext:operation-exclude "update|delete";
            when "../signal-type='static'" {
              tailf:xpath-root 3;
            }
            type uint32 {
              range "0..1048575";
            }
            description
              "Label for sending packets.";
          }
          leaf receive-label {
            ext:operation-exclude "update|delete";
            when "../signal-type='static'" {
              tailf:xpath-root 3;
            }
            type uint32 {
              range "16..1048575";
            }
            description
              "Label for receiving packets.";
          }
          leaf control-word {
            when '../name' {
              tailf:xpath-root 3;
            }
            type l2vpn-control-word;
            default "default";
            description
              "Enable the control word function.";
          }
          leaf vccv {
            when '../name' {
              tailf:xpath-root 3;
            }
            type boolean;
            default "true";
            description
              "Enable/disable virtual circuit connectivity verification capability. VCCV supports two modes: control word and label alert.";
          }
          leaf ignore-standby {
            ext:operation-exclude "update|delete";
            type boolean;
            default "false";
            description
              "Enable/disable the function for the created PW to ignore the standby state sent from the peer device.";
          }
          leaf upe {
            ext:operation-exclude "update|delete";
            type boolean;
            default "false";
            description
              "Enable/disable the peer device as a UPE.";
          }
          leaf tunnel-policy {
            type string {
              length "1..39";
            }
            description
              "Name of the tunnel policy for a PW.";
          }
          leaf traffic-statistics-collection {
            type l2vpn-vpls-traffic-statistics-enable-type;
            must ". = 'default' or not(../../../../traffic-statistics-collection = 'true')" {
              tailf:xpath-root 3;
            }
            default "default";
            description
              "Enable the function to collect traffic statistics.";
          }
          leaf track-hub-pw {
            when '../name' {
              tailf:xpath-root 3;
            }
            type boolean;
            must "../track-hub-pw='false' or (../track-hub-pw='true' and ../upe='true' and ../../../../work-mode!='i-vsi-b-evpn-interworking')" {
              tailf:xpath-root 3;
            }
            default "false";
            description
              "Enable/disable the function for the spoke PW to track the hub PW. If a PW is not a spoke PW, it cannot track the hub PW.";
          }
          leaf ignore-stp-loop-check {
            when '../name' {
              tailf:xpath-root 3;
            }
            type boolean;
            default "false";
            description
              "Enable/disable the function of ignoring STP loops.";
          }
          leaf hard-pipe-bandwidth {
            ext:operation-exclude "delete";
            when "../../../hard-pipe='true'" {
              tailf:xpath-root 3;
            }
            type uint32 {
              range "16..4294967294";
            }
            units "kbit/s";
            description
              "Specify bandwidth value.";
          }
          leaf hard-pipe-burst-time {
            ext:operation-exclude "delete";
            when '../hard-pipe-bandwidth' {
              tailf:xpath-root 3;
            }
            type uint32 {
              range "100..5000";
            }
            units "us";
            default "100";
            description
              "Burst time.";
          }
          leaf status-code-change-flush-mac-disable {
            when '../name' {
              tailf:xpath-root 3;
            }
            type boolean;
            default "false";
            description
              "Enable/disable the function of flushing MAC when status code change.";
          }
          leaf ac-mode {
            ext:operation-exclude "update|delete";
            when "../../../../work-mode='bd-mode'" {
              tailf:xpath-root 3;
            }
            type boolean;
            default "false";
            description
              "Enable/disable the AC mode.";
          }
          leaf etree-mode {
            when '../../../../etree and ../name' {
              tailf:xpath-root 3;
            }
            type etree-work-mode;
            default "default";
            description
              "Specify e-tree work mode.";
          }
          leaf etree-leaf {
            when "../etree-mode = 'compatible'" {
              tailf:xpath-root 3;
            }
            type boolean;
            default "false";
            description
              "Enable/disable e-tree leaf.";
          }
          container flow-label {
            when '../name' {
              tailf:xpath-root 3;
            }
            presence "enable flow label";
            description
              "Enable/disable the flow label capability of a PW.";
            leaf ability {
              type flow-label-ability;
              must ".!='default'" {
                tailf:xpath-root 3;
              }
              mandatory true;
              description
                "Flow label capability.";
            }
            leaf static {
              type boolean;
              must ".='false' or ../ability!='disable'" {
                tailf:xpath-root 3;
              }
              default "false";
              description
                "Enable/disable the static flow label function.";
            }
          }
          container bfd {
            when '../name and /bfd:bfd' {
              tailf:xpath-root 3;
            }
            presence "enable vpls ldp pw bfd.";
            description
              "Enable/disable BFD.";
            leaf min-rx-interval {
              type uint16 {
                range "0..65535";
              }
              units "ms";
              default "10";
              description
                "Minimum receive interval.";
            }
            leaf min-tx-interval {
              type uint16 {
                range "0..65535";
              }
              units "ms";
              default "10";
              description
                "Minimum transmit interval.";
            }
            leaf detect-multiplier {
              type uint16 {
                range "3..50";
              }
              default "3";
              description
                "Detection multiplier.";
            }
            leaf option-tlv {
              type boolean;
              default "false";
              description
                "Enable/disable BFD detection with options.";
            }
          }
          // NCS drop config false container 'pw-info'
          uses l2vpn:suppression-statisticss-grp;
          uses l2vpn:pw-traffic-statisticss-grp;
          // NCS drop config false container 'hard-pipe-traffic-statistics'
        }
      }
      container redundancy-protect-groups {
        when '../vsi-id' {
          tailf:xpath-root 3;
        }
        description
          "List of VPLS PW protection groups.";
        list redundancy-protect-group {
          key "name";
          max-elements 32;
          description
            "Configure VPLS PW protection groups.";
          leaf name {
            type l2vpn-protect-group-name;
            description
              "Name of a PW protection group. The name is a string of case-sensitive characters.";
          }
          leaf protect-mode {
            type vpls-redundancy-mode;
            default "none";
            description
              "Switching mode of the PW protection group.";
          }
          leaf dual-receive {
            when "../protect-mode!='none'" {
              tailf:xpath-root 3;
            }
            type boolean;
            default "false";
            description
              "Enable/disable the receipt of both the primary and secondary PWs.";
          }
          leaf holdoff {
            when "../protect-mode='master'" {
              tailf:xpath-root 3;
            }
            type uint16 {
              range "1..180";
            }
            units "s";
            description
              "Hold time for traffic switching.";
          }
          container reroute-policy {
            when "../protect-mode='master'" {
              tailf:xpath-root 3;
            }
            description
              "Configure a switchback policy.";
            uses l2vpn:l2vpn-reroute-policy-type;
          }
          container pw-members {
            when "not(../protect-mode='none')" {
              tailf:xpath-root 3;
            }
            description
              "List of PW members in a protection group.";
            list pw-member {
              must '../../../../pws/pw[peer-ip=current()/peer-ip][negotiation-vc-id=current()/negotiation-vc-id][encapsulation-type=current()/encapsulation-type]' {
                tailf:xpath-root 3;
              }
              key "peer-ip negotiation-vc-id encapsulation-type";
              unique "preference";
              max-elements 2;
              description
                "Configure PW members in a protection group.";
              leaf peer-ip {
                type inet:ipv4-address-no-zone;
                description
                  "Peer IP address. The loopback IP address of a peer is usually used as the peer IP address.";
              }
              leaf negotiation-vc-id {
                type uint32 {
                  range "1..4294967295";
                }
                description
                  "PW ID used to uniquely identify a VC. The PW ID is usually used when both ends need to communicate but the VSI IDs on both ends are different.";
              }
              leaf encapsulation-type {
                type l2vpn-vpls-ldp-pw-encap-type;
                description
                  "Encapsulate type.";
              }
              leaf preference {
                type uint32 {
                  range "1..32";
                }
                mandatory true;
                description
                  "Priority of a PW in the PW protection group.";
              }
              // NCS drop config false leaf role
              // NCS drop config false leaf 'active-state'
            }
          }
          // NCS drop config false container historys
        }
      }
      // NCS drop config false container 'traffic-statistics'
    }
    container bgp-signaling {
      when "../work-mode='normal' or ../work-mode='bd-mode'" {
        tailf:xpath-root 3;
      }
      must "../admin-vsi!='true' and ../track-admin-vsi!='true' and ../p2p-vsi!='true' and (../mac-remove-mode='invalid' or (../mac-remove-mode!='invalid' and ../ldp-signaling))" {
        tailf:xpath-root 3;
      }
      must 'not(../etree)' {
        tailf:xpath-root 3;
      }
      presence "Container for bgp protocol vpls instance.";
      description
        "Enable/disable BGP VSIs.";
      leaf route-distinguisher {
        type string {
          length "3..21";
        }
        description
          "Route distinguisher.";
      }
      leaf encapsulation-rfc4761-compatible {
        type boolean;
        default "false";
        description
          "Enable/disable the function of changing an encapsulation type.";
      }
      leaf encapsulation-vpls-family-compatible {
        type boolean;
        default "false";
        description
          "Enable/disable the function of changing an encapsulation type to private mode.";
      }
      leaf mtu-negotiate-disable {
        type boolean;
        default "false";
        description
          "Enable/disable the function of ignoring MTU match between local VSI and remote VSI. The default implementation is match.";
      }
      leaf control-word {
        type l2vpn-control-word;
        must "((../control-word='disable' or ../control-word='enable' ) )" {
          tailf:xpath-root 3;
        }
        default "disable";
        description
          "Enable the control word feature. The control word feature is usually used for TDM, ATM, and FR PWs.";
      }
      // NCS drop config false leaf 'auto-route-distinguisher'
      container sites {
        description
          "List of BGP sites.";
        list site {
          must 'not(site-id=0 and default-offset=1)' {
            tailf:xpath-root 3;
          }
          key "site-id";
          max-elements 1;
          description
            "Configure BGP sites.";
          leaf site-id {
            type uint32 {
              range "0..65534";
            }
            description
              "BGP site ID.";
          }
          leaf range {
            type uint32 {
              range "1..65535";
            }
            default "10";
            description
              "BGP site range. Cannot decrease site range.";
          }
          leaf default-offset {
            ext:operation-exclude "update|delete";
            type uint16 {
              range "0..1";
            }
            default "0";
            description
              "The default offset of BGP site. The value of this node cannot be modified or deleted after being set.";
          }
        }
      }
      container vpn-targets {
        description
          "List of VPN targets.";
        list vpn-target {
          key "rt-value rt-type";
          max-elements 32;
          description
            "Configure VPN targets.";
          leaf rt-value {
            type string {
              length "3..21";
            }
            description
              "Route target. The format of an RT can be:
               - 16-bit AS number:32-bit user-defined number, for example, 1:3. An AS number ranges from 0 to 65535, and a user-defined number ranges from 0 to 4294967295. The AS number and user-defined number cannot be both 0s. This means that the RT cannot be 0:0.
               - Integral 4-byte AS number:2-byte user-defined number, for example, 65537:3. An AS number ranges from 65536 to 4294967295. A user-defined number ranges from 0 to 65535. The AS number and user-defined number cannot be both 0s. This means that the RT cannot be 0:0.
               - 32-bit IP address:16-bit user-defined number, for example: 192.168.122.15:1. The IP address ranges from 0.0.0.0 to 255.255.255.255, and the user-defined number ranges from 0 to 65535.
               - 32-bit AS number:16-bit user-defined number, for example, 10.11:3. An AS number ranges from 0.0 to 65535.65535, and a user-defined number ranges from 0 to 65535. The AS number and user-defined number cannot be both 0s. This means that the RT cannot be 0.0:0.";
          }
          leaf rt-type {
            type vpn-rt-type;
            description
              "RT type, which can be:
               - export-extcommunity: specifies the value of the extended community attribute of the route from an outbound interface to the destination VPN.
               - import-extcommunity: receives routes that carry the specified extended community attribute value.";
          }
        }
      }
      container flow-label {
        presence "enable flow-label for bgp signaling pws.";
        description
          "Enable/disable flow label capability of a PW.";
        leaf ability {
          type flow-label-ability;
          must ".!='default' and .!='disable'" {
            tailf:xpath-root 3;
          }
          mandatory true;
          description
            "Flow label capability.";
        }
        leaf static {
          type boolean;
          default "false";
          description
            "Enable/disable the static flow label function.";
        }
      }
      container pws {
        description
          "List of VPLS BGP PWs.";
        list pw {
          must "name or traffic-statistics-collection='true'" {
            tailf:xpath-root 3;
          }
          key "peer-ip remote-site-id";
          unique "name";
          description
            "Configure VPLS BGP PWs.";
          leaf peer-ip {
            type inet:ipv4-address-no-zone;
            description
              "Peer IP address.";
          }
          leaf remote-site-id {
            type uint32 {
              range "0..65534";
            }
            description
              "Remote BGP site ID.";
          }
          leaf name {
            type string {
              length "1..15";
            }
            description
              "PW name.";
          }
          leaf traffic-statistics-collection {
            type boolean;
            must ". = 'false' or not(../../../../traffic-statistics-collection = 'true' or ../../../../ldp-signaling/traffic-statistics-collection = 'true' or ../../../../ldp-signaling/pws/pw[traffic-statistics-collection != 'default'])" {
              tailf:xpath-root 3;
            }
            default "false";
            description
              "Enable/disable the function to collect traffic statistics.";
          }
          uses l2vpn:suppression-statisticss-grp;
        }
      }
      // NCS drop config false container 'local-label-blocks'
      // NCS drop config false container 'remote-label-blocks'
      // NCS drop config false container 'pw-infos'
    }
    container bgp-multi-homing-signaling {
      when "../work-mode='normal'" {
        tailf:xpath-root 3;
      }
      must "../admin-vsi!='true' and ../track-admin-vsi!='true' and ../p2p-vsi!='true' and ../mac-remove-mode='invalid'" {
        tailf:xpath-root 3;
      }
      must 'not(../etree)' {
        tailf:xpath-root 3;
      }
      presence "Container for bgp protocol vpls instance.";
      description
        "Configure BGP VSIs.";
      leaf route-distinguisher {
        type string {
          length "3..21";
        }
        description
          "Route distinguisher.";
      }
      leaf encapsulation-rfc4761-compatible {
        type boolean;
        default "false";
        description
          "Enable/disable the setting of an encapsulation type.";
      }
      leaf encapsulation-vpls-family-compatible {
        type boolean;
        default "false";
        description
          "Enable/disable the setting of an encapsulation type to private mode.";
      }
      leaf mtu-negotiate-disable {
        type boolean;
        default "false";
        description
          "Enable/disable the function of ignoring MTU match between local VSI and remote VSI. The default implementation is match.";
      }
      leaf site-range {
        type uint32 {
          range "1..65535";
        }
        description
          "BGP site range. Cannot decrease site range.";
      }
      leaf default-offset {
        ext:operation-exclude "update|delete";
        when '../site-range' {
          tailf:xpath-root 3;
        }
        type uint16 {
          range "0..1";
        }
        default "0";
        description
          "BGP site offset. The value of this node cannot be modified after being set.";
      }
      leaf control-word {
        type l2vpn-control-word;
        must "(../control-word='disable' or ../control-word='enable')" {
          tailf:xpath-root 3;
        }
        default "disable";
        description
          "Enable the control word feature. The control word feature is usually used for TDM, ATM, and FR PWs.";
      }
      // NCS drop config false leaf 'auto-route-distinguisher'
      container default-site {
        description
          "Configure the default BGP multi-homing site.";
        leaf name {
          type vpls-multi-homing-site-name;
          must "../name='default'" {
            tailf:xpath-root 3;
          }
          default "default";
          description
            "BGP multi-homing default site name.";
        }
        leaf site-id {
          type uint32 {
            range "0..65534";
          }
          description
            "BGP multi-homing default site ID.";
        }
        leaf preference {
          when '../site-id' {
            tailf:xpath-root 3;
          }
          type uint32 {
            range "1..65535";
          }
          default "100";
          description
            "BGP multi-homing default site preference.";
        }
        // NCS drop config false leaf selected
        // NCS drop config false container 'remote-sites'
      }
      container sites {
        description
          "List of BGP multi-homing sites.";
        list site {
          key "name";
          max-elements 512;
          description
            "Configure BGP multi-homing sites.";
          leaf name {
            type vpls-multi-homing-site-name;
            must "not(../name='default')" {
              tailf:xpath-root 3;
            }
            description
              "BGP multi-homing site name.";
          }
          leaf site-id {
            type uint32 {
              range "0..65534";
            }
            description
              "BGP multi-homing site ID.";
          }
          leaf preference {
            when '../site-id' {
              tailf:xpath-root 3;
            }
            type uint32 {
              range "1..65535";
            }
            default "100";
            description
              "BGP multi-homing site preference.";
          }
          leaf active-delay-time {
            when "../name!='default' and not(../best-site) and ../site-id" {
              tailf:xpath-root 3;
            }
            type uint16 {
              range "0..256";
            }
            units "s";
            default "30";
            description
              "BGP multi-homing site active delay time.";
          }
          leaf recover-delay-time {
            when "../name!='default' and not(../best-site) and ../site-id" {
              tailf:xpath-root 3;
            }
            type uint16 {
              range "0..3600";
            }
            units "s";
            default "180";
            description
              "BGP multi-homing site recover delay time.";
          }
          leaf best-site {
            when "../name!='default' and ../site-id" {
              tailf:xpath-root 3;
            }
            type empty;
            description
              "BGP multi-homing best site.";
          }
          // NCS drop config false leaf selected
          // NCS drop config false container 'remote-sites'
          // NCS drop config false container 'ac-infos'
        }
      }
      container vpn-targets {
        description
          "List of VPN targets.";
        list vpn-target {
          key "rt-value rt-type";
          max-elements 32;
          description
            "Configure VPN targets.";
          leaf rt-value {
            type string {
              length "3..21";
            }
            description
              "Route target. The format of an RT can be:
               - 16-bit AS number:32-bit user-defined number, for example, 1:3. An AS number ranges from 0 to 65535, and a user-defined number ranges from 0 to 4294967295. The AS number and user-defined number cannot be both 0s. This means that the RT cannot be 0:0.
               - Integral 4-byte AS number:2-byte user-defined number, for example, 65537:3. An AS number ranges from 65536 to 4294967295. A user-defined number ranges from 0 to 65535. The AS number and user-defined number cannot be both 0s. This means that the RT cannot be 0:0.
               - 32-bit IP address:16-bit user-defined number, for example: 192.168.122.15:1. The IP address ranges from 0.0.0.0 to 255.255.255.255, and the user-defined number ranges from 0 to 65535.
               - 32-bit AS number:16-bit user-defined number, for example, 10.11:3. An AS number ranges from 0.0 to 65535.65535, and a user-defined number ranges from 0 to 65535. The AS number and user-defined number cannot be both 0s. This means that the RT cannot be 0.0:0.";
          }
          leaf rt-type {
            type vpn-rt-type;
            description
              "RT type, which can be:
               - export-extcommunity: specifies the value of the extended community attribute of the route from an outbound interface to the destination VPN.
               - import-extcommunity: receives routes that carry the specified extended community attribute value.";
          }
        }
      }
      container pws {
        description
          "List of VPLS BGP multi-homing PWs.";
        list pw {
          must "name or traffic-statistics-collection='true'" {
            tailf:xpath-root 3;
          }
          key "peer-ip";
          unique "name";
          description
            "Configure a VPLS BGP multi-homing PW.";
          leaf peer-ip {
            type inet:ipv4-address-no-zone;
            description
              "Peer IP address.";
          }
          leaf name {
            type string {
              length "1..15";
            }
            description
              "PW name.";
          }
          leaf traffic-statistics-collection {
            type boolean;
            must ". = 'false' or not(../../../../traffic-statistics-collection = 'true')" {
              tailf:xpath-root 3;
            }
            default "false";
            description
              "Enable/disable the function to collect traffic statistics.";
          }
          uses l2vpn:suppression-statisticss-grp;
        }
      }
      // NCS drop config false container 'pw-infos'
      // NCS drop config false container 'local-label-blocks'
      // NCS drop config false container 'remote-sites'
    }
    container bgpad-signaling {
      when "(../work-mode='normal' or ../work-mode='bd-mode')" {
        tailf:xpath-root 3;
      }
      must "../admin-vsi!='true' and ../track-admin-vsi!='true' and ../p2p-vsi !='true'" {
        tailf:xpath-root 3;
      }
      must 'not(../etree)' {
        tailf:xpath-root 3;
      }
      presence "Container for bgpad protocol vpls instance.";
      description
        "Enable/disable BGP AD VSI.";
      leaf vpls-id {
        type string {
          length "3..21";
        }
        description
          "VPLS domain ID. The format of a VPLS domain ID can be:
           - 16-bit AS number:32-bit user-defined number, for example, 1:3. An AS number ranges from 0 to 65535, and a user-defined number ranges from 0 to 4294967295. The AS number and user-defined number cannot be both 0s. This means that the VPLS domain ID cannot be 0:0.
           - Integral 4-byte AS number:2-byte user-defined number, for example, 65537:3. An AS number ranges from 65536 to 4294967295. A user-defined number ranges from 0 to 65535. The AS number and user-defined number cannot be both 0s. This means that the VPLS domain ID cannot be 0:0.
           - 32-bit IP address:16-bit user-defined number, for example: 192.168.122.15:1. The IP address ranges from 0.0.0.0 to 255.255.255.255, and the user-defined number ranges from 0 to 65535.
           - 32-bit AS number:16-bit user-defined number, for example, 10.11:3. An AS number ranges from 0.0 to 65535.65535, and a user-defined number ranges from 0 to 65535. The AS number and user-defined number cannot be both 0s. This means that the VPLS domain ID cannot be 0.0:0.";
      }
      leaf split-horizon {
        when '../vpls-id' {
          tailf:xpath-root 3;
        }
        type vpls-split-horizon-mode-type;
        default "hub";
        description
          "PW split horizon mode.";
      }
      leaf traffic-statistics-collection {
        when '../vpls-id' {
          tailf:xpath-root 3;
        }
        type boolean;
        must ". ='false' or not(../../traffic-statistics-collection='true' or ../../ldp-signaling/traffic-statistics-collection='true' or ../../ldp-signaling/pws/pw/traffic-statistics-collection!='default')" {
          tailf:xpath-root 3;
        }
        default "false";
        description
          "Enable/disable traffic statistics collection.";
      }
      // NCS drop config false leaf 'route-distinguisher'
      // NCS drop config false leaf 'vsi-id'
      container vpn-targets {
        when '../vpls-id' {
          tailf:xpath-root 3;
        }
        description
          "List of VPN targets.";
        list vpn-target {
          key "rt-value rt-type";
          max-elements 32;
          description
            "Configure VPN targets.";
          leaf rt-value {
            type string {
              length "3..21";
            }
            description
              "Route target. The format of an RT can be:
               - 16-bit AS number:32-bit user-defined number, for example, 1:3. An AS number ranges from 0 to 65535, and a user-defined number ranges from 0 to 4294967295. The AS number and user-defined number cannot be both 0s. This means that the RT cannot be 0:0.
               - Integral 4-byte AS number:2-byte user-defined number, for example, 65537:3. An AS number ranges from 65536 to 4294967295. A user-defined number ranges from 0 to 65535. The AS number and user-defined number cannot be both 0s. This means that the RT cannot be 0:0.
               - 32-bit IP address:16-bit user-defined number, for example: 192.168.122.15:1. The IP address ranges from 0.0.0.0 to 255.255.255.255, and the user-defined number ranges from 0 to 65535.
               - 32-bit AS number:16-bit user-defined number, for example, 10.11:3. An AS number ranges from 0.0 to 65535.65535, and a user-defined number ranges from 0 to 65535. The AS number and user-defined number cannot be both 0s. This means that the RT cannot be 0.0:0.";
          }
          leaf rt-type {
            type vpn-rt-type;
            description
              "RT type, which can be:
               - export-extcommunity: specifies the value of the extended community attribute of the route from an outbound interface to the destination VPN.
               - import-extcommunity: receives routes that carry the specified extended community attribute value.";
          }
        }
      }
      container pws {
        when '../vpls-id' {
          tailf:xpath-root 3;
        }
        description
          "List of BGP AD PWs.";
        list pw {
          must 'name or traffic-statistics-collection' {
            tailf:xpath-root 3;
          }
          key "peer-ip";
          description
            "Configure a BGP AD PW.";
          leaf peer-ip {
            type inet:ipv4-address-no-zone;
            description
              "Peer IP address.";
          }
          leaf name {
            type string {
              length "1..15";
            }
            description
              "PW name.";
          }
          leaf traffic-statistics-collection {
            type boolean;
            must "not(../../../../ldp-signaling/traffic-statistics-collection = 'true')" {
              tailf:xpath-root 3;
            }
            must "not(../../../../ldp-signaling/pws/pw[traffic-statistics-collection != 'default'])" {
              tailf:xpath-root 3;
            }
            must ". != 'true' or (../../../../traffic-statistics-collection = 'false')" {
              tailf:xpath-root 3;
            }
            description
              "Enable/disable the function to collect traffic statistics.";
          }
          uses l2vpn:suppression-statisticss-grp;
        }
      }
      // NCS drop config false container peers
    }
    container acs {
      when "../work-mode!='bd-mode'" {
        tailf:xpath-root 3;
      }
      description
        "List of VPLS ACs.";
      list ac {
        key "interface-name";
        description
          "Configure a VPLS AC.";
        leaf interface-name {
          type leafref {
            path "/ncs:devices/ncs:device/ncs:config/ifm:ifm/ifm:interfaces/ifm:interface/ifm:name" {
              tailf:xpath-root 3;
            }
          }
          must "/ifm:ifm/ifm:interfaces/ifm:interface[ifm:name=current()]/ifm:link-protocol='ethernet'" {
            tailf:xpath-root 3;
          }
          description
            "Name of the AC interface bound to a VSI.";
        }
        leaf site-name {
          when '../../../bgp-multi-homing-signaling/sites/site/site-id' {
            tailf:xpath-root 3;
          }
          type vpls-multi-homing-site-name;
          description
            "BGP multi-homing site name. The value of this node cannot be changed after being configured.";
        }
        leaf hub-mode {
          type boolean;
          default "false";
          description
            "Enable/disable an interface's support for the hub mode.";
        }
        leaf access-port {
          ext:operation-exclude "update|delete";
          type boolean;
          must "/ifm:ifm/ifm:interfaces/ifm:interface[ifm:name=current()/../interface-name]/ifm:class='main-interface' or (/ifm:ifm/ifm:interfaces/ifm:interface[ifm:name=current()/../interface-name]/ifm:class='sub-interface' and ../access-port = 'false')" {
            tailf:xpath-root 3;
          }
          default "false";
          description
            "Enable/disable the attribute that allows only untagged packets to pass through an interface.";
        }
        leaf etree-leaf {
          when '../../../etree' {
            tailf:xpath-root 3;
          }
          type boolean;
          must ".='false' or ../../../ldp-signaling" {
            tailf:xpath-root 3;
          }
          default "false";
          description
            "Enable/disable e-tree leaf.";
        }
        // NCS drop config false leaf state
        // NCS drop config false leaf 'block-state'
        // NCS drop config false leaf 'last-up-time'
        // NCS drop config false leaf 'total-up-time'
        // NCS drop config false leaf 'token-exceed'
        // NCS drop config false leaf 'oam-state'
      }
    }
    container bds {
      when "../work-mode='bd-mode' and (../ldp-signaling/vsi-id or ../bgp-signaling or ../bgpad-signaling/vpls-id)" {
        tailf:xpath-root 3;
      }
      must 'not(../etree)' {
        tailf:xpath-root 3;
      }
      description
        "List of VPLS BD ACs.";
      list bd {
        must '(pw-tag and count(.)>1) or (not(count(.)>1))' {
          tailf:xpath-root 3;
        }
        key "id";
        unique "pw-tag";
        description
          "Configure VPLS BD ACs.";
        leaf id {
          type leafref {
            path "/ncs:devices/ncs:device/ncs:config/bd:bd/bd:instances/bd:instance/bd:id" {
              tailf:xpath-root 3;
            }
          }
          description
            "BD ID.";
        }
        leaf pw-tag {
          type uint16 {
            range "1..4094";
          }
          description
            "PW tag.";
        }
        // NCS drop config false leaf state
        // NCS drop config false leaf 'last-up-time'
        // NCS drop config false leaf 'total-up-time'
      }
    }
    container pbb {
      when "../work-mode='b-vsi' or ../work-mode='i-vsi' or ../work-mode='i-vsi-p2p' or ../work-mode='i-vsi-b-evpn-interworking'" {
        tailf:xpath-root 3;
      }
      must "../admin-vsi!='true'" {
        tailf:xpath-root 3;
      }
      description
        "Configure PBB VPLS.";
      leaf i-tag {
        when "../../work-mode='i-vsi-b-evpn-interworking' or ../../work-mode='i-vsi' or ../../work-mode='i-vsi-p2p'" {
          tailf:xpath-root 3;
        }
        type uint32 {
          range "0..16777215";
        }
        description
          "Tag defined in 802.1ah to identify a service instance.";
      }
      leaf backbone-source-mac {
        when "../../work-mode='b-vsi' or ../../work-mode='i-vsi' or ../../work-mode='i-vsi-p2p'" {
          tailf:xpath-root 3;
        }
        type pub-type:mac-address;
        description
          "B-SMAC address.";
      }
      leaf backbone-destination-mac {
        when "../../work-mode='i-vsi' or ../../work-mode='i-vsi-p2p'" {
          tailf:xpath-root 3;
        }
        type pub-type:mac-address;
        description
          "B-DMAC address.";
      }
      leaf mac-withdraw-rfc7361-compatible {
        when "../../work-mode='b-vsi'" {
          tailf:xpath-root 3;
        }
        type boolean;
        default "false";
        description
          "Enable/disable MAC withdraw messages that carry PBB B-MAC and I-tag TLVs in accordance with RFC 7361.";
      }
      leaf b-vsi {
        type leafref {
          path "/ncs:devices/ncs:device/ncs:config/l2vpn:l2vpn/l2vpn:instances/l2vpn:instance/l2vpn:name" {
            tailf:xpath-root 3;
          }
        }
        must "/l2vpn:l2vpn/l2vpn:instances/l2vpn:instance[l2vpn:name=current()][l2vpn:type='vpls']/l2vpn:vpls/l2vpn:work-mode='b-vsi' and ../../work-mode='i-vsi-p2p' and ../i-tag and ../backbone-destination-mac and ../backbone-source-mac" {
          tailf:xpath-root 3;
        }
        description
          "Name of the B-VSI instance to which the I-VSI is bound.";
      }
      leaf b-evpn {
        type string {
          length "1..31";
        }
        must "../../work-mode='i-vsi-b-evpn-interworking' and ../i-tag" {
          tailf:xpath-root 3;
        }
        description
          "Name of the B-EVPN instance to which the I-VSI is bound.";
      }
      // NCS drop config false leaf 'learned-flag'
      // NCS drop config false leaf 'learned-in-label'
      // NCS drop config false leaf 'learned-out-label'
      // NCS drop config false container 'i-vsis'
    }
    container ipmsi {
      when "../work-mode!='bd-mode'" {
        tailf:xpath-root 3;
      }
      must '../bgpad-signaling/vpls-id or ../bgp-multi-homing-signaling' {
        tailf:xpath-root 3;
      }
      must 'not(../etree)' {
        tailf:xpath-root 3;
      }
      presence "enable ipmsi.";
      description
        "Enable/disable multicast VPLS.";
      container root {
        presence "root";
        description
          "Enable/disable the P2MP tunnel root.";
        leaf data-switch-disable {
          type boolean;
          default "false";
          description
            "Enable/disable broadcast, unknown unicast, and multicast traffic's switching to a PW when a P2MP tunnel goes down.";
        }
        leaf mc-tunnel-type {
          type multicast-tunnel-type;
          default "invalid";
          description
            "P2MP tunnel type.";
        }
        leaf root-ip {
          when "../mc-tunnel-type!='invalid' and ../mc-tunnel-type!='te-p2mp'" {
            tailf:xpath-root 3;
          }
          type inet:ipv4-address-no-zone;
          description
            "Root IP address of a P2MP tunnel.";
        }
        leaf te-p2mp-dynamic {
          when "../mc-tunnel-type!='invalid' and ../mc-tunnel-type!='mldp-p2mp'" {
            tailf:xpath-root 3;
          }
          type boolean;
          default "false";
          description
            "Enable/disable P2MP dynamic TE.";
        }
        leaf p2mp-template-name {
          when "../te-p2mp-dynamic='false' and ../mc-tunnel-type='te-p2mp'" {
            tailf:xpath-root 3;
          }
          type string {
            length "1..31";
          }
          description
            "P2MP template name.";
        }
        leaf bfd-track-if-name {
          when '../../../acs/ac' {
            tailf:xpath-root 3;
          }
          type leafref {
            path "/ncs:devices/ncs:device/ncs:config/ifm:ifm/ifm:interfaces/ifm:interface/ifm:name" {
              tailf:xpath-root 3;
            }
          }
          description
            "Name of the interface bound to a BFD session.";
        }
        // NCS drop config false leaf 'leaf-count'
        // NCS drop config false container tunnel
        // NCS drop config false container leafs
      }
      container leaf {
        presence "leaf";
        description
          "Enable/disable the leaf of a P2MP tunnel.";
        // NCS drop config false leaf 'egress-count'
        container pw-protect-groups {
          description
            "List of PW protection groups.";
          list pw-protect-group {
            key "primary-root-ip backup-root-ip";
            description
              "Configure a PW protection group.";
            leaf primary-root-ip {
              type inet:ipv4-address-no-zone;
              description
                "IP address of the primary root.";
            }
            leaf backup-root-ip {
              type inet:ipv4-address-no-zone;
              description
                "IP address of the backup root.";
            }
            leaf wtr {
              type uint32 {
                range "0..600";
              }
              units "min";
              default "30";
              description
                "Wait-to-Restore time.";
            }
            leaf primary-track-bfd {
              type boolean;
              default "false";
              description
                "Enable/disable the association between the primary root and a BFD session.";
            }
            leaf backup-track-bfd {
              type boolean;
              default "false";
              description
                "Enable/disable the association between the backup root and a BFD session.";
            }
            // NCS drop config false container primary
            // NCS drop config false container backup
          }
        }
        // NCS drop config false container 'mldp-p2mp-tunnels'
        // NCS drop config false container 'te-p2mp-tunnels'
      }
    }
    // NCS drop config false container 'mac-withdraw-loop-detect'
    // NCS drop config false container 'down-causes'
    // NCS drop config false container statistic
    // NCS drop config false container 'ac-suppression-statisticss'
  }

  grouping l2vpn-protect-group-historys-type {
    description
      "List of L2VPN protect group histroy info container.";
    list history {
      key "num";
      max-elements 5;
      description
        "Operational data of historical switching information of a PW protection group.";
      leaf num {
        type uint32 {
          range "1..5";
        }
        description
          "Sequence number.";
      }
      leaf reroute-time {
        type string {
          length "1..60";
        }
        description
          "Switchback time.";
      }
      leaf reroute-action {
        type string {
          length "1..100";
        }
        description
          "Switchback action.";
      }
      leaf reroute-reason {
        type string {
          length "0..100";
        }
        description
          "Switchback reason.";
      }
    }
  }

  grouping bgp-local-label-block-grp {
    description
      "List of a local label blocks.";
    list local-label-block {
      key "offset";
      description
        "Operational data of local label blocks.";
      leaf offset {
        type uint16;
        description
          "BGP site offset.";
      }
      leaf label-start {
        type uint32;
        description
          "Start of the label.";
      }
      leaf add-range {
        type uint32;
        description
          "BGP site range.";
      }
      leaf site-base {
        type uint32;
        description
          "Base of the site.";
      }
    }
  }

  grouping bgp-remote-label-block-grp {
    description
      "List of remote label blocks.";
    list remote-label-block {
      key "route-distinguisher site-id offset";
      description
        "Operational data of remote label blocks.";
      leaf route-distinguisher {
        type string {
          length "3..21";
        }
        description
          "Route distinguisher.";
      }
      leaf site-id {
        type uint32 {
          range "0..65534";
        }
        description
          "BGP site ID.";
      }
      leaf offset {
        type uint16;
        description
          "BGP site offset.";
      }
      leaf label-start {
        type uint32;
        description
          "Start of the label.";
      }
      leaf add-range {
        type uint32;
        description
          "BGP site range.";
      }
    }
  }

  grouping ac-arp-grp {
    description
      "List of ARP information about all ACs.";
    list ac-arp {
      key "mac-type";
      max-elements 3;
      description
        "Operational data of ARP information about an AC.";
      leaf mac-type {
        type l2vpn-mac-type;
        description
          "MAC address learning type.";
      }
      leaf mac-address {
        type pub-type:mac-address;
        description
          "MAC address of the local CE.";
      }
      leaf expire-time {
        type uint32;
        units "min";
        description
          "Aging time.";
      }
      leaf vlan-id {
        type uint32;
        description
          "VLAN ID corresponding to a MAC address.";
      }
      leaf ip-address {
        type inet:ipv4-address-no-zone;
        description
          "Dynamically learned IP address of the local CE.";
      }
    }
  }

  grouping ipmsi-leaf-protect-group-parameter {
    description
      "Operational data of Ipmsi leaf protect group parameters.";
    leaf valid {
      type boolean;
      default "false";
      description
        "The root is valid.";
    }
    leaf active-state {
      type multicast-active-state;
      description
        "The root is active.";
    }
    leaf oam-protocol {
      type multicast-oam-type;
      description
        "Root OAM protocol.";
    }
    leaf oam-state {
      type oam-state;
      description
        "Root OAM status.";
    }
  }

  grouping mldp-p2mp-tunnel-grp {
    description
      "Operational data of Ipmsi mLDP P2MP tunnel.";
    list mldp-p2mp-tunnel {
      key "root-ip opaque-value";
      max-elements 65536;
      description
        "Operational data of tunnel information on a leaf node.";
      leaf root-ip {
        type inet:ipv4-address-no-zone;
        description
          "Root IP address of a P2MP tunnel.";
      }
      leaf opaque-value {
        type string {
          length "0..21";
        }
        description
          "Original opaque value in a message. The value is displayed in the format of TLV.";
      }
      leaf state {
        type l2vpn-state;
        description
          "P2MP tunnel status.";
      }
    }
  }

  grouping te-p2mp-tunnel-grp {
    description
      "Operational data of Ipmsi te P2MP tunnel.";
    list te-p2mp-tunnel {
      key "ingress-lsr-id session-id p2mp-id";
      max-elements 65536;
      description
        "Operational data of tunnel information on a leaf node.";
      leaf ingress-lsr-id {
        type inet:ipv4-address-no-zone;
        description
          "Ingress LSR ID.";
      }
      leaf session-id {
        type uint32 {
          range "0..4294967295";
        }
        description
          "RSVP session ID.";
      }
      leaf p2mp-id {
        type string {
          length "0..14";
        }
        description
          "P2MP session ID.";
      }
      leaf state {
        type l2vpn-state;
        description
          "P2MP tunnel status.";
      }
    }
  }

  grouping bgp-mh-remote-site-grp {
    description
      "Operational data of BGP multi-homing remote site information.";
    list remote-site {
      key "remote-site-id peer-ip";
      description
        "Operational data of BGP multi-homing remote site information.";
      leaf remote-site-id {
        type uint32;
        description
          "BGP multi-homing remote site ID.";
      }
      leaf peer-ip {
        type inet:ipv4-address-no-zone;
        description
          "BGP multi-homing peer IP.";
      }
    }
  }

  grouping suppression-statistics-grp {
    description
      "Suppression statistics.";
    leaf suppression-type {
      type suppression-type;
      description
        "Suppression statistics type.";
    }
    leaf cir {
      type uint32;
      description
        "CIR value.";
    }
    leaf pir {
      type uint32;
      description
        "PIR value.";
    }
    leaf cbs {
      type uint32;
      description
        "CBS value.";
    }
    leaf pbs {
      type uint32;
      description
        "PBS value.";
    }
    leaf passed-packets {
      type uint64;
      description
        "Passed packets.";
    }
    leaf passed-bytes {
      type uint64;
      description
        "Passed bytes.";
    }
    leaf discard-packets {
      type uint64;
      description
        "Discard packets.";
    }
    leaf discard-bytes {
      type uint64;
      description
        "Discard bytes.";
    }
    leaf passed-packet-rate {
      type uint64;
      units "pps";
      description
        "Passed packet rate.";
    }
    leaf passed-bit-rate {
      type uint64;
      units "bit/s";
      description
        "Passed bit rate.";
    }
    leaf discard-packet-rate {
      type uint64;
      units "pps";
      description
        "Discard packet rate.";
    }
    leaf discard-bit-rate {
      type uint64;
      units "bit/s";
      description
        "Discard bit rate.";
    }
  }

  grouping suppression-statisticss-grp {
    description
      "Suppression statistics.";
    // NCS drop config false container 'suppression-statisticss'
  }

  grouping pw-traffic-statisticss-grp {
    description
      "Traffic statistics of PW.";
    // NCS drop config false container 'traffic-statistics'
  }

  augment "/ncs:devices/ncs:device/ncs:rpc" {
    container rpc-reset-vpls-pw-suppression-statistics {
      tailf:ncs-device-type "netconf";
      tailf:display-when "not(../../ncs:module) or ../../ncs:module[ncs:name='huawei-l2vpn']";
      tailf:action reset-vpls-pw-suppression-statistics {
        tailf:actionpoint ncsproxy {
          tailf:internal;
        }
        description
          "Clear VPLS PW suppression statistics.";
        ext:node-ref "/l2vpn/instances/instance/vpls/ldp-signaling/pws/pw";
        ext:node-ref "/l2vpn/instances/instance";
        input {
          leaf name {
            type ncs_rpc_notif_l2vpn-instance-name;
            mandatory true;
            description
              "VSI name.";
          }
          leaf signal-type {
            type ncs_rpc_notif_pw-signal-type;
            mandatory true;
            description
              "LDP signaling.";
          }
          leaf peer-ip {
            type inet:ipv4-address-no-zone;
            mandatory true;
            description
              "Peer IP address. The loopback IP address of a peer is usually used as the peer IP address.";
          }
          leaf negotiation-vc-id {
            type uint32 {
              range "1..4294967295";
            }
            mandatory true;
            description
              "PW ID used to uniquely identify a VC. The PW ID is usually used when both ends need to communicate but the VSI IDs on both ends are different.";
          }
        }
      }
    }
  }
  augment "/ncs:devices/ncs:device-group/ncs:ned-id/ncs:rpc" {
    container rpc-reset-vpls-pw-suppression-statistics {
      tailf:ncs-device-type "netconf";
      tailf:display-when "/ncs:devices/ncs:device[ncs:name=current()/../../../ncs:member]/ncs:module[ncs:name='huawei-l2vpn']";
      tailf:action reset-vpls-pw-suppression-statistics {
        tailf:actionpoint ncsproxy {
          tailf:internal;
        }
        description
          "Clear VPLS PW suppression statistics.";
        ext:node-ref "/l2vpn/instances/instance/vpls/ldp-signaling/pws/pw";
        ext:node-ref "/l2vpn/instances/instance";
        input {
          leaf name {
            type ncs_rpc_notif_l2vpn-instance-name;
            mandatory true;
            description
              "VSI name.";
          }
          leaf signal-type {
            type ncs_rpc_notif_pw-signal-type;
            mandatory true;
            description
              "LDP signaling.";
          }
          leaf peer-ip {
            type inet:ipv4-address-no-zone;
            mandatory true;
            description
              "Peer IP address. The loopback IP address of a peer is usually used as the peer IP address.";
          }
          leaf negotiation-vc-id {
            type uint32 {
              range "1..4294967295";
            }
            mandatory true;
            description
              "PW ID used to uniquely identify a VC. The PW ID is usually used when both ends need to communicate but the VSI IDs on both ends are different.";
          }
        }
      }
    }
  }
  augment "/ncs:devices/ncs:device/ncs:rpc" {
    container rpc-switch-vpls-protect-group {
      tailf:ncs-device-type "netconf";
      tailf:display-when "not(../../ncs:module) or ../../ncs:module[ncs:name='huawei-l2vpn']";
      tailf:action switch-vpls-protect-group {
        tailf:actionpoint ncsproxy {
          tailf:internal;
        }
        description
          "Manual PW protection group switching.";
        ext:node-ref "/l2vpn/instances/instance/vpls/ldp-signaling/redundancy-protect-groups/redundancy-protect-group";
        ext:node-ref "/l2vpn/instances/instance";
        input {
          leaf instance-name {
            type ncs_rpc_notif_l2vpn-instance-name;
            mandatory true;
            description
              "Name of the instance for manual switching.";
          }
          leaf protect-group-name {
            type string {
              length "1..15";
            }
            mandatory true;
            description
              "Name of a PW protection group. The name is a string of case-sensitive characters.";
          }
          leaf protect-switch-type {
            type ncs_rpc_notif_l2vpn-protect-group-ps-type;
            mandatory true;
            description
              "Manual switching.";
          }
        }
      }
    }
  }
  augment "/ncs:devices/ncs:device-group/ncs:ned-id/ncs:rpc" {
    container rpc-switch-vpls-protect-group {
      tailf:ncs-device-type "netconf";
      tailf:display-when "/ncs:devices/ncs:device[ncs:name=current()/../../../ncs:member]/ncs:module[ncs:name='huawei-l2vpn']";
      tailf:action switch-vpls-protect-group {
        tailf:actionpoint ncsproxy {
          tailf:internal;
        }
        description
          "Manual PW protection group switching.";
        ext:node-ref "/l2vpn/instances/instance/vpls/ldp-signaling/redundancy-protect-groups/redundancy-protect-group";
        ext:node-ref "/l2vpn/instances/instance";
        input {
          leaf instance-name {
            type ncs_rpc_notif_l2vpn-instance-name;
            mandatory true;
            description
              "Name of the instance for manual switching.";
          }
          leaf protect-group-name {
            type string {
              length "1..15";
            }
            mandatory true;
            description
              "Name of a PW protection group. The name is a string of case-sensitive characters.";
          }
          leaf protect-switch-type {
            type ncs_rpc_notif_l2vpn-protect-group-ps-type;
            mandatory true;
            description
              "Manual switching.";
          }
        }
      }
    }
  }
  augment "/ncs:devices/ncs:device/ncs:rpc" {
    container rpc-reset-vpls-ldp-pw-traffic-statistics {
      tailf:ncs-device-type "netconf";
      tailf:display-when "not(../../ncs:module) or ../../ncs:module[ncs:name='huawei-l2vpn']";
      tailf:action reset-vpls-ldp-pw-traffic-statistics {
        tailf:actionpoint ncsproxy {
          tailf:internal;
        }
        description
          "Clear VPLS PW traffic statistics.";
        ext:node-ref "/l2vpn/instances/instance/vpls/ldp-signaling/pws/pw";
        ext:node-ref "/l2vpn/instances/instance";
        input {
          leaf name {
            type ncs_rpc_notif_l2vpn-instance-name;
            mandatory true;
            description
              "VSI name.";
          }
          leaf signal-type {
            type ncs_rpc_notif_pw-signal-type;
            mandatory true;
            description
              "LDP signaling.";
          }
          leaf peer-ip {
            type inet:ipv4-address-no-zone;
            mandatory true;
            description
              "Peer IP address. The loopback IP address of a peer is usually used as the peer IP address.";
          }
          leaf negotiation-vc-id {
            type uint32 {
              range "1..4294967295";
            }
            mandatory true;
            description
              "PW ID used to uniquely identify a VC. The PW ID is usually used when both ends need to communicate but the VSI IDs on both ends are different.";
          }
        }
      }
    }
  }
  augment "/ncs:devices/ncs:device-group/ncs:ned-id/ncs:rpc" {
    container rpc-reset-vpls-ldp-pw-traffic-statistics {
      tailf:ncs-device-type "netconf";
      tailf:display-when "/ncs:devices/ncs:device[ncs:name=current()/../../../ncs:member]/ncs:module[ncs:name='huawei-l2vpn']";
      tailf:action reset-vpls-ldp-pw-traffic-statistics {
        tailf:actionpoint ncsproxy {
          tailf:internal;
        }
        description
          "Clear VPLS PW traffic statistics.";
        ext:node-ref "/l2vpn/instances/instance/vpls/ldp-signaling/pws/pw";
        ext:node-ref "/l2vpn/instances/instance";
        input {
          leaf name {
            type ncs_rpc_notif_l2vpn-instance-name;
            mandatory true;
            description
              "VSI name.";
          }
          leaf signal-type {
            type ncs_rpc_notif_pw-signal-type;
            mandatory true;
            description
              "LDP signaling.";
          }
          leaf peer-ip {
            type inet:ipv4-address-no-zone;
            mandatory true;
            description
              "Peer IP address. The loopback IP address of a peer is usually used as the peer IP address.";
          }
          leaf negotiation-vc-id {
            type uint32 {
              range "1..4294967295";
            }
            mandatory true;
            description
              "PW ID used to uniquely identify a VC. The PW ID is usually used when both ends need to communicate but the VSI IDs on both ends are different.";
          }
        }
      }
    }
  }
  augment "/ncs:devices/ncs:device/ncs:rpc" {
    container rpc-reset-vpls-traffic-statistics {
      tailf:ncs-device-type "netconf";
      tailf:display-when "not(../../ncs:module) or ../../ncs:module[ncs:name='huawei-l2vpn']";
      tailf:action reset-vpls-traffic-statistics {
        tailf:actionpoint ncsproxy {
          tailf:internal;
        }
        description
          "Clear VPLS traffic statistics.";
        ext:node-ref "/l2vpn/instances/instance";
        input {
          leaf name {
            type ncs_rpc_notif_l2vpn-instance-name;
            mandatory true;
            description
              "VSI name.";
          }
        }
      }
    }
  }
  augment "/ncs:devices/ncs:device-group/ncs:ned-id/ncs:rpc" {
    container rpc-reset-vpls-traffic-statistics {
      tailf:ncs-device-type "netconf";
      tailf:display-when "/ncs:devices/ncs:device[ncs:name=current()/../../../ncs:member]/ncs:module[ncs:name='huawei-l2vpn']";
      tailf:action reset-vpls-traffic-statistics {
        tailf:actionpoint ncsproxy {
          tailf:internal;
        }
        description
          "Clear VPLS traffic statistics.";
        ext:node-ref "/l2vpn/instances/instance";
        input {
          leaf name {
            type ncs_rpc_notif_l2vpn-instance-name;
            mandatory true;
            description
              "VSI name.";
          }
        }
      }
    }
  }
  augment "/ncs:devices/ncs:device/ncs:rpc" {
    container rpc-reset-vpws-bgp-traffic-statistics {
      tailf:ncs-device-type "netconf";
      tailf:display-when "not(../../ncs:module) or ../../ncs:module[ncs:name='huawei-l2vpn']";
      tailf:action reset-vpws-bgp-traffic-statistics {
        tailf:actionpoint ncsproxy {
          tailf:internal;
        }
        description
          "Reset VPWS BGP PW traffic.";
        ext:node-ref "/l2vpn/instances/instance/vpws-bgp/pws/pw";
        ext:node-ref "/l2vpn/instances/instance/vpws-bgp";
        ext:node-ref "/l2vpn/instances/instance";
        input {
          leaf name {
            type ncs_rpc_notif_l2vpn-instance-name;
            mandatory true;
            description
              "Instance name.";
          }
          leaf type {
            type ncs_rpc_notif_l2vpn-instance-type;
            mandatory true;
            description
              "Instance type.";
          }
          leaf local-site {
            type ncs_rpc_notif_vpws-bgp-ce-name-type;
            mandatory true;
            description
              "CE name.";
          }
          leaf remote-site-id {
            type uint16 {
              range "0..65534";
            }
            mandatory true;
            description
              "Remote CE ID.";
          }
        }
      }
    }
  }
  augment "/ncs:devices/ncs:device-group/ncs:ned-id/ncs:rpc" {
    container rpc-reset-vpws-bgp-traffic-statistics {
      tailf:ncs-device-type "netconf";
      tailf:display-when "/ncs:devices/ncs:device[ncs:name=current()/../../../ncs:member]/ncs:module[ncs:name='huawei-l2vpn']";
      tailf:action reset-vpws-bgp-traffic-statistics {
        tailf:actionpoint ncsproxy {
          tailf:internal;
        }
        description
          "Reset VPWS BGP PW traffic.";
        ext:node-ref "/l2vpn/instances/instance/vpws-bgp/pws/pw";
        ext:node-ref "/l2vpn/instances/instance/vpws-bgp";
        ext:node-ref "/l2vpn/instances/instance";
        input {
          leaf name {
            type ncs_rpc_notif_l2vpn-instance-name;
            mandatory true;
            description
              "Instance name.";
          }
          leaf type {
            type ncs_rpc_notif_l2vpn-instance-type;
            mandatory true;
            description
              "Instance type.";
          }
          leaf local-site {
            type ncs_rpc_notif_vpws-bgp-ce-name-type;
            mandatory true;
            description
              "CE name.";
          }
          leaf remote-site-id {
            type uint16 {
              range "0..65534";
            }
            mandatory true;
            description
              "Remote CE ID.";
          }
        }
      }
    }
  }
  augment "/ncs:devices/ncs:device/ncs:rpc" {
    container rpc-reset-vpws-ldp-traffic-statistics {
      tailf:ncs-device-type "netconf";
      tailf:display-when "not(../../ncs:module) or ../../ncs:module[ncs:name='huawei-l2vpn']";
      tailf:action reset-vpws-ldp-traffic-statistics {
        tailf:actionpoint ncsproxy {
          tailf:internal;
        }
        description
          "Reset VPWS PW traffic.";
        ext:node-ref "/l2vpn/instances/instance/vpws-ldp/pws/pw";
        ext:node-ref "/l2vpn/instances/instance";
        input {
          leaf name {
            type ncs_rpc_notif_l2vpn-instance-name;
            mandatory true;
            description
              "Instance name.";
          }
          leaf type {
            type ncs_rpc_notif_l2vpn-instance-type;
            mandatory true;
            description
              "Instance type.";
          }
          leaf role {
            type ncs_rpc_notif_pw-role-type;
            mandatory true;
            description
              "PW role.";
          }
        }
      }
    }
  }
  augment "/ncs:devices/ncs:device-group/ncs:ned-id/ncs:rpc" {
    container rpc-reset-vpws-ldp-traffic-statistics {
      tailf:ncs-device-type "netconf";
      tailf:display-when "/ncs:devices/ncs:device[ncs:name=current()/../../../ncs:member]/ncs:module[ncs:name='huawei-l2vpn']";
      tailf:action reset-vpws-ldp-traffic-statistics {
        tailf:actionpoint ncsproxy {
          tailf:internal;
        }
        description
          "Reset VPWS PW traffic.";
        ext:node-ref "/l2vpn/instances/instance/vpws-ldp/pws/pw";
        ext:node-ref "/l2vpn/instances/instance";
        input {
          leaf name {
            type ncs_rpc_notif_l2vpn-instance-name;
            mandatory true;
            description
              "Instance name.";
          }
          leaf type {
            type ncs_rpc_notif_l2vpn-instance-type;
            mandatory true;
            description
              "Instance type.";
          }
          leaf role {
            type ncs_rpc_notif_pw-role-type;
            mandatory true;
            description
              "PW role.";
          }
        }
      }
    }
  }
  augment "/ncs:devices/ncs:device/ncs:rpc" {
    container rpc-reset-vpws-ldp-ac {
      tailf:ncs-device-type "netconf";
      tailf:display-when "not(../../ncs:module) or ../../ncs:module[ncs:name='huawei-l2vpn']";
      tailf:action reset-vpws-ldp-ac {
        tailf:actionpoint ncsproxy {
          tailf:internal;
        }
        description
          "Clear MAC addresses and VLAN IDs dynamically learned by an ethernet interface on a local CE.";
        ext:node-ref "/l2vpn/instances/instance/vpws-ldp/acs/ac";
        input {
          leaf interface-name {
            type pub-type:ncs_rpc_notif_if-name;
            description
              "Interface name.";
          }
        }
      }
    }
  }
  augment "/ncs:devices/ncs:device-group/ncs:ned-id/ncs:rpc" {
    container rpc-reset-vpws-ldp-ac {
      tailf:ncs-device-type "netconf";
      tailf:display-when "/ncs:devices/ncs:device[ncs:name=current()/../../../ncs:member]/ncs:module[ncs:name='huawei-l2vpn']";
      tailf:action reset-vpws-ldp-ac {
        tailf:actionpoint ncsproxy {
          tailf:internal;
        }
        description
          "Clear MAC addresses and VLAN IDs dynamically learned by an ethernet interface on a local CE.";
        ext:node-ref "/l2vpn/instances/instance/vpws-ldp/acs/ac";
        input {
          leaf interface-name {
            type pub-type:ncs_rpc_notif_if-name;
            description
              "Interface name.";
          }
        }
      }
    }
  }
  augment "/ncs:devices/ncs:device/ncs:rpc" {
    container rpc-reset-pw-template {
      tailf:ncs-device-type "netconf";
      tailf:display-when "not(../../ncs:module) or ../../ncs:module[ncs:name='huawei-l2vpn']";
      tailf:action reset-pw-template {
        tailf:actionpoint ncsproxy {
          tailf:internal;
        }
        description
          "Reestablish a PW template.";
        ext:node-ref "/l2vpn/common/pw-templates/pw-template";
        input {
          leaf name {
            type string {
              length "1..19";
            }
            mandatory true;
            description
              "PW template name.";
          }
        }
      }
    }
  }
  augment "/ncs:devices/ncs:device-group/ncs:ned-id/ncs:rpc" {
    container rpc-reset-pw-template {
      tailf:ncs-device-type "netconf";
      tailf:display-when "/ncs:devices/ncs:device[ncs:name=current()/../../../ncs:member]/ncs:module[ncs:name='huawei-l2vpn']";
      tailf:action reset-pw-template {
        tailf:actionpoint ncsproxy {
          tailf:internal;
        }
        description
          "Reestablish a PW template.";
        ext:node-ref "/l2vpn/common/pw-templates/pw-template";
        input {
          leaf name {
            type string {
              length "1..19";
            }
            mandatory true;
            description
              "PW template name.";
          }
        }
      }
    }
  }
  augment "/ncs:devices/ncs:device/ncs:rpc" {
    container rpc-reset-vpws-ldp-pw {
      tailf:ncs-device-type "netconf";
      tailf:display-when "not(../../ncs:module) or ../../ncs:module[ncs:name='huawei-l2vpn']";
      tailf:action reset-vpws-ldp-pw {
        tailf:actionpoint ncsproxy {
          tailf:internal;
        }
        description
          "Reestablish a PW.";
        ext:node-ref "/l2vpn/instances/instance/vpws-ldp/pws/pw";
        ext:node-ref "/l2vpn/instances/instance";
        input {
          leaf name {
            type ncs_rpc_notif_l2vpn-instance-name;
            mandatory true;
            description
              "Name of the reset instance.";
          }
          leaf type {
            type ncs_rpc_notif_l2vpn-instance-type;
            mandatory true;
            description
              "Type of the reset instance.";
          }
          leaf role {
            type ncs_rpc_notif_pw-role-type;
            mandatory true;
            description
              "Role of the reset PW.";
          }
        }
      }
    }
  }
  augment "/ncs:devices/ncs:device-group/ncs:ned-id/ncs:rpc" {
    container rpc-reset-vpws-ldp-pw {
      tailf:ncs-device-type "netconf";
      tailf:display-when "/ncs:devices/ncs:device[ncs:name=current()/../../../ncs:member]/ncs:module[ncs:name='huawei-l2vpn']";
      tailf:action reset-vpws-ldp-pw {
        tailf:actionpoint ncsproxy {
          tailf:internal;
        }
        description
          "Reestablish a PW.";
        ext:node-ref "/l2vpn/instances/instance/vpws-ldp/pws/pw";
        ext:node-ref "/l2vpn/instances/instance";
        input {
          leaf name {
            type ncs_rpc_notif_l2vpn-instance-name;
            mandatory true;
            description
              "Name of the reset instance.";
          }
          leaf type {
            type ncs_rpc_notif_l2vpn-instance-type;
            mandatory true;
            description
              "Type of the reset instance.";
          }
          leaf role {
            type ncs_rpc_notif_pw-role-type;
            mandatory true;
            description
              "Role of the reset PW.";
          }
        }
      }
    }
  }
  augment "/ncs:devices/ncs:device/ncs:rpc" {
    container rpc-switch-protect-aps {
      tailf:ncs-device-type "netconf";
      tailf:display-when "not(../../ncs:module) or ../../ncs:module[ncs:name='huawei-l2vpn']";
      tailf:action switch-protect-aps {
        tailf:actionpoint ncsproxy {
          tailf:internal;
        }
        description
          "PW APS.";
        ext:node-ref "/l2vpn/common/pw-apss/pw-aps";
        input {
          leaf aps-id {
            type uint32 {
              range "1..65535";
            }
            mandatory true;
            description
              "ID of a PW APS instance.";
          }
          leaf protect-switch-type {
            type ncs_rpc_notif_l2vpn-pw-aps-ps-type;
            mandatory true;
            description
              "Configure a manual switching request for a specified PW APS instance. By default, the manual switching request is not configured.";
          }
        }
      }
    }
  }
  augment "/ncs:devices/ncs:device-group/ncs:ned-id/ncs:rpc" {
    container rpc-switch-protect-aps {
      tailf:ncs-device-type "netconf";
      tailf:display-when "/ncs:devices/ncs:device[ncs:name=current()/../../../ncs:member]/ncs:module[ncs:name='huawei-l2vpn']";
      tailf:action switch-protect-aps {
        tailf:actionpoint ncsproxy {
          tailf:internal;
        }
        description
          "PW APS.";
        ext:node-ref "/l2vpn/common/pw-apss/pw-aps";
        input {
          leaf aps-id {
            type uint32 {
              range "1..65535";
            }
            mandatory true;
            description
              "ID of a PW APS instance.";
          }
          leaf protect-switch-type {
            type ncs_rpc_notif_l2vpn-pw-aps-ps-type;
            mandatory true;
            description
              "Configure a manual switching request for a specified PW APS instance. By default, the manual switching request is not configured.";
          }
        }
      }
    }
  }
  augment "/ncs:devices/ncs:device/ncs:config" {
    container l2vpn {
      tailf:ncs-device-type "netconf";
      tailf:display-when "not(../../ncs:module) or ../../ncs:module[ncs:name='huawei-l2vpn']";
      when "/mpls:mpls/mpls:common/mpls:global/mpls:mpls-enable='true'" {
        tailf:xpath-root 3;
      }
      presence "Enable l2 virtual private network.";
      description
        "L2 virtual private network.";
      container common {
        description
          "Configure L2VPN common attributes.";
        container global {
          description
            "Configure a global L2VPN.";
          leaf ldp-default-mode {
            type ldp-signal-type;
            default "pwe3";
            description
              "LDP is used as the signaling protocol. The dynamic VC will then not send a notification during signaling negotiation. The LDP signaling mode is also called the Martini mode.";
          }
          leaf vpls-ignore-ac-state {
            type boolean;
            default "false";
            description
              "Enable/disable the function of the VSI status not to be affected by changes in the AC status.";
          }
          leaf vpls-loop-detect-enable {
            type boolean;
            default "false";
            description
              "Enable/disable MAC withdraw loop detection.";
          }
          leaf bfd-cv-type {
            type bfd-vccv-cv-type;
            default "cv-linkage-bfd";
            description
              "The field of CV will be all filled corresponding BFD CV type after global enable BFDCV.";
          }
          leaf ignore-te-oam-state {
            type boolean;
            default "false";
            description
              "Enable/disable ignoring TE OAM detecting state.";
          }
          leaf auto-create-session {
            type boolean;
            default "false";
            description
              "Enable/disable creating LDP session automatically.";
          }
          leaf grp-selective-ldp-enable {
            type boolean;
            default "false";
            description
              "Enable/disable the selective mLDP P2MP LSP group.";
          }
          leaf label-block-size {
            type uint32 {
              range "2..8";
            }
            must '(../label-block-size=2 or ../label-block-size=4 or ../label-block-size=8)' {
              tailf:xpath-root 3;
            }
            default "8";
            description
              "Configure the label block size for BGP L2VPN.";
          }
        }
        container pw-templates {
          description
            "List of PW templates.";
          list pw-template {
            key "name";
            max-elements 2000;
            description
              "Configure PW attributes in a PW template, such as the peer, control word, and tunnel policy.";
            leaf name {
              type l2vpn-pw-template-name;
              description
                "Name of a PW template.";
            }
            leaf peer-address {
              ext:operation-exclude "update";
              type inet:ipv4-address-no-zone;
              description
                "Peer IP address. The loopback IP address of a peer is usually used as the peer IP address.";
            }
            leaf mtu {
              type uint16 {
                range "46..9600";
              }
              description
                "MTU in a PW template.";
            }
            leaf control-word {
              type enumeration {
                enum "disable" {
                  value 1;
                  description
                    "Disable control word.";
                }
                enum "enable" {
                  value 2;
                  description
                    "Enable control word.";
                }
              }
              default "disable";
              description
                "Enable the control word function.";
            }
            leaf tunnel-policy {
              type string {
                length "1..39";
              }
              description
                "Tunnel policy configured in a PW template.";
            }
            // NCS drop config false leaf 'vccv-capability'
            // NCS drop config false leaf 'total-pw-num'
            // NCS drop config false leaf 'static-pw-num'
            // NCS drop config false leaf 'ldp-pw-num'
            container tdm-parameter {
              description
                "Configure TDM parameters.";
              leaf tdm-encapsulate-number {
                type uint32 {
                  range "1..40";
                }
                ext:dynamic-default;
                description
                  "Number of TDM frames encapsulated in a CESoPSN or SAToP packet in the TDMoPSN application.";
              }
              leaf jitter-buffer {
                type uint32 {
                  range "1..64000";
                }
                units "us";
                ext:dynamic-default;
                description
                  "Depth of the jitter buffer in the application of TDMoPSN.";
              }
              leaf jitter-buffer-cep {
                type uint32 {
                  range "125..16000";
                }
                units "us";
                default "1000";
                description
                  "Depth of the jitter buffer in the application of CEP.";
              }
              leaf rtp-header {
                type boolean;
                default "false";
                description
                  "Enable/disable transparently transmission of TDM frames.";
              }
              leaf idle-code {
                type yang:hex-string {
                  length "1..2";
                }
                default "ff";
                description
                  "Idle code that is filled when the jitter buffer underflow occurs.";
              }
              leaf payload-compression {
                type l2vpn-payload-comp;
                default "disable";
                description
                  "Payload compression mode.";
              }
            }
            container atm-parameter {
              description
                "Configure ATM parameters.";
              leaf max-atm-cells {
                type uint32 {
                  range "1..28";
                }
                ext:dynamic-default;
                description
                  "Maximum number of ATM cells to be encapsulated into a packet that can be received by a device.";
              }
              leaf atm-pack-overtime {
                type uint32 {
                  range "100..10000";
                }
                units "us";
                ext:dynamic-default;
                description
                  "Delay in encapsulating ATM cells into a packet.";
              }
              leaf atm-transmit-cell {
                type uint32 {
                  range "1..28";
                }
                description
                  "Maximum number of ATM cells to be encapsulated into a packet that can be sent by a device.";
              }
              leaf sequence-number {
                when "../../control-word='enable'" {
                  tailf:xpath-root 3;
                }
                type boolean;
                default "false";
                description
                  "Enable/disable the sequence number function.";
              }
            }
            container bfd-parameter {
              when '/bfd:bfd' {
                tailf:xpath-root 3;
              }
              must "../control-word='enable'" {
                tailf:xpath-root 3;
              }
              presence "enable bfd-parameter for pw";
              description
                "Enable/disable BFD.";
              leaf min-rx-interval {
                type uint16 {
                  range "0..65535";
                }
                units "ms";
                default "10";
                description
                  "Minimum receive interval.";
              }
              leaf min-tx-interval {
                type uint16 {
                  range "0..65535";
                }
                units "ms";
                default "10";
                description
                  "Minimum transmit interval.";
              }
              leaf detect-multiplier {
                type uint16 {
                  range "3..50";
                }
                default "3";
                description
                  "Detection multiplier.";
              }
            }
            container flow-label {
              presence "enable flow-label for pw";
              description
                "Enable/disable the flow-label function.";
              leaf ability {
                type flow-label-ability;
                must ".!='default' and .!='disable'" {
                  tailf:xpath-root 3;
                }
                mandatory true;
                description
                  "Specify the flow-label ability.";
              }
              leaf static {
                type boolean;
                default "false";
                description
                  "Enable/disable the static flow-label function.";
              }
            }
          }
        }
        container pw-apss {
          description
            "List of APS instances.";
          list pw-aps {
            key "aps-id";
            max-elements 65536;
            description
              "Configure APS instances.";
            leaf aps-id {
              type uint32 {
                range "1..65535";
              }
              description
                "ID of a PW APS instance.";
            }
            leaf description {
              type string {
                length "1..63";
              }
              description
                "PW APS description.";
            }
            leaf protect-type {
              ext:operation-exclude "update|delete";
              type l2vpn-pw-aps-type;
              must "((../protect-type='pw-aps' or ../protect-type='pw-fps') and ../role='pw-aps') or (../protect-type='mc-pw-aps' and (../role='master' or ../role='slave'))" {
                tailf:xpath-root 3;
              }
              default "pw-aps";
              description
                "Protection type.";
            }
            leaf role {
              type l2vpn-pw-aps-role;
              must "((../protect-type='pw-aps' or ../protect-type='pw-fps') and ../role='pw-aps') or (../protect-type='mc-pw-aps' and (../role='master' or ../role='slave'))" {
                tailf:xpath-root 3;
              }
              default "pw-aps";
              description
                "E-PW APS role.";
            }
            leaf remote-aps-id {
              when "not(../role='pw-aps')" {
                tailf:xpath-root 3;
              }
              type uint32 {
                range "1..65535";
              }
              description
                "Remote ID of E-PW APS.";
            }
            leaf holdoff {
              type uint32 {
                range "0..100";
              }
              units "ms";
              default "0";
              description
                "Hold time.";
            }
            leaf wtr {
              when "../role!='slave'" {
                tailf:xpath-root 3;
              }
              type uint32 {
                range "0..12";
              }
              units "min";
              default "5";
              description
                "Wait-to-Restore time.";
            }
            leaf operation-type {
              when "../role!='slave'" {
                tailf:xpath-root 3;
              }
              type l2vpn-pw-aps-oper-type;
              default "revertive";
              description
                "Operation type.";
            }
            // NCS drop config false leaf 'protect-mode'
            // NCS drop config false container 'pw-aps-info'
            // NCS drop config false container 'aps-vpws-instances'
          }
        }
        container service-peers {
          description
            "List of peers.";
          list service-peer {
            key "peer-ip";
            description
              "Configure the list of peers.";
            leaf peer-ip {
              type inet:ipv4-address-no-zone;
              description
                "Indicates the LSR ID of the remote device.";
            }
            leaf ldp-mode {
              type l2vpn-peer-ldp-signal-mode;
              default "default";
              description
                "Peer signal mode.";
            }
          }
        }
        container peer-no-requests {
          description
            "List of no-request peers.";
          list peer-no-request {
            key "peer-ip";
            description
              "Configure no-request peers.";
            leaf peer-ip {
              type inet:ipv4-address-no-zone;
              description
                "Indicates the LSR ID of the remote device.";
            }
          }
        }
        container peer-bfd-cv-stds {
          description
            "List of BFD CV standard peers.";
          list peer-bfd-cv-std {
            must "(enable='disable' and type='cv-bfd') or enable='enable'" {
              tailf:xpath-root 3;
            }
            key "peer-ip";
            description
              "Configure BFD CV standard peers.";
            leaf peer-ip {
              type inet:ipv4-address-no-zone;
              description
                "Indicates the LSR ID of the remote device.";
            }
            leaf enable {
              type l2vpn-common-enable-type;
              default "enable";
              description
                "Enable BFDCV.";
            }
            leaf type {
              type bfd-vccv-cv-type;
              default "cv-bfd";
              description
                "The BFDCV type of the peer.";
            }
          }
        }
        container vpws-bgp-vpns {
          description
            "List of VPWS BGP VPN instances.";
          list vpws-bgp-vpn {
            key "name";
            description
              "Configure VPWS BGP VPN instance.";
            leaf name {
              type string {
                length "1..31";
              }
              description
                "VPWS BGP VPN instance name.";
            }
            leaf encapsulation-type {
              type vpws-bgp-vpn-encap;
              mandatory true;
              description
                "VPWS BGP VPN instance encapsulation type.";
            }
            leaf control-word {
              type enumeration {
                enum "disable" {
                  value 1;
                  description
                    "The control word mode is disable.";
                }
                enum "enable" {
                  value 2;
                  description
                    "The control word mode is enable.";
                }
              }
              default "disable";
              description
                "Control word of the VPWS BGP VPN instance. If the encapsulation type is low speed, disabling the control word causes the VPWS BGP instance to fail.";
            }
            leaf route-distinguisher {
              type string {
                length "3..21";
              }
              description
                "Route distinguisher of VPWS BGP VPN instance.";
            }
            leaf mtu {
              type uint16 {
                range "0..16352";
              }
              default "1500";
              description
                "MTU of VPWS BGP VPN instance.";
            }
            leaf ignore-mtu-match {
              type boolean;
              default "false";
              description
                "Enable/disable the function of the ignoring MTU match of a VPWS BGP VPN instance.";
            }
            // NCS drop config false leaf 'auto-route-distinguisher'
            container vpn-targets {
              description
                "List of route targets of VPWS BGP VPN instances.";
              list vpn-target {
                key "rt-value rt-type";
                max-elements 32;
                description
                  "Configure a route target list of the VPWS BGP VPN instances.";
                leaf rt-value {
                  type string {
                    length "3..21";
                  }
                  description
                    "Route target value of the VPWS BGP VPN instance.";
                }
                leaf rt-type {
                  type vpn-rt-type;
                  description
                    "Route target type of the VPWS BGP VPN instance.";
                }
              }
            }
            container sites {
              description
                "List of CEs in a VPWS BGP VPN instance.";
              list site {
                must 'not(id=0 and default-offset=1)' {
                  tailf:xpath-root 3;
                }
                key "name";
                unique "id";
                description
                  "Configure a CE in a VPWS BGP VPN instance.";
                leaf name {
                  type vpws-bgp-ce-name-type;
                  description
                    "Local site name.";
                }
                leaf id {
                  ext:operation-exclude "update";
                  type uint16 {
                    range "0..65534";
                  }
                  mandatory true;
                  description
                    "VPWS BGP VPN instance customer edge identifier.";
                }
                leaf range {
                  type uint16 {
                    range "1..65535";
                  }
                  must '../l2vpn:range >= /l2vpn:l2vpn/l2vpn:common/l2vpn:vpws-bgp-vpns/l2vpn:vpws-bgp-vpn[l2vpn:name=current()/../../../l2vpn:name]/l2vpn:sites/l2vpn:site[l2vpn:name = current()/../l2vpn:name]/range' {
                    tailf:xpath-root 3;
                  }
                  default "10";
                  description
                    "VPWS BGP VPN instance customer edge range.";
                }
                leaf default-offset {
                  type uint16 {
                    range "0..1";
                  }
                  default "0";
                  description
                    "VPWS BGP VPN instance customer edge default offset.";
                }
                // NCS drop config false container 'label-blocks'
              }
            }
            // NCS drop config false container 'remote-sites'
          }
        }
        // NCS drop config false container 'not-match-remote-ldps'
        // NCS drop config false container 'vpws-statistic'
        // NCS drop config false container 'vpls-statistic'
        // NCS drop config false container 'track-route-statistics'
        // NCS drop config false container 'vrf-routes'
      }
      container instances {
        description
          "List of L2VPN instances.";
        list instance {
          key "name type";
          description
            "Configure L2VPN instances.";
          leaf name {
            type string {
              length "1..31";
            }
            description
              "The name of L2VPN instance.";
          }
          leaf type {
            type l2vpn-instance-type;
            description
              "The type of L2VPN instance.";
          }
          leaf description {
            when "not(../type='vpws-switch' or ../type='vpws-bgp')" {
              tailf:xpath-root 3;
            }
            type string {
              length "1..128";
            }
            description
              "Description of a VSI.";
          }
          // NCS drop config false leaf state
          // NCS drop config false leaf 'last-up-time'
          // NCS drop config false leaf 'total-up-time'
          container vpws-local-ccc {
            ext:operation-exclude "delete";
            when "../type='vpws-local-ccc'" {
              tailf:xpath-root 3;
            }
            description
              "Configure VPWS local CCC instance.";
            uses vpws-localccc-instance-grp;
          }
          container vpws-remote-ccc {
            ext:operation-exclude "delete";
            when "../type='vpws-remote-ccc'" {
              tailf:xpath-root 3;
            }
            description
              "Configure a VPWS remote CCC instance.";
            uses vpws-remoteccc-instance-grp;
          }
          container vpws-ldp {
            ext:operation-exclude "delete";
            when "../type='vpws-ldp' or ../type='vpws-svc' or ../type='vpws-single-ccc'" {
              tailf:xpath-root 3;
            }
            must 'not(out-acs and ac-oam-mapping)' {
              tailf:xpath-root 3;
            }
            must '(count(pws/pw) + count(out-acs/out-ac) >= 1)' {
              tailf:xpath-root 3;
            }
            description
              "Configure VPWS LDP instance.";
            leaf encapsulation-type {
              ext:operation-exclude "update";
              type encapsulation-type;
              must "../encapsulation-type='vlan' or
../encapsulation-type='ethernet' or
../encapsulation-type='hdlc' or
../encapsulation-type='ppp' or
../encapsulation-type='atm-nto1-vcc' or
../encapsulation-type='atm-nto1-vpc' or
../encapsulation-type='atm-1to1-vcc' or
../encapsulation-type='atm-1to1-vpc' or
../encapsulation-type='atm-aal5-sdu' or
../encapsulation-type='atm-trans-cell' or
../encapsulation-type='cep' or
../encapsulation-type='satop-e1' or
../encapsulation-type='cesopsn-basic' or
../encapsulation-type='ip-interworking' or
../encapsulation-type='unsupport' or
(../../type!='vpws-svc' and ../encapsulation-type='ip-layer2')" {
                tailf:xpath-root 3;
              }
              mandatory true;
              description
                "Encapsulation type of a VPWS instance.";
            }
            leaf mac-withdraw-disable {
              when "../../type='vpws-ldp' and
(../encapsulation-type='ethernet' or
../encapsulation-type='vlan' or
../encapsulation-type='ip-interworking' or
../encapsulation-type='ip-layer2')" {
                tailf:xpath-root 3;
              }
              type boolean;
              default "false";
              description
                "Enable/disable the function to send MAC withdraw messages during the primary/secondary PW switchover for Ethernet-encapsulated or VLAN-encapsulated VLLs.";
            }
            leaf load-balance {
              when "../../type='vpws-ldp' or ../../type='vpws-svc'" {
                tailf:xpath-root 3;
              }
              type l2vpn-load-balance-type;
              default "flow";
              description
                "Load balancing mode, which can be:
                 - Flow: indicates per-flow load balancing.
                 - Packet: indicates per-packet load balancing.";
            }
            leaf service-name {
              type string {
                length "1..31";
              }
              description
                "Service name of a VPWS instance.";
            }
            leaf bit-error-detection {
              when "../../type='vpws-ldp'" {
                tailf:xpath-root 3;
              }
              type boolean;
              must "../bit-error-detection='false' or (not(../reliability/aps-parameter) and not(../out-acs/out-ac))" {
                tailf:xpath-root 3;
              }
              default "false";
              description
                "Enable/disable bit error detection on SPEs for an LDP MS-PW.";
            }
            container acs {
              description
                "List of information about all ACs.";
              list ac {
                ext:operation-exclude "update|delete";
                must "(not(arp-entry)) or (arp-entry and (/ifm:ifm/ifm:interfaces/ifm:interface[ifm:name=current()/interface-name]/ifm:link-protocol='ethernet'))" {
                  tailf:xpath-root 3;
                }
                key "interface-name";
                min-elements 1;
                max-elements 1;
                description
                  "Configure information about an AC.";
                leaf interface-name {
                  type leafref {
                    path "/ncs:devices/ncs:device/ncs:config/ifm:ifm/ifm:interfaces/ifm:interface/ifm:name" {
                      tailf:xpath-root 3;
                    }
                  }
                  description
                    "Name of an AC interface.";
                }
                leaf tagged {
                  ext:operation-exclude "update|delete";
                  when "../../../encapsulation-type='ethernet' or
../../../encapsulation-type='vlan'" {
                    tailf:xpath-root 3;
                  }
                  type boolean;
                  ext:dynamic-default {
                    ext:default-value "false" {
                      when "../../../encapsulation-type='ethernet'" {
                        tailf:xpath-root 3;
                      }
                      description
                        "The default value is false when encapsulation-type is ethernet.";
                    }
                    ext:default-value "true" {
                      when "../../../encapsulation-type='vlan'" {
                        tailf:xpath-root 3;
                      }
                      description
                        "The default value is true when encapsulation-type is VLAN.";
                    }
                  }
                  must "(../../../encapsulation-type='ethernet' and ../tagged='false') or
(../../../encapsulation-type='vlan' and ../tagged='true')" {
                    tailf:xpath-root 3;
                  }
                  description
                    "Enable/disable the VLAN tag setting.";
                }
                leaf access-port {
                  ext:operation-exclude "update|delete";
                  when "../../../encapsulation-type='ethernet' or
../../../encapsulation-type='ip-interworking' or
../../../encapsulation-type='ip-layer2' or
../../../encapsulation-type='vlan'" {
                    tailf:xpath-root 3;
                  }
                  type boolean;
                  must "/ifm:ifm/ifm:interfaces/ifm:interface[ifm:name=current()/../interface-name]/ifm:class='main-interface' or (/ifm:ifm/ifm:interfaces/ifm:interface[ifm:name=current()/../interface-name]/ifm:class='sub-interface' and ../access-port = 'false')" {
                    tailf:xpath-root 3;
                  }
                  default "false";
                  description
                    "Enable/disable the function of allowing only untagged packets to pass through an interface. The access port attribute can be configured only on main Ethernet interfaces. The access port attribute of outbound interface must be consistent with that of inbound interface.";
                }
                leaf trigger-interface-down {
                  when "../../../../type='vpws-ldp'" {
                    tailf:xpath-root 3;
                  }
                  type boolean;
                  must "(/ifm:ifm/ifm:interfaces/ifm:interface[ifm:name=current()/../interface-name]/ifm:class='main-interface' and /ifm:ifm/ifm:interfaces/ifm:interface[ifm:name=current()/../interface-name]/ifm:link-protocol='ethernet' and . = 'true') or (. = 'false')" {
                    tailf:xpath-root 3;
                  }
                  must "(. = 'true' and not(../../../out-acs/out-ac)) or . = 'false'" {
                    tailf:xpath-root 3;
                  }
                  default "false";
                  description
                    "Enable/disable remote interface shutdown to associate PW status with interface status.";
                }
                leaf forward-mode {
                  ext:operation-exclude "update";
                  type boolean;
                  must "(/ifm:ifm/ifm:interfaces/ifm:interface[ifm:name=current()/../interface-name]/ifm:type='PW-VE' and ../forward-mode='true') or ../forward-mode='false'" {
                    tailf:xpath-root 3;
                  }
                  default "false";
                  description
                    "Enable/disable the raw forwarding mode.";
                }
                leaf performance-statistics {
                  when "(../../../encapsulation-type='satop-e1' or
../../../encapsulation-type='cesopsn-basic' or
../../../encapsulation-type='cep' or
../../../encapsulation-type='atm-aal5-sdu' or
../../../encapsulation-type='atm-trans-cell' or
../../../encapsulation-type='atm-nto1-vcc' or
../../../encapsulation-type='atm-nto1-vpc' or
../../../encapsulation-type='atm-1to1-vcc' or
../../../encapsulation-type='atm-1to1-vpc' or
../../../encapsulation-type='atm-aal5-pdu') and
/ifm:ifm/ifm:interfaces/ifm:interface[ifm:name=current()/../interface-name]/ifm:type!='Remote-Ap' and
../../../../type!='vpws-single-ccc'" {
                    tailf:xpath-root 3;
                  }
                  type boolean;
                  default "true";
                  description
                    "Enable/disable PW performance statistics collection.";
                }
                // NCS drop config false leaf state
                // NCS drop config false leaf 'token-exceed'
                container arp-entry {
                  presence "Enable the ARP entry for AC.";
                  description
                    "Configure ARP entry attribute used for IP interworking between PEs.";
                  leaf local-ce-mac {
                    type pub-type:mac-address;
                    description
                      "MAC address of the Ethernet interface or sub-interface on a CE connected to the local AC interface. If MAC, IP, and broadcast addresses are all configured, these addresses take effect in the sequence of MAC address, IP address, and broadcast address.";
                  }
                  leaf local-ce-ip {
                    type inet:ipv4-address-no-zone;
                    description
                      "IP address of the Ethernet interface or sub-interface on a CE connected to the local AC interface.";
                  }
                  leaf local-ce-broadcast {
                    type boolean;
                    must "((.='false' and (../local-ce-mac or ../local-ce-ip or ../remote-ce-ip)) or (.='true'))" {
                      tailf:xpath-root 3;
                    }
                    default "false";
                    description
                      "Enable/disable the broadcast function on a PE Ethernet interface connected to a CE.";
                  }
                  leaf remote-ce-ip {
                    type inet:ipv4-address-no-zone;
                    description
                      "IP address of the remote CE connected to the local AC interface.";
                  }
                }
                // NCS drop config false container 'ac-arps'
                // NCS drop config false container 'tdm-performance-statistic'
                // NCS drop config false container 'atm-performance-statistic'
              }
            }
            container pws {
              description
                "List of all VPWS PWs.";
              list pw {
                must 'peer-ip or (pw-template and /l2vpn:l2vpn/l2vpn:common/l2vpn:pw-templates/l2vpn:pw-template[l2vpn:name=current()/pw-template]/l2vpn:peer-address)' {
                  tailf:xpath-root 3;
                }
                must "((../../../type='vpws-ldp' or ../../../type='vpws-single-ccc') and pw-id) or (../../../type='vpws-svc' and transmit-label and receive-label and ((pw-template and pw-id) or not(pw-template)))" {
                  tailf:xpath-root 3;
                }
                key "role";
                max-elements 3;
                description
                  "Configure a VPWS PW.";
                leaf role {
                  type pw-role-type;
                  must "((../../../../type='vpws-ldp' and .='primary') or (../../../../type='vpws-ldp' and .='backup' and ../../pw[role='primary']) or (../../../../type='vpws-ldp' and .='bypass' and ../../pw[role='primary'] and not(../../pw[role='backup'])) or (../../../../type='vpws-ldp' and .='ac-bypass' and ../../pw[role='primary'] and not(../../pw[role='bypass'])) or (../../../../type='vpws-ldp' and .='pw-bypass' and ../../pw[role='ac-bypass'])) or ((../../../../type='vpws-svc' and .='primary') or (../../../../type='vpws-svc' and .='backup' and ../../pw[role='primary']) or (../../../../type='vpws-svc' and .='bypass' and ../../pw[role='primary'] and not(../../pw[role='backup']))) or (../../../../type='vpws-single-ccc' and .='backup' and ../../../out-acs/out-ac)" {
                    tailf:xpath-root 3;
                  }
                  description
                    "Role of a PW. Configure a primary PW first.";
                }
                leaf pw-id {
                  ext:operation-exclude "update|delete";
                  ext:support-filter "true";
                  type uint32 {
                    range "1..4294967295";
                  }
                  description
                    "PW ID.";
                }
                leaf peer-ip {
                  ext:operation-exclude "update|delete";
                  type l2vpn-peer-address-type;
                  description
                    "IP address of a peer.";
                }
                leaf admin-pw {
                  ext:operation-exclude "update|delete";
                  when "../../../../type!='vpws-svc'" {
                    tailf:xpath-root 3;
                  }
                  type boolean;
                  must "(../admin-pw='true' and ../role='primary' and ../../../encapsulation-type='ip-interworking' and ../control-word!='disable' and /ifm:ifm/ifm:interfaces/ifm:interface[ifm:name=current()/../../../acs/ac/interface-name]/ifm:type='LoopBack' and ../../../load-balance!='packet' and ../../../bit-error-detection!='true') or ../admin-pw='false'" {
                    tailf:xpath-root 3;
                    error-message "The PW role must be primary when admin-pw enabled.";
                  }
                  default "false";
                  description
                    "Enable/disable administrative PW.";
                }
                leaf transmit-label {
                  ext:operation-exclude "update|delete";
                  when "../../../../type='vpws-svc'" {
                    tailf:xpath-root 3;
                  }
                  type uint32 {
                    range "0..1048575";
                  }
                  description
                    "Label for sending packets.";
                }
                leaf receive-label {
                  ext:operation-exclude "update|delete";
                  when "../../../../type='vpws-svc'" {
                    tailf:xpath-root 3;
                  }
                  type uint32 {
                    range "16..1048575";
                  }
                  description
                    "Label for receiving packets.";
                }
                leaf control-word {
                  when "../role!='pw-bypass'" {
                    tailf:xpath-root 3;
                  }
                  type l2vpn-control-word;
                  must "../control-word!='prefer'" {
                    tailf:xpath-root 3;
                  }
                  default "default";
                  description
                    "Enable the control word function. The control word is usually used for TDM, ATM, and FR PWs.";
                }
                leaf vccv-ability {
                  when "../../../../type!='vpws-svc' and /ifm:ifm/ifm:interfaces/ifm:interface[ifm:name=current()/../../../acs/ac/interface-name]/ifm:type!='LoopBack' and /ifm:ifm/ifm:interfaces/ifm:interface[ifm:name=current()/../../../acs/ac/interface-name]/ifm:type!='PW-VE' and /ifm:ifm/ifm:interfaces/ifm:interface[ifm:name=current()/../../../acs/ac/interface-name]/ifm:type!='Remote-Ap'" {
                    tailf:xpath-root 3;
                  }
                  type boolean;
                  default "true";
                  description
                    "Enable/disable virtual circuit connectivity verification (VCCV) capability. VCCV supports two modes: control word and label alert.";
                }
                leaf tunnel-policy {
                  when "../role!='pw-bypass'" {
                    tailf:xpath-root 3;
                  }
                  type string {
                    length "1..39";
                  }
                  description
                    "Name of a tunnel policy. If the tunnel policy name is not specified, the system uses the default tunnel policy. The default tunnel policy preferentially selects LSPs for packet transmission and the number of load-balancing tunnels is 1. If the tunnel policy name is specified but the corresponding tunnel policy does not exist, the system still uses the default tunnel policy.";
                }
                leaf pw-template {
                  ext:operation-exclude "update|delete";
                  when "../role!='pw-bypass'" {
                    tailf:xpath-root 3;
                  }
                  type leafref {
                    path "/ncs:devices/ncs:device/ncs:config/l2vpn/common/pw-templates/pw-template/name" {
                      tailf:xpath-root 3;
                    }
                  }
                  description
                    "Name of a PW template. You can configure PW attributes such as the remote peer, tunnel policy, and control word in a PW template. When configuring an LDP PW, you can reference the PW attributes configured in an existing PW template.";
                }
                leaf ignore-standby {
                  when "../../../../type='vpws-ldp' and ../admin-pw='false'" {
                    tailf:xpath-root 3;
                  }
                  type boolean;
                  default "false";
                  description
                    "Enable/disable the PW's function of ignoring the standby state informed by the VSI peer.";
                }
                leaf set-fault {
                  when "../../../../type='vpws-ldp' and ../admin-pw='false'" {
                    tailf:xpath-root 3;
                  }
                  type boolean;
                  must "../set-fault='false' or (../set-fault='true' and not(../../../out-acs/out-ac) and ../../../reliability/redundancy-mode!='independent' and ../../../reliability/redundancy-mode!='master')" {
                    tailf:xpath-root 3;
                  }
                  default "false";
                  description
                    "Enable/disable simulating a fault on a primary or secondary PW.";
                }
                leaf pw-ttl {
                  when "../admin-pw!='true'" {
                    tailf:xpath-root 3;
                  }
                  type uint32 {
                    range "1..255";
                  }
                  must "((../role='ac-bypass' or ../role='pw-bypass' or ../../../out-acs/out-ac or ../../../../type='vpws-single-ccc') and ../pw-ttl=1) or not(../role='ac-bypass' or ../role='pw-bypass' or ../../../out-acs/out-ac or ../../../../type='vpws-single-ccc')" {
                    tailf:xpath-root 3;
                  }
                  default "1";
                  description
                    "TTL of a PW.";
                }
                leaf track-admin-pw {
                  when "../role!='pw-bypass' and ../admin-pw='false'" {
                    tailf:xpath-root 3;
                  }
                  type leafref {
                    path "/ncs:devices/ncs:device/ncs:config/ifm:ifm/ifm:interfaces/ifm:interface/ifm:name" {
                      tailf:xpath-root 3;
                    }
                  }
                  must "/ifm:ifm/ifm:interfaces/ifm:interface[ifm:name=current()]/ifm:type='LoopBack' and /l2vpn:l2vpn/l2vpn:instances/l2vpn:instance/l2vpn:vpws-ldp/l2vpn:acs/l2vpn:ac/l2vpn:interface-name[.=current()]" {
                    tailf:xpath-root 3;
                  }
                  description
                    "Configure a service PW to track the mPW.";
                }
                leaf traffic-statistics-collection {
                  when "../role!='ac-bypass' and ../role!='pw-bypass' and (../admin-pw='false' or not(../admin-pw))" {
                    tailf:xpath-root 3;
                  }
                  type boolean;
                  default "false";
                  description
                    "Enable/disable collecting traffic statistics.";
                }
                leaf ignore-ac-state {
                  when "../role!='ac-bypass' and ../role!='pw-bypass' and (../admin-pw='false' or not(../admin-pw))" {
                    tailf:xpath-root 3;
                  }
                  type boolean;
                  default "false";
                  description
                    "Enable/disable the function of the VPWS PW status not to be affected by changes in the AC status.";
                }
                container tdm-parameter {
                  when "../role!='pw-bypass' and ../admin-pw='false' and
(../../../encapsulation-type='cep' or
../../../encapsulation-type='cesopsn-basic' or
../../../encapsulation-type='satop-e1')" {
                    tailf:xpath-root 3;
                  }
                  description
                    "Configure TDM parameters.";
                  leaf tdm-encapsulate-number {
                    ext:dynamic-default;
                    type uint32 {
                      range "1..5000";
                    }
                    description
                      "Number of TDM frames encapsulated in a CESoPSN or SAToP packet in the TDMoPSN application.";
                  }
                  leaf jitter-buffer {
                    ext:dynamic-default;
                    type uint32 {
                      range "1..64000";
                    }
                    units "ms";
                    description
                      "Depth of the jitter buffer in the application of TDMoPSN.";
                  }
                  leaf sequence-number {
                    type boolean;
                    default "false";
                    description
                      "Enable/disable the TDM sequence number function.";
                  }
                  leaf rtp-header {
                    type l2vpn-rtp-header-type;
                    default "false";
                    description
                      "Add the RTP header to transparently transmitted TDM frames.";
                  }
                  leaf idle-code {
                    ext:dynamic-default;
                    type string {
                      length "1..2";
                      pattern '[a-fA-F0-9]{1,2}';
                    }
                    description
                      "Idle code that is filled when the jitter buffer underflow occurs.";
                  }
                  leaf payload-compression {
                    type l2vpn-payload-comp;
                    must "(../payload-compression!='disable' and ../../../../encapsulation-type='cep') or (../payload-compression='disable')" {
                      tailf:xpath-root 3;
                    }
                    default "disable";
                    description
                      "Payload compression mode.";
                  }
                }
                container atm-parameter {
                  when "../role!='pw-bypass' and ../admin-pw='false' and
(../../../encapsulation-type='atm-1to1-vcc' or
../../../encapsulation-type='atm-1to1-vpc' or
../../../encapsulation-type='atm-aal5-pdu' or
../../../encapsulation-type='atm-aal5-sdu' or
../../../encapsulation-type='atm-nto1-vcc' or
../../../encapsulation-type='atm-nto1-vpc' or
../../../encapsulation-type='atm-trans-cell')" {
                    tailf:xpath-root 3;
                  }
                  description
                    "Configure ATM parameters.";
                  leaf max-atm-cells {
                    type uint32 {
                      range "1..28";
                    }
                    ext:dynamic-default;
                    description
                      "Maximum number of ATM cells to be encapsulated into a packet that can be received by a device.";
                  }
                  leaf atm-pack-overtime {
                    type uint32 {
                      range "100..10000";
                    }
                    units "ms";
                    ext:dynamic-default;
                    description
                      "Delay in encapsulating ATM cells into a packet.";
                  }
                  leaf atm-transmit-cell {
                    when "../../../../../type!='vpws-svc'" {
                      tailf:xpath-root 3;
                    }
                    ext:dynamic-default;
                    type uint32 {
                      range "1..28";
                    }
                    description
                      "Maximum number of ATM cells to be encapsulated into a packet that can be sent by a device.";
                  }
                  leaf sequence-number {
                    type boolean;
                    must "(../sequence-number='true' and ../../control-word='enable') or (../sequence-number='false')" {
                      tailf:xpath-root 3;
                    }
                    default "false";
                    description
                      "Enable/disable the control-word-based ATM packet sequencing feature. Performance statistics can then be collected based on this feature.";
                  }
                }
                container track-vrrp {
                  when "../../../../type='vpws-ldp' and ../role='primary' and ../role='backup' and ../admin-pw='false'" {
                    tailf:xpath-root 3;
                  }
                  must 'not (../../../out-acs/out-ac)' {
                    tailf:xpath-root 3;
                  }
                  presence "enable track vrrp.";
                  description
                    "Enable/disable associating a PW with the mVRRP backup group.";
                  leaf vrrp-interface-name {
                    type leafref {
                      path "/ncs:devices/ncs:device/ncs:config/ifm:ifm/ifm:interfaces/ifm:interface/ifm:name" {
                        tailf:xpath-root 3;
                      }
                    }
                    must "../../role='primary' or (../../role='backup' and ../../../pw[role='primary']/track-vrrp[vrrp-interface-name=current()])" {
                      tailf:xpath-root 3;
                    }
                    mandatory true;
                    description
                      "The name of mVRRP interface.";
                  }
                  leaf vrrp-vrid {
                    type uint32 {
                      range "1..255";
                    }
                    must "../../role='primary' or (../../role='backup' and ../../../pw[role='primary']/track-vrrp[vrrp-vrid=current()])" {
                      tailf:xpath-root 3;
                    }
                    mandatory true;
                    description
                      "VRID of a VRRP backup group.";
                  }
                  leaf pw-redundancy {
                    type boolean;
                    must "../../role='primary' or (../../role='backup' and ../../../pw[role='primary']/track-vrrp[pw-redundancy=current()])" {
                      tailf:xpath-root 3;
                    }
                    default "false";
                    description
                      "Enable/disable the PW protection group associated with an mVRRP backup group in PW redundancy.";
                  }
                }
                container flow-label {
                  when "../admin-pw='false' and (../role='primary' or ../role='backup')" {
                    tailf:xpath-root 3;
                  }
                  presence "enbale flow label for pw";
                  description
                    "Enable/disable the flow label capability of a PW.";
                  leaf ability {
                    type flow-label-ability;
                    must ".!='default' and .!='disable'" {
                      tailf:xpath-root 3;
                    }
                    mandatory true;
                    description
                      "Flow label capability.";
                  }
                  leaf static {
                    type boolean;
                    default "false";
                    description
                      "Enable/disable the static flow label.";
                  }
                }
                container track-vrf-routes {
                  when "../../../../type='vpws-ldp' and ../admin-pw='false' and
((/ifm:ifm/ifm:interfaces/ifm:interface[ifm:name=current()/../../../acs/ac/interface-name]/ifm:type='Virtual-Ethernet' or /ifm:ifm/ifm:interfaces/ifm:interface[ifm:name=current()/../../../acs/ac/interface-name]/ifm:type='Global-VE') and
/ifm:ifm/ifm:interfaces/ifm:interface[ifm:name=current()/../../../acs/ac/interface-name]/ifm:class='sub-interface')" {
                    tailf:xpath-root 3;
                  }
                  description
                    "List of PWs to track the VPN instance route.";
                  list track-vrf-route {
                    key "vrf-name ip-address mask-length";
                    description
                      "Configure a PW associated with a VPN instance route.";
                    leaf vrf-name {
                      type leafref {
                        path "/ncs:devices/ncs:device/ncs:config/ni:network-instance/ni:instances/ni:instance/ni:name" {
                          tailf:xpath-root 3;
                        }
                      }
                      description
                        "The name of the VPN instance.";
                    }
                    leaf ip-address {
                      type inet:ip-address-no-zone;
                      description
                        "IP address of a VPN instance route.";
                    }
                    leaf mask-length {
                      type uint32 {
                        range "0..128";
                      }
                      description
                        "Mask of a VPN instance route.";
                    }
                  }
                }
                container bfd {
                  when "(../role='primary' or ../role='backup') and /bfd:bfd" {
                    tailf:xpath-root 3;
                  }
                  presence "enable pw bfd.";
                  description
                    "Enable/disable the BFD parameter list.";
                  uses l2vpn:l2vpn-dyn-bfd-para-type;
                  leaf remote-vc-id {
                    type uint32 {
                      range "1..4294967295";
                    }
                    description
                      "Remote VC ID.";
                  }
                  leaf track-interface {
                    when "../../admin-pw!='true'" {
                      tailf:xpath-root 3;
                    }
                    type boolean;
                    default "false";
                    description
                      "Enable/disable BFD track interface state.";
                  }
                  leaf track-interface-name {
                    when "../../admin-pw='true'" {
                      tailf:xpath-root 3;
                    }
                    type leafref {
                      path "/ncs:devices/ncs:device/ncs:config/ifm:ifm/ifm:interfaces/ifm:interface/ifm:name" {
                        tailf:xpath-root 3;
                      }
                    }
                    description
                      "Specify the interface to be tracked.";
                  }
                }
                // NCS drop config false container 'pw-info'
                // NCS drop config false container 'traffic-statistics'
              }
            }
            container out-acs {
              when "../../type='vpws-single-ccc' or ../../type='vpws-ldp'" {
                tailf:xpath-root 3;
              }
              description
                "List of all out ACs.";
              list out-ac {
                key "interface-name";
                max-elements 1;
                description
                  "Configure outbound interface of single CCC.";
                leaf interface-name {
                  type leafref {
                    path "/ncs:devices/ncs:device/ncs:config/ifm:ifm/ifm:interfaces/ifm:interface/ifm:name" {
                      tailf:xpath-root 3;
                    }
                  }
                  must 'not(../../../acs/ac[interface-name=current()])' {
                    tailf:xpath-root 3;
                  }
                  description
                    "Name of an AC interface.";
                }
                leaf role {
                  ext:operation-exclude "update";
                  type pw-role-type;
                  must "(../role='primary' and ../../../../type='vpws-single-ccc') or (../role='backup' and ../../../../type='vpws-ldp')" {
                    tailf:xpath-root 3;
                  }
                  mandatory true;
                  description
                    "Role of out AC.";
                }
                container tdm-parameter {
                  when "../../../encapsulation-type='satop-e1' or ../../../encapsulation-type='satop-t1' or ../../../encapsulation-type='satop-e3' or ../../../encapsulation-type='cesopsn-basic' or ../../../encapsulation-type='cep'" {
                    tailf:xpath-root 3;
                  }
                  description
                    "Configure TDM parameters of CCC instance.";
                  uses l2vpn-ccc-tdm-type;
                }
                container atm-parameter {
                  when "../../../encapsulation-type='atm-1to1-vcc' or
../../../encapsulation-type='atm-1to1-vpc' or
../../../encapsulation-type='atm-aal5-pdu' or
../../../encapsulation-type='atm-aal5-sdu' or
../../../encapsulation-type='atm-nto1-vcc' or
../../../encapsulation-type='atm-nto1-vpc' or
../../../encapsulation-type='atm-trans-cell'" {
                    tailf:xpath-root 3;
                  }
                  description
                    "Configure ATM parameters.";
                  uses l2vpn-ccc-atm-type;
                }
              }
            }
            container hard-pipe {
              when "../../type='vpws-svc' and ../pws/pw/tunnel-policy" {
                tailf:xpath-root 3;
              }
              must "../encapsulation-type='ethernet' or ../encapsulation-type='vlan'" {
                tailf:xpath-root 3;
              }
              presence "Enable hard pipe for pw.";
              description
                "Enable/disable hard pipe. The hard-pipe node and the qos-parameter node cannot be configured together.";
              leaf bandwidth {
                type uint32 {
                  range "16..4294967294";
                }
                units "kbit/s";
                mandatory true;
                description
                  "Specify bandwidth value.";
              }
              leaf expand-ratio {
                type uint16 {
                  range "0..10000";
                }
                default "10";
                description
                  "Specify the value of bandwidth expand ratio (%). As to CES service, expand ratio ranges from 0 to 10000. The other service, expand ratio ranges from 0 to 100.";
              }
              leaf burst-time {
                when "../../encapsulation-type='ethernet' or ../../encapsulation-type='vlan'" {
                  tailf:xpath-root 3;
                }
                type uint32 {
                  range "100..5000";
                }
                units "us";
                default "100";
                description
                  "Burst time.";
              }
            }
            container ac-oam-mapping {
              ext:operation-exclude "update";
              when "../../type='vpws-ldp' and
(../encapsulation-type='vlan' or
../encapsulation-type='ethernet' or
../encapsulation-type='atm-nto1-vcc' or
../encapsulation-type='atm-nto1-vpc' or
../encapsulation-type='atm-1to1-vcc' or
../encapsulation-type='atm-1to1-vpc' or
../encapsulation-type='atm-trans-cell' or
../encapsulation-type='cep' or
../encapsulation-type='satop-e1' or
../encapsulation-type='cesopsn-basic')" {
                tailf:xpath-root 3;
              }
              presence "enable AC OAM mapping";
              description
                "Enable/disable OAM mapping.";
              leaf type {
                ext:operation-exclude "update";
                type ac-oam-mapping-type;
                must "(../type='1ag' and ../md-name and ../ma-name) or ../type!='1ag'" {
                  tailf:xpath-root 3;
                }
                mandatory true;
                description
                  "VPWS attachment circuit OAM mapping type.";
              }
              leaf md-name {
                ext:operation-exclude "update|delete";
                when "../type='1ag'" {
                  tailf:xpath-root 3;
                }
                type string {
                  length "1..43";
                }
                description
                  "VPWS OAM mapping parameter md name.";
              }
              leaf ma-name {
                ext:operation-exclude "update|delete";
                when "../type='1ag'" {
                  tailf:xpath-root 3;
                }
                type string {
                  length "1..43";
                }
                description
                  "VPWS OAM mapping parameter ma name.";
              }
            }
            container reliability {
              when 'count(../pws/pw)>=2 or (count(../pws/pw)=1 and count(../out-acs/out-ac)=1)' {
                tailf:xpath-root 3;
              }
              description
                "Configure PW reliability.";
              leaf redundancy-mode {
                type pw-redundancy-mode;
                must "../redundancy-mode='frr' or ../../../type!='vpws-svc'" {
                  tailf:xpath-root 3;
                }
                must "../redundancy-mode='frr' or ../redundancy-mode='independent' or ../redundancy-mode='master'" {
                  tailf:xpath-root 3;
                }
                default "frr";
                description
                  "PW redundancy mode.";
              }
              leaf switchover {
                when "../redundancy-mode='master'" {
                  tailf:xpath-root 3;
                }
                type boolean;
                must ".='true' and (not(../../out-acs/out-ac)) or .='false'" {
                  tailf:xpath-root 3;
                }
                default "false";
                description
                  "Enable/disable manual PW switchover.";
              }
              leaf dual-receive {
                type boolean;
                default "false";
                description
                  "Enable/disable the packet reception of both the primary and secondary PWs.";
              }
              leaf dual-send {
                type boolean;
                must "../dual-send='false' or (../dual-send='true' and ../../../type='vpws-ldp' and count(../../out-acs/out-ac)=0 and ../redundancy-mode='frr' and not(../aps-parameter) and (../../encapsulation-type='cep' or ../../encapsulation-type='satop-e1' or ../../encapsulation-type='cesopsn-basic'))" {
                  tailf:xpath-root 3;
                }
                default "false";
                description
                  "Enable/disable the packet transmission of both the primary and secondary PWs.";
              }
              leaf holdoff {
                when "../redundancy-mode='master' and not(../../out-acs/out-ac)" {
                  tailf:xpath-root 3;
                }
                type uint32 {
                  range "1..180";
                }
                units "s";
                description
                  "Hold time for traffic switching.";
              }
              container reroute {
                when "../redundancy-mode='master' or ../redundancy-mode='frr'" {
                  tailf:xpath-root 3;
                }
                description
                  "Configure a switchback policy list.";
                leaf reroute-policy {
                  type l2vpn-reroute-mode;
                  default "delay";
                  description
                    "Switchback policy.";
                }
                leaf delay-time {
                  when "../reroute-policy='delay'" {
                    tailf:xpath-root 3;
                  }
                  type uint32 {
                    range "10..10800";
                  }
                  units "s";
                  default "30";
                  description
                    "Delay for switching traffic back to the primary PW.";
                }
                leaf resume-time {
                  when "(../../redundancy-mode='frr' and (../reroute-policy='delay' or ../reroute-policy='immediately')) and ../../../../type='vpws-ldp' and not(../../../out-acs/out-ac)" {
                    tailf:xpath-root 3;
                  }
                  type uint32 {
                    range "0..600";
                  }
                  units "s";
                  default "10";
                  description
                    "Time after which the peer PE on the secondary PW is notified that the local PE has recovered. This parameter can be configured only in FRR mode.";
                }
                // NCS drop config false leaf 'last-switchback-reason'
                // NCS drop config false leaf 'last-switchback-time'
                // NCS drop config false leaf 'delay-residual'
                // NCS drop config false leaf 'resume-residual'
              }
              container aps-parameter {
                ext:operation-exclude "update";
                when "count(../../out-acs/out-ac)=0 and ../redundancy-mode='frr' and ../reroute/reroute-policy='delay' and ../reroute/delay-time='30' and (../../../type='vpws-svc' or ../reroute/resume-time='10')" {
                  tailf:xpath-root 3;
                }
                presence "enable aps protection for pw.";
                description
                  "Enable/disable APS.";
                leaf aps-id {
                  ext:operation-exclude "update";
                  type leafref {
                    path "/ncs:devices/ncs:device/ncs:config/l2vpn/common/pw-apss/pw-aps/aps-id" {
                      tailf:xpath-root 3;
                    }
                  }
                  mandatory true;
                  description
                    "PW APS instance ID.";
                }
                leaf bind-type {
                  ext:operation-exclude "update|delete";
                  type l2vpn-aps-bind-type;
                  default "admin";
                  description
                    "Type of a PW protection group associated with the PW APS instance.";
                }
              }
            }
          }
          container vpws-switch {
            ext:operation-exclude "delete";
            when "../type='vpws-switch'" {
              tailf:xpath-root 3;
            }
            must "(switch-type!='ldp-ldp-bak' and count(pws/pw)=2 and pws/pw[role='left-primary'] and pws/pw[role='right-primary']) or (switch-type='ldp-ldp-bak' and count(pws/pw)=3)" {
              tailf:xpath-root 3;
            }
            description
              "Configure a VPWS switch instance.";
            uses vpws-swtich-instance-grp;
          }
          container vpws-bgp {
            ext:operation-exclude "delete";
            when "../type='vpws-bgp'" {
              tailf:xpath-root 3;
            }
            description
              "Configure a VPWS BGP instance. This container cannot be deleted.";
            uses vpws-bgp-instance-grp;
          }
          container vpls {
            ext:operation-exclude "delete";
            when "../type='vpls'" {
              tailf:xpath-root 3;
            }
            must "(shutdown='false') or (not (admin-vsi)) or (shutdown='true' and admin-vsi='false')" {
              tailf:xpath-root 3;
            }
            must 'not(ldp-signaling and bgp-multi-homing-signaling)' {
              tailf:xpath-root 3;
            }
            must 'not(bgp-signaling and bgp-multi-homing-signaling)' {
              tailf:xpath-root 3;
            }
            must 'not(bgp-signaling and bgpad-signaling)' {
              tailf:xpath-root 3;
            }
            must 'not(bgp-multi-homing-signaling and bgpad-signaling)' {
              tailf:xpath-root 3;
            }
            description
              "Configure a VPLS instance.";
            uses vpls-instance-grp;
          }
        }
      }
    }
  }
  augment "/ncs:devices/ncs:device/ncs:live-status" {
    container l2vpn {
      tailf:ncs-device-type "netconf";
      tailf:display-when "not(../../ncs:module) or ../../ncs:module[ncs:name='huawei-l2vpn'] or (../../ncs:live-status-protocol[not(ncs:capability)]) or (../../ncs:live-status-protocol/ncs:capability/ncs:module[.='huawei-l2vpn'])";
      // NCS drop when statement
      presence "Enable l2 virtual private network.";
      description
        "L2 virtual private network.";
      container common {
        description
          "Configure L2VPN common attributes.";
        container global {
          description
            "Configure a global L2VPN.";
          leaf ldp-default-mode {
            type live_ncs_ldp-signal-type;
            // NCS drop default statement
            description
              "LDP is used as the signaling protocol. The dynamic VC will then not send a notification during signaling negotiation. The LDP signaling mode is also called the Martini mode.";
          }
          leaf vpls-ignore-ac-state {
            type boolean;
            // NCS drop default statement
            description
              "Enable/disable the function of the VSI status not to be affected by changes in the AC status.";
          }
          leaf vpls-loop-detect-enable {
            type boolean;
            // NCS drop default statement
            description
              "Enable/disable MAC withdraw loop detection.";
          }
          leaf bfd-cv-type {
            type live_ncs_bfd-vccv-cv-type;
            // NCS drop default statement
            description
              "The field of CV will be all filled corresponding BFD CV type after global enable BFDCV.";
          }
          leaf ignore-te-oam-state {
            type boolean;
            // NCS drop default statement
            description
              "Enable/disable ignoring TE OAM detecting state.";
          }
          leaf auto-create-session {
            type boolean;
            // NCS drop default statement
            description
              "Enable/disable creating LDP session automatically.";
          }
          leaf grp-selective-ldp-enable {
            type boolean;
            // NCS drop default statement
            description
              "Enable/disable the selective mLDP P2MP LSP group.";
          }
          leaf label-block-size {
            type uint32 {
              range "2..8";
            }
            // NCS drop must statement
            // NCS drop default statement
            description
              "Configure the label block size for BGP L2VPN.";
          }
        }
        container pw-templates {
          description
            "List of PW templates.";
          list pw-template {
            key "name";
            // NCS drop max-elements statement
            description
              "Configure PW attributes in a PW template, such as the peer, control word, and tunnel policy.";
            leaf name {
              type live_ncs_l2vpn-pw-template-name;
              description
                "Name of a PW template.";
            }
            leaf peer-address {
              ext:operation-exclude "update";
              type inet:ipv4-address-no-zone;
              description
                "Peer IP address. The loopback IP address of a peer is usually used as the peer IP address.";
            }
            leaf mtu {
              type uint16 {
                range "46..9600";
              }
              description
                "MTU in a PW template.";
            }
            leaf control-word {
              type enumeration {
                enum "disable" {
                  value 1;
                  description
                    "Disable control word.";
                }
                enum "enable" {
                  value 2;
                  description
                    "Enable control word.";
                }
              }
              // NCS drop default statement
              description
                "Enable the control word function.";
            }
            leaf tunnel-policy {
              type string {
                length "1..39";
              }
              description
                "Tunnel policy configured in a PW template.";
            }
            leaf vccv-capability {
              type string {
                length "0..40";
              }
              description
                "VCCV capability. VCCV supports two modes: control word and label alert.";
            }
            leaf total-pw-num {
              type uint32;
              // NCS drop default statement
              description
                "Total number of PWs using a specific PW template, including static PWs and dynamic PWs.";
            }
            leaf static-pw-num {
              type uint32;
              // NCS drop default statement
              description
                "Number of static PWs using a specific PW template.";
            }
            leaf ldp-pw-num {
              type uint32;
              // NCS drop default statement
              description
                "Number of dynamic PWs using a specific PW template.";
            }
            container tdm-parameter {
              description
                "Configure TDM parameters.";
              leaf tdm-encapsulate-number {
                type uint32 {
                  range "1..40";
                }
                ext:dynamic-default;
                description
                  "Number of TDM frames encapsulated in a CESoPSN or SAToP packet in the TDMoPSN application.";
              }
              leaf jitter-buffer {
                type uint32 {
                  range "1..64000";
                }
                units "us";
                ext:dynamic-default;
                description
                  "Depth of the jitter buffer in the application of TDMoPSN.";
              }
              leaf jitter-buffer-cep {
                type uint32 {
                  range "125..16000";
                }
                units "us";
                // NCS drop default statement
                description
                  "Depth of the jitter buffer in the application of CEP.";
              }
              leaf rtp-header {
                type boolean;
                // NCS drop default statement
                description
                  "Enable/disable transparently transmission of TDM frames.";
              }
              leaf idle-code {
                type yang:hex-string {
                  length "1..2";
                }
                // NCS drop default statement
                description
                  "Idle code that is filled when the jitter buffer underflow occurs.";
              }
              leaf payload-compression {
                type live_ncs_l2vpn-payload-comp;
                // NCS drop default statement
                description
                  "Payload compression mode.";
              }
            }
            container atm-parameter {
              description
                "Configure ATM parameters.";
              leaf max-atm-cells {
                type uint32 {
                  range "1..28";
                }
                ext:dynamic-default;
                description
                  "Maximum number of ATM cells to be encapsulated into a packet that can be received by a device.";
              }
              leaf atm-pack-overtime {
                type uint32 {
                  range "100..10000";
                }
                units "us";
                ext:dynamic-default;
                description
                  "Delay in encapsulating ATM cells into a packet.";
              }
              leaf atm-transmit-cell {
                type uint32 {
                  range "1..28";
                }
                description
                  "Maximum number of ATM cells to be encapsulated into a packet that can be sent by a device.";
              }
              leaf sequence-number {
                // NCS drop when statement
                type boolean;
                // NCS drop default statement
                description
                  "Enable/disable the sequence number function.";
              }
            }
            container bfd-parameter {
              // NCS drop when statement
              // NCS drop must statement
              presence "enable bfd-parameter for pw";
              description
                "Enable/disable BFD.";
              leaf min-rx-interval {
                type uint16 {
                  range "0..65535";
                }
                units "ms";
                // NCS drop default statement
                description
                  "Minimum receive interval.";
              }
              leaf min-tx-interval {
                type uint16 {
                  range "0..65535";
                }
                units "ms";
                // NCS drop default statement
                description
                  "Minimum transmit interval.";
              }
              leaf detect-multiplier {
                type uint16 {
                  range "3..50";
                }
                // NCS drop default statement
                description
                  "Detection multiplier.";
              }
            }
            container flow-label {
              presence "enable flow-label for pw";
              description
                "Enable/disable the flow-label function.";
              leaf ability {
                type live_ncs_flow-label-ability;
                // NCS drop must statement
                // NCS drop mandatory statement
                description
                  "Specify the flow-label ability.";
              }
              leaf static {
                type boolean;
                // NCS drop default statement
                description
                  "Enable/disable the static flow-label function.";
              }
            }
          }
        }
        container pw-apss {
          description
            "List of APS instances.";
          list pw-aps {
            key "aps-id";
            // NCS drop max-elements statement
            description
              "Configure APS instances.";
            leaf aps-id {
              type uint32 {
                range "1..65535";
              }
              description
                "ID of a PW APS instance.";
            }
            leaf description {
              type string {
                length "1..63";
              }
              description
                "PW APS description.";
            }
            leaf protect-type {
              ext:operation-exclude "update|delete";
              type live_ncs_l2vpn-pw-aps-type;
              // NCS drop must statement
              // NCS drop default statement
              description
                "Protection type.";
            }
            leaf role {
              type live_ncs_l2vpn-pw-aps-role;
              // NCS drop must statement
              // NCS drop default statement
              description
                "E-PW APS role.";
            }
            leaf remote-aps-id {
              // NCS drop when statement
              type uint32 {
                range "1..65535";
              }
              description
                "Remote ID of E-PW APS.";
            }
            leaf holdoff {
              type uint32 {
                range "0..100";
              }
              units "ms";
              // NCS drop default statement
              description
                "Hold time.";
            }
            leaf wtr {
              // NCS drop when statement
              type uint32 {
                range "0..12";
              }
              units "min";
              // NCS drop default statement
              description
                "Wait-to-Restore time.";
            }
            leaf operation-type {
              // NCS drop when statement
              type live_ncs_l2vpn-pw-aps-oper-type;
              // NCS drop default statement
              description
                "Operation type.";
            }
            leaf protect-mode {
              type live_ncs_l2vpn-pw-aps-mode;
              // NCS drop default statement
              description
                "Protection mode.";
            }
            container pw-aps-info {
              description
                "Statistics of APS instances.";
              leaf aps-status {
                type live_ncs_l2vpn-aps-status;
                description
                  "PW APS status.";
              }
              leaf work-path-status {
                type live_ncs_l2vpn-aps-path-status;
                description
                  "Working path status.";
              }
              leaf protect-path-status {
                type live_ncs_l2vpn-aps-path-status;
                description
                  "Protection path status.";
              }
              leaf far-end-status {
                type live_ncs_l2vpn-aps-status;
                description
                  "PW APS status on the remote end.";
              }
              leaf request-result {
                type live_ncs_l2vpn-aps-result;
                description
                  "APS request result.";
              }
              leaf alarm {
                type string {
                  length "1..256";
                }
                description
                  "Alarm information.";
              }
              leaf total-vpn-num {
                type uint32;
                // NCS drop default statement
                description
                  "Total number of VPN instances (PW protection groups) bound to a PW APS instance.";
              }
            }
            container aps-vpws-instances {
              description
                "List of VPWS PW protection groups.";
              list aps-vpws-instance {
                key "client-interface";
                // NCS drop max-elements statement
                description
                  "Operational data of a VPWS PW protection group.";
                leaf client-interface {
                  type leafref {
                    path "/ncs:devices/ncs:device/ncs:live-status/ifm:ifm/ifm:interfaces/ifm:interface/ifm:name" {
                      tailf:xpath-root 3;
                    }
                  }
                  description
                    "Interface bound to an L2VPN.";
                }
                leaf instance-name {
                  type live_ncs_l2vpn-instance-name;
                  description
                    "VPWS instance name.";
                }
                leaf bind-type {
                  type live_ncs_l2vpn-aps-bind-type;
                  description
                    "Binding relationship between a PW protection group and a PW APS instance.";
                }
                leaf encapsulation-type {
                  ext:support-filter "true";
                  type live_ncs_encapsulation-type;
                  description
                    "Encapsulation type of a VPWS instance bound to a PW APS instance.";
                }
                leaf description {
                  type string {
                    length "1..128";
                  }
                  description
                    "Description of a VPWS instance. The value is a string of characters.";
                }
                container aps-vpws-pws {
                  description
                    "List of protection group PW member.";
                  list aps-vpws-pw {
                    key "role";
                    // NCS drop max-elements statement
                    description
                      "Operational data of PW members in a protection group.";
                    leaf role {
                      type live_ncs_pw-role-type;
                      description
                        "Role of a PW, either primary or secondary.";
                    }
                    leaf pw-id {
                      type uint32;
                      description
                        "PW ID.";
                    }
                    leaf encapsulation-type {
                      type live_ncs_encapsulation-type;
                      description
                        "Encapsulation type of a PW.";
                    }
                    leaf peer-ip {
                      type inet:ipv4-address-no-zone;
                      description
                        "LSR ID of the remote device.";
                    }
                    leaf pw-state {
                      type live_ncs_l2vpn-pw-state;
                      description
                        "Status of a PW.";
                    }
                  }
                }
              }
            }
          }
        }
        container service-peers {
          description
            "List of peers.";
          list service-peer {
            key "peer-ip";
            description
              "Configure the list of peers.";
            leaf peer-ip {
              type inet:ipv4-address-no-zone;
              description
                "Indicates the LSR ID of the remote device.";
            }
            leaf ldp-mode {
              type live_ncs_l2vpn-peer-ldp-signal-mode;
              // NCS drop default statement
              description
                "Peer signal mode.";
            }
          }
        }
        container peer-no-requests {
          description
            "List of no-request peers.";
          list peer-no-request {
            key "peer-ip";
            description
              "Configure no-request peers.";
            leaf peer-ip {
              type inet:ipv4-address-no-zone;
              description
                "Indicates the LSR ID of the remote device.";
            }
          }
        }
        container peer-bfd-cv-stds {
          description
            "List of BFD CV standard peers.";
          list peer-bfd-cv-std {
            // NCS drop must statement
            key "peer-ip";
            description
              "Configure BFD CV standard peers.";
            leaf peer-ip {
              type inet:ipv4-address-no-zone;
              description
                "Indicates the LSR ID of the remote device.";
            }
            leaf enable {
              type live_ncs_l2vpn-common-enable-type;
              // NCS drop default statement
              description
                "Enable BFDCV.";
            }
            leaf type {
              type live_ncs_bfd-vccv-cv-type;
              // NCS drop default statement
              description
                "The BFDCV type of the peer.";
            }
          }
        }
        container vpws-bgp-vpns {
          description
            "List of VPWS BGP VPN instances.";
          list vpws-bgp-vpn {
            key "name";
            description
              "Configure VPWS BGP VPN instance.";
            leaf name {
              type string {
                length "1..31";
              }
              description
                "VPWS BGP VPN instance name.";
            }
            leaf encapsulation-type {
              type live_ncs_vpws-bgp-vpn-encap;
              // NCS drop mandatory statement
              description
                "VPWS BGP VPN instance encapsulation type.";
            }
            leaf control-word {
              type enumeration {
                enum "disable" {
                  value 1;
                  description
                    "The control word mode is disable.";
                }
                enum "enable" {
                  value 2;
                  description
                    "The control word mode is enable.";
                }
              }
              // NCS drop default statement
              description
                "Control word of the VPWS BGP VPN instance. If the encapsulation type is low speed, disabling the control word causes the VPWS BGP instance to fail.";
            }
            leaf route-distinguisher {
              type string {
                length "3..21";
              }
              description
                "Route distinguisher of VPWS BGP VPN instance.";
            }
            leaf mtu {
              type uint16 {
                range "0..16352";
              }
              // NCS drop default statement
              description
                "MTU of VPWS BGP VPN instance.";
            }
            leaf ignore-mtu-match {
              type boolean;
              // NCS drop default statement
              description
                "Enable/disable the function of the ignoring MTU match of a VPWS BGP VPN instance.";
            }
            leaf auto-route-distinguisher {
              type string {
                length "3..21";
              }
              description
                "Automatic route distinguisher (RD). If no RD is configured for an L2VPN instance, you can specify an IPv4 address using the rd-ip parameter, based on which an RD is automatically generated in the format of 32-bit prefix IP address:index, for example, 192.168.122.15:1. An index is an integer automatically allocated by the system and ranges from 1 to 65535.Each L2VPN instance must use a unique RD.";
            }
            container vpn-targets {
              description
                "List of route targets of VPWS BGP VPN instances.";
              list vpn-target {
                key "rt-value rt-type";
                // NCS drop max-elements statement
                description
                  "Configure a route target list of the VPWS BGP VPN instances.";
                leaf rt-value {
                  type string {
                    length "3..21";
                  }
                  description
                    "Route target value of the VPWS BGP VPN instance.";
                }
                leaf rt-type {
                  type live_ncs_vpn-rt-type;
                  description
                    "Route target type of the VPWS BGP VPN instance.";
                }
              }
            }
            container sites {
              description
                "List of CEs in a VPWS BGP VPN instance.";
              list site {
                // NCS drop must statement
                key "name";
                unique "id";
                description
                  "Configure a CE in a VPWS BGP VPN instance.";
                leaf name {
                  type live_ncs_vpws-bgp-ce-name-type;
                  description
                    "Local site name.";
                }
                leaf id {
                  ext:operation-exclude "update";
                  type uint16 {
                    range "0..65534";
                  }
                  // NCS drop mandatory statement
                  description
                    "VPWS BGP VPN instance customer edge identifier.";
                }
                leaf range {
                  type uint16 {
                    range "1..65535";
                  }
                  // NCS drop must statement
                  // NCS drop default statement
                  description
                    "VPWS BGP VPN instance customer edge range.";
                }
                leaf default-offset {
                  type uint16 {
                    range "0..1";
                  }
                  // NCS drop default statement
                  description
                    "VPWS BGP VPN instance customer edge default offset.";
                }
                container label-blocks {
                  description
                    "List of label blocks of a CE in a VPWS BGP VPN instance.";
                  list label-block {
                    key "label-offset";
                    description
                      "Operational data of a label block of a CE in aVPWS BGP VPN instance.";
                    leaf label-offset {
                      type uint8;
                      description
                        "VPWS BGP VPN instance customer edge label offset.";
                    }
                    leaf label-base {
                      type uint32;
                      description
                        "VPWS BGP VPN instance customer edge label benchmark.";
                    }
                    leaf ce-base {
                      type uint32;
                      description
                        "VPWS BGP VPN instance customer edge benchmark.";
                    }
                    leaf label-range {
                      type uint16;
                      description
                        "VPWS BGP VPN instance customer edge label range.";
                    }
                  }
                }
              }
            }
            container remote-sites {
              description
                "List of remote CE information in a VPWS BGP VPN instance.";
              list remote-site {
                key "id";
                description
                  "Operational data of remote label information of a remote CE in a VPWS BGP VPN instance.";
                leaf id {
                  type uint16;
                  description
                    "VPWS BGP VPN instance remote customer edge info customer edge identifier.";
                }
                leaf peer-ip {
                  type inet:ipv4-address-no-zone;
                  description
                    "VPWS BGP VPN instance remote customer edge info peer IP address.";
                }
                leaf route-distinguisher {
                  type string {
                    length "0..21";
                  }
                  description
                    "VPWS BGP VPN instance remote customer edge info remote route distinguisher.";
                }
                container labels {
                  description
                    "List of remote label information of a remote CE in a VPWS BGP VPN instance.";
                  list label {
                    key "label-offset";
                    description
                      "Operational data of remote label information of a remote CE in a VPWS BGP VPN instance.";
                    leaf label-offset {
                      type uint8;
                      description
                        "VPWS BGP VPN instance remote customer edge info remote label offset.";
                    }
                    leaf label-base {
                      type uint32;
                      description
                        "VPWS BGP VPN instance remote customer edge info remote label benchmark.";
                    }
                    leaf label-range {
                      type uint16;
                      description
                        "VPWS BGP VPN instance remote customer edge info remote label range.";
                    }
                  }
                }
              }
            }
          }
        }
        container not-match-remote-ldps {
          description
            "List of incongruous remote signaling.";
          list not-match-remote-ldp {
            key "pw-id peer-ip encapsulation-type";
            description
              "Operational data of incongruous remote signaling.";
            leaf pw-id {
              type uint32 {
                range "0..4294967295";
              }
              description
                "PW ID used by the remote end for PW negotiation.";
            }
            leaf peer-ip {
              type inet:ipv4-address-no-zone;
              description
                "IP address of the remote end.";
            }
            leaf encapsulation-type {
              type live_ncs_encapsulation-type;
              description
                "Encapsulate type on the remote end.";
            }
            leaf remote-label {
              type uint32;
              description
                "Label information on the remote end.";
            }
            leaf remote-group-id {
              type uint32;
              description
                "Group ID on the remote end.";
            }
            leaf remote-mtu {
              type uint32;
              description
                "MTU information on the remote end.";
            }
            leaf remote-state-code {
              type live_ncs_l2vpn-vpls-ldp-pw-state-code;
              description
                "Status code information on the remote end.";
            }
          }
        }
        container vpws-statistic {
          description
            "VPWS statistics.";
          container vpws-ccc-instance {
            description
              "CCC statistics.";
            leaf total-num {
              type uint32;
              // NCS drop default statement
              description
                "Total number of local and remote CCCs on the local end.";
            }
            leaf local-num {
              type uint32;
              // NCS drop default statement
              description
                "Number of local CCCs on the local end.";
            }
            leaf local-up-num {
              type uint32;
              // NCS drop default statement
              description
                "Number of local CCCs in the up state.";
            }
            leaf remote-num {
              type uint32;
              // NCS drop default statement
              description
                "Number of remote CCCs on the local end.";
            }
            leaf remote-up-num {
              type uint32;
              // NCS drop default statement
              description
                "Number of remote CCCs in the up state.";
            }
          }
          container vpws-ccc-ac {
            description
              "CCC AC statistics.";
            leaf total-num {
              type uint32;
              // NCS drop default statement
              description
                "Total number of CCC ACs.";
            }
            leaf up-num {
              type uint32;
              // NCS drop default statement
              description
                "Number of CCC ACs in the up state.";
            }
            leaf down-num {
              type uint32;
              // NCS drop default statement
              description
                "Number of CCC ACs in the down state.";
            }
          }
          container vpws-ldp-ac {
            description
              "VPWS LDP AC statistics.";
            leaf total-num {
              type uint32;
              // NCS drop default statement
              description
                "Total number of VPWS LDP ACs.";
            }
            leaf up-num {
              type uint32;
              // NCS drop default statement
              description
                "Number of VPWS LDP ACs in the up state.";
            }
            leaf down-num {
              type uint32;
              // NCS drop default statement
              description
                "Number of VPWS LDP ACs in the down state.";
            }
          }
          container vpws-ldp-pw {
            description
              "VPWS PW statistics.";
            leaf total-num {
              type uint32;
              // NCS drop default statement
              description
                "Total number of VPWS LDP PWs, including those in the up state and those in the down state.";
            }
            leaf up-num {
              type uint32;
              // NCS drop default statement
              description
                "Number of VPWS LDP PWs in the up state.";
            }
            leaf down-num {
              type uint32;
              // NCS drop default statement
              description
                "VPWS LDP PWs in the down state.";
            }
          }
          container vpws-ldp-pw-remote {
            description
              "Remote VPWS PW statistics.";
            leaf remote-num {
              type uint32;
              // NCS drop default statement
              description
                "Remote VPWS LDP PWs.";
            }
          }
          container vpws-static-ac {
            description
              "VPWS static AC statistics.";
            leaf total-num {
              type uint32;
              // NCS drop default statement
              description
                "Total number of VPWS static ACs.";
            }
            leaf up-num {
              type uint32;
              // NCS drop default statement
              description
                "Number of VPWS static ACs in the up state.";
            }
            leaf down-num {
              type uint32;
              // NCS drop default statement
              description
                "Number of VPWS static ACs in the down state.";
            }
          }
          container vpws-static-pw {
            description
              "VPWS static PW statistics.";
            leaf total-num {
              type uint32;
              // NCS drop default statement
              description
                "Total number of VPWS static PWs, including those in the up state and those in the down state.";
            }
            leaf up-num {
              type uint32;
              // NCS drop default statement
              description
                "Number of VPWS static PWs in the up state.";
            }
            leaf down-num {
              type uint32;
              // NCS drop default statement
              description
                "VPWS static PWs in the down state.";
            }
          }
          container vpws-switch-instance {
            description
              "VPWS MS-PW statistics.";
            leaf total-num {
              type uint32;
              // NCS drop default statement
              description
                "Total number of MS-PWs.";
            }
            leaf up-num {
              type uint32;
              // NCS drop default statement
              description
                "Number of MS-PWs in the up state.";
            }
            leaf down-num {
              type uint32;
              // NCS drop default statement
              description
                "Number of MS-PWs in the down state.";
            }
          }
          container vpws-vrrps {
            description
              "List of mVRRP backup group.";
            list vpws-vrrp {
              key "vrrp-interface-name vrrp-vrid";
              // NCS drop max-elements statement
              description
                "Operational data of MVRRP backup group.";
              leaf vrrp-interface-name {
                type leafref {
                  path "/ncs:devices/ncs:device/ncs:live-status/ifm:ifm/ifm:interfaces/ifm:interface/ifm:name" {
                    tailf:xpath-root 3;
                  }
                }
                description
                  "Name of the interface bound to an mVRRP backup group.";
              }
              leaf vrrp-vrid {
                type uint32 {
                  range "1..255";
                }
                description
                  "VRID of the mVRRP backup group.";
              }
              leaf vrrp-state {
                type live_ncs_l2vpn-vpws-vrrp-state;
                description
                  "Status of the mVRRP backup group, which can be master, backup, or initialize.";
              }
              leaf pw-number {
                type uint32;
                // NCS drop default statement
                description
                  "Number of PWs bound to an mVRRP backup group.";
              }
              container pw-infos {
                description
                  "List of PWs bound to mVRRP backup groups.";
                list pw-info {
                  key "client-interface-name";
                  // NCS drop max-elements statement
                  description
                    "Operational data of PW bound to an mVRRP backup group.";
                  leaf client-interface-name {
                    type leafref {
                      path "/ncs:devices/ncs:device/ncs:live-status/ifm:ifm/ifm:interfaces/ifm:interface/ifm:name" {
                        tailf:xpath-root 3;
                      }
                    }
                    description
                      "Name of the interface bound to an L2VPN.";
                  }
                  leaf pw-state {
                    type live_ncs_l2vpn-pw-state;
                    description
                      "PW status, either down or up.";
                  }
                  leaf pw-id {
                    type uint32;
                    description
                      "PW ID. The combination of the PW ID and encapsulation type uniquely identify a PW.";
                  }
                  leaf encapsulation-type {
                    type live_ncs_encapsulation-type;
                    description
                      "Encapsulation type of a PW.";
                  }
                  leaf link-state {
                    type live_ncs_l2vpn-state;
                    description
                      "Forwarding status of a PW.";
                  }
                }
              }
            }
          }
          container arp {
            description
              "ARP statistics.";
            leaf total-ce-mac-num {
              type uint32;
              // NCS drop default statement
              description
                "Total number of CE MAC addresses.";
            }
            leaf dynamic-ce-mac-num {
              type uint32;
              // NCS drop default statement
              description
                "Number of dynamic CE MAC entries.";
            }
            leaf static-ce-mac-num {
              type uint32;
              // NCS drop default statement
              description
                "Number of static CE MAC entries.";
            }
            leaf brd-ce-mac-num {
              type uint32;
              // NCS drop default statement
              description
                "Number of broadcast CE MAC addresses.";
            }
          }
          container vpws-bgp-pw {
            description
              "BGP VLL PW statistics.";
            leaf total-num {
              type uint32;
              // NCS drop default statement
              description
                "Total number of BGP VLL PWs, including those in the up state and those in the down state.";
            }
            leaf up-num {
              type uint32;
              // NCS drop default statement
              description
                "Number of BGP VLL PWs in the up state.";
            }
            leaf down-num {
              type uint32;
              // NCS drop default statement
              description
                "BGP VLL PWs in the down state.";
            }
          }
        }
        container vpls-statistic {
          description
            "VPLS statistics.";
          container vpls-instance {
            description
              "VSI statistics.";
            leaf total-vsi-num {
              type uint32;
              description
                "Total number of VSIs, including those in the up state and those in the down state.";
            }
            leaf vsi-up-num {
              type uint32;
              description
                "Number of VSIs in the up state.";
            }
            leaf vsi-down-num {
              type uint32;
              description
                "Number of VSIs in the down state.";
            }
            leaf ldp-mode-num {
              type uint32;
              description
                "Number of LDP VSIs.";
            }
            leaf bgp-vsi-num {
              type uint32;
              description
                "Number of BGP VSIs.";
            }
            leaf bgpad-vsi-num {
              type uint32;
              description
                "Number of BGP AD VSIs.";
            }
            leaf unspecified-num {
              type uint32;
              description
                "Number of VSIs whose signaling modes are not specified.";
            }
            leaf mix-vsi-num {
              type uint32;
              description
                "Number of hybrid VSIs.";
            }
            leaf max-vsi-num {
              type uint32;
              description
                "Maximum number of VSIs that can be configured.";
            }
          }
          container vpls-pw {
            description
              "VPLS PW statistics.";
            leaf total-pw-num {
              type uint32;
              description
                "Total number of PWs, including those in the up state and those in the down state.";
            }
            leaf up-pw-num {
              type uint32;
              description
                "Number of PWs in the up state.";
            }
            leaf down-pw-num {
              type uint32;
              description
                "Number of PWs in the down state.";
            }
            leaf ldp-pw-num {
              type uint32;
              description
                "Number of LDP PWs.";
            }
            leaf bgp-pw-num {
              type uint32;
              description
                "Number of BGP VSI PWs.";
            }
            leaf bgpad-pw-num {
              type uint32;
              description
                "Number of BGP AD PWs.";
            }
          }
          container ac {
            description
              "VPLS AC statistics.";
            leaf total-num {
              type uint32;
              description
                "Total number of VPLS ACs, including those in the up state and those in the down state.";
            }
            leaf up-num {
              type uint32;
              description
                "Number of VPLS ACs in the up state.";
            }
            leaf down-num {
              type uint32;
              description
                "Number of VPLS ACs in the down state.";
            }
          }
          container vpls-tunnel-references {
            description
              "List of tunnel policy reference.";
            list vpls-tunnel-reference {
              key "tunnel-policy";
              // NCS drop max-elements statement
              description
                "Operational data of times a tunnel policy is referenced.";
              leaf tunnel-policy {
                type string {
                  length "1..39";
                }
                description
                  "Name of a tunnel policy. If the tunnel policy name is not specified, the system uses the default tunnel policy. The default tunnel policy preferentially selects LSPs for packet transmission and the number of load-balancing tunnels is 1. If the tunnel policy name is specified but the corresponding tunnel policy does not exist, the system still uses the default tunnel policy.";
              }
              container references {
                description
                  "List of tunnel policy reference.";
                list reference {
                  key "instance-name";
                  // NCS drop max-elements statement
                  description
                    "Operational data of times a tunnel policy is referenced.";
                  leaf instance-name {
                    type string {
                      length "1..31";
                    }
                    description
                      "VSI name.";
                  }
                }
              }
            }
          }
          container vpls-loop-detect {
            description
              "MAC withdraw loop detection statistics.";
            leaf total-num {
              type uint32;
              description
                "Total number of MAC withdraw loop detection times.";
            }
          }
          container vpls-bgpads {
            description
              "List of BGP AD local VPN target.";
            list vpls-bgpad {
              key "vpls-id rt-value rt-type";
              description
                "Operational data of BGP AD local VPN target.";
              leaf vpls-id {
                type string {
                  length "3..21";
                }
                description
                  "VPLS domain ID.";
              }
              leaf rt-value {
                type string {
                  length "3..21";
                }
                description
                  "Route target. The format of an RT can be:
                   - 16-bit AS number:32-bit user-defined number, for example, 1:3. An AS number ranges from 0 to 65535, and a user-defined number ranges from 0 to 4294967295. The AS number and user-defined number cannot be both 0s. This means that the RT value cannot be 0:0.
                   - Integral 4-byte AS number:2-byte user-defined number, for example, 65537:3. An AS number ranges from 65536 to 4294967295. A user-defined number ranges from 0 to 65535. The AS number and user-defined number cannot be both 0s. This means that the RT value cannot be 0:0.
                   - 32-bit IP address:16-bit user-defined number, for example, 192.168.122.15:1. The IP address ranges from 0.0.0.0 to 255.255.255.255, and the user-defined number ranges from 0 to 65535.
                   - 32-bit AS number:16-bit user-defined number, for example, 10.11:3. An AS number ranges from 0.0 to 65535.65535, and a user-defined number ranges from 0 to 65535. The AS number and user-defined number cannot be both 0s. This means that the RT value cannot be 0.0:0.";
              }
              leaf rt-type {
                type live_ncs_vpn-rt-type;
                description
                  "RT type, which can be:
                   - export-extcommunity: specifies the value of the extended community attribute of the route from an outbound interface to the destination VPN.
                   - import-extcommunity: receives routes that carry the specified extended community attribute value.";
              }
            }
          }
          container bgpad-remotes {
            description
              "List of BGP AD remote site.";
            list bgpad-remote {
              key "peer-ip vpls-id";
              description
                "Operational data of BGP AD remote site.";
              leaf peer-ip {
                type inet:ipv4-address-no-zone;
                description
                  "Peer IP information on the remote end.";
              }
              leaf vpls-id {
                type string {
                  length "3..21";
                }
                description
                  "VPLS domain ID on the remote end.";
              }
              leaf vsi-id {
                type inet:ipv4-address-no-zone;
                description
                  "VSI ID on the remote end.";
              }
              leaf vsi-index {
                type uint32;
                description
                  "VSI index.";
              }
              container export-vpn-targets {
                description
                  "List of Export VPN target on the remote end.";
                list export-vpn-target {
                  key "rt-value rt-type";
                  description
                    "Operational data of VPN target.";
                  leaf rt-value {
                    type string {
                      length "3..21";
                    }
                    description
                      "Route target. The format of an RT can be:
                       - 16-bit AS number:32-bit user-defined number, for example, 1:3. An AS number ranges from 0 to 65535, and a user-defined number ranges from 0 to 4294967295. The AS number and user-defined number cannot be both 0s. This means that the RT cannot be 0:0.
                       - Integral 4-byte AS number:2-byte user-defined number, for example, 65537:3. An AS number ranges from 65536 to 4294967295. A user-defined number ranges from 0 to 65535. The AS number and user-defined number cannot be both 0s. This means that the RT cannot be 0:0.
                       - 32-bit IP address:16-bit user-defined number, for example: 192.168.122.15:1. The IP address ranges from 0.0.0.0 to 255.255.255.255, and the user-defined number ranges from 0 to 65535.
                       - 32-bit AS number:16-bit user-defined number, for example, 10.11:3. An AS number ranges from 0.0 to 65535.65535, and a user-defined number ranges from 0 to 65535. The AS number and user-defined number cannot be both 0s. This means that the RT cannot be 0.0:0.";
                  }
                  leaf rt-type {
                    type live_ncs_vpn-rt-type;
                    description
                      "RT type, which can be:
                       - export-extcommunity: specifies the value of the extended community attribute of the route from an outbound interface to the destination VPN.
                       - import-extcommunity: receives routes that carry the specified extended community attribute value.";
                  }
                }
              }
            }
          }
          container remote-fec129s {
            description
              "List of remote FEC129 signal.";
            list remote-fec129 {
              key "peer-router-id encapsulation-type vpls-id saii taii";
              description
                "Operational data of remote FEC129 signaling.";
              leaf peer-router-id {
                type inet:ipv4-address-no-zone;
                description
                  "Remote peer IP address.";
              }
              leaf encapsulation-type {
                type live_ncs_encapsulation-type;
                description
                  "Remote encapsulation type.";
              }
              leaf vpls-id {
                type string {
                  length "3..21";
                }
                description
                  "Remote VPLS domain ID.";
              }
              leaf saii {
                type inet:ipv4-address-no-zone;
                description
                  "Remote source attachment individual identifier.";
              }
              leaf taii {
                type inet:ipv4-address-no-zone;
                description
                  "Remote target attachment individual identifier.";
              }
              leaf vc-label {
                type uint32;
                description
                  "Remote VC label.";
              }
              leaf mtu {
                type uint32;
                description
                  "Remote MTU information.";
              }
              leaf vsi-index {
                type uint32;
                description
                  "Remote VSI index.";
              }
              leaf remote-vccv {
                type string {
                  length "0..16";
                }
                description
                  "VCCV capability supported by the remote end. By default, the LSP ping and BFD for the label alert mode can be used if the control word function is disabled. If the control word function is enabled, the LSP ping and BFD for both the label alert mode and control word mode can be used.";
              }
              leaf remote-vccv-code {
                type pub-type:live_ncs_hex-binary;
                description
                  "Remote VCCV code.";
              }
            }
          }
          container bgp-remotes {
            description
              "List of BGP remote site.";
            list bgp-remote {
              key "site-id offset route-distinguisher";
              description
                "Operational data of BGP remote site.";
              leaf site-id {
                type uint32 {
                  range "0..65534";
                }
                description
                  "BGP site ID.";
              }
              leaf offset {
                type uint16;
                description
                  "BGP site offset.";
              }
              leaf route-distinguisher {
                type string {
                  length "3..21";
                }
                description
                  "Route distinguisher.";
              }
              leaf label-start {
                type uint32;
                description
                  "Start of the label.";
              }
              leaf add-range {
                type uint32;
                description
                  "BGP site range.";
              }
              leaf peer-ip {
                type inet:ipv4-address-no-zone;
                description
                  "BGP peer Ip.";
              }
              leaf mtu {
                type uint32;
                description
                  "Maximum transmission unit.";
              }
              leaf encapsulation-type {
                type live_ncs_vpls-bgp-encapsulation-type;
                description
                  "Encapsulation type.";
              }
              leaf control-lags {
                type pub-type:live_ncs_hex-binary;
                description
                  "Control flags.";
              }
              leaf preference {
                type uint32;
                description
                  "Preference value.";
              }
              container export-vpn-targets {
                description
                  "List of VPN target.";
                list export-vpn-target {
                  key "rt-value rt-type";
                  description
                    "Operational data of VPN target.";
                  leaf rt-value {
                    type string {
                      length "3..21";
                    }
                    description
                      "Route target. The format of an RT can be:
                       - 16-bit AS number:32-bit user-defined number, for example, 1:3. An AS number ranges from 0 to 65535, and a user-defined number ranges from 0 to 4294967295. The AS number and user-defined number cannot be both 0s. This means that the RT cannot be 0:0.
                       - Integral 4-byte AS number:2-byte user-defined number, for example, 65537:3. An AS number ranges from 65536 to 4294967295. A user-defined number ranges from 0 to 65535. The AS number and user-defined number cannot be both 0s. This means that the RT cannot be 0:0.
                       - 32-bit IP address:16-bit user-defined number, for example: 192.168.122.15:1. The IP address ranges from 0.0.0.0 to 255.255.255.255, and the user-defined number ranges from 0 to 65535.
                       - 32-bit AS number:16-bit user-defined number, for example, 10.11:3. An AS number ranges from 0.0 to 65535.65535, and a user-defined number ranges from 0 to 65535. The AS number and user-defined number cannot be both 0s. This means that the RT cannot be 0.0:0.";
                  }
                  leaf rt-type {
                    type live_ncs_vpn-rt-type;
                    description
                      "RT type, which can be:
                       - export-extcommunity: specifies the value of the extended community attribute of the route from an outbound interface to the destination VPN.
                       - import-extcommunity: receives routes that carry the specified extended community attribute value.";
                  }
                }
              }
            }
          }
          container vpls-pbb-b-dmacs {
            description
              "List of B-DMAC address.";
            list vpls-pbb-b-dmac {
              key "b-dmac";
              description
                "Operational data of B-DMAC address.";
              leaf b-dmac {
                type pub-type:live_ncs_mac-address;
                description
                  "B-DMAC address.";
              }
              container reference-vsis {
                description
                  "List of VPLS instance.";
                list reference-vsi {
                  key "vsi-name";
                  description
                    "Operational data of VPLS instance.";
                  leaf vsi-name {
                    type string {
                      length "1..31";
                    }
                    description
                      "VPLS instance name.";
                  }
                  leaf flag {
                    type enumeration {
                      enum "first" {
                        value 1;
                        description
                          "First configured B-DMAC address.";
                      }
                    }
                    description
                      "Flag indicating whether the B-DMAC address is first or second configured.";
                  }
                }
              }
            }
          }
          container vpls-pbb-b-smacs {
            description
              "List of B-SMAC address.";
            list vpls-pbb-b-smac {
              key "b-smac";
              description
                "Operational data of B-SMAC address.";
              leaf b-smac {
                type pub-type:live_ncs_mac-address;
                description
                  "B-SMAC address.";
              }
              container reference-vsis {
                description
                  "List of VPLS instance.";
                list reference-vsi {
                  key "vsi-name";
                  description
                    "Operational data of VPLS instance.";
                  leaf vsi-name {
                    type string {
                      length "1..31";
                    }
                    description
                      "VPLS instance name.";
                  }
                  leaf vsi-type {
                    type live_ncs_vsi-pbb-instance-type;
                    description
                      "VSI working mode.";
                  }
                }
              }
            }
          }
        }
        container track-route-statistics {
          description
            "Associated route statistics.";
          leaf total-track-route-num {
            type uint32;
            description
              "Total number of associated routes.";
          }
          leaf reach-track-route-num {
            type uint32;
            description
              "Number of reachable associated routes.";
          }
          leaf unreach-track-route-num {
            type uint32;
            description
              "Number of unreachable associated routes.";
          }
        }
        container vrf-routes {
          description
            "List of Associated routes.";
          list vrf-route {
            key "vrf-name destination mask-length";
            // NCS drop max-elements statement
            description
              "Statistics of an Associated route.";
            leaf vrf-name {
              type leafref {
                path "/ncs:devices/ncs:device/ncs:live-status/ni:network-instance/ni:instances/ni:instance/ni:name" {
                  tailf:xpath-root 3;
                }
              }
              description
                "VPN instance name.";
            }
            leaf destination {
              type inet:ip-address-no-zone;
              description
                "Destination address.";
            }
            leaf mask-length {
              type uint32 {
                range "0..128";
              }
              description
                "The length of the mask.";
            }
            leaf route-state {
              type live_ncs_l2vpn-route-status;
              description
                "Route status.";
            }
            leaf pw-number {
              type uint32;
              description
                "Number of PWs.";
            }
            container vrf-route-pws {
              description
                "List of PWs associated with the route.";
              list vrf-route-pw {
                key "peer-ip pw-id encapsulation-type";
                // NCS drop max-elements statement
                description
                  "Statistics of a PW associated with the route.";
                leaf peer-ip {
                  type inet:ipv4-address-no-zone;
                  description
                    "Peer IP address.";
                }
                leaf pw-id {
                  type uint32;
                  description
                    "PW ID.";
                }
                leaf encapsulation-type {
                  type live_ncs_encapsulation-type;
                  description
                    "Encapsulation type.";
                }
                leaf pw-state {
                  type live_ncs_l2vpn-pw-state;
                  description
                    "PW status.";
                }
              }
            }
          }
        }
      }
      container instances {
        description
          "List of L2VPN instances.";
        list instance {
          key "name type";
          description
            "Configure L2VPN instances.";
          leaf name {
            type string {
              length "1..31";
            }
            description
              "The name of L2VPN instance.";
          }
          leaf type {
            type live_ncs_l2vpn-instance-type;
            description
              "The type of L2VPN instance.";
          }
          leaf description {
            // NCS drop when statement
            type string {
              length "1..128";
            }
            description
              "Description of a VSI.";
          }
          leaf state {
            type live_ncs_instance-state;
            description
              "Status of a L2VPN instance.";
          }
          leaf last-up-time {
            type string {
              length "1..80";
            }
            description
              "Date and time when a L2VPN instance was up the last time, for example, 2012/07/20 02:30:46.";
          }
          leaf total-up-time {
            type string {
              length "1..80";
            }
            description
              "Total up time of a L2VPN instance.";
          }
          container vpws-local-ccc {
            ext:operation-exclude "delete";
            // NCS drop when statement
            description
              "Configure VPWS local CCC instance.";
            uses live_ncs_vpws-localccc-instance-grp;
          }
          container vpws-remote-ccc {
            ext:operation-exclude "delete";
            // NCS drop when statement
            description
              "Configure a VPWS remote CCC instance.";
            uses live_ncs_vpws-remoteccc-instance-grp;
          }
          container vpws-ldp {
            ext:operation-exclude "delete";
            // NCS drop when statement
            // NCS drop must statement
            // NCS drop must statement
            description
              "Configure VPWS LDP instance.";
            leaf encapsulation-type {
              ext:operation-exclude "update";
              type live_ncs_encapsulation-type;
              // NCS drop must statement
              // NCS drop mandatory statement
              description
                "Encapsulation type of a VPWS instance.";
            }
            leaf mac-withdraw-disable {
              // NCS drop when statement
              type boolean;
              // NCS drop default statement
              description
                "Enable/disable the function to send MAC withdraw messages during the primary/secondary PW switchover for Ethernet-encapsulated or VLAN-encapsulated VLLs.";
            }
            leaf load-balance {
              // NCS drop when statement
              type live_ncs_l2vpn-load-balance-type;
              // NCS drop default statement
              description
                "Load balancing mode, which can be:
                 - Flow: indicates per-flow load balancing.
                 - Packet: indicates per-packet load balancing.";
            }
            leaf service-name {
              type string {
                length "1..31";
              }
              description
                "Service name of a VPWS instance.";
            }
            leaf bit-error-detection {
              // NCS drop when statement
              type boolean;
              // NCS drop must statement
              // NCS drop default statement
              description
                "Enable/disable bit error detection on SPEs for an LDP MS-PW.";
            }
            container acs {
              description
                "List of information about all ACs.";
              list ac {
                ext:operation-exclude "update|delete";
                // NCS drop must statement
                key "interface-name";
                // NCS drop min-elements statement
                // NCS drop max-elements statement
                description
                  "Configure information about an AC.";
                leaf interface-name {
                  type leafref {
                    path "/ncs:devices/ncs:device/ncs:live-status/ifm:ifm/ifm:interfaces/ifm:interface/ifm:name" {
                      tailf:xpath-root 3;
                    }
                  }
                  description
                    "Name of an AC interface.";
                }
                leaf tagged {
                  ext:operation-exclude "update|delete";
                  // NCS drop when statement
                  type boolean;
                  ext:dynamic-default {
                    ext:default-value "false" {
                      // NCS drop when statement
                      description
                        "The default value is false when encapsulation-type is ethernet.";
                    }
                    ext:default-value "true" {
                      // NCS drop when statement
                      description
                        "The default value is true when encapsulation-type is VLAN.";
                    }
                  }
                  // NCS drop must statement
                  description
                    "Enable/disable the VLAN tag setting.";
                }
                leaf access-port {
                  ext:operation-exclude "update|delete";
                  // NCS drop when statement
                  type boolean;
                  // NCS drop must statement
                  // NCS drop default statement
                  description
                    "Enable/disable the function of allowing only untagged packets to pass through an interface. The access port attribute can be configured only on main Ethernet interfaces. The access port attribute of outbound interface must be consistent with that of inbound interface.";
                }
                leaf trigger-interface-down {
                  // NCS drop when statement
                  type boolean;
                  // NCS drop must statement
                  // NCS drop must statement
                  // NCS drop default statement
                  description
                    "Enable/disable remote interface shutdown to associate PW status with interface status.";
                }
                leaf forward-mode {
                  ext:operation-exclude "update";
                  type boolean;
                  // NCS drop must statement
                  // NCS drop default statement
                  description
                    "Enable/disable the raw forwarding mode.";
                }
                leaf performance-statistics {
                  // NCS drop when statement
                  type boolean;
                  // NCS drop default statement
                  description
                    "Enable/disable PW performance statistics collection.";
                }
                leaf state {
                  type live_ncs_l2vpn-state;
                  description
                    "Status of an AC.";
                }
                leaf token-exceed {
                  type boolean;
                  // NCS drop default statement
                  description
                    "Indicates whether the number of AC tokens exceeds the maximum limit.";
                }
                container arp-entry {
                  presence "Enable the ARP entry for AC.";
                  description
                    "Configure ARP entry attribute used for IP interworking between PEs.";
                  leaf local-ce-mac {
                    type pub-type:live_ncs_mac-address;
                    description
                      "MAC address of the Ethernet interface or sub-interface on a CE connected to the local AC interface. If MAC, IP, and broadcast addresses are all configured, these addresses take effect in the sequence of MAC address, IP address, and broadcast address.";
                  }
                  leaf local-ce-ip {
                    type inet:ipv4-address-no-zone;
                    description
                      "IP address of the Ethernet interface or sub-interface on a CE connected to the local AC interface.";
                  }
                  leaf local-ce-broadcast {
                    type boolean;
                    // NCS drop must statement
                    // NCS drop default statement
                    description
                      "Enable/disable the broadcast function on a PE Ethernet interface connected to a CE.";
                  }
                  leaf remote-ce-ip {
                    type inet:ipv4-address-no-zone;
                    description
                      "IP address of the remote CE connected to the local AC interface.";
                  }
                }
                container ac-arps {
                  description
                    "Operational data of ARP information about all ACs.";
                  uses live_ncs_ac-arp-grp;
                }
                container tdm-performance-statistic {
                  // NCS drop when statement
                  description
                    "Operational data of TDM PW performance statistics.";
                  leaf missing-packets {
                    type uint64;
                    description
                      "Number of missing packets.";
                  }
                  leaf jitter-buffer-overruns {
                    type uint64;
                    description
                      "Number of times the jitter buffer was overrun.";
                  }
                  leaf jitter-buffer-underruns {
                    type uint64;
                    description
                      "Number of times the jitter buffer was underrun.";
                  }
                  leaf misorder-packets {
                    type uint64;
                    description
                      "Number of disordered packets.";
                  }
                  leaf malformed-packet {
                    type uint64;
                    description
                      "Number of malformed packets.";
                  }
                  leaf misconnected-packets {
                    type uint64;
                    description
                      "Number of misconnected packets.";
                  }
                  leaf error-seconds {
                    type uint64;
                    description
                      "Accumulated number of seconds in which errored bits exist, that is, in which the TDM-encapsulated PW drops packets or receives errored packets, including disordered packets and malformed packets.";
                  }
                  leaf severely-error-seconds {
                    type uint64;
                    description
                      "Number of severely errored seconds.";
                  }
                  leaf unavailable-seconds {
                    type uint64;
                    description
                      "Number of unavailable seconds.";
                  }
                }
                container atm-performance-statistic {
                  // NCS drop when statement
                  description
                    "Operational data of ATM PW performance statistics.";
                  leaf missing-packets {
                    type uint64;
                    description
                      "Number of dropped packets.";
                  }
                  leaf misorder-packets {
                    type uint64;
                    description
                      "Number of packets dropped due to packet disorder.";
                  }
                  leaf transmitted-cells {
                    type uint64;
                    description
                      "Number of sent cells.";
                  }
                  leaf received-cells {
                    type uint64;
                    description
                      "Number of received cells.";
                  }
                  leaf unknown-cells {
                    type uint64;
                    description
                      "Number of unknown cells.";
                  }
                }
              }
            }
            container pws {
              description
                "List of all VPWS PWs.";
              list pw {
                // NCS drop must statement
                // NCS drop must statement
                key "role";
                // NCS drop max-elements statement
                description
                  "Configure a VPWS PW.";
                leaf role {
                  type live_ncs_pw-role-type;
                  // NCS drop must statement
                  description
                    "Role of a PW. Configure a primary PW first.";
                }
                leaf pw-id {
                  ext:operation-exclude "update|delete";
                  ext:support-filter "true";
                  type uint32 {
                    range "1..4294967295";
                  }
                  description
                    "PW ID.";
                }
                leaf peer-ip {
                  ext:operation-exclude "update|delete";
                  type live_ncs_l2vpn-peer-address-type;
                  description
                    "IP address of a peer.";
                }
                leaf admin-pw {
                  ext:operation-exclude "update|delete";
                  // NCS drop when statement
                  type boolean;
                  // NCS drop must statement
                  // NCS drop default statement
                  description
                    "Enable/disable administrative PW.";
                }
                leaf transmit-label {
                  ext:operation-exclude "update|delete";
                  // NCS drop when statement
                  type uint32 {
                    range "0..1048575";
                  }
                  description
                    "Label for sending packets.";
                }
                leaf receive-label {
                  ext:operation-exclude "update|delete";
                  // NCS drop when statement
                  type uint32 {
                    range "16..1048575";
                  }
                  description
                    "Label for receiving packets.";
                }
                leaf control-word {
                  // NCS drop when statement
                  type live_ncs_l2vpn-control-word;
                  // NCS drop must statement
                  // NCS drop default statement
                  description
                    "Enable the control word function. The control word is usually used for TDM, ATM, and FR PWs.";
                }
                leaf vccv-ability {
                  // NCS drop when statement
                  type boolean;
                  // NCS drop default statement
                  description
                    "Enable/disable virtual circuit connectivity verification (VCCV) capability. VCCV supports two modes: control word and label alert.";
                }
                leaf tunnel-policy {
                  // NCS drop when statement
                  type string {
                    length "1..39";
                  }
                  description
                    "Name of a tunnel policy. If the tunnel policy name is not specified, the system uses the default tunnel policy. The default tunnel policy preferentially selects LSPs for packet transmission and the number of load-balancing tunnels is 1. If the tunnel policy name is specified but the corresponding tunnel policy does not exist, the system still uses the default tunnel policy.";
                }
                leaf pw-template {
                  ext:operation-exclude "update|delete";
                  // NCS drop when statement
                  type leafref {
                    path "/ncs:devices/ncs:device/ncs:live-status/l2vpn/common/pw-templates/pw-template/name" {
                      tailf:xpath-root 3;
                    }
                  }
                  description
                    "Name of a PW template. You can configure PW attributes such as the remote peer, tunnel policy, and control word in a PW template. When configuring an LDP PW, you can reference the PW attributes configured in an existing PW template.";
                }
                leaf ignore-standby {
                  // NCS drop when statement
                  type boolean;
                  // NCS drop default statement
                  description
                    "Enable/disable the PW's function of ignoring the standby state informed by the VSI peer.";
                }
                leaf set-fault {
                  // NCS drop when statement
                  type boolean;
                  // NCS drop must statement
                  // NCS drop default statement
                  description
                    "Enable/disable simulating a fault on a primary or secondary PW.";
                }
                leaf pw-ttl {
                  // NCS drop when statement
                  type uint32 {
                    range "1..255";
                  }
                  // NCS drop must statement
                  // NCS drop default statement
                  description
                    "TTL of a PW.";
                }
                leaf track-admin-pw {
                  // NCS drop when statement
                  type leafref {
                    path "/ncs:devices/ncs:device/ncs:live-status/ifm:ifm/ifm:interfaces/ifm:interface/ifm:name" {
                      tailf:xpath-root 3;
                    }
                  }
                  // NCS drop must statement
                  description
                    "Configure a service PW to track the mPW.";
                }
                leaf traffic-statistics-collection {
                  // NCS drop when statement
                  type boolean;
                  // NCS drop default statement
                  description
                    "Enable/disable collecting traffic statistics.";
                }
                leaf ignore-ac-state {
                  // NCS drop when statement
                  type boolean;
                  // NCS drop default statement
                  description
                    "Enable/disable the function of the VPWS PW status not to be affected by changes in the AC status.";
                }
                container tdm-parameter {
                  // NCS drop when statement
                  description
                    "Configure TDM parameters.";
                  leaf tdm-encapsulate-number {
                    ext:dynamic-default;
                    type uint32 {
                      range "1..5000";
                    }
                    description
                      "Number of TDM frames encapsulated in a CESoPSN or SAToP packet in the TDMoPSN application.";
                  }
                  leaf jitter-buffer {
                    ext:dynamic-default;
                    type uint32 {
                      range "1..64000";
                    }
                    units "ms";
                    description
                      "Depth of the jitter buffer in the application of TDMoPSN.";
                  }
                  leaf sequence-number {
                    type boolean;
                    // NCS drop default statement
                    description
                      "Enable/disable the TDM sequence number function.";
                  }
                  leaf rtp-header {
                    type live_ncs_l2vpn-rtp-header-type;
                    // NCS drop default statement
                    description
                      "Add the RTP header to transparently transmitted TDM frames.";
                  }
                  leaf idle-code {
                    ext:dynamic-default;
                    type string {
                      length "1..2";
                      pattern '[a-fA-F0-9]{1,2}';
                    }
                    description
                      "Idle code that is filled when the jitter buffer underflow occurs.";
                  }
                  leaf payload-compression {
                    type live_ncs_l2vpn-payload-comp;
                    // NCS drop must statement
                    // NCS drop default statement
                    description
                      "Payload compression mode.";
                  }
                }
                container atm-parameter {
                  // NCS drop when statement
                  description
                    "Configure ATM parameters.";
                  leaf max-atm-cells {
                    type uint32 {
                      range "1..28";
                    }
                    ext:dynamic-default;
                    description
                      "Maximum number of ATM cells to be encapsulated into a packet that can be received by a device.";
                  }
                  leaf atm-pack-overtime {
                    type uint32 {
                      range "100..10000";
                    }
                    units "ms";
                    ext:dynamic-default;
                    description
                      "Delay in encapsulating ATM cells into a packet.";
                  }
                  leaf atm-transmit-cell {
                    // NCS drop when statement
                    ext:dynamic-default;
                    type uint32 {
                      range "1..28";
                    }
                    description
                      "Maximum number of ATM cells to be encapsulated into a packet that can be sent by a device.";
                  }
                  leaf sequence-number {
                    type boolean;
                    // NCS drop must statement
                    // NCS drop default statement
                    description
                      "Enable/disable the control-word-based ATM packet sequencing feature. Performance statistics can then be collected based on this feature.";
                  }
                }
                container track-vrrp {
                  // NCS drop when statement
                  // NCS drop must statement
                  presence "enable track vrrp.";
                  description
                    "Enable/disable associating a PW with the mVRRP backup group.";
                  leaf vrrp-interface-name {
                    type leafref {
                      path "/ncs:devices/ncs:device/ncs:live-status/ifm:ifm/ifm:interfaces/ifm:interface/ifm:name" {
                        tailf:xpath-root 3;
                      }
                    }
                    // NCS drop must statement
                    // NCS drop mandatory statement
                    description
                      "The name of mVRRP interface.";
                  }
                  leaf vrrp-vrid {
                    type uint32 {
                      range "1..255";
                    }
                    // NCS drop must statement
                    // NCS drop mandatory statement
                    description
                      "VRID of a VRRP backup group.";
                  }
                  leaf pw-redundancy {
                    type boolean;
                    // NCS drop must statement
                    // NCS drop default statement
                    description
                      "Enable/disable the PW protection group associated with an mVRRP backup group in PW redundancy.";
                  }
                }
                container flow-label {
                  // NCS drop when statement
                  presence "enbale flow label for pw";
                  description
                    "Enable/disable the flow label capability of a PW.";
                  leaf ability {
                    type live_ncs_flow-label-ability;
                    // NCS drop must statement
                    // NCS drop mandatory statement
                    description
                      "Flow label capability.";
                  }
                  leaf static {
                    type boolean;
                    // NCS drop default statement
                    description
                      "Enable/disable the static flow label.";
                  }
                }
                container track-vrf-routes {
                  // NCS drop when statement
                  description
                    "List of PWs to track the VPN instance route.";
                  list track-vrf-route {
                    key "vrf-name ip-address mask-length";
                    description
                      "Configure a PW associated with a VPN instance route.";
                    leaf vrf-name {
                      type leafref {
                        path "/ncs:devices/ncs:device/ncs:live-status/ni:network-instance/ni:instances/ni:instance/ni:name" {
                          tailf:xpath-root 3;
                        }
                      }
                      description
                        "The name of the VPN instance.";
                    }
                    leaf ip-address {
                      type inet:ip-address-no-zone;
                      description
                        "IP address of a VPN instance route.";
                    }
                    leaf mask-length {
                      type uint32 {
                        range "0..128";
                      }
                      description
                        "Mask of a VPN instance route.";
                    }
                  }
                }
                container bfd {
                  // NCS drop when statement
                  presence "enable pw bfd.";
                  description
                    "Enable/disable the BFD parameter list.";
                  uses l2vpn:live_ncs_l2vpn-dyn-bfd-para-type;
                  leaf remote-vc-id {
                    type uint32 {
                      range "1..4294967295";
                    }
                    description
                      "Remote VC ID.";
                  }
                  leaf track-interface {
                    // NCS drop when statement
                    type boolean;
                    // NCS drop default statement
                    description
                      "Enable/disable BFD track interface state.";
                  }
                  leaf track-interface-name {
                    // NCS drop when statement
                    type leafref {
                      path "/ncs:devices/ncs:device/ncs:live-status/ifm:ifm/ifm:interfaces/ifm:interface/ifm:name" {
                        tailf:xpath-root 3;
                      }
                    }
                    description
                      "Specify the interface to be tracked.";
                  }
                }
                container pw-info {
                  description
                    "Operational data of VPWS PW information.";
                  leaf interface-name {
                    type leafref {
                      path "/ncs:devices/ncs:device/ncs:live-status/ifm:ifm/ifm:interfaces/ifm:interface/ifm:name" {
                        tailf:xpath-root 3;
                      }
                    }
                    description
                      "Name of an AC interface.";
                  }
                  leaf if-state {
                    type live_ncs_ac-state;
                    description
                      "Status of an AC interface.";
                  }
                  leaf session-state {
                    type live_ncs_l2vpn-state;
                    description
                      "Status of an LDP session between the endpoint devices of a VC.";
                  }
                  leaf integrative-ac-state {
                    type live_ncs_ac-state;
                    description
                      "Integrative AC status.";
                  }
                  leaf ac-state {
                    type live_ncs_ac-state;
                    description
                      "Status of an AC.";
                  }
                  leaf pw-state {
                    type live_ncs_l2vpn-pw-state;
                    description
                      "Status of a PW.";
                  }
                  leaf pw-id {
                    type uint32;
                    description
                      "PW ID.";
                  }
                  leaf encapsulation-type {
                    type live_ncs_encapsulation-type;
                    description
                      "Encapsulation type of a PW.";
                  }
                  leaf destination {
                    type inet:ipv4-address-no-zone;
                    description
                      "Destination address, usually the LSR ID of a peer.";
                  }
                  leaf local-group-id {
                    type uint32;
                    description
                      "PW group ID on the local end.";
                  }
                  leaf remote-group-id {
                    type uint32;
                    description
                      "PW group ID on the remote end.";
                  }
                  leaf local-vc-label {
                    type uint32;
                    description
                      "Local VC label.";
                  }
                  leaf remote-vc-label {
                    type uint32;
                    description
                      "VC label on the remote end.";
                  }
                  leaf local-tdm-encapsulate-num {
                    type uint32;
                    description
                      "Number of TDM frames encapsulated in a CESoPSN or SAToP packet in the TDMoPSN application.";
                  }
                  leaf remote-tdm-encapsulate-num {
                    type uint32;
                    description
                      "Number of TDM frames encapsulated in a CESoPSN or SAToP packet on the remote end.";
                  }
                  leaf jitter-buffer {
                    type uint32;
                    units "ms";
                    description
                      "Depth of the jitter buffer in the application of TDMoPSN.";
                  }
                  leaf idle-code {
                    type string {
                      length "0..3";
                    }
                    description
                      "Idle code that is filled when the jitter buffer underflow occurs.";
                  }
                  leaf local-rtp-header-enable {
                    type live_ncs_l2vpn-rtp-header-type;
                    description
                      "Add the RTP header to transparently transmitted TDM frames.";
                  }
                  leaf remote-rtp-header-enable {
                    type live_ncs_l2vpn-rtp-header-type;
                    description
                      "Add the RTP header to transparently transmitted TDM frames on the remote end.";
                  }
                  leaf max-atm-cells {
                    type uint32 {
                      range "1..28";
                    }
                    description
                      "Maximum number of ATM cells to be encapsulated into a packet that can be sent by the local device.";
                  }
                  leaf remote-max-atm-cells {
                    type uint32 {
                      range "0..28";
                    }
                    description
                      "Maximum number of ATM cells to be encapsulated into a packet that can be sent by the remote device.";
                  }
                  leaf atm-pack-overtime {
                    type uint32 {
                      range "100..10000";
                    }
                    units "ms";
                    description
                      "Delay in encapsulating ATM cells into a packet.";
                  }
                  leaf atm-transmit-cell {
                    type uint32 {
                      range "1..28";
                    }
                    description
                      "Maximum number of ATM cells to be encapsulated into a packet that can be sent by the local device.";
                  }
                  leaf sequence-number {
                    type boolean;
                    description
                      "Enable the sequence number function.";
                  }
                  leaf local-bit-rate {
                    type uint32;
                    description
                      "Bit rate of the local VC.";
                  }
                  leaf remote-bit-rate {
                    type uint32;
                    description
                      "Bit rate on the remote end.";
                  }
                  leaf local-ac-oam {
                    type live_ncs_l2vpn-state;
                    description
                      "OAM status of a local AC.";
                  }
                  leaf local-psn-oam {
                    type live_ncs_l2vpn-state;
                    description
                      "PSN OAM status on the local end.";
                  }
                  leaf local-forward-state {
                    type live_ncs_l2vpn-forward-state;
                    description
                      "Forwarding status of the local end.";
                  }
                  leaf local-state-code {
                    type pub-type:live_ncs_hex-binary;
                    description
                      "Status code on the local end.";
                  }
                  leaf remote-ac-oam {
                    type live_ncs_l2vpn-state;
                    description
                      "OAM status on the remote end.";
                  }
                  leaf remote-psn-oam {
                    type live_ncs_l2vpn-state;
                    description
                      "PSN OAM status on the remote end.";
                  }
                  leaf remote-forward-state {
                    type live_ncs_l2vpn-forward-state;
                    description
                      "Forwarding status of the remote end.";
                  }
                  leaf remote-state-code {
                    type pub-type:live_ncs_hex-binary;
                    description
                      "Status code on the remote end.";
                  }
                  leaf ignore-standby {
                    type boolean;
                    description
                      "Ignore the standby state of the VPWS PW.";
                  }
                  leaf bfd-enable {
                    type boolean;
                    description
                      "Enable BFD.";
                  }
                  leaf bfd-state {
                    type live_ncs_l2vpn-vpws-bfd-state;
                    description
                      "BFD status.";
                  }
                  leaf bfd-session-index {
                    type uint32;
                    description
                      "BFD index.";
                  }
                  leaf is-manual-fault {
                    type boolean;
                    description
                      "Simulate a PW fault.";
                  }
                  leaf is-active {
                    type boolean;
                    description
                      "Whether an interface is active.";
                  }
                  leaf is-forward-exist {
                    type boolean;
                    description
                      "The forwarding entry for an AC interface exists.";
                  }
                  leaf link-state {
                    type live_ncs_l2vpn-state;
                    description
                      "Integrative status of a PW.";
                  }
                  leaf local-vc-mtu {
                    type uint32;
                    description
                      "MTU for a local VC.";
                  }
                  leaf remote-vc-mtu {
                    type uint32;
                    description
                      "VC MTU on the remote end.";
                  }
                  leaf local-vccv {
                    type string {
                      length "0..40";
                    }
                    description
                      "VCCV capability supported by the local end. By default, the LSP ping and BFD for the label alert mode can be used if the control word function is disabled. If the control word function is enabled, the LSP ping and BFD for both the label alert mode and control word mode can be used.";
                  }
                  leaf remote-vccv {
                    type string {
                      length "0..40";
                    }
                    description
                      "VCCV capability supported by the remote end. By default, the LSP ping and BFD for the label alert mode can be used if the control word function is disabled. If the control word function is enabled, the LSP ping and BFD for both the label alert mode and control word mode can be used.";
                  }
                  leaf local-control-word {
                    type live_ncs_l2vpn-control-word;
                    description
                      "Enable the control word function on the local end.";
                  }
                  leaf remote-control-word {
                    type live_ncs_l2vpn-control-word;
                    description
                      "Enable the control word function on the remote end.";
                  }
                  leaf tunnel-policy {
                    type string {
                      length "1..39";
                    }
                    description
                      "Name of a tunnel policy.";
                  }
                  leaf template-name {
                    type string {
                      length "1..19";
                    }
                    description
                      "Name of a PW template.";
                  }
                  leaf primary-or-second {
                    type live_ncs_l2vpn-backup-mode;
                    description
                      "Primary/secondary status of a PW.";
                  }
                  leaf access-port {
                    type boolean;
                    description
                      "Attribute that allows only untagged packets to pass through an interface.";
                  }
                  leaf oam-protocol {
                    type live_ncs_oam-protocal;
                    description
                      "Link (PW) status detection protocol.";
                  }
                  leaf oam-status {
                    type live_ncs_oam-status;
                    description
                      "Link (PW) status detected by the link detection protocol.";
                  }
                  leaf oam-fault-type {
                    type string {
                      length "1..100";
                    }
                    description
                      "Type of a link fault detected by a link detection protocol.";
                  }
                  leaf aps-id {
                    type uint32;
                    description
                      "ID of the PW APS instance associated with the local PW.";
                  }
                  leaf aps-status {
                    type live_ncs_l2vpn-aps-status;
                    description
                      "PW APS status.";
                  }
                  leaf aps-ttl {
                    type uint32;
                    description
                      "PW TTL.";
                  }
                  leaf tunnel-count {
                    type uint16;
                    // NCS drop default statement
                    description
                      "Number of effective tunnels.";
                  }
                  leaf spe-count {
                    type uint32 {
                      range "0..4294967295";
                    }
                    // NCS drop default statement
                    description
                      "Number of SPEs in the path to the peer.";
                  }
                  leaf create-time {
                    type string {
                      length "1..80";
                    }
                    description
                      "How long a PW has been created.";
                  }
                  leaf up-time {
                    type string {
                      length "1..80";
                    }
                    description
                      "How long a PW has been in the up state. If a PW is in the down state, its PW up duration is 0.";
                  }
                  leaf last-change-time {
                    type string {
                      length "1..80";
                    }
                    description
                      "How long the status of a PW has stayed unchanged since the last change time.";
                  }
                  leaf last-up-time {
                    type string {
                      length "1..80";
                    }
                    description
                      "Date and time when a PW was up for the last time, for example, 2012/07/20 02:30:46.";
                  }
                  leaf total-up-time {
                    type string {
                      length "1..80";
                    }
                    description
                      "Total up time of a PW.";
                  }
                  leaf c-key {
                    type uint32;
                    description
                      "Customer key. Each CKey corresponds to a PW.";
                  }
                  leaf n-key {
                    type uint32;
                    description
                      "Network key. Each NKey corresponds to a combination of the peer and tunnel policy.";
                  }
                  leaf support-notification {
                    type boolean;
                    description
                      "Whether a PW can send notification packets.";
                  }
                  leaf route-state {
                    type live_ncs_l2vpn-route-status;
                    description
                      "Route status.";
                  }
                  leaf received-flow-label {
                    type live_ncs_flow-label-ability;
                    description
                      "Received flow label.";
                  }
                  leaf negotiated-flow-label {
                    type live_ncs_flow-label-ability;
                    description
                      "Negotiated flow label.";
                  }
                  leaf dynamic-bfd-session {
                    type string {
                      length "1..19";
                    }
                    description
                      "Dynamic BFD session.";
                  }
                  leaf bfd-for-pw {
                    type string {
                      length "1..19";
                    }
                    description
                      "BFD for PW information.";
                  }
                  leaf remote-vccv-code {
                    type pub-type:live_ncs_hex-binary;
                    description
                      "Remote VCCV code.";
                  }
                  leaf hard-pipe-bandwidth {
                    type uint32 {
                      range "16..4294967294";
                    }
                    units "kbit/s";
                    description
                      "Specify bandwidth value.";
                  }
                  leaf hard-pipe-expand-ratio {
                    type string {
                      length "0..7";
                    }
                    description
                      "Specify the value of bandwidth expand ratio (%).";
                  }
                  leaf hard-pipe-burst-time {
                    type uint32 {
                      range "100..5000";
                    }
                    units "us";
                    description
                      "Burst time.";
                  }
                  leaf local-payload-compression {
                    type live_ncs_l2vpn-payload-comp;
                    description
                      "Local payload compression.";
                  }
                  leaf remote-payload-compression {
                    type live_ncs_l2vpn-payload-comp;
                    description
                      "Remote payload compression.";
                  }
                  leaf send-receive-active {
                    type live_ncs_send-receive-active-status;
                    // NCS drop default statement
                    description
                      "Send and receive status.";
                  }
                  leaf ac-block-state {
                    type live_ncs_ac-block-status;
                    description
                      "AC block state.";
                  }
                  leaf pw-token-exceed {
                    type boolean;
                    // NCS drop default statement
                    description
                      "Indicates whether the number of PW tokens exceeds the maximum limit.";
                  }
                  container tunnels {
                    description
                      "List of tunnels.";
                    list tunnel {
                      key "tunnel-key";
                      // NCS drop max-elements statement
                      description
                        "Operational data of tunnels.";
                      leaf tunnel-key {
                        type string {
                          length "0..21";
                        }
                        description
                          "Index of a public network tunnel.";
                      }
                      leaf tunnel-type {
                        type live_ncs_l2vpn-tunnel-type;
                        description
                          "Type of the tunnel used by the PW.";
                      }
                      leaf tunnel-name {
                        type string {
                          length "0..64";
                        }
                        description
                          "Name of the tunnel used by the PW.";
                      }
                      leaf public-next-hop {
                        type inet:ipv4-address-no-zone;
                        description
                          "Next hop of a PW on the public network.";
                      }
                    }
                  }
                  container spes {
                    description
                      "Operational data of SPEs on the path to the peer.";
                    uses l2vpn:live_ncs_spe-infos-type;
                  }
                  container label-stacks {
                    description
                      "Operational data of PW label stacks.";
                    uses l2vpn:live_ncs_l2vpn-label-stacks-type;
                  }
                  container down-causes {
                    description
                      "Operational data of the down causes.";
                    uses l2vpn:live_ncs_l2vpn-pw-down-causes-type;
                  }
                  container status-changes {
                    description
                      "Operational data of the reason and time.";
                    uses l2vpn:live_ncs_l2vpn-pw-status-changes-type;
                  }
                }
                container traffic-statistics {
                  description
                    "VPWS LDP PW traffic statistics.";
                  leaf interface-name {
                    type leafref {
                      path "/ncs:devices/ncs:device/ncs:live-status/ifm:ifm/ifm:interfaces/ifm:interface/ifm:name" {
                        tailf:xpath-root 3;
                      }
                    }
                    description
                      "The name of interface.";
                  }
                  leaf last-clear-time {
                    type string {
                      length "1..60";
                    }
                    description
                      "Time when statistics are cleared for the last time.";
                  }
                  leaf input-bytes-rate {
                    type uint64;
                    description
                      "Rate of traffic received on the PW.";
                  }
                  leaf output-bytes-rate {
                    type uint64;
                    description
                      "Rate of traffic transmitted out of the PW.";
                  }
                  leaf input-packets-rate {
                    type uint64;
                    description
                      "Rate of frames received on the PW.";
                  }
                  leaf output-packets-rate {
                    type uint64;
                    description
                      "Rate of frames transmitted out of the PW.";
                  }
                  leaf input-bytes {
                    type uint64;
                    description
                      "Number of bytes received on the PW.";
                  }
                  leaf output-bytes {
                    type uint64;
                    description
                      "Number of bytes transmitted out of the PW.";
                  }
                  leaf input-packets {
                    type uint64;
                    description
                      "Number of frames received on the PW.";
                  }
                  leaf output-packets {
                    type uint64;
                    description
                      "Number of frames transmitted out of the PW.";
                  }
                }
              }
            }
            container out-acs {
              // NCS drop when statement
              description
                "List of all out ACs.";
              list out-ac {
                key "interface-name";
                // NCS drop max-elements statement
                description
                  "Configure outbound interface of single CCC.";
                leaf interface-name {
                  type leafref {
                    path "/ncs:devices/ncs:device/ncs:live-status/ifm:ifm/ifm:interfaces/ifm:interface/ifm:name" {
                      tailf:xpath-root 3;
                    }
                  }
                  // NCS drop must statement
                  description
                    "Name of an AC interface.";
                }
                leaf role {
                  ext:operation-exclude "update";
                  type live_ncs_pw-role-type;
                  // NCS drop must statement
                  // NCS drop mandatory statement
                  description
                    "Role of out AC.";
                }
                container tdm-parameter {
                  // NCS drop when statement
                  description
                    "Configure TDM parameters of CCC instance.";
                  uses live_ncs_l2vpn-ccc-tdm-type;
                }
                container atm-parameter {
                  // NCS drop when statement
                  description
                    "Configure ATM parameters.";
                  uses live_ncs_l2vpn-ccc-atm-type;
                }
              }
            }
            container hard-pipe {
              // NCS drop when statement
              // NCS drop must statement
              presence "Enable hard pipe for pw.";
              description
                "Enable/disable hard pipe. The hard-pipe node and the qos-parameter node cannot be configured together.";
              leaf bandwidth {
                type uint32 {
                  range "16..4294967294";
                }
                units "kbit/s";
                // NCS drop mandatory statement
                description
                  "Specify bandwidth value.";
              }
              leaf expand-ratio {
                type uint16 {
                  range "0..10000";
                }
                // NCS drop default statement
                description
                  "Specify the value of bandwidth expand ratio (%). As to CES service, expand ratio ranges from 0 to 10000. The other service, expand ratio ranges from 0 to 100.";
              }
              leaf burst-time {
                // NCS drop when statement
                type uint32 {
                  range "100..5000";
                }
                units "us";
                // NCS drop default statement
                description
                  "Burst time.";
              }
            }
            container ac-oam-mapping {
              ext:operation-exclude "update";
              // NCS drop when statement
              presence "enable AC OAM mapping";
              description
                "Enable/disable OAM mapping.";
              leaf type {
                ext:operation-exclude "update";
                type live_ncs_ac-oam-mapping-type;
                // NCS drop must statement
                // NCS drop mandatory statement
                description
                  "VPWS attachment circuit OAM mapping type.";
              }
              leaf md-name {
                ext:operation-exclude "update|delete";
                // NCS drop when statement
                type string {
                  length "1..43";
                }
                description
                  "VPWS OAM mapping parameter md name.";
              }
              leaf ma-name {
                ext:operation-exclude "update|delete";
                // NCS drop when statement
                type string {
                  length "1..43";
                }
                description
                  "VPWS OAM mapping parameter ma name.";
              }
            }
            container reliability {
              // NCS drop when statement
              description
                "Configure PW reliability.";
              leaf redundancy-mode {
                type live_ncs_pw-redundancy-mode;
                // NCS drop must statement
                // NCS drop must statement
                // NCS drop default statement
                description
                  "PW redundancy mode.";
              }
              leaf switchover {
                // NCS drop when statement
                type boolean;
                // NCS drop must statement
                // NCS drop default statement
                description
                  "Enable/disable manual PW switchover.";
              }
              leaf dual-receive {
                type boolean;
                // NCS drop default statement
                description
                  "Enable/disable the packet reception of both the primary and secondary PWs.";
              }
              leaf dual-send {
                type boolean;
                // NCS drop must statement
                // NCS drop default statement
                description
                  "Enable/disable the packet transmission of both the primary and secondary PWs.";
              }
              leaf holdoff {
                // NCS drop when statement
                type uint32 {
                  range "1..180";
                }
                units "s";
                description
                  "Hold time for traffic switching.";
              }
              container reroute {
                // NCS drop when statement
                description
                  "Configure a switchback policy list.";
                leaf reroute-policy {
                  type live_ncs_l2vpn-reroute-mode;
                  // NCS drop default statement
                  description
                    "Switchback policy.";
                }
                leaf delay-time {
                  // NCS drop when statement
                  type uint32 {
                    range "10..10800";
                  }
                  units "s";
                  // NCS drop default statement
                  description
                    "Delay for switching traffic back to the primary PW.";
                }
                leaf resume-time {
                  // NCS drop when statement
                  type uint32 {
                    range "0..600";
                  }
                  units "s";
                  // NCS drop default statement
                  description
                    "Time after which the peer PE on the secondary PW is notified that the local PE has recovered. This parameter can be configured only in FRR mode.";
                }
                leaf last-switchback-reason {
                  type string {
                    length "0..100";
                  }
                  description
                    "Last switchback reason.";
                }
                leaf last-switchback-time {
                  type string {
                    length "1..60";
                  }
                  description
                    "Last switchback time.";
                }
                leaf delay-residual {
                  type uint32;
                  units "s";
                  description
                    "Remaining delay time.";
                }
                leaf resume-residual {
                  type uint32;
                  units "s";
                  description
                    "Remaining resume time.";
                }
              }
              container aps-parameter {
                ext:operation-exclude "update";
                // NCS drop when statement
                presence "enable aps protection for pw.";
                description
                  "Enable/disable APS.";
                leaf aps-id {
                  ext:operation-exclude "update";
                  type leafref {
                    path "/ncs:devices/ncs:device/ncs:live-status/l2vpn/common/pw-apss/pw-aps/aps-id" {
                      tailf:xpath-root 3;
                    }
                  }
                  // NCS drop mandatory statement
                  description
                    "PW APS instance ID.";
                }
                leaf bind-type {
                  ext:operation-exclude "update|delete";
                  type live_ncs_l2vpn-aps-bind-type;
                  // NCS drop default statement
                  description
                    "Type of a PW protection group associated with the PW APS instance.";
                }
              }
            }
          }
          container vpws-switch {
            ext:operation-exclude "delete";
            // NCS drop when statement
            // NCS drop must statement
            description
              "Configure a VPWS switch instance.";
            uses live_ncs_vpws-swtich-instance-grp;
          }
          container vpws-bgp {
            ext:operation-exclude "delete";
            // NCS drop when statement
            description
              "Configure a VPWS BGP instance. This container cannot be deleted.";
            uses live_ncs_vpws-bgp-instance-grp;
          }
          container vpls {
            ext:operation-exclude "delete";
            // NCS drop when statement
            // NCS drop must statement
            // NCS drop must statement
            // NCS drop must statement
            // NCS drop must statement
            // NCS drop must statement
            description
              "Configure a VPLS instance.";
            uses live_ncs_vpls-instance-grp;
          }
        }
      }
    }
  }
  augment "/ncs:devices/ncs:template/ncs:ned-id/ncs:config" {
    container l2vpn {
      // NCS drop when statement
      presence "Enable l2 virtual private network.";
      description
        "L2 virtual private network.";
      container common {
        description
          "Configure L2VPN common attributes.";
        container global {
          description
            "Configure a global L2VPN.";
          leaf ldp-default-mode {
            type ncs_template_ldp-signal-type;
            // NCS drop default statement
            description
              "LDP is used as the signaling protocol. The dynamic VC will then not send a notification during signaling negotiation. The LDP signaling mode is also called the Martini mode.";
          }
          leaf vpls-ignore-ac-state {
            type string;
            // NCS drop default statement
            description
              "Enable/disable the function of the VSI status not to be affected by changes in the AC status.";
          }
          leaf vpls-loop-detect-enable {
            type string;
            // NCS drop default statement
            description
              "Enable/disable MAC withdraw loop detection.";
          }
          leaf bfd-cv-type {
            type ncs_template_bfd-vccv-cv-type;
            // NCS drop default statement
            description
              "The field of CV will be all filled corresponding BFD CV type after global enable BFDCV.";
          }
          leaf ignore-te-oam-state {
            type string;
            // NCS drop default statement
            description
              "Enable/disable ignoring TE OAM detecting state.";
          }
          leaf auto-create-session {
            type string;
            // NCS drop default statement
            description
              "Enable/disable creating LDP session automatically.";
          }
          leaf grp-selective-ldp-enable {
            type string;
            // NCS drop default statement
            description
              "Enable/disable the selective mLDP P2MP LSP group.";
          }
          leaf label-block-size {
            type string;
            // NCS drop must statement
            // NCS drop default statement
            description
              "Configure the label block size for BGP L2VPN.";
          }
        }
        container pw-templates {
          description
            "List of PW templates.";
          list pw-template {
            // NCS patched for predictable order
            ordered-by user;
            key "name";
            // NCS drop max-elements statement
            description
              "Configure PW attributes in a PW template, such as the peer, control word, and tunnel policy.";
            leaf name {
              type ncs_template_l2vpn-pw-template-name;
              description
                "Name of a PW template.";
            }
            leaf peer-address {
              ext:operation-exclude "update";
              type string;
              description
                "Peer IP address. The loopback IP address of a peer is usually used as the peer IP address.";
            }
            leaf mtu {
              type string;
              description
                "MTU in a PW template.";
            }
            leaf control-word {
              type string;
              // NCS drop default statement
              description
                "Enable the control word function.";
            }
            leaf tunnel-policy {
              type string;
              description
                "Tunnel policy configured in a PW template.";
            }
            // NCS drop config false leaf 'vccv-capability'
            // NCS drop config false leaf 'total-pw-num'
            // NCS drop config false leaf 'static-pw-num'
            // NCS drop config false leaf 'ldp-pw-num'
            container tdm-parameter {
              description
                "Configure TDM parameters.";
              leaf tdm-encapsulate-number {
                type string;
                ext:dynamic-default;
                description
                  "Number of TDM frames encapsulated in a CESoPSN or SAToP packet in the TDMoPSN application.";
              }
              leaf jitter-buffer {
                type string;
                units "us";
                ext:dynamic-default;
                description
                  "Depth of the jitter buffer in the application of TDMoPSN.";
              }
              leaf jitter-buffer-cep {
                type string;
                units "us";
                // NCS drop default statement
                description
                  "Depth of the jitter buffer in the application of CEP.";
              }
              leaf rtp-header {
                type string;
                // NCS drop default statement
                description
                  "Enable/disable transparently transmission of TDM frames.";
              }
              leaf idle-code {
                type string;
                // NCS drop default statement
                description
                  "Idle code that is filled when the jitter buffer underflow occurs.";
              }
              leaf payload-compression {
                type ncs_template_l2vpn-payload-comp;
                // NCS drop default statement
                description
                  "Payload compression mode.";
              }
            }
            container atm-parameter {
              description
                "Configure ATM parameters.";
              leaf max-atm-cells {
                type string;
                ext:dynamic-default;
                description
                  "Maximum number of ATM cells to be encapsulated into a packet that can be received by a device.";
              }
              leaf atm-pack-overtime {
                type string;
                units "us";
                ext:dynamic-default;
                description
                  "Delay in encapsulating ATM cells into a packet.";
              }
              leaf atm-transmit-cell {
                type string;
                description
                  "Maximum number of ATM cells to be encapsulated into a packet that can be sent by a device.";
              }
              leaf sequence-number {
                // NCS drop when statement
                type string;
                // NCS drop default statement
                description
                  "Enable/disable the sequence number function.";
              }
            }
            container bfd-parameter {
              // NCS drop when statement
              // NCS drop must statement
              presence "enable bfd-parameter for pw";
              description
                "Enable/disable BFD.";
              leaf min-rx-interval {
                type string;
                units "ms";
                // NCS drop default statement
                description
                  "Minimum receive interval.";
              }
              leaf min-tx-interval {
                type string;
                units "ms";
                // NCS drop default statement
                description
                  "Minimum transmit interval.";
              }
              leaf detect-multiplier {
                type string;
                // NCS drop default statement
                description
                  "Detection multiplier.";
              }
            }
            container flow-label {
              presence "enable flow-label for pw";
              description
                "Enable/disable the flow-label function.";
              leaf ability {
                type ncs_template_flow-label-ability;
                // NCS drop must statement
                // NCS drop mandatory statement
                description
                  "Specify the flow-label ability.";
              }
              leaf static {
                type string;
                // NCS drop default statement
                description
                  "Enable/disable the static flow-label function.";
              }
            }
          }
        }
        container pw-apss {
          description
            "List of APS instances.";
          list pw-aps {
            // NCS patched for predictable order
            ordered-by user;
            key "aps-id";
            // NCS drop max-elements statement
            description
              "Configure APS instances.";
            leaf aps-id {
              type string;
              description
                "ID of a PW APS instance.";
            }
            leaf description {
              type string;
              description
                "PW APS description.";
            }
            leaf protect-type {
              ext:operation-exclude "update|delete";
              type ncs_template_l2vpn-pw-aps-type;
              // NCS drop must statement
              // NCS drop default statement
              description
                "Protection type.";
            }
            leaf role {
              type ncs_template_l2vpn-pw-aps-role;
              // NCS drop must statement
              // NCS drop default statement
              description
                "E-PW APS role.";
            }
            leaf remote-aps-id {
              // NCS drop when statement
              type string;
              description
                "Remote ID of E-PW APS.";
            }
            leaf holdoff {
              type string;
              units "ms";
              // NCS drop default statement
              description
                "Hold time.";
            }
            leaf wtr {
              // NCS drop when statement
              type string;
              units "min";
              // NCS drop default statement
              description
                "Wait-to-Restore time.";
            }
            leaf operation-type {
              // NCS drop when statement
              type ncs_template_l2vpn-pw-aps-oper-type;
              // NCS drop default statement
              description
                "Operation type.";
            }
            // NCS drop config false leaf 'protect-mode'
            // NCS drop config false container 'pw-aps-info'
            // NCS drop config false container 'aps-vpws-instances'
          }
        }
        container service-peers {
          description
            "List of peers.";
          list service-peer {
            // NCS patched for predictable order
            ordered-by user;
            key "peer-ip";
            description
              "Configure the list of peers.";
            leaf peer-ip {
              type string;
              description
                "Indicates the LSR ID of the remote device.";
            }
            leaf ldp-mode {
              type ncs_template_l2vpn-peer-ldp-signal-mode;
              // NCS drop default statement
              description
                "Peer signal mode.";
            }
          }
        }
        container peer-no-requests {
          description
            "List of no-request peers.";
          list peer-no-request {
            // NCS patched for predictable order
            ordered-by user;
            key "peer-ip";
            description
              "Configure no-request peers.";
            leaf peer-ip {
              type string;
              description
                "Indicates the LSR ID of the remote device.";
            }
          }
        }
        container peer-bfd-cv-stds {
          description
            "List of BFD CV standard peers.";
          list peer-bfd-cv-std {
            // NCS patched for predictable order
            ordered-by user;
            // NCS drop must statement
            key "peer-ip";
            description
              "Configure BFD CV standard peers.";
            leaf peer-ip {
              type string;
              description
                "Indicates the LSR ID of the remote device.";
            }
            leaf enable {
              type ncs_template_l2vpn-common-enable-type;
              // NCS drop default statement
              description
                "Enable BFDCV.";
            }
            leaf type {
              type ncs_template_bfd-vccv-cv-type;
              // NCS drop default statement
              description
                "The BFDCV type of the peer.";
            }
          }
        }
        container vpws-bgp-vpns {
          description
            "List of VPWS BGP VPN instances.";
          list vpws-bgp-vpn {
            // NCS patched for predictable order
            ordered-by user;
            key "name";
            description
              "Configure VPWS BGP VPN instance.";
            leaf name {
              type string;
              description
                "VPWS BGP VPN instance name.";
            }
            leaf encapsulation-type {
              type ncs_template_vpws-bgp-vpn-encap;
              // NCS drop mandatory statement
              description
                "VPWS BGP VPN instance encapsulation type.";
            }
            leaf control-word {
              type string;
              // NCS drop default statement
              description
                "Control word of the VPWS BGP VPN instance. If the encapsulation type is low speed, disabling the control word causes the VPWS BGP instance to fail.";
            }
            leaf route-distinguisher {
              type string;
              description
                "Route distinguisher of VPWS BGP VPN instance.";
            }
            leaf mtu {
              type string;
              // NCS drop default statement
              description
                "MTU of VPWS BGP VPN instance.";
            }
            leaf ignore-mtu-match {
              type string;
              // NCS drop default statement
              description
                "Enable/disable the function of the ignoring MTU match of a VPWS BGP VPN instance.";
            }
            // NCS drop config false leaf 'auto-route-distinguisher'
            container vpn-targets {
              description
                "List of route targets of VPWS BGP VPN instances.";
              list vpn-target {
                // NCS patched for predictable order
                ordered-by user;
                key "rt-value rt-type";
                // NCS drop max-elements statement
                description
                  "Configure a route target list of the VPWS BGP VPN instances.";
                leaf rt-value {
                  type string;
                  description
                    "Route target value of the VPWS BGP VPN instance.";
                }
                leaf rt-type {
                  type ncs_template_vpn-rt-type;
                  description
                    "Route target type of the VPWS BGP VPN instance.";
                }
              }
            }
            container sites {
              description
                "List of CEs in a VPWS BGP VPN instance.";
              list site {
                // NCS patched for predictable order
                ordered-by user;
                // NCS drop must statement
                key "name";
                unique "id";
                description
                  "Configure a CE in a VPWS BGP VPN instance.";
                leaf name {
                  type ncs_template_vpws-bgp-ce-name-type;
                  description
                    "Local site name.";
                }
                leaf id {
                  ext:operation-exclude "update";
                  type string;
                  // NCS drop mandatory statement
                  description
                    "VPWS BGP VPN instance customer edge identifier.";
                }
                leaf range {
                  type string;
                  // NCS drop must statement
                  // NCS drop default statement
                  description
                    "VPWS BGP VPN instance customer edge range.";
                }
                leaf default-offset {
                  type string;
                  // NCS drop default statement
                  description
                    "VPWS BGP VPN instance customer edge default offset.";
                }
                // NCS drop config false container 'label-blocks'
              }
            }
            // NCS drop config false container 'remote-sites'
          }
        }
        // NCS drop config false container 'not-match-remote-ldps'
        // NCS drop config false container 'vpws-statistic'
        // NCS drop config false container 'vpls-statistic'
        // NCS drop config false container 'track-route-statistics'
        // NCS drop config false container 'vrf-routes'
      }
      container instances {
        description
          "List of L2VPN instances.";
        list instance {
          // NCS patched for predictable order
          ordered-by user;
          key "name type";
          description
            "Configure L2VPN instances.";
          leaf name {
            type string;
            description
              "The name of L2VPN instance.";
          }
          leaf type {
            type ncs_template_l2vpn-instance-type;
            description
              "The type of L2VPN instance.";
          }
          leaf description {
            // NCS drop when statement
            type string;
            description
              "Description of a VSI.";
          }
          // NCS drop config false leaf state
          // NCS drop config false leaf 'last-up-time'
          // NCS drop config false leaf 'total-up-time'
          container vpws-local-ccc {
            ext:operation-exclude "delete";
            // NCS drop when statement
            description
              "Configure VPWS local CCC instance.";
            uses ncs_template_vpws-localccc-instance-grp;
          }
          container vpws-remote-ccc {
            ext:operation-exclude "delete";
            // NCS drop when statement
            description
              "Configure a VPWS remote CCC instance.";
            uses ncs_template_vpws-remoteccc-instance-grp;
          }
          container vpws-ldp {
            ext:operation-exclude "delete";
            // NCS drop when statement
            // NCS drop must statement
            // NCS drop must statement
            description
              "Configure VPWS LDP instance.";
            leaf encapsulation-type {
              ext:operation-exclude "update";
              type ncs_template_encapsulation-type;
              // NCS drop must statement
              // NCS drop mandatory statement
              description
                "Encapsulation type of a VPWS instance.";
            }
            leaf mac-withdraw-disable {
              // NCS drop when statement
              type string;
              // NCS drop default statement
              description
                "Enable/disable the function to send MAC withdraw messages during the primary/secondary PW switchover for Ethernet-encapsulated or VLAN-encapsulated VLLs.";
            }
            leaf load-balance {
              // NCS drop when statement
              type ncs_template_l2vpn-load-balance-type;
              // NCS drop default statement
              description
                "Load balancing mode, which can be:
                 - Flow: indicates per-flow load balancing.
                 - Packet: indicates per-packet load balancing.";
            }
            leaf service-name {
              type string;
              description
                "Service name of a VPWS instance.";
            }
            leaf bit-error-detection {
              // NCS drop when statement
              type string;
              // NCS drop must statement
              // NCS drop default statement
              description
                "Enable/disable bit error detection on SPEs for an LDP MS-PW.";
            }
            container acs {
              description
                "List of information about all ACs.";
              list ac {
                // NCS patched for predictable order
                ordered-by user;
                ext:operation-exclude "update|delete";
                // NCS drop must statement
                key "interface-name";
                // NCS drop min-elements statement
                // NCS drop max-elements statement
                description
                  "Configure information about an AC.";
                leaf interface-name {
                  type string;
                  description
                    "Name of an AC interface.";
                }
                leaf tagged {
                  ext:operation-exclude "update|delete";
                  // NCS drop when statement
                  type string;
                  ext:dynamic-default {
                    ext:default-value "false" {
                      // NCS drop when statement
                      description
                        "The default value is false when encapsulation-type is ethernet.";
                    }
                    ext:default-value "true" {
                      // NCS drop when statement
                      description
                        "The default value is true when encapsulation-type is VLAN.";
                    }
                  }
                  // NCS drop must statement
                  description
                    "Enable/disable the VLAN tag setting.";
                }
                leaf access-port {
                  ext:operation-exclude "update|delete";
                  // NCS drop when statement
                  type string;
                  // NCS drop must statement
                  // NCS drop default statement
                  description
                    "Enable/disable the function of allowing only untagged packets to pass through an interface. The access port attribute can be configured only on main Ethernet interfaces. The access port attribute of outbound interface must be consistent with that of inbound interface.";
                }
                leaf trigger-interface-down {
                  // NCS drop when statement
                  type string;
                  // NCS drop must statement
                  // NCS drop must statement
                  // NCS drop default statement
                  description
                    "Enable/disable remote interface shutdown to associate PW status with interface status.";
                }
                leaf forward-mode {
                  ext:operation-exclude "update";
                  type string;
                  // NCS drop must statement
                  // NCS drop default statement
                  description
                    "Enable/disable the raw forwarding mode.";
                }
                leaf performance-statistics {
                  // NCS drop when statement
                  type string;
                  // NCS drop default statement
                  description
                    "Enable/disable PW performance statistics collection.";
                }
                // NCS drop config false leaf state
                // NCS drop config false leaf 'token-exceed'
                container arp-entry {
                  presence "Enable the ARP entry for AC.";
                  description
                    "Configure ARP entry attribute used for IP interworking between PEs.";
                  leaf local-ce-mac {
                    type pub-type:ncs_template_mac-address;
                    description
                      "MAC address of the Ethernet interface or sub-interface on a CE connected to the local AC interface. If MAC, IP, and broadcast addresses are all configured, these addresses take effect in the sequence of MAC address, IP address, and broadcast address.";
                  }
                  leaf local-ce-ip {
                    type string;
                    description
                      "IP address of the Ethernet interface or sub-interface on a CE connected to the local AC interface.";
                  }
                  leaf local-ce-broadcast {
                    type string;
                    // NCS drop must statement
                    // NCS drop default statement
                    description
                      "Enable/disable the broadcast function on a PE Ethernet interface connected to a CE.";
                  }
                  leaf remote-ce-ip {
                    type string;
                    description
                      "IP address of the remote CE connected to the local AC interface.";
                  }
                }
                // NCS drop config false container 'ac-arps'
                // NCS drop config false container 'tdm-performance-statistic'
                // NCS drop config false container 'atm-performance-statistic'
              }
            }
            container pws {
              description
                "List of all VPWS PWs.";
              list pw {
                // NCS patched for predictable order
                ordered-by user;
                // NCS drop must statement
                // NCS drop must statement
                key "role";
                // NCS drop max-elements statement
                description
                  "Configure a VPWS PW.";
                leaf role {
                  type ncs_template_pw-role-type;
                  // NCS drop must statement
                  description
                    "Role of a PW. Configure a primary PW first.";
                }
                leaf pw-id {
                  ext:operation-exclude "update|delete";
                  ext:support-filter "true";
                  type string;
                  description
                    "PW ID.";
                }
                leaf peer-ip {
                  ext:operation-exclude "update|delete";
                  type ncs_template_l2vpn-peer-address-type;
                  description
                    "IP address of a peer.";
                }
                leaf admin-pw {
                  ext:operation-exclude "update|delete";
                  // NCS drop when statement
                  type string;
                  // NCS drop must statement
                  // NCS drop default statement
                  description
                    "Enable/disable administrative PW.";
                }
                leaf transmit-label {
                  ext:operation-exclude "update|delete";
                  // NCS drop when statement
                  type string;
                  description
                    "Label for sending packets.";
                }
                leaf receive-label {
                  ext:operation-exclude "update|delete";
                  // NCS drop when statement
                  type string;
                  description
                    "Label for receiving packets.";
                }
                leaf control-word {
                  // NCS drop when statement
                  type ncs_template_l2vpn-control-word;
                  // NCS drop must statement
                  // NCS drop default statement
                  description
                    "Enable the control word function. The control word is usually used for TDM, ATM, and FR PWs.";
                }
                leaf vccv-ability {
                  // NCS drop when statement
                  type string;
                  // NCS drop default statement
                  description
                    "Enable/disable virtual circuit connectivity verification (VCCV) capability. VCCV supports two modes: control word and label alert.";
                }
                leaf tunnel-policy {
                  // NCS drop when statement
                  type string;
                  description
                    "Name of a tunnel policy. If the tunnel policy name is not specified, the system uses the default tunnel policy. The default tunnel policy preferentially selects LSPs for packet transmission and the number of load-balancing tunnels is 1. If the tunnel policy name is specified but the corresponding tunnel policy does not exist, the system still uses the default tunnel policy.";
                }
                leaf pw-template {
                  ext:operation-exclude "update|delete";
                  // NCS drop when statement
                  type string;
                  description
                    "Name of a PW template. You can configure PW attributes such as the remote peer, tunnel policy, and control word in a PW template. When configuring an LDP PW, you can reference the PW attributes configured in an existing PW template.";
                }
                leaf ignore-standby {
                  // NCS drop when statement
                  type string;
                  // NCS drop default statement
                  description
                    "Enable/disable the PW's function of ignoring the standby state informed by the VSI peer.";
                }
                leaf set-fault {
                  // NCS drop when statement
                  type string;
                  // NCS drop must statement
                  // NCS drop default statement
                  description
                    "Enable/disable simulating a fault on a primary or secondary PW.";
                }
                leaf pw-ttl {
                  // NCS drop when statement
                  type string;
                  // NCS drop must statement
                  // NCS drop default statement
                  description
                    "TTL of a PW.";
                }
                leaf track-admin-pw {
                  // NCS drop when statement
                  type string;
                  // NCS drop must statement
                  description
                    "Configure a service PW to track the mPW.";
                }
                leaf traffic-statistics-collection {
                  // NCS drop when statement
                  type string;
                  // NCS drop default statement
                  description
                    "Enable/disable collecting traffic statistics.";
                }
                leaf ignore-ac-state {
                  // NCS drop when statement
                  type string;
                  // NCS drop default statement
                  description
                    "Enable/disable the function of the VPWS PW status not to be affected by changes in the AC status.";
                }
                container tdm-parameter {
                  // NCS drop when statement
                  description
                    "Configure TDM parameters.";
                  leaf tdm-encapsulate-number {
                    ext:dynamic-default;
                    type string;
                    description
                      "Number of TDM frames encapsulated in a CESoPSN or SAToP packet in the TDMoPSN application.";
                  }
                  leaf jitter-buffer {
                    ext:dynamic-default;
                    type string;
                    units "ms";
                    description
                      "Depth of the jitter buffer in the application of TDMoPSN.";
                  }
                  leaf sequence-number {
                    type string;
                    // NCS drop default statement
                    description
                      "Enable/disable the TDM sequence number function.";
                  }
                  leaf rtp-header {
                    type ncs_template_l2vpn-rtp-header-type;
                    // NCS drop default statement
                    description
                      "Add the RTP header to transparently transmitted TDM frames.";
                  }
                  leaf idle-code {
                    ext:dynamic-default;
                    type string;
                    description
                      "Idle code that is filled when the jitter buffer underflow occurs.";
                  }
                  leaf payload-compression {
                    type ncs_template_l2vpn-payload-comp;
                    // NCS drop must statement
                    // NCS drop default statement
                    description
                      "Payload compression mode.";
                  }
                }
                container atm-parameter {
                  // NCS drop when statement
                  description
                    "Configure ATM parameters.";
                  leaf max-atm-cells {
                    type string;
                    ext:dynamic-default;
                    description
                      "Maximum number of ATM cells to be encapsulated into a packet that can be received by a device.";
                  }
                  leaf atm-pack-overtime {
                    type string;
                    units "ms";
                    ext:dynamic-default;
                    description
                      "Delay in encapsulating ATM cells into a packet.";
                  }
                  leaf atm-transmit-cell {
                    // NCS drop when statement
                    ext:dynamic-default;
                    type string;
                    description
                      "Maximum number of ATM cells to be encapsulated into a packet that can be sent by a device.";
                  }
                  leaf sequence-number {
                    type string;
                    // NCS drop must statement
                    // NCS drop default statement
                    description
                      "Enable/disable the control-word-based ATM packet sequencing feature. Performance statistics can then be collected based on this feature.";
                  }
                }
                container track-vrrp {
                  // NCS drop when statement
                  // NCS drop must statement
                  presence "enable track vrrp.";
                  description
                    "Enable/disable associating a PW with the mVRRP backup group.";
                  leaf vrrp-interface-name {
                    type string;
                    // NCS drop must statement
                    // NCS drop mandatory statement
                    description
                      "The name of mVRRP interface.";
                  }
                  leaf vrrp-vrid {
                    type string;
                    // NCS drop must statement
                    // NCS drop mandatory statement
                    description
                      "VRID of a VRRP backup group.";
                  }
                  leaf pw-redundancy {
                    type string;
                    // NCS drop must statement
                    // NCS drop default statement
                    description
                      "Enable/disable the PW protection group associated with an mVRRP backup group in PW redundancy.";
                  }
                }
                container flow-label {
                  // NCS drop when statement
                  presence "enbale flow label for pw";
                  description
                    "Enable/disable the flow label capability of a PW.";
                  leaf ability {
                    type ncs_template_flow-label-ability;
                    // NCS drop must statement
                    // NCS drop mandatory statement
                    description
                      "Flow label capability.";
                  }
                  leaf static {
                    type string;
                    // NCS drop default statement
                    description
                      "Enable/disable the static flow label.";
                  }
                }
                container track-vrf-routes {
                  // NCS drop when statement
                  description
                    "List of PWs to track the VPN instance route.";
                  list track-vrf-route {
                    // NCS patched for predictable order
                    ordered-by user;
                    key "vrf-name ip-address mask-length";
                    description
                      "Configure a PW associated with a VPN instance route.";
                    leaf vrf-name {
                      type string;
                      description
                        "The name of the VPN instance.";
                    }
                    leaf ip-address {
                      type string;
                      description
                        "IP address of a VPN instance route.";
                    }
                    leaf mask-length {
                      type string;
                      description
                        "Mask of a VPN instance route.";
                    }
                  }
                }
                container bfd {
                  // NCS drop when statement
                  presence "enable pw bfd.";
                  description
                    "Enable/disable the BFD parameter list.";
                  uses l2vpn:ncs_template_l2vpn-dyn-bfd-para-type;
                  leaf remote-vc-id {
                    type string;
                    description
                      "Remote VC ID.";
                  }
                  leaf track-interface {
                    // NCS drop when statement
                    type string;
                    // NCS drop default statement
                    description
                      "Enable/disable BFD track interface state.";
                  }
                  leaf track-interface-name {
                    // NCS drop when statement
                    type string;
                    description
                      "Specify the interface to be tracked.";
                  }
                }
                // NCS drop config false container 'pw-info'
                // NCS drop config false container 'traffic-statistics'
              }
            }
            container out-acs {
              // NCS drop when statement
              description
                "List of all out ACs.";
              list out-ac {
                // NCS patched for predictable order
                ordered-by user;
                key "interface-name";
                // NCS drop max-elements statement
                description
                  "Configure outbound interface of single CCC.";
                leaf interface-name {
                  type string;
                  // NCS drop must statement
                  description
                    "Name of an AC interface.";
                }
                leaf role {
                  ext:operation-exclude "update";
                  type ncs_template_pw-role-type;
                  // NCS drop must statement
                  // NCS drop mandatory statement
                  description
                    "Role of out AC.";
                }
                container tdm-parameter {
                  // NCS drop when statement
                  description
                    "Configure TDM parameters of CCC instance.";
                  uses ncs_template_l2vpn-ccc-tdm-type;
                }
                container atm-parameter {
                  // NCS drop when statement
                  description
                    "Configure ATM parameters.";
                  uses ncs_template_l2vpn-ccc-atm-type;
                }
              }
            }
            container hard-pipe {
              // NCS drop when statement
              // NCS drop must statement
              presence "Enable hard pipe for pw.";
              description
                "Enable/disable hard pipe. The hard-pipe node and the qos-parameter node cannot be configured together.";
              leaf bandwidth {
                type string;
                units "kbit/s";
                // NCS drop mandatory statement
                description
                  "Specify bandwidth value.";
              }
              leaf expand-ratio {
                type string;
                // NCS drop default statement
                description
                  "Specify the value of bandwidth expand ratio (%). As to CES service, expand ratio ranges from 0 to 10000. The other service, expand ratio ranges from 0 to 100.";
              }
              leaf burst-time {
                // NCS drop when statement
                type string;
                units "us";
                // NCS drop default statement
                description
                  "Burst time.";
              }
            }
            container ac-oam-mapping {
              ext:operation-exclude "update";
              // NCS drop when statement
              presence "enable AC OAM mapping";
              description
                "Enable/disable OAM mapping.";
              leaf type {
                ext:operation-exclude "update";
                type ncs_template_ac-oam-mapping-type;
                // NCS drop must statement
                // NCS drop mandatory statement
                description
                  "VPWS attachment circuit OAM mapping type.";
              }
              leaf md-name {
                ext:operation-exclude "update|delete";
                // NCS drop when statement
                type string;
                description
                  "VPWS OAM mapping parameter md name.";
              }
              leaf ma-name {
                ext:operation-exclude "update|delete";
                // NCS drop when statement
                type string;
                description
                  "VPWS OAM mapping parameter ma name.";
              }
            }
            container reliability {
              // NCS drop when statement
              description
                "Configure PW reliability.";
              leaf redundancy-mode {
                type ncs_template_pw-redundancy-mode;
                // NCS drop must statement
                // NCS drop must statement
                // NCS drop default statement
                description
                  "PW redundancy mode.";
              }
              leaf switchover {
                // NCS drop when statement
                type string;
                // NCS drop must statement
                // NCS drop default statement
                description
                  "Enable/disable manual PW switchover.";
              }
              leaf dual-receive {
                type string;
                // NCS drop default statement
                description
                  "Enable/disable the packet reception of both the primary and secondary PWs.";
              }
              leaf dual-send {
                type string;
                // NCS drop must statement
                // NCS drop default statement
                description
                  "Enable/disable the packet transmission of both the primary and secondary PWs.";
              }
              leaf holdoff {
                // NCS drop when statement
                type string;
                units "s";
                description
                  "Hold time for traffic switching.";
              }
              container reroute {
                // NCS drop when statement
                description
                  "Configure a switchback policy list.";
                leaf reroute-policy {
                  type ncs_template_l2vpn-reroute-mode;
                  // NCS drop default statement
                  description
                    "Switchback policy.";
                }
                leaf delay-time {
                  // NCS drop when statement
                  type string;
                  units "s";
                  // NCS drop default statement
                  description
                    "Delay for switching traffic back to the primary PW.";
                }
                leaf resume-time {
                  // NCS drop when statement
                  type string;
                  units "s";
                  // NCS drop default statement
                  description
                    "Time after which the peer PE on the secondary PW is notified that the local PE has recovered. This parameter can be configured only in FRR mode.";
                }
                // NCS drop config false leaf 'last-switchback-reason'
                // NCS drop config false leaf 'last-switchback-time'
                // NCS drop config false leaf 'delay-residual'
                // NCS drop config false leaf 'resume-residual'
              }
              container aps-parameter {
                ext:operation-exclude "update";
                // NCS drop when statement
                presence "enable aps protection for pw.";
                description
                  "Enable/disable APS.";
                leaf aps-id {
                  ext:operation-exclude "update";
                  type string;
                  // NCS drop mandatory statement
                  description
                    "PW APS instance ID.";
                }
                leaf bind-type {
                  ext:operation-exclude "update|delete";
                  type ncs_template_l2vpn-aps-bind-type;
                  // NCS drop default statement
                  description
                    "Type of a PW protection group associated with the PW APS instance.";
                }
              }
            }
          }
          container vpws-switch {
            ext:operation-exclude "delete";
            // NCS drop when statement
            // NCS drop must statement
            description
              "Configure a VPWS switch instance.";
            uses ncs_template_vpws-swtich-instance-grp;
          }
          container vpws-bgp {
            ext:operation-exclude "delete";
            // NCS drop when statement
            description
              "Configure a VPWS BGP instance. This container cannot be deleted.";
            uses ncs_template_vpws-bgp-instance-grp;
          }
          container vpls {
            ext:operation-exclude "delete";
            // NCS drop when statement
            // NCS drop must statement
            // NCS drop must statement
            // NCS drop must statement
            // NCS drop must statement
            // NCS drop must statement
            description
              "Configure a VPLS instance.";
            uses ncs_template_vpls-instance-grp;
          }
        }
      }
    }
  }
  augment "/ncs:devices/ncs:template/ncs:ned-id/ncs:config/ifm:ifm/ifm:interfaces/ifm:interface" {
    description
      "Adds L2VPN configuration to the IFM module.";
    container track-pw-state {
      // NCS drop when statement
      presence "Enable association between the PW status with the interface status.";
      description
        "Enable/disable association between the PW status with the interface status.";
    }
    container l3ve-delay-up {
      // NCS drop when statement
      presence "Enable the delay function for an L3VE interface to go up.";
      description
        "Configure the delay function for an L3VE interface to go up.";
      leaf time {
        type string;
        units "s";
        // NCS drop mandatory statement
        description
          "Delay up time.";
      }
    }
    container arp-sending {
      presence "Enable arp sending";
      description
        "Configure the ARP sending mode.";
      leaf type {
        type ncs_template_l2vpn-arp-send-type;
        // NCS drop default statement
        description
          "ARP sending type.";
      }
      leaf expire-time {
        type string;
        units "s";
        // NCS drop default statement
        description
          "Set expire time.";
      }
    }
    container nd-sending {
      presence "Enable nd sending";
      description
        "Configure the ND sending mode.";
      leaf type {
        type ncs_template_l2vpn-nd-send-type;
        // NCS drop default statement
        description
          "ND sending type.";
      }
      leaf expire-time {
        type string;
        units "s";
        // NCS drop default statement
        description
          "Set expire time.";
      }
    }
  }
  augment "/ncs:devices/ncs:device/ncs:live-status/ifm:ifm/ifm:interfaces/ifm:interface" {
    description
      "Adds L2VPN configuration to the IFM module.";
    container track-pw-state {
      tailf:ncs-device-type "netconf";
      tailf:display-when "not(../../../../../ncs:module) or ../../../../../ncs:module[ncs:name='huawei-l2vpn'] or (../../../../../ncs:live-status-protocol[not(ncs:capability)]) or (../../../../../ncs:live-status-protocol/ncs:capability/ncs:module[.='huawei-l2vpn'])";
      // NCS drop when statement
      presence "Enable association between the PW status with the interface status.";
      description
        "Enable/disable association between the PW status with the interface status.";
    }
    container l3ve-delay-up {
      tailf:ncs-device-type "netconf";
      tailf:display-when "not(../../../../../ncs:module) or ../../../../../ncs:module[ncs:name='huawei-l2vpn'] or (../../../../../ncs:live-status-protocol[not(ncs:capability)]) or (../../../../../ncs:live-status-protocol/ncs:capability/ncs:module[.='huawei-l2vpn'])";
      // NCS drop when statement
      presence "Enable the delay function for an L3VE interface to go up.";
      description
        "Configure the delay function for an L3VE interface to go up.";
      leaf time {
        type uint16 {
          range "1..300";
        }
        units "s";
        // NCS drop mandatory statement
        description
          "Delay up time.";
      }
    }
    container arp-sending {
      tailf:ncs-device-type "netconf";
      tailf:display-when "not(../../../../../ncs:module) or ../../../../../ncs:module[ncs:name='huawei-l2vpn'] or (../../../../../ncs:live-status-protocol[not(ncs:capability)]) or (../../../../../ncs:live-status-protocol/ncs:capability/ncs:module[.='huawei-l2vpn'])";
      presence "Enable arp sending";
      description
        "Configure the ARP sending mode.";
      leaf type {
        type live_ncs_l2vpn-arp-send-type;
        // NCS drop default statement
        description
          "ARP sending type.";
      }
      leaf expire-time {
        type uint32 {
          range "60..4294967295";
        }
        units "s";
        // NCS drop default statement
        description
          "Set expire time.";
      }
    }
    container nd-sending {
      tailf:ncs-device-type "netconf";
      tailf:display-when "not(../../../../../ncs:module) or ../../../../../ncs:module[ncs:name='huawei-l2vpn'] or (../../../../../ncs:live-status-protocol[not(ncs:capability)]) or (../../../../../ncs:live-status-protocol/ncs:capability/ncs:module[.='huawei-l2vpn'])";
      presence "Enable nd sending";
      description
        "Configure the ND sending mode.";
      leaf type {
        type live_ncs_l2vpn-nd-send-type;
        // NCS drop default statement
        description
          "ND sending type.";
      }
      leaf expire-time {
        type uint32 {
          range "60..4294967295";
        }
        units "s";
        // NCS drop default statement
        description
          "Set expire time.";
      }
    }
  }
  augment "/ncs:devices/ncs:device/ncs:config/ifm:ifm/ifm:interfaces/ifm:interface" {
    description
      "Adds L2VPN configuration to the IFM module.";
    container track-pw-state {
      tailf:ncs-device-type "netconf";
      tailf:display-when "not(../../../../../ncs:module) or ../../../../../ncs:module[ncs:name='huawei-l2vpn']";
      when "(../ifm:type='Virtual-Ethernet' or ../ifm:type='Global-VE') and ../ifm:class='sub-interface'" {
        tailf:xpath-root 3;
      }
      presence "Enable association between the PW status with the interface status.";
      description
        "Enable/disable association between the PW status with the interface status.";
    }
    container l3ve-delay-up {
      tailf:ncs-device-type "netconf";
      tailf:display-when "not(../../../../../ncs:module) or ../../../../../ncs:module[ncs:name='huawei-l2vpn']";
      when "(../ifm:type='Virtual-Ethernet' or ../ifm:type='Global-VE') and ../ifm:class='sub-interface'" {
        tailf:xpath-root 3;
      }
      presence "Enable the delay function for an L3VE interface to go up.";
      description
        "Configure the delay function for an L3VE interface to go up.";
      leaf time {
        type uint16 {
          range "1..300";
        }
        units "s";
        mandatory true;
        description
          "Delay up time.";
      }
    }
    container arp-sending {
      tailf:ncs-device-type "netconf";
      tailf:display-when "not(../../../../../ncs:module) or ../../../../../ncs:module[ncs:name='huawei-l2vpn']";
      presence "Enable arp sending";
      description
        "Configure the ARP sending mode.";
      leaf type {
        type l2vpn-arp-send-type;
        default "dual-send";
        description
          "ARP sending type.";
      }
      leaf expire-time {
        type uint32 {
          range "60..4294967295";
        }
        units "s";
        default "3600";
        description
          "Set expire time.";
      }
    }
    container nd-sending {
      tailf:ncs-device-type "netconf";
      tailf:display-when "not(../../../../../ncs:module) or ../../../../../ncs:module[ncs:name='huawei-l2vpn']";
      presence "Enable nd sending";
      description
        "Configure the ND sending mode.";
      leaf type {
        type l2vpn-nd-send-type;
        default "dual-send";
        description
          "ND sending type.";
      }
      leaf expire-time {
        type uint32 {
          range "60..4294967295";
        }
        units "s";
        default "3600";
        description
          "Set expire time.";
      }
    }
  }
}
