module huawei-emdi {
  // Generated by yanger -t ncs
  tailf:mount-id "huawei-nc-1.0:huawei-nc-1.0";
  tailf:ncs-device-type "netconf";

  yang-version 1;
  namespace "urn:huawei:yang:huawei-emdi";
  prefix emdi;

  import ietf-inet-types {
    prefix inet;
  }
  import huawei-extension {
    prefix ext;
  }
  import huawei-network-instance {
    prefix ni;
  }
  import huawei-l2vpn {
    prefix l2vpn;
  }
  import huawei-l3vpn {
    prefix l3vpn;
  }
  import huawei-bd {
    prefix bd;
  }
  import ietf-yang-types {
    prefix yang;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Enhanced Media Delivery Index.";
  reference "Huawei private.";

  revision 2019-06-27 {
    description
      "Init revision.";
    reference "Huawei private.";
  }
  ext:task-name "emdi";

  typedef ncs_template_channel-ref {
    type string;
    description
      "This type is used by data models that need to reference configured channels.";
  }

  typedef ncs_rpc_notif_channel-ref {
    type string;
    description
      "This type is used by data models that need to reference configured channels.";
  }

  typedef live_ncs_channel-ref {
    type leafref {
      path "/ncs:devices/ncs:device/ncs:live-status/emdi:emdi/emdi:emdi-channels/emdi:emdi-channel/emdi:channel-name" {
        tailf:xpath-root 3;
      }
    }
    description
      "This type is used by data models that need to reference configured channels.";
  }

  typedef channel-ref {
    type leafref {
      path "/ncs:devices/ncs:device/ncs:live-status/emdi:emdi/emdi:emdi-channels/emdi:emdi-channel/emdi:channel-name" {
        tailf:xpath-root 2;
      }
    }
    description
      "This type is used by data models that need to reference configured channels.";
  }

  augment "/ncs:devices/ncs:device/ncs:rpc" {
    container rpc-filter-history-statistic {
      tailf:ncs-device-type "netconf";
      tailf:display-when "not(../../ncs:module) or ../../ncs:module[ncs:name='huawei-emdi']";
      tailf:action filter-history-statistic {
        tailf:actionpoint ncsproxy {
          tailf:internal;
        }
        description
          "Filter EMDI history statistics.";
        ext:node-ref "/emdi/emdi-history-statistic-records/emdi-history-statistic-record";
        input {
          leaf channel-name {
            type string {
              length "1..31";
            }
            description
              "Channel name.";
          }
          leaf start-index {
            type uint16 {
              range "1..1000";
            }
            description
              "Start index. This parameter is used only as a filter criterion and is not displayed.";
          }
          leaf end-index {
            type uint16 {
              range "1..1000";
            }
            description
              "End index. It is only used as a filter criterion and is not displayed.";
          }
          leaf last-record-num {
            type uint8 {
              range "1..5";
            }
            description
              "Query the latest specified number of detection records. This parameter is used only as a filter criterion and is not displayed.";
          }
          leaf direction {
            type enumeration {
              enum "inbound" {
                value 0;
                description
                  "Inbound.";
              }
              enum "outbound" {
                value 1;
                description
                  "Outbound.";
              }
            }
            description
              "Specify the direction of EMDI.";
          }
          leaf slot-id {
            type string {
              length "1..15";
            }
            description
              "Slot ID.";
          }
        }
        output {
          container emdi-history-statistic-records {
            description
              "List of configure query historical EMDI detection information.";
            list emdi-history-statistic-record {
              key "channel-name record-index direction";
              description
                "Configure query historical EMDI detection information.";
              leaf channel-name {
                type string {
                  length "1..31";
                }
                description
                  "Channel name.";
              }
              leaf record-index {
                type uint16 {
                  range "1..1000";
                }
                description
                  "Index of each detection message.";
              }
              leaf direction {
                type enumeration {
                  enum "inbound" {
                    value 0;
                    description
                      "Inbound.";
                  }
                  enum "outbound" {
                    value 1;
                    description
                      "Outbound.";
                  }
                }
                description
                  "Specify the direction of EMDI.";
              }
              leaf record-time {
                type string {
                  length "1..19";
                }
                description
                  "Time when each piece of information is detected.";
              }
              leaf monitor-period {
                type enumeration {
                  enum "second-10s" {
                    value 10;
                    description
                      "Monitor period is 10 second.";
                  }
                  enum "second-30s" {
                    value 30;
                    description
                      "Monitor period is 30 second.";
                  }
                  enum "second-60s" {
                    value 60;
                    description
                      "Monitor period is 60 second.";
                  }
                }
                description
                  "Detection period of each detection message.";
              }
              leaf monitor-status {
                type enumeration {
                  enum "normal" {
                    value 0;
                    description
                      "Status normal.";
                  }
                  enum "car-drop" {
                    value 1;
                    description
                      "Status abnormal, NP drop.";
                  }
                  enum "rate-only" {
                    value 2;
                    description
                      "Only the rate of video streams is detected.";
                  }
                }
                description
                  "Detection status of each detection message.";
              }
              leaf receive-packet {
                type uint64;
                description
                  "Number of received packets.";
              }
              leaf rate-pps {
                type uint64;
                units "pps";
                description
                  "Rate (pps) at which packets are received.";
              }
              leaf rate-bps {
                type uint64;
                units "bit/s";
                description
                  "Rate (bit/s) at which packets are received.";
              }
              leaf lost-packet {
                type uint64;
                description
                  "Number of lost packets on a channel.";
              }
              leaf disorder-packet {
                type uint64;
                description
                  "Number of disordered packets.";
              }
              leaf rtp-lr {
                type uint32;
                units "0.001 %";
                description
                  "Packet loss rate of a channel.";
              }
              leaf rtp-ser {
                type uint32;
                units "0.001 %";
                description
                  "Check the channel disorder rate.";
              }
              leaf rtp-jitter {
                type string {
                  length "1..9";
                }
                description
                  "Check the jitter of the channel.";
              }
              leaf slot-id {
                type string {
                  length "1..15";
                }
                description
                  "Slot ID.";
              }
              leaf interface-name {
                type string {
                  length "1..63";
                }
                description
                  "Interface name.";
              }
            }
          }
        }
      }
    }
  }
  augment "/ncs:devices/ncs:device-group/ncs:ned-id/ncs:rpc" {
    container rpc-filter-history-statistic {
      tailf:ncs-device-type "netconf";
      tailf:display-when "/ncs:devices/ncs:device[ncs:name=current()/../../../ncs:member]/ncs:module[ncs:name='huawei-emdi']";
      tailf:action filter-history-statistic {
        tailf:actionpoint ncsproxy {
          tailf:internal;
        }
        description
          "Filter EMDI history statistics.";
        ext:node-ref "/emdi/emdi-history-statistic-records/emdi-history-statistic-record";
        input {
          leaf channel-name {
            type string {
              length "1..31";
            }
            description
              "Channel name.";
          }
          leaf start-index {
            type uint16 {
              range "1..1000";
            }
            description
              "Start index. This parameter is used only as a filter criterion and is not displayed.";
          }
          leaf end-index {
            type uint16 {
              range "1..1000";
            }
            description
              "End index. It is only used as a filter criterion and is not displayed.";
          }
          leaf last-record-num {
            type uint8 {
              range "1..5";
            }
            description
              "Query the latest specified number of detection records. This parameter is used only as a filter criterion and is not displayed.";
          }
          leaf direction {
            type enumeration {
              enum "inbound" {
                value 0;
                description
                  "Inbound.";
              }
              enum "outbound" {
                value 1;
                description
                  "Outbound.";
              }
            }
            description
              "Specify the direction of EMDI.";
          }
          leaf slot-id {
            type string {
              length "1..15";
            }
            description
              "Slot ID.";
          }
        }
        output {
          container "device" {
            leaf "name" {
              type string;
            }
            leaf "info" {
              type string;
            }
            container "result" {
              container emdi-history-statistic-records {
                description
                  "List of configure query historical EMDI detection information.";
                list emdi-history-statistic-record {
                  key "channel-name record-index direction";
                  description
                    "Configure query historical EMDI detection information.";
                  leaf channel-name {
                    type string {
                      length "1..31";
                    }
                    description
                      "Channel name.";
                  }
                  leaf record-index {
                    type uint16 {
                      range "1..1000";
                    }
                    description
                      "Index of each detection message.";
                  }
                  leaf direction {
                    type enumeration {
                      enum "inbound" {
                        value 0;
                        description
                          "Inbound.";
                      }
                      enum "outbound" {
                        value 1;
                        description
                          "Outbound.";
                      }
                    }
                    description
                      "Specify the direction of EMDI.";
                  }
                  leaf record-time {
                    type string {
                      length "1..19";
                    }
                    description
                      "Time when each piece of information is detected.";
                  }
                  leaf monitor-period {
                    type enumeration {
                      enum "second-10s" {
                        value 10;
                        description
                          "Monitor period is 10 second.";
                      }
                      enum "second-30s" {
                        value 30;
                        description
                          "Monitor period is 30 second.";
                      }
                      enum "second-60s" {
                        value 60;
                        description
                          "Monitor period is 60 second.";
                      }
                    }
                    description
                      "Detection period of each detection message.";
                  }
                  leaf monitor-status {
                    type enumeration {
                      enum "normal" {
                        value 0;
                        description
                          "Status normal.";
                      }
                      enum "car-drop" {
                        value 1;
                        description
                          "Status abnormal, NP drop.";
                      }
                      enum "rate-only" {
                        value 2;
                        description
                          "Only the rate of video streams is detected.";
                      }
                    }
                    description
                      "Detection status of each detection message.";
                  }
                  leaf receive-packet {
                    type uint64;
                    description
                      "Number of received packets.";
                  }
                  leaf rate-pps {
                    type uint64;
                    units "pps";
                    description
                      "Rate (pps) at which packets are received.";
                  }
                  leaf rate-bps {
                    type uint64;
                    units "bit/s";
                    description
                      "Rate (bit/s) at which packets are received.";
                  }
                  leaf lost-packet {
                    type uint64;
                    description
                      "Number of lost packets on a channel.";
                  }
                  leaf disorder-packet {
                    type uint64;
                    description
                      "Number of disordered packets.";
                  }
                  leaf rtp-lr {
                    type uint32;
                    units "0.001 %";
                    description
                      "Packet loss rate of a channel.";
                  }
                  leaf rtp-ser {
                    type uint32;
                    units "0.001 %";
                    description
                      "Check the channel disorder rate.";
                  }
                  leaf rtp-jitter {
                    type string {
                      length "1..9";
                    }
                    description
                      "Check the jitter of the channel.";
                  }
                  leaf slot-id {
                    type string {
                      length "1..15";
                    }
                    description
                      "Slot ID.";
                  }
                  leaf interface-name {
                    type string {
                      length "1..63";
                    }
                    description
                      "Interface name.";
                  }
                }
              }
            }
          }
        }
      }
    }
  }
  augment "/ncs:devices/ncs:device/ncs:rpc" {
    container rpc-reset-bier-out-statistic-history {
      tailf:ncs-device-type "netconf";
      tailf:display-when "not(../../ncs:module) or ../../ncs:module[ncs:name='huawei-emdi']";
      tailf:action reset-bier-out-statistic-history {
        tailf:actionpoint ncsproxy {
          tailf:internal;
        }
        description
          "Reset outbound BIER channel statistics.";
        ext:node-ref "/emdi/bier-out-history-records/bier-out-history-record";
        input {
          leaf slot-id {
            type string {
              length "1..15";
            }
            mandatory true;
            description
              "Slot ID.";
          }
        }
      }
    }
  }
  augment "/ncs:devices/ncs:device-group/ncs:ned-id/ncs:rpc" {
    container rpc-reset-bier-out-statistic-history {
      tailf:ncs-device-type "netconf";
      tailf:display-when "/ncs:devices/ncs:device[ncs:name=current()/../../../ncs:member]/ncs:module[ncs:name='huawei-emdi']";
      tailf:action reset-bier-out-statistic-history {
        tailf:actionpoint ncsproxy {
          tailf:internal;
        }
        description
          "Reset outbound BIER channel statistics.";
        ext:node-ref "/emdi/bier-out-history-records/bier-out-history-record";
        input {
          leaf slot-id {
            type string {
              length "1..15";
            }
            mandatory true;
            description
              "Slot ID.";
          }
        }
      }
    }
  }
  augment "/ncs:devices/ncs:device/ncs:rpc" {
    container rpc-reset-bier-statistic-history {
      tailf:ncs-device-type "netconf";
      tailf:display-when "not(../../ncs:module) or ../../ncs:module[ncs:name='huawei-emdi']";
      tailf:action reset-bier-statistic-history {
        tailf:actionpoint ncsproxy {
          tailf:internal;
        }
        description
          "Reset BIER channel statistics.";
        ext:node-ref "/emdi/bier-history-records/bier-history-record";
        input {
          leaf slot-id {
            type string {
              length "1..15";
            }
            mandatory true;
            description
              "Slot ID.";
          }
        }
      }
    }
  }
  augment "/ncs:devices/ncs:device-group/ncs:ned-id/ncs:rpc" {
    container rpc-reset-bier-statistic-history {
      tailf:ncs-device-type "netconf";
      tailf:display-when "/ncs:devices/ncs:device[ncs:name=current()/../../../ncs:member]/ncs:module[ncs:name='huawei-emdi']";
      tailf:action reset-bier-statistic-history {
        tailf:actionpoint ncsproxy {
          tailf:internal;
        }
        description
          "Reset BIER channel statistics.";
        ext:node-ref "/emdi/bier-history-records/bier-history-record";
        input {
          leaf slot-id {
            type string {
              length "1..15";
            }
            mandatory true;
            description
              "Slot ID.";
          }
        }
      }
    }
  }
  augment "/ncs:devices/ncs:device/ncs:rpc" {
    container rpc-reset-outbound-history-statistic {
      tailf:ncs-device-type "netconf";
      tailf:display-when "not(../../ncs:module) or ../../ncs:module[ncs:name='huawei-emdi']";
      tailf:action reset-outbound-history-statistic {
        tailf:actionpoint ncsproxy {
          tailf:internal;
        }
        description
          "Reset outbound channel statistics.";
        ext:node-ref "/emdi/emdi-history-statistic-records/emdi-history-statistic-record";
        input {
          leaf slot-id {
            type string {
              length "1..15";
            }
            mandatory true;
            description
              "Slot ID.";
          }
          leaf channel-name {
            type string {
              length "1..31";
            }
            description
              "Channel name.";
          }
        }
      }
    }
  }
  augment "/ncs:devices/ncs:device-group/ncs:ned-id/ncs:rpc" {
    container rpc-reset-outbound-history-statistic {
      tailf:ncs-device-type "netconf";
      tailf:display-when "/ncs:devices/ncs:device[ncs:name=current()/../../../ncs:member]/ncs:module[ncs:name='huawei-emdi']";
      tailf:action reset-outbound-history-statistic {
        tailf:actionpoint ncsproxy {
          tailf:internal;
        }
        description
          "Reset outbound channel statistics.";
        ext:node-ref "/emdi/emdi-history-statistic-records/emdi-history-statistic-record";
        input {
          leaf slot-id {
            type string {
              length "1..15";
            }
            mandatory true;
            description
              "Slot ID.";
          }
          leaf channel-name {
            type string {
              length "1..31";
            }
            description
              "Channel name.";
          }
        }
      }
    }
  }
  augment "/ncs:devices/ncs:device/ncs:rpc" {
    container rpc-reset-statistic-history {
      tailf:ncs-device-type "netconf";
      tailf:display-when "not(../../ncs:module) or ../../ncs:module[ncs:name='huawei-emdi']";
      tailf:action reset-statistic-history {
        tailf:actionpoint ncsproxy {
          tailf:internal;
        }
        description
          "Reset channel statistics.";
        ext:node-ref "/emdi/emdi-history-statistic-records/emdi-history-statistic-record";
        input {
          leaf channel-name {
            type string {
              length "1..31";
            }
            description
              "Channel name.";
          }
        }
      }
    }
  }
  augment "/ncs:devices/ncs:device-group/ncs:ned-id/ncs:rpc" {
    container rpc-reset-statistic-history {
      tailf:ncs-device-type "netconf";
      tailf:display-when "/ncs:devices/ncs:device[ncs:name=current()/../../../ncs:member]/ncs:module[ncs:name='huawei-emdi']";
      tailf:action reset-statistic-history {
        tailf:actionpoint ncsproxy {
          tailf:internal;
        }
        description
          "Reset channel statistics.";
        ext:node-ref "/emdi/emdi-history-statistic-records/emdi-history-statistic-record";
        input {
          leaf channel-name {
            type string {
              length "1..31";
            }
            description
              "Channel name.";
          }
        }
      }
    }
  }
  augment "/ncs:devices/ncs:device/ncs:config" {
    container emdi {
      tailf:ncs-device-type "netconf";
      tailf:display-when "not(../../ncs:module) or ../../ncs:module[ncs:name='huawei-emdi']";
      description
        "On-board EMDI detection that obtains packet header information to sample multicast quality data.";
      container emdi-enable {
        presence "Enable EMDI";
        description
          "Enable/disable EMDI detection.";
        container emdi-global {
          description
            "Configure global EMDI attribute information.";
          leaf age-periods {
            type uint8 {
              range "3..60";
            }
            default "10";
            description
              "Bier channel statistics age periods.";
          }
        }
        container emdi-channel-groups {
          description
            "List of configure channel group information. Multiple channels can be bound to a channel group.";
          list emdi-channel-group {
            key "channel-group-name";
            max-elements 32;
            description
              "Configure channel group information. Multiple channels can be bound to a channel group.";
            leaf channel-group-name {
              type string {
                length "1..31";
              }
              description
                "Channel group name.";
            }
            choice channel-type {
              description
                "Configure EMDI channel information.";
              case emdi-channel {
                description
                  "Configure channel information.";
                container emdi-channels {
                  description
                    "List of configure channel information.";
                  list emdi-channel {
                    key "channel-name";
                    max-elements 2100;
                    description
                      "Configure channel information. The group-address and source-address combination of different instances cannot overlap.";
                    leaf channel-name {
                      type string {
                        length "1..31";
                      }
                      description
                        "Channel name.";
                    }
                    leaf source-address {
                      type inet:ipv4-address-no-zone;
                      mandatory true;
                      description
                        "Multicast IP source address.";
                    }
                    leaf group-address {
                      type inet:ipv4-address-no-zone;
                      mandatory true;
                      description
                        "Multicast IP address.";
                    }
                    choice channel-group-parameters {
                      description
                        "EMDI channel group parameters.";
                      case vpn-name {
                        description
                          "Specify the name of a VPN instance. Multicast traffic is bound to a VPN tunnel.";
                        leaf vpn-name {
                          type leafref {
                            path "/ncs:devices/ncs:device/ncs:config/ni:network-instance/ni:instances/ni:instance/ni:name" {
                              tailf:xpath-root 3;
                            }
                          }
                          must "/ni:network-instance/ni:instances/ni:instance[ni:name=current()]/l3vpn:afs/l3vpn:af[l3vpn:type='ipv4-unicast'] and ../vpn-name!='_public_'" {
                            tailf:xpath-root 3;
                          }
                          description
                            "Specify the name of a VPN instance. Multicast traffic is bound to a VPN tunnel.";
                        }
                      }
                      case vlan-id {
                        description
                          "VLAN information. Multicast traffic is bound to VLANs.";
                        leaf vlan-id {
                          type uint16 {
                            range "1..4094";
                          }
                          description
                            "VLAN information. Multicast traffic is bound to VLANs.";
                        }
                      }
                      case vsi-name {
                        description
                          "Name of a VSI. Multicast traffic is bound to a VSI tunnel.";
                        leaf vsi-name {
                          type leafref {
                            path "/ncs:devices/ncs:device/ncs:config/l2vpn:l2vpn/l2vpn:instances/l2vpn:instance/l2vpn:name" {
                              tailf:xpath-root 3;
                            }
                          }
                          must "/l2vpn:l2vpn/l2vpn:instances/l2vpn:instance[l2vpn:name=current()][l2vpn:type='vpls']" {
                            tailf:xpath-root 3;
                          }
                          description
                            "Name of a VSI. Multicast traffic is bound to a VSI tunnel.";
                        }
                      }
                      case bd-id {
                        description
                          "DB information. Multicast traffic is bound to a BD.";
                        leaf bd-id {
                          type leafref {
                            path "/ncs:devices/ncs:device/ncs:config/bd:bd/bd:instances/bd:instance/bd:id" {
                              tailf:xpath-root 3;
                            }
                          }
                          description
                            "DB information. Multicast traffic is bound to a BD.";
                        }
                      }
                      case transit {
                        description
                          "In the P node scenario, enable the transit detection function to ensure that the P node detection function is proper.";
                        leaf transit {
                          type empty;
                          description
                            "In the P node scenario, enable the transit detection function to ensure that the P node detection function is proper.";
                        }
                      }
                    }
                    leaf pt-value {
                      type uint16 {
                        range "25..34 | 96..127";
                      }
                      must "(../clock-rate='clock-90khz') or (../clock-rate!='clock-90khz' and ../pt-value >= 96 and ../pt-value <= 127)" {
                        tailf:xpath-root 3;
                      }
                      default "33";
                      description
                        "Payload type. Only payload type (PT) videos are detected.";
                    }
                    leaf clock-rate {
                      type enumeration {
                        enum "clock-90khz" {
                          value 0;
                          description
                            "Clock rate 90kHz frequency.";
                        }
                        enum "clock-27000khz" {
                          value 1;
                          description
                            "Clock rate 27000kHz frequency.";
                        }
                        enum "clock-148500khz" {
                          value 2;
                          description
                            "Clock rate 148500kHz frequency.";
                        }
                        enum "clock-about-148mhz" {
                          value 3;
                          description
                            "Clock rate 148.5/1.001MHz frequency.";
                        }
                      }
                      must "(../clock-rate='clock-90khz') or (../clock-rate!='clock-90khz' and ../pt-value >= 96 and ../pt-value <= 127)" {
                        tailf:xpath-root 3;
                      }
                      default "clock-90khz";
                      description
                        "Clock frequency information.";
                    }
                    leaf uncompressed {
                      type empty;
                      description
                        "Whether non-compressed multicast traffic detection is enabled.";
                    }
                  }
                }
              }
              case emdi-bier-channel {
                description
                  "Configure bier channel information.";
                container emdi-bier-channels {
                  description
                    "List of configure bier channel information.";
                  list emdi-bier-channel {
                    key "channel-name";
                    max-elements 2100;
                    description
                      "Configure bier channel information.";
                    leaf channel-name {
                      type string {
                        length "1..31";
                      }
                      description
                        "Channel name.";
                    }
                    leaf source-address {
                      type inet:ipv4-address-no-zone;
                      mandatory true;
                      description
                        "Multicast IP source address.";
                    }
                    leaf group-address {
                      type inet:ipv4-address-no-zone;
                      mandatory true;
                      description
                        "Multicast IP address.";
                    }
                    leaf bier-vpn-name {
                      type leafref {
                        path "/ncs:devices/ncs:device/ncs:config/ni:network-instance/ni:instances/ni:instance/ni:name" {
                          tailf:xpath-root 3;
                        }
                      }
                      must "/ni:network-instance/ni:instances/ni:instance[ni:name=current()]/l3vpn:afs/l3vpn:af[l3vpn:type='ipv4-unicast'] and ../bier-vpn-name!='_public_'" {
                        tailf:xpath-root 3;
                      }
                      mandatory true;
                      description
                        "Specify the name of a VPN instance. Multicast traffic is bound to a VPN tunnel.";
                    }
                    leaf sub-domain {
                      type uint16 {
                        range "0..255";
                      }
                      mandatory true;
                      description
                        "The bier sub-domain.";
                    }
                    leaf bsl {
                      type enumeration {
                        enum "bsl-64" {
                          value 64;
                          description
                            "The bit string length is 64.";
                        }
                        enum "bsl-128" {
                          value 128;
                          description
                            "The bit string length is 128.";
                        }
                        enum "bsl-256" {
                          value 256;
                          description
                            "The bit string length is 256.";
                        }
                      }
                      mandatory true;
                      description
                        "The bit string length.";
                    }
                  }
                }
              }
            }
          }
        }
        container emdi-lpu-groups {
          description
            "List of configure Board group information.";
          list emdi-lpu-group {
            key "lpu-group-name";
            max-elements 32;
            description
              "Configure board group information.";
            ext:generated-by "system" {
              ext:filter "lpu-group-name='_default_'";
              description
                "The default board group named _default_ is automatically generated by the system.";
            }
            ext:operation-exclude "update" {
              ext:filter "lpu-group-name='_default_'";
              description
                "The default board group named _default_ cannot be updated.";
            }
            leaf lpu-group-name {
              type string {
                length "1..31";
              }
              description
                "Board group name.";
            }
            choice bind-lpu {
              description
                "Bind slot <all> or <slot-number>.";
              case bind-all {
                description
                  "Bind slot <all>.";
                container bind-all {
                  description
                    "Configure bind slot <all>.";
                  leaf all {
                    type empty;
                    description
                      "Bind slot <all>.";
                  }
                }
              }
              case bind-slots {
                description
                  "Bind slot <slot-number>.";
                leaf-list slot {
                  type string {
                    length "1..15";
                  }
                  max-elements 128;
                  description
                    "Configure slot number.";
                }
              }
            }
          }
        }
        container channel-group-bind-lpu-groups {
          description
            "List of configure binding between a channel group and a board.";
          list channel-group-bind-lpu-group {
            key "lpu-group-name channel-group-name";
            unique "channel-group-name";
            max-elements 32;
            description
              "Configure binding between a channel group and a board.";
            leaf lpu-group-name {
              type leafref {
                path "../../../emdi-lpu-groups/emdi-lpu-group/lpu-group-name";
              }
              description
                "Name of a bound board group.";
            }
            leaf channel-group-name {
              type leafref {
                path "../../../emdi-channel-groups/emdi-channel-group/channel-group-name";
              }
              description
                "Name of a bound channel group.";
            }
          }
        }
        container outbound-channel-group-bind-lpu-groups {
          description
            "List of configure outbound binding between a channel group and a board.";
          list outbound-channel-group-bind-lpu-group {
            key "lpu-group-name channel-group-name";
            unique "channel-group-name";
            max-elements 32;
            description
              "Configure outbound binding between a channel group and a board.";
            leaf lpu-group-name {
              type leafref {
                path "../../../emdi-lpu-groups/emdi-lpu-group/lpu-group-name";
              }
              description
                "Name of a bound board group.";
            }
            leaf channel-group-name {
              type leafref {
                path "../../../emdi-channel-groups/emdi-channel-group/channel-group-name";
              }
              description
                "Name of a bound channel group.";
            }
          }
        }
        container bier-enable {
          description
            "Configure bier lpu group.";
          leaf lpu-group-name {
            type leafref {
              path "../../emdi-lpu-groups/emdi-lpu-group/lpu-group-name";
            }
            description
              "Name of a bound board group.";
          }
        }
      }
      // NCS drop config false container 'emdi-history-records'
      // NCS drop config false container 'bier-history-records'
      // NCS drop config false container 'bier-out-history-records'
      // NCS drop config false container 'emdi-channels'
      // NCS drop config false container 'emdi-telem-reps'
      // NCS drop config false container 'emdi-telem-rtps'
      // NCS drop config false container 'out-telem-reps'
      // NCS drop config false container 'bier-telem-reps'
      // NCS drop config false container 'bier-telem-rtps'
      // NCS drop config false container 'bier-out-telem-reps'
      // NCS drop config false container 'bier-out-telem-rtps'
    }
  }
  augment "/ncs:devices/ncs:device/ncs:live-status" {
    container emdi {
      tailf:ncs-device-type "netconf";
      tailf:display-when "not(../../ncs:module) or ../../ncs:module[ncs:name='huawei-emdi'] or (../../ncs:live-status-protocol[not(ncs:capability)]) or (../../ncs:live-status-protocol/ncs:capability/ncs:module[.='huawei-emdi'])";
      description
        "On-board EMDI detection that obtains packet header information to sample multicast quality data.";
      container emdi-enable {
        presence "Enable EMDI";
        description
          "Enable/disable EMDI detection.";
        container emdi-global {
          description
            "Configure global EMDI attribute information.";
          leaf age-periods {
            type uint8 {
              range "3..60";
            }
            // NCS drop default statement
            description
              "Bier channel statistics age periods.";
          }
        }
        container emdi-channel-groups {
          description
            "List of configure channel group information. Multiple channels can be bound to a channel group.";
          list emdi-channel-group {
            key "channel-group-name";
            // NCS drop max-elements statement
            description
              "Configure channel group information. Multiple channels can be bound to a channel group.";
            leaf channel-group-name {
              type string {
                length "1..31";
              }
              description
                "Channel group name.";
            }
            choice channel-type {
              description
                "Configure EMDI channel information.";
              case emdi-channel {
                description
                  "Configure channel information.";
                container emdi-channels {
                  description
                    "List of configure channel information.";
                  list emdi-channel {
                    key "channel-name";
                    // NCS drop max-elements statement
                    description
                      "Configure channel information. The group-address and source-address combination of different instances cannot overlap.";
                    leaf channel-name {
                      type string {
                        length "1..31";
                      }
                      description
                        "Channel name.";
                    }
                    leaf source-address {
                      type inet:ipv4-address-no-zone;
                      // NCS drop mandatory statement
                      description
                        "Multicast IP source address.";
                    }
                    leaf group-address {
                      type inet:ipv4-address-no-zone;
                      // NCS drop mandatory statement
                      description
                        "Multicast IP address.";
                    }
                    choice channel-group-parameters {
                      description
                        "EMDI channel group parameters.";
                      case vpn-name {
                        description
                          "Specify the name of a VPN instance. Multicast traffic is bound to a VPN tunnel.";
                        leaf vpn-name {
                          type leafref {
                            path "/ncs:devices/ncs:device/ncs:live-status/ni:network-instance/ni:instances/ni:instance/ni:name" {
                              tailf:xpath-root 3;
                            }
                          }
                          // NCS drop must statement
                          description
                            "Specify the name of a VPN instance. Multicast traffic is bound to a VPN tunnel.";
                        }
                      }
                      case vlan-id {
                        description
                          "VLAN information. Multicast traffic is bound to VLANs.";
                        leaf vlan-id {
                          type uint16 {
                            range "1..4094";
                          }
                          description
                            "VLAN information. Multicast traffic is bound to VLANs.";
                        }
                      }
                      case vsi-name {
                        description
                          "Name of a VSI. Multicast traffic is bound to a VSI tunnel.";
                        leaf vsi-name {
                          type leafref {
                            path "/ncs:devices/ncs:device/ncs:live-status/l2vpn:l2vpn/l2vpn:instances/l2vpn:instance/l2vpn:name" {
                              tailf:xpath-root 3;
                            }
                          }
                          // NCS drop must statement
                          description
                            "Name of a VSI. Multicast traffic is bound to a VSI tunnel.";
                        }
                      }
                      case bd-id {
                        description
                          "DB information. Multicast traffic is bound to a BD.";
                        leaf bd-id {
                          type leafref {
                            path "/ncs:devices/ncs:device/ncs:live-status/bd:bd/bd:instances/bd:instance/bd:id" {
                              tailf:xpath-root 3;
                            }
                          }
                          description
                            "DB information. Multicast traffic is bound to a BD.";
                        }
                      }
                      case transit {
                        description
                          "In the P node scenario, enable the transit detection function to ensure that the P node detection function is proper.";
                        leaf transit {
                          type empty;
                          description
                            "In the P node scenario, enable the transit detection function to ensure that the P node detection function is proper.";
                        }
                      }
                    }
                    leaf pt-value {
                      type uint16 {
                        range "25..34 | 96..127";
                      }
                      // NCS drop must statement
                      // NCS drop default statement
                      description
                        "Payload type. Only payload type (PT) videos are detected.";
                    }
                    leaf clock-rate {
                      type enumeration {
                        enum "clock-90khz" {
                          value 0;
                          description
                            "Clock rate 90kHz frequency.";
                        }
                        enum "clock-27000khz" {
                          value 1;
                          description
                            "Clock rate 27000kHz frequency.";
                        }
                        enum "clock-148500khz" {
                          value 2;
                          description
                            "Clock rate 148500kHz frequency.";
                        }
                        enum "clock-about-148mhz" {
                          value 3;
                          description
                            "Clock rate 148.5/1.001MHz frequency.";
                        }
                      }
                      // NCS drop must statement
                      // NCS drop default statement
                      description
                        "Clock frequency information.";
                    }
                    leaf uncompressed {
                      type empty;
                      description
                        "Whether non-compressed multicast traffic detection is enabled.";
                    }
                  }
                }
              }
              case emdi-bier-channel {
                description
                  "Configure bier channel information.";
                container emdi-bier-channels {
                  description
                    "List of configure bier channel information.";
                  list emdi-bier-channel {
                    key "channel-name";
                    // NCS drop max-elements statement
                    description
                      "Configure bier channel information.";
                    leaf channel-name {
                      type string {
                        length "1..31";
                      }
                      description
                        "Channel name.";
                    }
                    leaf source-address {
                      type inet:ipv4-address-no-zone;
                      // NCS drop mandatory statement
                      description
                        "Multicast IP source address.";
                    }
                    leaf group-address {
                      type inet:ipv4-address-no-zone;
                      // NCS drop mandatory statement
                      description
                        "Multicast IP address.";
                    }
                    leaf bier-vpn-name {
                      type leafref {
                        path "/ncs:devices/ncs:device/ncs:live-status/ni:network-instance/ni:instances/ni:instance/ni:name" {
                          tailf:xpath-root 3;
                        }
                      }
                      // NCS drop must statement
                      // NCS drop mandatory statement
                      description
                        "Specify the name of a VPN instance. Multicast traffic is bound to a VPN tunnel.";
                    }
                    leaf sub-domain {
                      type uint16 {
                        range "0..255";
                      }
                      // NCS drop mandatory statement
                      description
                        "The bier sub-domain.";
                    }
                    leaf bsl {
                      type enumeration {
                        enum "bsl-64" {
                          value 64;
                          description
                            "The bit string length is 64.";
                        }
                        enum "bsl-128" {
                          value 128;
                          description
                            "The bit string length is 128.";
                        }
                        enum "bsl-256" {
                          value 256;
                          description
                            "The bit string length is 256.";
                        }
                      }
                      // NCS drop mandatory statement
                      description
                        "The bit string length.";
                    }
                  }
                }
              }
            }
          }
        }
        container emdi-lpu-groups {
          description
            "List of configure Board group information.";
          list emdi-lpu-group {
            key "lpu-group-name";
            // NCS drop max-elements statement
            description
              "Configure board group information.";
            ext:generated-by "system" {
              ext:filter "lpu-group-name='_default_'";
              description
                "The default board group named _default_ is automatically generated by the system.";
            }
            ext:operation-exclude "update" {
              ext:filter "lpu-group-name='_default_'";
              description
                "The default board group named _default_ cannot be updated.";
            }
            leaf lpu-group-name {
              type string {
                length "1..31";
              }
              description
                "Board group name.";
            }
            choice bind-lpu {
              description
                "Bind slot <all> or <slot-number>.";
              case bind-all {
                description
                  "Bind slot <all>.";
                container bind-all {
                  description
                    "Configure bind slot <all>.";
                  leaf all {
                    type empty;
                    description
                      "Bind slot <all>.";
                  }
                }
              }
              case bind-slots {
                description
                  "Bind slot <slot-number>.";
                leaf-list slot {
                  type string {
                    length "1..15";
                  }
                  // NCS drop max-elements statement
                  description
                    "Configure slot number.";
                }
              }
            }
          }
        }
        container channel-group-bind-lpu-groups {
          description
            "List of configure binding between a channel group and a board.";
          list channel-group-bind-lpu-group {
            key "lpu-group-name channel-group-name";
            unique "channel-group-name";
            // NCS drop max-elements statement
            description
              "Configure binding between a channel group and a board.";
            leaf lpu-group-name {
              type leafref {
                path "../../../emdi-lpu-groups/emdi-lpu-group/lpu-group-name";
              }
              description
                "Name of a bound board group.";
            }
            leaf channel-group-name {
              type leafref {
                path "../../../emdi-channel-groups/emdi-channel-group/channel-group-name";
              }
              description
                "Name of a bound channel group.";
            }
          }
        }
        container outbound-channel-group-bind-lpu-groups {
          description
            "List of configure outbound binding between a channel group and a board.";
          list outbound-channel-group-bind-lpu-group {
            key "lpu-group-name channel-group-name";
            unique "channel-group-name";
            // NCS drop max-elements statement
            description
              "Configure outbound binding between a channel group and a board.";
            leaf lpu-group-name {
              type leafref {
                path "../../../emdi-lpu-groups/emdi-lpu-group/lpu-group-name";
              }
              description
                "Name of a bound board group.";
            }
            leaf channel-group-name {
              type leafref {
                path "../../../emdi-channel-groups/emdi-channel-group/channel-group-name";
              }
              description
                "Name of a bound channel group.";
            }
          }
        }
        container bier-enable {
          description
            "Configure bier lpu group.";
          leaf lpu-group-name {
            type leafref {
              path "../../emdi-lpu-groups/emdi-lpu-group/lpu-group-name";
            }
            description
              "Name of a bound board group.";
          }
        }
      }
      container emdi-history-records {
        description
          "List of query historical EMDI detection state.";
        list emdi-history-record {
          key "channel-name record-index direction";
          description
            "Query historical EMDI detection state.";
          leaf channel-name {
            type string {
              length "1..31";
            }
            description
              "Channel name.";
          }
          leaf record-index {
            type uint16 {
              range "0..1000";
            }
            description
              "Index of each detection message. The value 0 indicates that no abnormal flow.";
          }
          leaf direction {
            type enumeration {
              enum "inbound" {
                value 0;
                description
                  "Inbound.";
              }
              enum "outbound" {
                value 1;
                description
                  "Outbound.";
              }
            }
            description
              "Specify the direction of EMDI.";
          }
          leaf record-time {
            type string {
              length "1..19";
            }
            description
              "Time when each piece of information is detected.";
          }
          leaf monitor-period {
            type enumeration {
              enum "second-10s" {
                value 10;
                description
                  "Monitor period is 10 second.";
              }
              enum "second-30s" {
                value 30;
                description
                  "Monitor period is 30 second.";
              }
              enum "second-60s" {
                value 60;
                description
                  "Monitor period is 60 second.";
              }
            }
            description
              "Detection period of each detection message.";
          }
          leaf monitor-status {
            type enumeration {
              enum "normal" {
                value 0;
                description
                  "Status normal.";
              }
              enum "car-drop" {
                value 1;
                description
                  "Status abnormal, NP drop.";
              }
              enum "rate-only" {
                value 2;
                description
                  "Only the rate of video streams is detected.";
              }
            }
            description
              "Detection status of each detection message.";
          }
          leaf receive-packet {
            type uint64;
            description
              "Number of received packets.";
          }
          leaf rate-pps {
            type uint64;
            units "pps";
            description
              "Rate (pps) at which packets are received.";
          }
          leaf rate-bps {
            type uint64;
            units "bit/s";
            description
              "Rate (bit/s) at which packets are received.";
          }
          leaf lost-packet {
            type uint64;
            description
              "Number of lost packets on a channel.";
          }
          leaf disorder-packet {
            type uint64;
            description
              "Number of disordered packets.";
          }
          leaf rtp-lr {
            type uint32;
            units "0.001 %";
            description
              "Packet loss rate of a channel.";
          }
          leaf rtp-ser {
            type uint32;
            units "0.001 %";
            description
              "Check the channel disorder rate.";
          }
          leaf rtp-jitter {
            type string {
              length "1..9";
            }
            description
              "Check the jitter of the channel.";
          }
          leaf slot-id {
            type string {
              length "1..15";
            }
            description
              "Slot ID.";
            ext:support-filter "true";
          }
          leaf interface-name {
            type string {
              length "1..63";
            }
            description
              "Interface name.";
          }
          leaf latest-rate {
            type uint64;
            units "pps";
            description
              "Latest rate.";
          }
          leaf latest-detect-time {
            type yang:date-and-time;
            description
              "Latest detect time.";
          }
        }
      }
      container bier-history-records {
        description
          "List of query historical BIER EMDI detection state.";
        list bier-history-record {
          key "source-address group-address vpn-label bfir-id sub-domain bsl si record-index slot-id";
          description
            "Query historical BIER EMDI detection state.";
          leaf source-address {
            type inet:ipv4-address-no-zone;
            description
              "Multicast IP source address.";
          }
          leaf group-address {
            type inet:ipv4-address-no-zone;
            description
              "Multicast IP address.";
          }
          leaf vpn-label {
            type uint32;
            description
              "Vpn label of vpn in bier.";
          }
          leaf bfir-id {
            type uint16;
            description
              "Bit forwarding router ID.";
          }
          leaf sub-domain {
            type uint16 {
              range "0..255";
            }
            description
              "Bier sub domain.";
          }
          leaf bsl {
            type enumeration {
              enum "bsl-64" {
                value 64;
                description
                  "The bit string length is 64.";
              }
              enum "bsl-128" {
                value 128;
                description
                  "The bit string length is 128.";
              }
              enum "bsl-256" {
                value 256;
                description
                  "The bit string length is 256.";
              }
            }
            description
              "Bit string length.";
          }
          leaf si {
            type uint16 {
              range "0..255";
            }
            description
              "Set identifier.";
          }
          leaf record-index {
            type uint16 {
              range "0..1000";
            }
            description
              "Index of each detection message. The value 0 indicates that no abnormal flow.";
          }
          leaf slot-id {
            type string {
              length "1..15";
            }
            description
              "Slot ID.";
          }
          leaf record-time {
            type string {
              length "1..19";
            }
            description
              "Time when each piece of information is detected.";
          }
          leaf monitor-period {
            type enumeration {
              enum "second-10s" {
                value 10;
                description
                  "Monitor period is 10 second.";
              }
              enum "second-30s" {
                value 30;
                description
                  "Monitor period is 30 second.";
              }
              enum "second-60s" {
                value 60;
                description
                  "Monitor period is 60 second.";
              }
            }
            description
              "Detection period of each detection message.";
          }
          leaf monitor-status {
            type enumeration {
              enum "normal" {
                value 0;
                description
                  "Status normal.";
              }
              enum "car-drop" {
                value 1;
                description
                  "Status abnormal, NP drop.";
              }
              enum "rate-only" {
                value 2;
                description
                  "Only the rate of video streams is detected.";
              }
            }
            description
              "Detection status of each detection message.";
          }
          leaf receive-packet {
            type uint64;
            description
              "Number of received packets.";
          }
          leaf rate-pps {
            type uint64;
            units "pps";
            description
              "Rate (pps) at which packets are received.";
          }
          leaf rate-bps {
            type uint64;
            units "bit/s";
            description
              "Rate (bit/s) at which packets are received.";
          }
          leaf lost-packet {
            type uint64;
            description
              "Number of lost packets on a channel.";
          }
          leaf disorder-packet {
            type uint64;
            description
              "Number of disordered packets.";
          }
          leaf rtp-lr {
            type uint32;
            units "0.001 %";
            description
              "Packet loss rate of a channel.";
          }
          leaf rtp-ser {
            type uint32;
            units "0.001 %";
            description
              "Check the channel disorder rate.";
          }
          leaf latest-rate {
            type uint64;
            units "pps";
            description
              "Latest rate.";
          }
          leaf latest-detect-time {
            type yang:date-and-time;
            description
              "Latest detect time.";
          }
        }
      }
      container bier-out-history-records {
        description
          "List of query historical BIER EMDI out detection state.";
        list bier-out-history-record {
          key "source-address group-address vpn-label bfir-id sub-domain bsl si record-index slot-id interface-name token";
          description
            "Query historical BIER EMDI out detection state.";
          leaf source-address {
            type inet:ipv4-address-no-zone;
            description
              "Multicast IP source address.";
          }
          leaf group-address {
            type inet:ipv4-address-no-zone;
            description
              "Multicast IP address.";
          }
          leaf vpn-label {
            type uint32;
            description
              "Vpn label of vpn in bier.";
          }
          leaf bfir-id {
            type uint16;
            description
              "Bit forwarding router ID.";
          }
          leaf sub-domain {
            type uint16 {
              range "0..255";
            }
            description
              "Bier sub domain.";
          }
          leaf bsl {
            type enumeration {
              enum "bsl-64" {
                value 64;
                description
                  "The bit string length is 64.";
              }
              enum "bsl-128" {
                value 128;
                description
                  "The bit string length is 128.";
              }
              enum "bsl-256" {
                value 256;
                description
                  "The bit string length is 256.";
              }
            }
            description
              "Bit string length.";
          }
          leaf si {
            type uint16 {
              range "0..255";
            }
            description
              "Set identifier.";
          }
          leaf record-index {
            type uint16 {
              range "0..1000";
            }
            description
              "Index of each detection message. The value 0 indicates that no abnormal flow.";
          }
          leaf slot-id {
            type string {
              length "1..15";
            }
            description
              "Slot ID.";
          }
          leaf interface-name {
            type string {
              length "1..63";
            }
            description
              "Interface name.";
          }
          leaf token {
            type uint32;
            description
              "Multicast leaf token.";
          }
          leaf record-time {
            type string {
              length "1..19";
            }
            description
              "Time when each piece of information is detected.";
          }
          leaf monitor-period {
            type enumeration {
              enum "second-10s" {
                value 10;
                description
                  "Monitor period is 10 second.";
              }
              enum "second-30s" {
                value 30;
                description
                  "Monitor period is 30 second.";
              }
              enum "second-60s" {
                value 60;
                description
                  "Monitor period is 60 second.";
              }
            }
            description
              "Detection period of each detection message.";
          }
          leaf monitor-status {
            type enumeration {
              enum "normal" {
                value 0;
                description
                  "Status normal.";
              }
              enum "car-drop" {
                value 1;
                description
                  "Status abnormal, NP drop.";
              }
              enum "rate-only" {
                value 2;
                description
                  "Only the rate of video streams is detected.";
              }
            }
            description
              "Detection status of each detection message.";
          }
          leaf receive-packet {
            type uint64;
            description
              "Number of received packets.";
          }
          leaf rate-pps {
            type uint64;
            units "pps";
            description
              "Rate (pps) at which packets are received.";
          }
          leaf rate-bps {
            type uint64;
            units "bit/s";
            description
              "Rate (bit/s) at which packets are received.";
          }
          leaf lost-packet {
            type uint64;
            description
              "Number of lost packets on a channel.";
          }
          leaf disorder-packet {
            type uint64;
            description
              "Number of disordered packets.";
          }
          leaf rtp-lr {
            type uint32;
            units "0.001 %";
            description
              "Packet loss rate of a channel.";
          }
          leaf rtp-ser {
            type uint32;
            units "0.001 %";
            description
              "Check the channel disorder rate.";
          }
          leaf latest-rate {
            type uint64;
            units "pps";
            description
              "Latest rate.";
          }
          leaf latest-detect-time {
            type yang:date-and-time;
            description
              "Latest detect time.";
          }
        }
      }
      container emdi-channels {
        description
          "List of Channel state.";
        list emdi-channel {
          key "channel-name";
          description
            "Channel state.";
          leaf channel-name {
            type string {
              length "1..31";
            }
            description
              "Channel name.";
          }
        }
      }
      container emdi-telem-reps {
        description
          "List of EMDI Telemetry IPTV Report Yang Models state.";
        list emdi-telem-rep {
          key "vr-id channel-name";
          description
            "EMDI Telemetry IPTV Report Yang Model state.";
          leaf vr-id {
            type uint32 {
              range "0..32";
            }
            description
              "Index of the VR that the channel belongs to.";
          }
          leaf channel-name {
            type emdi:live_ncs_channel-ref;
            description
              "Name of the multicast channel.";
          }
          leaf channel-source-address {
            type inet:ipv4-address-no-zone;
            description
              "IPv4 source adddress of the multicast channel.";
          }
          leaf channel-group-address {
            type inet:ipv4-address-no-zone;
            description
              "IPv4 group adddress of the multicast channel.";
          }
          leaf channel-vpn-type {
            type uint32 {
              range "0..4";
            }
            description
              "The VPN type that the multicast channel belongs to.";
          }
          leaf vpn-name {
            type string {
              length "1..31";
            }
            description
              "The L3VPN name of the multicast channel.";
          }
          leaf vlan-id {
            type uint32 {
              range "0..65535";
            }
            description
              "The L2VPN VLAN Id of the multicast channel.";
          }
          leaf vsi-name {
            type string {
              length "1..31";
            }
            description
              "The L2VPN VSI name of the multicast channel.";
          }
          leaf bd-id {
            type uint32 {
              range "0..16777215";
            }
            description
              "The L2VPN BD name of the multicast channel.";
          }
          leaf report-period {
            type uint32 {
              range "0..65535";
            }
            units "s";
            description
              "The EMDI statistics data report period.";
          }
          leaf report-time {
            type uint64;
            units "s";
            description
              "The report time of current report period.";
          }
          leaf total-recv-packets {
            type uint64;
            description
              "The total received RTP packets number in current report period.";
          }
          leaf total-loss-packets {
            type uint64;
            description
              "The total lost RTP packets number in current report period.";
          }
          leaf total-disorderd-packets {
            type uint64;
            description
              "The total disordered RTP packets number in current report period.";
          }
          leaf monitor-period {
            type uint32 {
              range "0..65535";
            }
            units "s";
            description
              "The EMDI statistics data monitor period.";
          }
          leaf monitor-time {
            type uint64;
            units "s";
            description
              "The start time of current monitor period.";
          }
          leaf worst-recv-packets {
            type uint64;
            description
              "The received RTP packets number in the worst monitor period in current report period.";
          }
          leaf worst-loss-packets {
            type uint64;
            description
              "The lost RTP packets number in the worst monitor period in current report period.";
          }
          leaf worst-disorderd-packets {
            type uint64;
            description
              "The disordered RTP packets number in the worst monitor period in current report period.";
          }
        }
      }
      container emdi-telem-rtps {
        description
          "List of EMDI Telemetry RTP Report Yang Models state.";
        list emdi-telem-rtp {
          key "vr-id channel-name";
          description
            "EMDI Telemetry RTP Report Yang Model state.";
          leaf vr-id {
            type uint32 {
              range "0..32";
            }
            description
              "Index of the VR that the channel belongs to.";
          }
          leaf channel-name {
            type emdi:live_ncs_channel-ref;
            description
              "Name of the multicast channel.";
          }
          leaf channel-source-address {
            type inet:ipv4-address-no-zone;
            description
              "IPv4 source adddress of the multicast channel.";
          }
          leaf channel-group-address {
            type inet:ipv4-address-no-zone;
            description
              "IPv4 group adddress of the multicast channel.";
          }
          leaf channel-vpn-type {
            type uint32 {
              range "0..4";
            }
            description
              "The VPN type that the multicast channel belongs to.";
          }
          leaf vpn-name {
            type string {
              length "1..31";
            }
            description
              "The L3VPN name of the multicast channel.";
          }
          leaf vlan-id {
            type uint32 {
              range "0..65535";
            }
            description
              "The L2VPN VLAN Id of the multicast channel.";
          }
          leaf vsi-name {
            type string {
              length "1..31";
            }
            description
              "The L2VPN VSI name of the multicast channel.";
          }
          leaf bd-id {
            type uint32 {
              range "0..16777215";
            }
            description
              "The L2VPN BD name of the multicast channel.";
          }
          leaf report-period {
            type uint32 {
              range "0..65535";
            }
            units "s";
            description
              "The EMDI statistics data report period.";
          }
          leaf report-time {
            type uint64;
            units "s";
            description
              "The report time of current report period.";
          }
          leaf recv-packets {
            type uint64;
            description
              "The received RTP packets number in current report period.";
          }
          leaf loss-packets {
            type uint64;
            description
              "The lost RTP packets number in current report period.";
          }
          leaf disorderd-packets {
            type uint64;
            description
              "The disordered RTP packets number in current report period.";
          }
          leaf monitor-period {
            type uint32 {
              range "0..65535";
            }
            units "s";
            description
              "The EMDI statistics data monitor period.";
          }
          leaf monitor-time {
            type uint64;
            units "s";
            description
              "The start time of current monitor period.";
          }
        }
      }
      container out-telem-reps {
        description
          "List of outbound EMDI Telemetry IPTV Report Yang Models state.";
        list out-telem-rep {
          key "vr-id channel-name slot-id";
          description
            "Outbound EMDI Telemetry IPTV Report Yang Model state.";
          leaf vr-id {
            type uint32;
            description
              "Index of the VR that the channel belongs to.";
          }
          leaf channel-name {
            type emdi:live_ncs_channel-ref;
            description
              "Name of the multicast channel.";
          }
          leaf slot-id {
            type string {
              length "1..15";
            }
            description
              "Slot name of the multicast channel.";
          }
          leaf channel-source-address {
            type inet:ipv4-address-no-zone;
            description
              "IPv4 source adddress of the multicast channel.";
          }
          leaf channel-group-address {
            type inet:ipv4-address-no-zone;
            description
              "IPv4 group adddress of the multicast channel.";
          }
          leaf channel-vpn-type {
            type uint32 {
              range "0..1";
            }
            description
              "The VPN type that the multicast channel belongs to.";
          }
          leaf vpn-name {
            type string {
              length "1..31";
            }
            description
              "The L3VPN name of the multicast channel.";
          }
          leaf interface-name {
            type string {
              length "1..63";
            }
            description
              "Interface name of the multicast channel.";
          }
          leaf report-period {
            type uint32 {
              range "0..65535";
            }
            units "s";
            description
              "The EMDI statistics data report period.";
          }
          leaf report-time {
            type uint64;
            units "s";
            description
              "The report time of current report period.";
          }
          leaf total-recv-packets {
            type uint64;
            description
              "The total received REP packets number in current report period.";
          }
          leaf total-loss-packets {
            type uint64;
            description
              "The total lost REP packets number in current report period.";
          }
          leaf total-disorderd-packets {
            type uint64;
            description
              "The total disordered REP packets number in current report period.";
          }
          leaf monitor-period {
            type uint32 {
              range "0..65535";
            }
            units "s";
            description
              "The EMDI statistics data monitor period.";
          }
          leaf monitor-time {
            type uint64;
            units "s";
            description
              "The start time of current monitor period.";
          }
          leaf worst-recv-packets {
            type uint64;
            description
              "The received REP packets number in the worst monitor period in current report period.";
          }
          leaf worst-loss-packets {
            type uint64;
            description
              "The lost REP packets number in the worst monitor period in current report period.";
          }
          leaf worst-disorderd-packets {
            type uint64;
            description
              "The disordered REP packets number in the worst monitor period in current report period.";
          }
        }
      }
      container bier-telem-reps {
        description
          "List of EMDI BIER telemetry IPTV report state.";
        list bier-telem-rep {
          key "vr-id source-address group-address vpn-label sub-domain bsl si bfr-id slot-id";
          description
            "EMDI BIER telemetry IPTV report state.";
          leaf vr-id {
            type uint32;
            description
              "Index of the VR that the channel belongs to.";
          }
          leaf source-address {
            type inet:ipv4-address-no-zone;
            description
              "IPv4 source adddress of the multicast channel.";
          }
          leaf group-address {
            type inet:ipv4-address-no-zone;
            description
              "IPv4 group adddress of the multicast channel.";
          }
          leaf vpn-label {
            type uint32 {
              range "0..1048575";
            }
            description
              "The VPN label that the multicast channel belongs to.";
          }
          leaf sub-domain {
            type uint16 {
              range "0..255";
            }
            description
              "The sub domain of the bier multicast.";
          }
          leaf bsl {
            type enumeration {
              enum "bsl-64" {
                value 64;
                description
                  "The bit string length is 64.";
              }
              enum "bsl-128" {
                value 128;
                description
                  "The bit string length is 128.";
              }
              enum "bsl-256" {
                value 256;
                description
                  "The bit string length is 256.";
              }
            }
            description
              "Bit string length.";
          }
          leaf si {
            type uint16 {
              range "0..255";
            }
            description
              "Index of each detection message.";
          }
          leaf bfr-id {
            type uint16 {
              range "1..65535";
            }
            description
              "Bit forwarding router (BFR) ID.";
          }
          leaf slot-id {
            type string {
              length "1..15";
            }
            description
              "Slot name of the multicast channel.";
          }
          leaf report-period {
            type uint32 {
              range "0..65535";
            }
            units "s";
            description
              "The EMDI statistics data report period.";
          }
          leaf report-time {
            type uint64;
            units "s";
            description
              "The report time of current report period.";
          }
          leaf total-recv-packets {
            type uint64;
            description
              "The total received RTP packets number in current report period.";
          }
          leaf total-loss-packets {
            type uint64;
            description
              "The total lost RTP packets number in current report period.";
          }
          leaf total-disorderd-packets {
            type uint64;
            description
              "The total disordered RTP packets number in current report period.";
          }
          leaf monitor-period {
            type enumeration {
              enum "second-10s" {
                value 10;
                description
                  "Monitor period is 10 second.";
              }
              enum "second-30s" {
                value 30;
                description
                  "Monitor period is 30 second.";
              }
              enum "second-60s" {
                value 60;
                description
                  "Monitor period is 60 second.";
              }
            }
            description
              "The EMDI statistics data monitor period.";
          }
          leaf monitor-time {
            type uint64;
            units "s";
            description
              "The start time of current monitor period.";
          }
          leaf worst-recv-packets {
            type uint64;
            description
              "The received RTP packets number in the worst monitor period in current report period.";
          }
          leaf worst-loss-packets {
            type uint64;
            description
              "The lost RTP packets number in the worst monitor period in current report period.";
          }
          leaf worst-disorderd-packets {
            type uint64;
            description
              "The disordered RTP packets number in the worst monitor period in current report period.";
          }
          leaf vpn-name {
            type string {
              length "1..31";
            }
            description
              "The L3VPN name of the multicast channel.";
          }
        }
      }
      container bier-telem-rtps {
        description
          "List of EMDI telemetry RTP report state.";
        list bier-telem-rtp {
          key "vr-id source-address group-address vpn-label sub-domain bsl si bfr-id slot-id";
          description
            "EMDI BIER telemetry RTP report state.";
          leaf vr-id {
            type uint32;
            description
              "Index of the VR that the channel belongs to.";
          }
          leaf source-address {
            type inet:ipv4-address-no-zone;
            description
              "IPv4 source adddress of the multicast channel.";
          }
          leaf group-address {
            type inet:ipv4-address-no-zone;
            description
              "IPv4 group adddress of the multicast channel.";
          }
          leaf vpn-label {
            type uint32 {
              range "0..1048575";
            }
            description
              "The VPN label that the multicast channel belongs to.";
          }
          leaf sub-domain {
            type uint16 {
              range "0..255";
            }
            description
              "The sub domain of the bier multicast.";
          }
          leaf bsl {
            type enumeration {
              enum "bsl-64" {
                value 64;
                description
                  "The bit string length is 64.";
              }
              enum "bsl-128" {
                value 128;
                description
                  "The bit string length is 128.";
              }
              enum "bsl-256" {
                value 256;
                description
                  "The bit string length is 256.";
              }
            }
            description
              "Bit string length.";
          }
          leaf si {
            type uint16 {
              range "0..255";
            }
            description
              "Index of each detection message.";
          }
          leaf bfr-id {
            type uint16 {
              range "1..65535";
            }
            description
              "Bit forwarding router (BFR) ID.";
          }
          leaf slot-id {
            type string {
              length "1..15";
            }
            description
              "Slot name of the multicast channel.";
          }
          leaf report-period {
            type uint32 {
              range "0..65535";
            }
            units "s";
            description
              "The EMDI statistics data report period.";
          }
          leaf report-time {
            type uint64;
            units "s";
            description
              "The report time of current report period.";
          }
          leaf recv-packets {
            type uint64;
            description
              "The received RTP packets number in current report period.";
          }
          leaf loss-packets {
            type uint64;
            description
              "The lost RTP packets number in current report period.";
          }
          leaf disorderd-packets {
            type uint64;
            description
              "The disordered RTP packets number in current report period.";
          }
          leaf monitor-period {
            type enumeration {
              enum "second-10s" {
                value 10;
                description
                  "Monitor period is 10 second.";
              }
              enum "second-30s" {
                value 30;
                description
                  "Monitor period is 30 second.";
              }
              enum "second-60s" {
                value 60;
                description
                  "Monitor period is 60 second.";
              }
            }
            description
              "The EMDI statistics data monitor period.";
          }
          leaf monitor-time {
            type uint64;
            units "s";
            description
              "The start time of current monitor period.";
          }
          leaf vpn-name {
            type string {
              length "1..31";
            }
            description
              "The L3VPN name of the multicast channel.";
          }
        }
      }
      container bier-out-telem-reps {
        description
          "List of outbound EMDI telemetry IPTV report state.";
        list bier-out-telem-rep {
          key "vr-id source-address group-address vpn-label sub-domain bsl si bfr-id interface-name slot-id";
          description
            "Outbound EMDI BIER telemetry IPTV report state.";
          leaf vr-id {
            type uint32;
            description
              "Index of the VR that the channel belongs to.";
          }
          leaf source-address {
            type inet:ipv4-address-no-zone;
            description
              "IPv4 source adddress of the multicast channel.";
          }
          leaf group-address {
            type inet:ipv4-address-no-zone;
            description
              "IPv4 group adddress of the multicast channel.";
          }
          leaf vpn-label {
            type uint32 {
              range "0..1048575";
            }
            description
              "The VPN label that the multicast channel belongs to.";
          }
          leaf sub-domain {
            type uint16 {
              range "0..255";
            }
            description
              "The sub domain of the bier multicast.";
          }
          leaf bsl {
            type enumeration {
              enum "bsl-64" {
                value 64;
                description
                  "The bit string length is 64.";
              }
              enum "bsl-128" {
                value 128;
                description
                  "The bit string length is 128.";
              }
              enum "bsl-256" {
                value 256;
                description
                  "The bit string length is 256.";
              }
            }
            description
              "Bit string length.";
          }
          leaf si {
            type uint16 {
              range "0..255";
            }
            description
              "Index of each detection message.";
          }
          leaf bfr-id {
            type uint16 {
              range "1..65535";
            }
            description
              "Bit forwarding router (BFR) ID.";
          }
          leaf interface-name {
            type string {
              length "1..63";
            }
            description
              "Interface name of the multicast channel.";
          }
          leaf slot-id {
            type string {
              length "1..15";
            }
            description
              "Slot name of the multicast channel.";
          }
          leaf report-period {
            type uint32 {
              range "0..65535";
            }
            units "s";
            description
              "The EMDI statistics data report period.";
          }
          leaf report-time {
            type uint64;
            units "s";
            description
              "The report time of current report period.";
          }
          leaf total-recv-packets {
            type uint64;
            description
              "The total received REP packets number in current report period.";
          }
          leaf total-loss-packets {
            type uint64;
            description
              "The total lost REP packets number in current report period.";
          }
          leaf total-disorderd-packets {
            type uint64;
            description
              "The total disordered REP packets number in current report period.";
          }
          leaf monitor-period {
            type enumeration {
              enum "second-10s" {
                value 10;
                description
                  "Monitor period is 10 second.";
              }
              enum "second-30s" {
                value 30;
                description
                  "Monitor period is 30 second.";
              }
              enum "second-60s" {
                value 60;
                description
                  "Monitor period is 60 second.";
              }
            }
            description
              "The EMDI statistics data monitor period.";
          }
          leaf monitor-time {
            type uint64;
            units "s";
            description
              "The start time of current monitor period.";
          }
          leaf worst-recv-packets {
            type uint64;
            description
              "The received REP packets number in the worst monitor period in current report period.";
          }
          leaf worst-loss-packets {
            type uint64;
            description
              "The lost REP packets number in the worst monitor period in current report period.";
          }
          leaf worst-disorderd-packets {
            type uint64;
            description
              "The disordered REP packets number in the worst monitor period in current report period.";
          }
          leaf vpn-name {
            type string {
              length "1..31";
            }
            description
              "The L3VPN name of the multicast channel.";
          }
        }
      }
      container bier-out-telem-rtps {
        description
          "List of outbound EMDI telemetry RTP report state.";
        list bier-out-telem-rtp {
          key "vr-id source-address group-address vpn-label sub-domain bsl si bfr-id interface-name slot-id";
          description
            "Outbound EMDI BIER telemetry RTP report state.";
          leaf vr-id {
            type uint32;
            description
              "Index of the VR that the channel belongs to.";
          }
          leaf source-address {
            type inet:ipv4-address-no-zone;
            description
              "IPv4 source adddress of the multicast channel.";
          }
          leaf group-address {
            type inet:ipv4-address-no-zone;
            description
              "IPv4 group adddress of the multicast channel.";
          }
          leaf vpn-label {
            type uint32 {
              range "0..1048575";
            }
            description
              "The VPN label that the multicast channel belongs to.";
          }
          leaf sub-domain {
            type uint16 {
              range "0..255";
            }
            description
              "The sub domain of the bier multicast.";
          }
          leaf bsl {
            type enumeration {
              enum "bsl-64" {
                value 64;
                description
                  "The bit string length is 64.";
              }
              enum "bsl-128" {
                value 128;
                description
                  "The bit string length is 128.";
              }
              enum "bsl-256" {
                value 256;
                description
                  "The bit string length is 256.";
              }
            }
            description
              "Bit string length.";
          }
          leaf si {
            type uint16 {
              range "0..255";
            }
            description
              "Index of each detection message.";
          }
          leaf bfr-id {
            type uint16 {
              range "1..65535";
            }
            description
              "Bit forwarding router (BFR) ID.";
          }
          leaf interface-name {
            type string {
              length "1..63";
            }
            description
              "Interface name of the multicast channel.";
          }
          leaf slot-id {
            type string {
              length "1..15";
            }
            description
              "Slot name of the multicast channel.";
          }
          leaf report-period {
            type uint32 {
              range "0..65535";
            }
            units "s";
            description
              "The EMDI statistics data report period.";
          }
          leaf report-time {
            type uint64;
            units "s";
            description
              "The report time of current report period.";
          }
          leaf recv-packets {
            type uint64;
            description
              "The received RTP packets number in current report period.";
          }
          leaf loss-packets {
            type uint64;
            description
              "The lost RTP packets number in current report period.";
          }
          leaf disorderd-packets {
            type uint64;
            description
              "The disordered RTP packets number in current report period.";
          }
          leaf monitor-period {
            type enumeration {
              enum "second-10s" {
                value 10;
                description
                  "Monitor period is 10 second.";
              }
              enum "second-30s" {
                value 30;
                description
                  "Monitor period is 30 second.";
              }
              enum "second-60s" {
                value 60;
                description
                  "Monitor period is 60 second.";
              }
            }
            description
              "The EMDI statistics data monitor period.";
          }
          leaf monitor-time {
            type uint64;
            units "s";
            description
              "The start time of current monitor period.";
          }
          leaf vpn-name {
            type string {
              length "1..31";
            }
            description
              "The L3VPN name of the multicast channel.";
          }
        }
      }
    }
  }
  augment "/ncs:devices/ncs:template/ncs:ned-id/ncs:config" {
    container emdi {
      description
        "On-board EMDI detection that obtains packet header information to sample multicast quality data.";
      container emdi-enable {
        presence "Enable EMDI";
        description
          "Enable/disable EMDI detection.";
        container emdi-global {
          description
            "Configure global EMDI attribute information.";
          leaf age-periods {
            type string;
            // NCS drop default statement
            description
              "Bier channel statistics age periods.";
          }
        }
        container emdi-channel-groups {
          description
            "List of configure channel group information. Multiple channels can be bound to a channel group.";
          list emdi-channel-group {
            // NCS patched for predictable order
            ordered-by user;
            key "channel-group-name";
            // NCS drop max-elements statement
            description
              "Configure channel group information. Multiple channels can be bound to a channel group.";
            leaf channel-group-name {
              type string;
              description
                "Channel group name.";
            }
            choice channel-type {
              description
                "Configure EMDI channel information.";
              case emdi-channel {
                description
                  "Configure channel information.";
                container emdi-channels {
                  description
                    "List of configure channel information.";
                  list emdi-channel {
                    // NCS patched for predictable order
                    ordered-by user;
                    key "channel-name";
                    // NCS drop max-elements statement
                    description
                      "Configure channel information. The group-address and source-address combination of different instances cannot overlap.";
                    leaf channel-name {
                      type string;
                      description
                        "Channel name.";
                    }
                    leaf source-address {
                      type string;
                      // NCS drop mandatory statement
                      description
                        "Multicast IP source address.";
                    }
                    leaf group-address {
                      type string;
                      // NCS drop mandatory statement
                      description
                        "Multicast IP address.";
                    }
                    choice channel-group-parameters {
                      description
                        "EMDI channel group parameters.";
                      case vpn-name {
                        description
                          "Specify the name of a VPN instance. Multicast traffic is bound to a VPN tunnel.";
                        leaf vpn-name {
                          type string;
                          // NCS drop must statement
                          description
                            "Specify the name of a VPN instance. Multicast traffic is bound to a VPN tunnel.";
                        }
                      }
                      case vlan-id {
                        description
                          "VLAN information. Multicast traffic is bound to VLANs.";
                        leaf vlan-id {
                          type string;
                          description
                            "VLAN information. Multicast traffic is bound to VLANs.";
                        }
                      }
                      case vsi-name {
                        description
                          "Name of a VSI. Multicast traffic is bound to a VSI tunnel.";
                        leaf vsi-name {
                          type string;
                          // NCS drop must statement
                          description
                            "Name of a VSI. Multicast traffic is bound to a VSI tunnel.";
                        }
                      }
                      case bd-id {
                        description
                          "DB information. Multicast traffic is bound to a BD.";
                        leaf bd-id {
                          type string;
                          description
                            "DB information. Multicast traffic is bound to a BD.";
                        }
                      }
                      case transit {
                        description
                          "In the P node scenario, enable the transit detection function to ensure that the P node detection function is proper.";
                        leaf transit {
                          type empty;
                          description
                            "In the P node scenario, enable the transit detection function to ensure that the P node detection function is proper.";
                        }
                      }
                    }
                    leaf pt-value {
                      type string;
                      // NCS drop must statement
                      // NCS drop default statement
                      description
                        "Payload type. Only payload type (PT) videos are detected.";
                    }
                    leaf clock-rate {
                      type string;
                      // NCS drop must statement
                      // NCS drop default statement
                      description
                        "Clock frequency information.";
                    }
                    leaf uncompressed {
                      type empty;
                      description
                        "Whether non-compressed multicast traffic detection is enabled.";
                    }
                  }
                }
              }
              case emdi-bier-channel {
                description
                  "Configure bier channel information.";
                container emdi-bier-channels {
                  description
                    "List of configure bier channel information.";
                  list emdi-bier-channel {
                    // NCS patched for predictable order
                    ordered-by user;
                    key "channel-name";
                    // NCS drop max-elements statement
                    description
                      "Configure bier channel information.";
                    leaf channel-name {
                      type string;
                      description
                        "Channel name.";
                    }
                    leaf source-address {
                      type string;
                      // NCS drop mandatory statement
                      description
                        "Multicast IP source address.";
                    }
                    leaf group-address {
                      type string;
                      // NCS drop mandatory statement
                      description
                        "Multicast IP address.";
                    }
                    leaf bier-vpn-name {
                      type string;
                      // NCS drop must statement
                      // NCS drop mandatory statement
                      description
                        "Specify the name of a VPN instance. Multicast traffic is bound to a VPN tunnel.";
                    }
                    leaf sub-domain {
                      type string;
                      // NCS drop mandatory statement
                      description
                        "The bier sub-domain.";
                    }
                    leaf bsl {
                      type string;
                      // NCS drop mandatory statement
                      description
                        "The bit string length.";
                    }
                  }
                }
              }
            }
          }
        }
        container emdi-lpu-groups {
          description
            "List of configure Board group information.";
          list emdi-lpu-group {
            // NCS patched for predictable order
            ordered-by user;
            key "lpu-group-name";
            // NCS drop max-elements statement
            description
              "Configure board group information.";
            ext:generated-by "system" {
              ext:filter "lpu-group-name='_default_'";
              description
                "The default board group named _default_ is automatically generated by the system.";
            }
            ext:operation-exclude "update" {
              ext:filter "lpu-group-name='_default_'";
              description
                "The default board group named _default_ cannot be updated.";
            }
            leaf lpu-group-name {
              type string;
              description
                "Board group name.";
            }
            choice bind-lpu {
              description
                "Bind slot <all> or <slot-number>.";
              case bind-all {
                description
                  "Bind slot <all>.";
                container bind-all {
                  description
                    "Configure bind slot <all>.";
                  leaf all {
                    type empty;
                    description
                      "Bind slot <all>.";
                  }
                }
              }
              case bind-slots {
                description
                  "Bind slot <slot-number>.";
                leaf-list slot {
                  // NCS patched for predictable order
                  ordered-by user;
                  type string;
                  // NCS drop max-elements statement
                  description
                    "Configure slot number.";
                }
              }
            }
          }
        }
        container channel-group-bind-lpu-groups {
          description
            "List of configure binding between a channel group and a board.";
          list channel-group-bind-lpu-group {
            // NCS patched for predictable order
            ordered-by user;
            key "lpu-group-name channel-group-name";
            unique "channel-group-name";
            // NCS drop max-elements statement
            description
              "Configure binding between a channel group and a board.";
            leaf lpu-group-name {
              type string;
              description
                "Name of a bound board group.";
            }
            leaf channel-group-name {
              type string;
              description
                "Name of a bound channel group.";
            }
          }
        }
        container outbound-channel-group-bind-lpu-groups {
          description
            "List of configure outbound binding between a channel group and a board.";
          list outbound-channel-group-bind-lpu-group {
            // NCS patched for predictable order
            ordered-by user;
            key "lpu-group-name channel-group-name";
            unique "channel-group-name";
            // NCS drop max-elements statement
            description
              "Configure outbound binding between a channel group and a board.";
            leaf lpu-group-name {
              type string;
              description
                "Name of a bound board group.";
            }
            leaf channel-group-name {
              type string;
              description
                "Name of a bound channel group.";
            }
          }
        }
        container bier-enable {
          description
            "Configure bier lpu group.";
          leaf lpu-group-name {
            type string;
            description
              "Name of a bound board group.";
          }
        }
      }
      // NCS drop config false container 'emdi-history-records'
      // NCS drop config false container 'bier-history-records'
      // NCS drop config false container 'bier-out-history-records'
      // NCS drop config false container 'emdi-channels'
      // NCS drop config false container 'emdi-telem-reps'
      // NCS drop config false container 'emdi-telem-rtps'
      // NCS drop config false container 'out-telem-reps'
      // NCS drop config false container 'bier-telem-reps'
      // NCS drop config false container 'bier-telem-rtps'
      // NCS drop config false container 'bier-out-telem-reps'
      // NCS drop config false container 'bier-out-telem-rtps'
    }
  }
}
