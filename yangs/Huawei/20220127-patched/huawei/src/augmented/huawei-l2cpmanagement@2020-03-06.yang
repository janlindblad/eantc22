module huawei-l2cpmanagement {
  // Generated by yanger -t ncs
  tailf:mount-id "huawei-nc-1.0:huawei-nc-1.0";
  tailf:ncs-device-type "netconf";

  namespace "urn:huawei:yang:huawei-l2cpmanagement";
  prefix l2cpmanagement;

  import huawei-ifm {
    prefix ifm;
  }
  import huawei-extension {
    prefix ext;
  }
  import huawei-l2vpn {
    prefix l2vpn;
  }
  ext:task-name "l2cpmanagement";

  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "L2 control protocol management.";

  revision 2020-03-06 {
    description
      "Change description.";
    reference "Huawei private.";
  }
  revision 2019-05-10 {
    description
      "Init revision.";
    reference "Huawei private.";
  }

  typedef ncs_template_global-action-status {
    type string;
    description
      "Global link protocol action.";
  }

  typedef ncs_template_action-status {
    type string;
    description
      "Link protocol action.";
  }

  typedef ncs_template_protocol-type {
    type string;
    description
      "Link protocol type.";
  }

  typedef ncs_rpc_notif_global-action-status {
    type enumeration {
      enum "forwarding" {
        value 1;
        description
          "Link protocol forwarding.";
      }
      enum "discard" {
        value 2;
        description
          "Link protocol discard.";
      }
    }
    description
      "Global link protocol action.";
  }

  typedef ncs_rpc_notif_action-status {
    type enumeration {
      enum "transport" {
        value 0;
        description
          "Link protocol transport.";
      }
      enum "forwarding" {
        value 1;
        description
          "Link protocol forwarding.";
      }
      enum "discard" {
        value 2;
        description
          "Link protocol discard.";
      }
    }
    description
      "Link protocol action.";
  }

  typedef ncs_rpc_notif_protocol-type {
    type enumeration {
      enum "bpdu" {
        value 13;
        description
          "Bridge Protocol Data Unit.";
      }
      enum "c-stp" {
        value 2;
        description
          "Customer Spanning Tree Protocol.";
      }
      enum "s-stp" {
        value 3;
        description
          "Provider Spanning Tree Protocol.";
      }
      enum "lacp" {
        value 5;
        description
          "Link Aggregation Marker Protocol.";
      }
      enum "lamp" {
        value 6;
        description
          "Link Aggregation Control Protocol.";
      }
      enum "lldp" {
        value 10;
        description
          "Link Layer Discovery Protocol.";
      }
      enum "eapol" {
        value 8;
        description
          "Port-Authentication Protocol(802.1X).";
      }
      enum "elmi" {
        value 4;
        description
          "Ethernet Local Management Interface Protocol.";
      }
      enum "link-oam" {
        value 14;
        description
          "Ethernet in the First Mile OAM (802.3AH).";
      }
      enum "esmc" {
        value 9;
        description
          "Synchronization Status Message Protocol (SSM).";
      }
      enum "ptp" {
        value 15;
        description
          "Precision Time Protocol (PTP-peer-delay).";
      }
      enum "mrp" {
        value 7;
        description
          "Multicast Registration Protocol (MRP).";
      }
    }
    description
      "Link protocol type.";
  }

  typedef live_ncs_global-action-status {
    type enumeration {
      enum "forwarding" {
        value 1;
        description
          "Link protocol forwarding.";
      }
      enum "discard" {
        value 2;
        description
          "Link protocol discard.";
      }
    }
    description
      "Global link protocol action.";
  }

  typedef live_ncs_action-status {
    type enumeration {
      enum "transport" {
        value 0;
        description
          "Link protocol transport.";
      }
      enum "forwarding" {
        value 1;
        description
          "Link protocol forwarding.";
      }
      enum "discard" {
        value 2;
        description
          "Link protocol discard.";
      }
    }
    description
      "Link protocol action.";
  }

  typedef live_ncs_protocol-type {
    type enumeration {
      enum "bpdu" {
        value 13;
        description
          "Bridge Protocol Data Unit.";
      }
      enum "c-stp" {
        value 2;
        description
          "Customer Spanning Tree Protocol.";
      }
      enum "s-stp" {
        value 3;
        description
          "Provider Spanning Tree Protocol.";
      }
      enum "lacp" {
        value 5;
        description
          "Link Aggregation Marker Protocol.";
      }
      enum "lamp" {
        value 6;
        description
          "Link Aggregation Control Protocol.";
      }
      enum "lldp" {
        value 10;
        description
          "Link Layer Discovery Protocol.";
      }
      enum "eapol" {
        value 8;
        description
          "Port-Authentication Protocol(802.1X).";
      }
      enum "elmi" {
        value 4;
        description
          "Ethernet Local Management Interface Protocol.";
      }
      enum "link-oam" {
        value 14;
        description
          "Ethernet in the First Mile OAM (802.3AH).";
      }
      enum "esmc" {
        value 9;
        description
          "Synchronization Status Message Protocol (SSM).";
      }
      enum "ptp" {
        value 15;
        description
          "Precision Time Protocol (PTP-peer-delay).";
      }
      enum "mrp" {
        value 7;
        description
          "Multicast Registration Protocol (MRP).";
      }
    }
    description
      "Link protocol type.";
  }

  typedef global-action-status {
    type enumeration {
      enum "forwarding" {
        value 1;
        description
          "Link protocol forwarding.";
      }
      enum "discard" {
        value 2;
        description
          "Link protocol discard.";
      }
    }
    description
      "Global link protocol action.";
  }

  typedef action-status {
    type enumeration {
      enum "transport" {
        value 0;
        description
          "Link protocol transport.";
      }
      enum "forwarding" {
        value 1;
        description
          "Link protocol forwarding.";
      }
      enum "discard" {
        value 2;
        description
          "Link protocol discard.";
      }
    }
    description
      "Link protocol action.";
  }

  typedef protocol-type {
    type enumeration {
      enum "bpdu" {
        value 13;
        description
          "Bridge Protocol Data Unit.";
      }
      enum "c-stp" {
        value 2;
        description
          "Customer Spanning Tree Protocol.";
      }
      enum "s-stp" {
        value 3;
        description
          "Provider Spanning Tree Protocol.";
      }
      enum "lacp" {
        value 5;
        description
          "Link Aggregation Marker Protocol.";
      }
      enum "lamp" {
        value 6;
        description
          "Link Aggregation Control Protocol.";
      }
      enum "lldp" {
        value 10;
        description
          "Link Layer Discovery Protocol.";
      }
      enum "eapol" {
        value 8;
        description
          "Port-Authentication Protocol(802.1X).";
      }
      enum "elmi" {
        value 4;
        description
          "Ethernet Local Management Interface Protocol.";
      }
      enum "link-oam" {
        value 14;
        description
          "Ethernet in the First Mile OAM (802.3AH).";
      }
      enum "esmc" {
        value 9;
        description
          "Synchronization Status Message Protocol (SSM).";
      }
      enum "ptp" {
        value 15;
        description
          "Precision Time Protocol (PTP-peer-delay).";
      }
      enum "mrp" {
        value 7;
        description
          "Multicast Registration Protocol (MRP).";
      }
    }
    description
      "Link protocol type.";
  }

  augment "/ncs:devices/ncs:device/ncs:config" {
    container l2cpmanagement {
      tailf:ncs-device-type "netconf";
      tailf:display-when "not(../../ncs:module) or ../../ncs:module[ncs:name='huawei-l2cpmanagement']";
      description
        "L2 control protocol management.";
      container link-protocol-global {
        description
          "Configure the global link protocol action.";
        leaf elmi-status {
          type global-action-status;
          default "discard";
          description
            "Specify Ethernet Local Management Interface Protocol (E-LMI) configuration information.";
        }
        leaf eoam3ah-status {
          type global-action-status;
          default "discard";
          description
            "Specify Ethernet in the First Mile OAM (802.3AH) configuration information.";
        }
        leaf linkoam-status {
          type global-action-status;
          default "discard";
          description
            "Specify Ethernet in the First Mile OAM (802.3AH) configuration information.";
        }
        leaf ptp-status {
          type global-action-status;
          default "discard";
          description
            "Specify Precision Time Protocol (PTP-peer-delay) configuration information.";
        }
        leaf bpdubridge-status {
          type global-action-status;
          default "discard";
          description
            "Specify bpdu bridge configuration information.";
        }
        leaf cstp-status {
          type global-action-status;
          default "forwarding";
          description
            "Specify Customer Spanning Tree Protocol (c-stp) configuration information.";
        }
      }
    }
  }
  augment "/ncs:devices/ncs:device/ncs:live-status" {
    container l2cpmanagement {
      tailf:ncs-device-type "netconf";
      tailf:display-when "not(../../ncs:module) or ../../ncs:module[ncs:name='huawei-l2cpmanagement'] or (../../ncs:live-status-protocol[not(ncs:capability)]) or (../../ncs:live-status-protocol/ncs:capability/ncs:module[.='huawei-l2cpmanagement'])";
      description
        "L2 control protocol management.";
      container link-protocol-global {
        description
          "Configure the global link protocol action.";
        leaf elmi-status {
          type live_ncs_global-action-status;
          // NCS drop default statement
          description
            "Specify Ethernet Local Management Interface Protocol (E-LMI) configuration information.";
        }
        leaf eoam3ah-status {
          type live_ncs_global-action-status;
          // NCS drop default statement
          description
            "Specify Ethernet in the First Mile OAM (802.3AH) configuration information.";
        }
        leaf linkoam-status {
          type live_ncs_global-action-status;
          // NCS drop default statement
          description
            "Specify Ethernet in the First Mile OAM (802.3AH) configuration information.";
        }
        leaf ptp-status {
          type live_ncs_global-action-status;
          // NCS drop default statement
          description
            "Specify Precision Time Protocol (PTP-peer-delay) configuration information.";
        }
        leaf bpdubridge-status {
          type live_ncs_global-action-status;
          // NCS drop default statement
          description
            "Specify bpdu bridge configuration information.";
        }
        leaf cstp-status {
          type live_ncs_global-action-status;
          // NCS drop default statement
          description
            "Specify Customer Spanning Tree Protocol (c-stp) configuration information.";
        }
      }
    }
  }
  augment "/ncs:devices/ncs:template/ncs:ned-id/ncs:config" {
    container l2cpmanagement {
      description
        "L2 control protocol management.";
      container link-protocol-global {
        description
          "Configure the global link protocol action.";
        leaf elmi-status {
          type ncs_template_global-action-status;
          // NCS drop default statement
          description
            "Specify Ethernet Local Management Interface Protocol (E-LMI) configuration information.";
        }
        leaf eoam3ah-status {
          type ncs_template_global-action-status;
          // NCS drop default statement
          description
            "Specify Ethernet in the First Mile OAM (802.3AH) configuration information.";
        }
        leaf linkoam-status {
          type ncs_template_global-action-status;
          // NCS drop default statement
          description
            "Specify Ethernet in the First Mile OAM (802.3AH) configuration information.";
        }
        leaf ptp-status {
          type ncs_template_global-action-status;
          // NCS drop default statement
          description
            "Specify Precision Time Protocol (PTP-peer-delay) configuration information.";
        }
        leaf bpdubridge-status {
          type ncs_template_global-action-status;
          // NCS drop default statement
          description
            "Specify bpdu bridge configuration information.";
        }
        leaf cstp-status {
          type ncs_template_global-action-status;
          // NCS drop default statement
          description
            "Specify Customer Spanning Tree Protocol (c-stp) configuration information.";
        }
      }
    }
  }
  augment "/ncs:devices/ncs:template/ncs:ned-id/ncs:config/ifm:ifm/ifm:interfaces/ifm:interface" {
    description
      "Interface link protocol actions.";
    container protocol-actions {
      // NCS drop when statement
      description
        "List of the interface link protocol actions.";
      list protocol-action {
        // NCS patched for predictable order
        ordered-by user;
        // NCS drop must statement
        key "protocol-type";
        description
          "Configure the link protocol action.";
        leaf protocol-type {
          type ncs_template_protocol-type;
          description
            "Protocol type.";
        }
        leaf action {
          type ncs_template_action-status;
          // NCS drop mandatory statement
          description
            "Protocol action.";
        }
      }
    }
  }
  augment "/ncs:devices/ncs:device/ncs:live-status/ifm:ifm/ifm:interfaces/ifm:interface" {
    description
      "Interface link protocol actions.";
    container protocol-actions {
      tailf:ncs-device-type "netconf";
      tailf:display-when "not(../../../../../ncs:module) or ../../../../../ncs:module[ncs:name='huawei-l2cpmanagement'] or (../../../../../ncs:live-status-protocol[not(ncs:capability)]) or (../../../../../ncs:live-status-protocol/ncs:capability/ncs:module[.='huawei-l2cpmanagement'])";
      // NCS drop when statement
      description
        "List of the interface link protocol actions.";
      list protocol-action {
        // NCS drop must statement
        key "protocol-type";
        description
          "Configure the link protocol action.";
        leaf protocol-type {
          type live_ncs_protocol-type;
          description
            "Protocol type.";
        }
        leaf action {
          type live_ncs_action-status;
          // NCS drop mandatory statement
          description
            "Protocol action.";
        }
      }
    }
  }
  augment "/ncs:devices/ncs:device/ncs:config/ifm:ifm/ifm:interfaces/ifm:interface" {
    description
      "Interface link protocol actions.";
    container protocol-actions {
      tailf:ncs-device-type "netconf";
      tailf:display-when "not(../../../../../ncs:module) or ../../../../../ncs:module[ncs:name='huawei-l2cpmanagement']";
      when "(../ifm:class='main-interface') and (../ifm:type='Ethernet' or ../ifm:type='GigabitEthernet' or ../ifm:type='Eth-Trunk' or ../ifm:type='100GE' or ../ifm:type='XGigabitEthernet' or ../ifm:type='40GE' or ../ifm:type='10GE' or ../ifm:type='400GE' or ../ifm:type='25GE' or ../ifm:type='FlexE' or ../ifm:type='50GE' or ../ifm:type='50|100GE')" {
        tailf:xpath-root 3;
      }
      description
        "List of the interface link protocol actions.";
      list protocol-action {
        must "(((action='discard') and (protocol-type='lacp' or protocol-type='lamp') and ((/l2vpn:l2vpn/l2vpn:instances/l2vpn:instance/l2vpn:vpws-ldp/l2vpn:acs/l2vpn:ac[l2vpn:interface-name=current()/../../ifm:name]/l2vpn:access-port) or (/l2vpn:l2vpn/l2vpn:instances/l2vpn:instance/l2vpn:vpws-local-ccc/l2vpn:acs/l2vpn:ac[l2vpn:interface-name=current()/../../ifm:name]/l2vpn:access-port))) or ((action='forwarding') and (protocol-type='lacp' or protocol-type='lamp') and (not((/l2vpn:l2vpn/l2vpn:instances/l2vpn:instance/l2vpn:vpws-ldp/l2vpn:acs/l2vpn:ac[l2vpn:interface-name=current()/../../ifm:name]/l2vpn:access-port) or (/l2vpn:l2vpn/l2vpn:instances/l2vpn:instance/l2vpn:vpws-local-ccc/l2vpn:acs/l2vpn:ac[l2vpn:interface-name=current()/../../ifm:name]/l2vpn:access-port)))) or (protocol-type!='lacp' and protocol-type!='lamp'))" {
          tailf:xpath-root 3;
        }
        key "protocol-type";
        description
          "Configure the link protocol action.";
        leaf protocol-type {
          type protocol-type;
          description
            "Protocol type.";
        }
        leaf action {
          type action-status;
          mandatory true;
          description
            "Protocol action.";
        }
      }
    }
  }
}
