module huawei-ifm-trunk-notification {
  // Generated by yanger -t ncs
  tailf:mount-id "huawei-nc-1.0:huawei-nc-1.0";
  tailf:ncs-device-type "netconf";

  yang-version 1;
  namespace "urn:huawei:yang:huawei-ifm-trunk-notification";
  prefix ifm-trunk-notification;

  import huawei-pub-type {
    prefix pub-type;
  }
  import huawei-extension {
    prefix ext;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Notification of ifm-trunk.";

  revision 2020-08-12 {
    description
      "Initial revision.";
    reference "Huawei private.";
  }
  ext:task-name "trunk";

  typedef ncs_template_port-status {
    type string;
    description
      "Interface suppression status.";
  }

  typedef ncs_rpc_notif_port-status {
    type enumeration {
      enum "up" {
        value 1;
        description
          "The interface is in Up state.";
      }
      enum "down" {
        value 2;
        description
          "The interface is in Down state.";
      }
    }
    description
      "Interface suppression status.";
  }

  typedef live_ncs_port-status {
    type enumeration {
      enum "up" {
        value 1;
        description
          "The interface is in Up state.";
      }
      enum "down" {
        value 2;
        description
          "The interface is in Down state.";
      }
    }
    description
      "Interface suppression status.";
  }

  typedef port-status {
    type enumeration {
      enum "up" {
        value 1;
        description
          "The interface is in Up state.";
      }
      enum "down" {
        value 2;
        description
          "The interface is in Down state.";
      }
    }
    description
      "Interface suppression status.";
  }

  augment "/ncs:devices/ncs:device/ncs:notifications/ncs:received-notifications/ncs:notification/ncs:data" {
    container trunk-bandwidth-change {
      presence "";
      config false;
      description
        "The trunk interface bandwidth changes.";
      leaf trunk-name {
        type pub-type:ncs_rpc_notif_if-name;
        // NCS drop mandatory statement
        description
          "Name of the trunk interface.";
      }
      leaf old-bandwidth {
        type uint64;
        units "bit/s";
        // NCS drop mandatory statement
        description
          "Old bandwidth of the trunk interface.";
      }
      leaf new-bandwidth {
        type uint64;
        units "bit/s";
        // NCS drop mandatory statement
        description
          "New bandwidth of the trunk interface.";
      }
    }
  }
  augment "/ncs:devices/ncs:device/ncs:notifications/ncs:received-notifications/ncs:notification/ncs:data" {
    container trunk-status-change {
      presence "";
      config false;
      description
        "The trunk interface status changes.";
      leaf trunk-name {
        type pub-type:ncs_rpc_notif_if-name;
        // NCS drop mandatory statement
        description
          "Name of the trunk interface.";
      }
      leaf trunk-index {
        type uint32;
        // NCS drop mandatory statement
        description
          "Trunk index.";
      }
      leaf trunk-admin-status {
        type ncs_rpc_notif_port-status;
        // NCS drop mandatory statement
        description
          "Administration status of trunk interface.";
      }
      leaf trunk-status {
        type ncs_rpc_notif_port-status;
        // NCS drop mandatory statement
        description
          "Status of trunk interface.";
      }
    }
  }
  augment "/ncs:devices/ncs:device/ncs:notifications/ncs:received-notifications/ncs:notification/ncs:data" {
    container member-number-change {
      presence "";
      config false;
      description
        "The number of active trunk member interfaces changed.";
      leaf trunk-name {
        type pub-type:ncs_rpc_notif_if-name;
        // NCS drop mandatory statement
        description
          "Name of the trunk interface.";
      }
      leaf port-name {
        type pub-type:ncs_rpc_notif_if-name;
        // NCS drop mandatory statement
        description
          "Name of the trunk member interface.";
      }
      leaf trunk-mem-number {
        type uint32;
        // NCS drop mandatory statement
        description
          "Number of active trunk member interfaces.";
      }
      leaf reason {
        type string {
          length "0..127";
        }
        // NCS drop mandatory statement
        description
          "Reason.";
      }
    }
  }
  augment "/ncs:devices/ncs:device/ncs:notifications/ncs:received-notifications/ncs:notification/ncs:data" {
    container member-link-up {
      presence "";
      config false;
      description
        "A trunk member interface went Up.";
      leaf port-index {
        type uint32;
        // NCS drop mandatory statement
        description
          "Index of a trunk member interface.";
      }
      leaf member-admin-status {
        type uint32;
        // NCS drop mandatory statement
        description
          "Administration status of a trunk member interface.";
      }
      leaf member-oper-status {
        type uint32;
        // NCS drop mandatory statement
        description
          "Operating status of a trunk member interface.";
      }
      leaf port-name {
        type pub-type:ncs_rpc_notif_if-name;
        // NCS drop mandatory statement
        description
          "Name of a trunk member interface.";
      }
      leaf member-phy-status {
        type uint32;
        // NCS drop mandatory statement
        description
          "Physical status of a trunk member interface.";
      }
      leaf trunk-index {
        type uint32;
        description
          "Index of a trunk interface.";
      }
      leaf trunk-name {
        type pub-type:ncs_rpc_notif_if-name;
        // NCS drop mandatory statement
        description
          "Name of the trunk interface to which the member interface belongs.";
      }
    }
  }
  augment "/ncs:devices/ncs:device/ncs:notifications/ncs:received-notifications/ncs:notification/ncs:data" {
    container member-link-down {
      presence "";
      config false;
      description
        "A trunk member interface went Down.";
      leaf port-index {
        type uint32;
        // NCS drop mandatory statement
        description
          "Index of a trunk member interface.";
      }
      leaf member-admin-status {
        type uint32;
        // NCS drop mandatory statement
        description
          "Administration status of a trunk member interface.";
      }
      leaf member-oper-status {
        type uint32;
        // NCS drop mandatory statement
        description
          "Operating status of a trunk member interface.";
      }
      leaf port-name {
        type pub-type:ncs_rpc_notif_if-name;
        // NCS drop mandatory statement
        description
          "Name of a trunk member interface.";
      }
      leaf member-phy-status {
        type uint32;
        // NCS drop mandatory statement
        description
          "Physical status of a trunk member interface.";
      }
      leaf trunk-index {
        type uint32;
        // NCS drop mandatory statement
        description
          "Index of the trunk interface to which the member interface belongs.";
      }
      leaf trunk-name {
        type pub-type:ncs_rpc_notif_if-name;
        // NCS drop mandatory statement
        description
          "Name of the trunk interface to which the member interface belongs.";
      }
    }
  }
  augment "/ncs:devices/ncs:device/ncs:notifications/ncs:received-notifications/ncs:notification/ncs:data" {
    container all-member-up {
      presence "";
      config false;
      description
        "All member links of the trunk went Up.";
      leaf trunk-name {
        type pub-type:ncs_rpc_notif_if-name;
        // NCS drop mandatory statement
        description
          "Name of the trunk interface.";
      }
    }
  }
  augment "/ncs:devices/ncs:device/ncs:notifications/ncs:received-notifications/ncs:notification/ncs:data" {
    container all-member-down-resume {
      presence "";
      config false;
      description
        "The first member interface link status changes to up.";
      leaf trunk-index {
        type uint32;
        // NCS drop mandatory statement
        description
          "Trunk interface index.";
      }
      leaf trunk-name {
        type pub-type:ncs_rpc_notif_if-name;
        // NCS drop mandatory statement
        description
          "Name of the Trunk interface.";
      }
    }
  }
  augment "/ncs:devices/ncs:device/ncs:notifications/ncs:received-notifications/ncs:notification/ncs:data" {
    container all-member-down {
      presence "";
      config false;
      description
        "The last member interface link status changes to down.";
      leaf trunk-index {
        type uint32;
        // NCS drop mandatory statement
        description
          "Trunk interface index.";
      }
      leaf trunk-name {
        type pub-type:ncs_rpc_notif_if-name;
        // NCS drop mandatory statement
        description
          "Name of the Trunk interface.";
      }
    }
  }
  augment "/ncs:devices/ncs:device/ncs:netconf-notifications/ncs:received-notifications/ncs:notification/ncs:data" {
    container trunk-bandwidth-change {
      presence "";
      config false;
      description
        "The trunk interface bandwidth changes.";
      leaf trunk-name {
        type pub-type:ncs_rpc_notif_if-name;
        // NCS drop mandatory statement
        description
          "Name of the trunk interface.";
      }
      leaf old-bandwidth {
        type uint64;
        units "bit/s";
        // NCS drop mandatory statement
        description
          "Old bandwidth of the trunk interface.";
      }
      leaf new-bandwidth {
        type uint64;
        units "bit/s";
        // NCS drop mandatory statement
        description
          "New bandwidth of the trunk interface.";
      }
    }
  }
  augment "/ncs:devices/ncs:device/ncs:netconf-notifications/ncs:received-notifications/ncs:notification/ncs:data" {
    container trunk-status-change {
      presence "";
      config false;
      description
        "The trunk interface status changes.";
      leaf trunk-name {
        type pub-type:ncs_rpc_notif_if-name;
        // NCS drop mandatory statement
        description
          "Name of the trunk interface.";
      }
      leaf trunk-index {
        type uint32;
        // NCS drop mandatory statement
        description
          "Trunk index.";
      }
      leaf trunk-admin-status {
        type ncs_rpc_notif_port-status;
        // NCS drop mandatory statement
        description
          "Administration status of trunk interface.";
      }
      leaf trunk-status {
        type ncs_rpc_notif_port-status;
        // NCS drop mandatory statement
        description
          "Status of trunk interface.";
      }
    }
  }
  augment "/ncs:devices/ncs:device/ncs:netconf-notifications/ncs:received-notifications/ncs:notification/ncs:data" {
    container member-number-change {
      presence "";
      config false;
      description
        "The number of active trunk member interfaces changed.";
      leaf trunk-name {
        type pub-type:ncs_rpc_notif_if-name;
        // NCS drop mandatory statement
        description
          "Name of the trunk interface.";
      }
      leaf port-name {
        type pub-type:ncs_rpc_notif_if-name;
        // NCS drop mandatory statement
        description
          "Name of the trunk member interface.";
      }
      leaf trunk-mem-number {
        type uint32;
        // NCS drop mandatory statement
        description
          "Number of active trunk member interfaces.";
      }
      leaf reason {
        type string {
          length "0..127";
        }
        // NCS drop mandatory statement
        description
          "Reason.";
      }
    }
  }
  augment "/ncs:devices/ncs:device/ncs:netconf-notifications/ncs:received-notifications/ncs:notification/ncs:data" {
    container member-link-up {
      presence "";
      config false;
      description
        "A trunk member interface went Up.";
      leaf port-index {
        type uint32;
        // NCS drop mandatory statement
        description
          "Index of a trunk member interface.";
      }
      leaf member-admin-status {
        type uint32;
        // NCS drop mandatory statement
        description
          "Administration status of a trunk member interface.";
      }
      leaf member-oper-status {
        type uint32;
        // NCS drop mandatory statement
        description
          "Operating status of a trunk member interface.";
      }
      leaf port-name {
        type pub-type:ncs_rpc_notif_if-name;
        // NCS drop mandatory statement
        description
          "Name of a trunk member interface.";
      }
      leaf member-phy-status {
        type uint32;
        // NCS drop mandatory statement
        description
          "Physical status of a trunk member interface.";
      }
      leaf trunk-index {
        type uint32;
        description
          "Index of a trunk interface.";
      }
      leaf trunk-name {
        type pub-type:ncs_rpc_notif_if-name;
        // NCS drop mandatory statement
        description
          "Name of the trunk interface to which the member interface belongs.";
      }
    }
  }
  augment "/ncs:devices/ncs:device/ncs:netconf-notifications/ncs:received-notifications/ncs:notification/ncs:data" {
    container member-link-down {
      presence "";
      config false;
      description
        "A trunk member interface went Down.";
      leaf port-index {
        type uint32;
        // NCS drop mandatory statement
        description
          "Index of a trunk member interface.";
      }
      leaf member-admin-status {
        type uint32;
        // NCS drop mandatory statement
        description
          "Administration status of a trunk member interface.";
      }
      leaf member-oper-status {
        type uint32;
        // NCS drop mandatory statement
        description
          "Operating status of a trunk member interface.";
      }
      leaf port-name {
        type pub-type:ncs_rpc_notif_if-name;
        // NCS drop mandatory statement
        description
          "Name of a trunk member interface.";
      }
      leaf member-phy-status {
        type uint32;
        // NCS drop mandatory statement
        description
          "Physical status of a trunk member interface.";
      }
      leaf trunk-index {
        type uint32;
        // NCS drop mandatory statement
        description
          "Index of the trunk interface to which the member interface belongs.";
      }
      leaf trunk-name {
        type pub-type:ncs_rpc_notif_if-name;
        // NCS drop mandatory statement
        description
          "Name of the trunk interface to which the member interface belongs.";
      }
    }
  }
  augment "/ncs:devices/ncs:device/ncs:netconf-notifications/ncs:received-notifications/ncs:notification/ncs:data" {
    container all-member-up {
      presence "";
      config false;
      description
        "All member links of the trunk went Up.";
      leaf trunk-name {
        type pub-type:ncs_rpc_notif_if-name;
        // NCS drop mandatory statement
        description
          "Name of the trunk interface.";
      }
    }
  }
  augment "/ncs:devices/ncs:device/ncs:netconf-notifications/ncs:received-notifications/ncs:notification/ncs:data" {
    container all-member-down-resume {
      presence "";
      config false;
      description
        "The first member interface link status changes to up.";
      leaf trunk-index {
        type uint32;
        // NCS drop mandatory statement
        description
          "Trunk interface index.";
      }
      leaf trunk-name {
        type pub-type:ncs_rpc_notif_if-name;
        // NCS drop mandatory statement
        description
          "Name of the Trunk interface.";
      }
    }
  }
  augment "/ncs:devices/ncs:device/ncs:netconf-notifications/ncs:received-notifications/ncs:notification/ncs:data" {
    container all-member-down {
      presence "";
      config false;
      description
        "The last member interface link status changes to down.";
      leaf trunk-index {
        type uint32;
        // NCS drop mandatory statement
        description
          "Trunk interface index.";
      }
      leaf trunk-name {
        type pub-type:ncs_rpc_notif_if-name;
        // NCS drop mandatory statement
        description
          "Name of the Trunk interface.";
      }
    }
  }
}
