submodule ietf-snmp-common {
  // Generated by yanger -t ncs
  tailf:mount-id "huawei-nc-1.0:huawei-nc-1.0";

  belongs-to ietf-snmp {
    prefix snmp;
  }

  import ietf-yang-types {
    prefix yang;
  }
  import tailf-common {
    prefix tailf;
  }
  import tailf-ncs {
    prefix ncs;
  }

  organization
    "IETF NETMOD (NETCONF Data Modeling Language) Working Group";
  contact
    "WG Web:   <http://tools.ietf.org/wg/netmod/>
     WG List:  <mailto:netmod@ietf.org>
     WG Chair: Thomas Nadeau
               <mailto:tnadeau@lucidvision.com>
     WG Chair: Juergen Schoenwaelder
               <mailto:j.schoenwaelder@jacobs-university.de>
     Editor:   Martin Bjorklund
               <mailto:mbj@tail-f.com>
     Editor:   Juergen Schoenwaelder
               <mailto:j.schoenwaelder@jacobs-university.de>";
  description
    "This submodule contains a collection of common YANG definitions
     for configuring SNMP engines.
     Copyright (c) 2014 IETF Trust and the persons identified as
     authors of the code.  All rights reserved.
     Redistribution and use in source and binary forms, with or
     without modification, is permitted pursuant to, and subject
     to the license terms contained in, the Simplified BSD License
     set forth in Section 4.c of the IETF Trust's Legal Provisions
     Relating to IETF Documents
     (http://trustee.ietf.org/license-info).
     This version of this YANG module is part of RFC 7407; see
     the RFC itself for full legal notices.";

  revision 2014-12-10 {
    description
      "Initial revision.";
    reference "RFC 7407: A YANG Data Model for SNMP Configuration";
  }

  typedef ncs_template_admin-string {
    type string;
    description
      "Represents SnmpAdminString as defined in RFC 3411.
       Note that the size of an SnmpAdminString is measured in
       octets, not characters.";
    reference
      "RFC 3411: An Architecture for Describing Simple Network
         Management Protocol (SNMP) Management Frameworks.
         SNMP-FRAMEWORK-MIB.SnmpAdminString";
  }

  typedef ncs_template_identifier {
    type ncs_template_admin-string;
    description
      "Identifiers are used to name items in the SNMP configuration
       datastore.";
  }

  typedef ncs_template_context-name {
    type ncs_template_admin-string;
    description
      "The context type represents an SNMP context name.";
    reference
      "RFC 3411: An Architecture for Describing Simple Network
         Management Protocol (SNMP) Management Frameworks";
  }

  typedef ncs_template_security-name {
    type ncs_template_admin-string;
    description
      "The security-name type represents an SNMP security name.";
    reference
      "RFC 3411: An Architecture for Describing Simple Network
         Management Protocol (SNMP) Management Frameworks";
  }

  typedef ncs_template_security-model {
    type string;
    reference
      "RFC 3411: An Architecture for Describing Simple Network
         Management Protocol (SNMP) Management Frameworks";
  }

  typedef ncs_template_security-model-or-any {
    type string;
    reference
      "RFC 3411: An Architecture for Describing Simple Network
         Management Protocol (SNMP) Management Frameworks";
  }

  typedef ncs_template_security-level {
    type string;
    reference
      "RFC 3411: An Architecture for Describing Simple Network
         Management Protocol (SNMP) Management Frameworks";
  }

  typedef ncs_template_engine-id {
    type string;
    description
      "The engine ID specified as a list of colon-specified
       hexadecimal octets, e.g., '80:00:02:b8:04:61:62:63'.";
    reference
      "RFC 3411: An Architecture for Describing Simple Network
         Management Protocol (SNMP) Management Frameworks";
  }

  typedef ncs_template_wildcard-object-identifier {
    type string;
    description
      "The wildcard-object-identifier type represents an SNMP object
       identifier where subidentifiers can be given either as a label,
       in numeric form, or a wildcard, represented by an asterisk
       ('*').";
  }

  typedef ncs_template_tag-value {
    type string;
    description
      "Represents SnmpTagValue as defined in RFC 3413.
       Note that the size of an SnmpTagValue is measured in
       octets, not characters.";
    reference
      "RFC 3413: Simple Network Management Protocol (SNMP)
         Applications.
         SNMP-TARGET-MIB.SnmpTagValue";
  }

  typedef ncs_rpc_notif_admin-string {
    type string {
      length "0..255";
    }
    description
      "Represents SnmpAdminString as defined in RFC 3411.
       Note that the size of an SnmpAdminString is measured in
       octets, not characters.";
    reference
      "RFC 3411: An Architecture for Describing Simple Network
         Management Protocol (SNMP) Management Frameworks.
         SNMP-FRAMEWORK-MIB.SnmpAdminString";
  }

  typedef ncs_rpc_notif_identifier {
    type ncs_rpc_notif_admin-string;
    description
      "Identifiers are used to name items in the SNMP configuration
       datastore.";
  }

  typedef ncs_rpc_notif_context-name {
    type ncs_rpc_notif_admin-string;
    description
      "The context type represents an SNMP context name.";
    reference
      "RFC 3411: An Architecture for Describing Simple Network
         Management Protocol (SNMP) Management Frameworks";
  }

  typedef ncs_rpc_notif_security-name {
    type ncs_rpc_notif_admin-string;
    description
      "The security-name type represents an SNMP security name.";
    reference
      "RFC 3411: An Architecture for Describing Simple Network
         Management Protocol (SNMP) Management Frameworks";
  }

  typedef ncs_rpc_notif_security-model {
    type union {
      type enumeration {
        enum "v1" {
          value 1;
        }
        enum "v2c" {
          value 2;
        }
        enum "usm" {
          value 3;
        }
        enum "tsm" {
          value 4;
        }
      }
      type int32 {
        range "1..2147483647";
      }
    }
    reference
      "RFC 3411: An Architecture for Describing Simple Network
         Management Protocol (SNMP) Management Frameworks";
  }

  typedef ncs_rpc_notif_security-model-or-any {
    type union {
      type enumeration {
        enum "any" {
          value 0;
        }
      }
      type ncs_rpc_notif_security-model;
    }
    reference
      "RFC 3411: An Architecture for Describing Simple Network
         Management Protocol (SNMP) Management Frameworks";
  }

  typedef ncs_rpc_notif_security-level {
    type enumeration {
      enum "no-auth-no-priv" {
        value 1;
      }
      enum "auth-no-priv" {
        value 2;
      }
      enum "auth-priv" {
        value 3;
      }
    }
    reference
      "RFC 3411: An Architecture for Describing Simple Network
         Management Protocol (SNMP) Management Frameworks";
  }

  typedef ncs_rpc_notif_engine-id {
    type yang:hex-string {
      pattern '([0-9a-fA-F]){2}(:([0-9a-fA-F]){2}){4,31}';
    }
    description
      "The engine ID specified as a list of colon-specified
       hexadecimal octets, e.g., '80:00:02:b8:04:61:62:63'.";
    reference
      "RFC 3411: An Architecture for Describing Simple Network
         Management Protocol (SNMP) Management Frameworks";
  }

  typedef ncs_rpc_notif_wildcard-object-identifier {
    type string;
    description
      "The wildcard-object-identifier type represents an SNMP object
       identifier where subidentifiers can be given either as a label,
       in numeric form, or a wildcard, represented by an asterisk
       ('*').";
  }

  typedef ncs_rpc_notif_tag-value {
    type string {
      length "0..255";
    }
    description
      "Represents SnmpTagValue as defined in RFC 3413.
       Note that the size of an SnmpTagValue is measured in
       octets, not characters.";
    reference
      "RFC 3413: Simple Network Management Protocol (SNMP)
         Applications.
         SNMP-TARGET-MIB.SnmpTagValue";
  }

  typedef live_ncs_admin-string {
    type string {
      length "0..255";
    }
    description
      "Represents SnmpAdminString as defined in RFC 3411.
       Note that the size of an SnmpAdminString is measured in
       octets, not characters.";
    reference
      "RFC 3411: An Architecture for Describing Simple Network
         Management Protocol (SNMP) Management Frameworks.
         SNMP-FRAMEWORK-MIB.SnmpAdminString";
  }

  typedef live_ncs_identifier {
    type live_ncs_admin-string;
    description
      "Identifiers are used to name items in the SNMP configuration
       datastore.";
  }

  typedef live_ncs_context-name {
    type live_ncs_admin-string;
    description
      "The context type represents an SNMP context name.";
    reference
      "RFC 3411: An Architecture for Describing Simple Network
         Management Protocol (SNMP) Management Frameworks";
  }

  typedef live_ncs_security-name {
    type live_ncs_admin-string;
    description
      "The security-name type represents an SNMP security name.";
    reference
      "RFC 3411: An Architecture for Describing Simple Network
         Management Protocol (SNMP) Management Frameworks";
  }

  typedef live_ncs_security-model {
    type union {
      type enumeration {
        enum "v1" {
          value 1;
        }
        enum "v2c" {
          value 2;
        }
        enum "usm" {
          value 3;
        }
        enum "tsm" {
          value 4;
        }
      }
      type int32 {
        range "1..2147483647";
      }
    }
    reference
      "RFC 3411: An Architecture for Describing Simple Network
         Management Protocol (SNMP) Management Frameworks";
  }

  typedef live_ncs_security-model-or-any {
    type union {
      type enumeration {
        enum "any" {
          value 0;
        }
      }
      type live_ncs_security-model;
    }
    reference
      "RFC 3411: An Architecture for Describing Simple Network
         Management Protocol (SNMP) Management Frameworks";
  }

  typedef live_ncs_security-level {
    type enumeration {
      enum "no-auth-no-priv" {
        value 1;
      }
      enum "auth-no-priv" {
        value 2;
      }
      enum "auth-priv" {
        value 3;
      }
    }
    reference
      "RFC 3411: An Architecture for Describing Simple Network
         Management Protocol (SNMP) Management Frameworks";
  }

  typedef live_ncs_engine-id {
    type yang:hex-string {
      pattern '([0-9a-fA-F]){2}(:([0-9a-fA-F]){2}){4,31}';
    }
    description
      "The engine ID specified as a list of colon-specified
       hexadecimal octets, e.g., '80:00:02:b8:04:61:62:63'.";
    reference
      "RFC 3411: An Architecture for Describing Simple Network
         Management Protocol (SNMP) Management Frameworks";
  }

  typedef live_ncs_wildcard-object-identifier {
    type string;
    description
      "The wildcard-object-identifier type represents an SNMP object
       identifier where subidentifiers can be given either as a label,
       in numeric form, or a wildcard, represented by an asterisk
       ('*').";
  }

  typedef live_ncs_tag-value {
    type string {
      length "0..255";
    }
    description
      "Represents SnmpTagValue as defined in RFC 3413.
       Note that the size of an SnmpTagValue is measured in
       octets, not characters.";
    reference
      "RFC 3413: Simple Network Management Protocol (SNMP)
         Applications.
         SNMP-TARGET-MIB.SnmpTagValue";
  }

  typedef admin-string {
    type string {
      length "0..255";
    }
    description
      "Represents SnmpAdminString as defined in RFC 3411.
       Note that the size of an SnmpAdminString is measured in
       octets, not characters.";
    reference
      "RFC 3411: An Architecture for Describing Simple Network
         Management Protocol (SNMP) Management Frameworks.
         SNMP-FRAMEWORK-MIB.SnmpAdminString";
  }

  typedef identifier {
    type admin-string {
      length "1..32";
    }
    description
      "Identifiers are used to name items in the SNMP configuration
       datastore.";
  }

  typedef context-name {
    type admin-string {
      length "0..32";
    }
    description
      "The context type represents an SNMP context name.";
    reference
      "RFC 3411: An Architecture for Describing Simple Network
         Management Protocol (SNMP) Management Frameworks";
  }

  typedef security-name {
    type admin-string {
      length "1..32";
    }
    description
      "The security-name type represents an SNMP security name.";
    reference
      "RFC 3411: An Architecture for Describing Simple Network
         Management Protocol (SNMP) Management Frameworks";
  }

  typedef security-model {
    type union {
      type enumeration {
        enum "v1" {
          value 1;
        }
        enum "v2c" {
          value 2;
        }
        enum "usm" {
          value 3;
        }
        enum "tsm" {
          value 4;
        }
      }
      type int32 {
        range "1..2147483647";
      }
    }
    reference
      "RFC 3411: An Architecture for Describing Simple Network
         Management Protocol (SNMP) Management Frameworks";
  }

  typedef security-model-or-any {
    type union {
      type enumeration {
        enum "any" {
          value 0;
        }
      }
      type security-model;
    }
    reference
      "RFC 3411: An Architecture for Describing Simple Network
         Management Protocol (SNMP) Management Frameworks";
  }

  typedef security-level {
    type enumeration {
      enum "no-auth-no-priv" {
        value 1;
      }
      enum "auth-no-priv" {
        value 2;
      }
      enum "auth-priv" {
        value 3;
      }
    }
    reference
      "RFC 3411: An Architecture for Describing Simple Network
         Management Protocol (SNMP) Management Frameworks";
  }

  typedef engine-id {
    type yang:hex-string {
      pattern '([0-9a-fA-F]){2}(:([0-9a-fA-F]){2}){4,31}';
    }
    description
      "The engine ID specified as a list of colon-specified
       hexadecimal octets, e.g., '80:00:02:b8:04:61:62:63'.";
    reference
      "RFC 3411: An Architecture for Describing Simple Network
         Management Protocol (SNMP) Management Frameworks";
  }

  typedef wildcard-object-identifier {
    type string;
    description
      "The wildcard-object-identifier type represents an SNMP object
       identifier where subidentifiers can be given either as a label,
       in numeric form, or a wildcard, represented by an asterisk
       ('*').";
  }

  typedef tag-value {
    type string {
      length "0..255";
    }
    description
      "Represents SnmpTagValue as defined in RFC 3413.
       Note that the size of an SnmpTagValue is measured in
       octets, not characters.";
    reference
      "RFC 3413: Simple Network Management Protocol (SNMP)
         Applications.
         SNMP-TARGET-MIB.SnmpTagValue";
  }

  augment "/ncs:devices/ncs:device/ncs:config" {
    container snmp {
      tailf:ncs-device-type "netconf";
      tailf:display-when "not(../../ncs:module) or ../../ncs:module[ncs:name='ietf-snmp']";
      description
        "Top-level container for SNMP-related configuration and
         status objects.";
    }
  }
  augment "/ncs:devices/ncs:device/ncs:live-status" {
    container snmp {
      tailf:ncs-device-type "netconf";
      tailf:display-when "not(../../ncs:module) or ../../ncs:module[ncs:name='ietf-snmp'] or (../../ncs:live-status-protocol[not(ncs:capability)]) or (../../ncs:live-status-protocol/ncs:capability/ncs:module[.='ietf-snmp'])";
      description
        "Top-level container for SNMP-related configuration and
         status objects.";
    }
  }
  augment "/ncs:devices/ncs:template/ncs:ned-id/ncs:config" {
    container snmp {
      description
        "Top-level container for SNMP-related configuration and
         status objects.";
    }
  }
}
