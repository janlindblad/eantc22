module huawei-clocksync-comm {
  // Generated by yanger -t ncs
  tailf:mount-id "huawei-nc-1.0:huawei-nc-1.0";
  tailf:ncs-device-type "netconf";

  namespace "urn:huawei:yang:huawei-clocksync-comm";
  prefix clocksync-comm;

  import huawei-extension {
    prefix ext;
  }
  import huawei-ifm {
    prefix ifm;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Clock comm data model define.";

  revision 2020-03-04 {
    description
      "Modify the node description.";
    reference "Huawei private.";
  }
  revision 2019-09-29 {
    description
      "Initial revision.";
    reference "Huawei private.";
  }
  ext:task-name "clksync";

  typedef ncs_template_clock-pull-in-status {
    type string;
    description
      "Clock pull-in state.";
  }

  typedef ncs_template_clock-run-mode {
    type string;
    description
      "Clock run mode.";
  }

  typedef ncs_template_clock-bits-type {
    type string;
    description
      "Clock bits type.";
  }

  typedef ncs_template_clock-trace-status {
    type string;
    description
      "Clock trace status.";
  }

  typedef ncs_template_clock-time-sync-mode {
    type string;
    description
      "Clock time sync mode.";
  }

  typedef ncs_template_clock-freq-sync-mode {
    type string;
    description
      "Clock freq sync mode.";
  }

  typedef ncs_template_clock-time-sync-status {
    type string;
    description
      "Clock time sync status.";
  }

  typedef ncs_rpc_notif_clock-pull-in-status {
    type enumeration {
      enum "out" {
        value 0;
        description
          "Pull-out.";
      }
      enum "in" {
        value 1;
        description
          "Pull-in.";
      }
    }
    description
      "Clock pull-in state.";
  }

  typedef ncs_rpc_notif_clock-run-mode {
    type enumeration {
      enum "free" {
        value 2;
        description
          "Run mode type is free.";
      }
      enum "hold" {
        value 1;
        description
          "Run mode type is hold.";
      }
      enum "normal" {
        value 0;
        description
          "Run mode type is normal.";
      }
    }
    description
      "Clock run mode.";
  }

  typedef ncs_rpc_notif_clock-bits-type {
    type enumeration {
      enum "1pps" {
        value 3;
        description
          "Bits type is 1pps.";
      }
      enum "2mhz" {
        value 1;
        description
          "Bits type is 2mhz.";
      }
      enum "2mbps" {
        value 0;
        description
          "Bits type is 2mbps.";
      }
      enum "dcls" {
        value 2;
        description
          "Bits type is dcls.";
      }
      enum "none" {
        value 255;
        description
          "Bits type is none.";
      }
    }
    description
      "Clock bits type.";
  }

  typedef ncs_rpc_notif_clock-trace-status {
    type enumeration {
      enum "freerun" {
        value 0;
        description
          "Trace ststus is freerun.";
      }
      enum "fastlock" {
        value 1;
        description
          "Trace ststus is fastlock.";
      }
      enum "trace" {
        value 2;
        description
          "Trace ststus is trace.";
      }
      enum "hold" {
        value 3;
        description
          "Trace ststus is hold.";
      }
    }
    description
      "Clock trace status.";
  }

  typedef ncs_rpc_notif_clock-time-sync-mode {
    type enumeration {
      enum "none" {
        value 0;
        description
          "Time sync mode is none.";
      }
      enum "ptp" {
        value 1;
        description
          "Time sync mode is ptp.";
      }
    }
    description
      "Clock time sync mode.";
  }

  typedef ncs_rpc_notif_clock-freq-sync-mode {
    type enumeration {
      enum "none" {
        value 0;
        description
          "Freq sync mode is none.";
      }
      enum "phyfreq" {
        value 1;
        description
          "Freq sync mode is phyfreq.";
      }
      enum "ptpfreq" {
        value 2;
        description
          "Freq sync mode is ptpfreq.";
      }
      enum "ptpacrfreq" {
        value 3;
        description
          "Freq sync mode is ptpacrfreq.";
      }
    }
    description
      "Clock freq sync mode.";
  }

  typedef ncs_rpc_notif_clock-time-sync-status {
    type enumeration {
      enum "sync" {
        value 0;
        description
          "Time sync status is sync.";
      }
      enum "unsync" {
        value 1;
        description
          "Time sync status is unsync.";
      }
    }
    description
      "Clock time sync status.";
  }

  typedef live_ncs_clock-pull-in-status {
    type enumeration {
      enum "out" {
        value 0;
        description
          "Pull-out.";
      }
      enum "in" {
        value 1;
        description
          "Pull-in.";
      }
    }
    description
      "Clock pull-in state.";
  }

  typedef live_ncs_clock-run-mode {
    type enumeration {
      enum "free" {
        value 2;
        description
          "Run mode type is free.";
      }
      enum "hold" {
        value 1;
        description
          "Run mode type is hold.";
      }
      enum "normal" {
        value 0;
        description
          "Run mode type is normal.";
      }
    }
    description
      "Clock run mode.";
  }

  typedef live_ncs_clock-bits-type {
    type enumeration {
      enum "1pps" {
        value 3;
        description
          "Bits type is 1pps.";
      }
      enum "2mhz" {
        value 1;
        description
          "Bits type is 2mhz.";
      }
      enum "2mbps" {
        value 0;
        description
          "Bits type is 2mbps.";
      }
      enum "dcls" {
        value 2;
        description
          "Bits type is dcls.";
      }
      enum "none" {
        value 255;
        description
          "Bits type is none.";
      }
    }
    description
      "Clock bits type.";
  }

  typedef live_ncs_clock-trace-status {
    type enumeration {
      enum "freerun" {
        value 0;
        description
          "Trace ststus is freerun.";
      }
      enum "fastlock" {
        value 1;
        description
          "Trace ststus is fastlock.";
      }
      enum "trace" {
        value 2;
        description
          "Trace ststus is trace.";
      }
      enum "hold" {
        value 3;
        description
          "Trace ststus is hold.";
      }
    }
    description
      "Clock trace status.";
  }

  typedef live_ncs_clock-time-sync-mode {
    type enumeration {
      enum "none" {
        value 0;
        description
          "Time sync mode is none.";
      }
      enum "ptp" {
        value 1;
        description
          "Time sync mode is ptp.";
      }
    }
    description
      "Clock time sync mode.";
  }

  typedef live_ncs_clock-freq-sync-mode {
    type enumeration {
      enum "none" {
        value 0;
        description
          "Freq sync mode is none.";
      }
      enum "phyfreq" {
        value 1;
        description
          "Freq sync mode is phyfreq.";
      }
      enum "ptpfreq" {
        value 2;
        description
          "Freq sync mode is ptpfreq.";
      }
      enum "ptpacrfreq" {
        value 3;
        description
          "Freq sync mode is ptpacrfreq.";
      }
    }
    description
      "Clock freq sync mode.";
  }

  typedef live_ncs_clock-time-sync-status {
    type enumeration {
      enum "sync" {
        value 0;
        description
          "Time sync status is sync.";
      }
      enum "unsync" {
        value 1;
        description
          "Time sync status is unsync.";
      }
    }
    description
      "Clock time sync status.";
  }

  typedef clock-pull-in-status {
    type enumeration {
      enum "out" {
        value 0;
        description
          "Pull-out.";
      }
      enum "in" {
        value 1;
        description
          "Pull-in.";
      }
    }
    description
      "Clock pull-in state.";
  }

  typedef clock-run-mode {
    type enumeration {
      enum "free" {
        value 2;
        description
          "Run mode type is free.";
      }
      enum "hold" {
        value 1;
        description
          "Run mode type is hold.";
      }
      enum "normal" {
        value 0;
        description
          "Run mode type is normal.";
      }
    }
    description
      "Clock run mode.";
  }

  typedef clock-bits-type {
    type enumeration {
      enum "1pps" {
        value 3;
        description
          "Bits type is 1pps.";
      }
      enum "2mhz" {
        value 1;
        description
          "Bits type is 2mhz.";
      }
      enum "2mbps" {
        value 0;
        description
          "Bits type is 2mbps.";
      }
      enum "dcls" {
        value 2;
        description
          "Bits type is dcls.";
      }
      enum "none" {
        value 255;
        description
          "Bits type is none.";
      }
    }
    description
      "Clock bits type.";
  }

  typedef clock-trace-status {
    type enumeration {
      enum "freerun" {
        value 0;
        description
          "Trace ststus is freerun.";
      }
      enum "fastlock" {
        value 1;
        description
          "Trace ststus is fastlock.";
      }
      enum "trace" {
        value 2;
        description
          "Trace ststus is trace.";
      }
      enum "hold" {
        value 3;
        description
          "Trace ststus is hold.";
      }
    }
    description
      "Clock trace status.";
  }

  typedef clock-time-sync-mode {
    type enumeration {
      enum "none" {
        value 0;
        description
          "Time sync mode is none.";
      }
      enum "ptp" {
        value 1;
        description
          "Time sync mode is ptp.";
      }
    }
    description
      "Clock time sync mode.";
  }

  typedef clock-freq-sync-mode {
    type enumeration {
      enum "none" {
        value 0;
        description
          "Freq sync mode is none.";
      }
      enum "phyfreq" {
        value 1;
        description
          "Freq sync mode is phyfreq.";
      }
      enum "ptpfreq" {
        value 2;
        description
          "Freq sync mode is ptpfreq.";
      }
      enum "ptpacrfreq" {
        value 3;
        description
          "Freq sync mode is ptpacrfreq.";
      }
    }
    description
      "Clock freq sync mode.";
  }

  typedef clock-time-sync-status {
    type enumeration {
      enum "sync" {
        value 0;
        description
          "Time sync status is sync.";
      }
      enum "unsync" {
        value 1;
        description
          "Time sync status is unsync.";
      }
    }
    description
      "Clock time sync status.";
  }

  augment "/ncs:devices/ncs:device/ncs:config" {
    // NCS drop config false container 'clocksync-comm'
  }
  augment "/ncs:devices/ncs:device/ncs:live-status" {
    container clocksync-comm {
      tailf:ncs-device-type "netconf";
      tailf:display-when "not(../../ncs:module) or ../../ncs:module[ncs:name='huawei-clocksync-comm'] or (../../ncs:live-status-protocol[not(ncs:capability)]) or (../../ncs:live-status-protocol/ncs:capability/ncs:module[.='huawei-clocksync-comm'])";
      description
        "Common clock information.";
      container clock-status {
        description
          "Statistics of system clock status.";
        leaf clk-pull-in-status {
          type live_ncs_clock-pull-in-status;
          description
            "Clock pull-in state.";
        }
        leaf time-sync-mode {
          type live_ncs_clock-time-sync-mode;
          // NCS drop default statement
          description
            "Mode of time synchronization.";
        }
        leaf time-sync-status {
          type live_ncs_clock-time-sync-status;
          // NCS drop default statement
          description
            "Status of time synchronization.";
        }
        leaf time-lock-status {
          type boolean;
          // NCS drop default statement
          description
            "Locking status of time synchronization.";
        }
        leaf freq-sync-mode {
          type live_ncs_clock-freq-sync-mode;
          // NCS drop default statement
          description
            "Mode of frequency synchronization.";
        }
        leaf sys-clk-trace-status {
          type live_ncs_clock-trace-status;
          // NCS drop default statement
          description
            "Status of frequency synchronization.";
        }
        leaf freq-lock-status {
          type boolean;
          // NCS drop default statement
          description
            "Locking status of frequency synchronization.";
        }
      }
    }
  }
  augment "/ncs:devices/ncs:template/ncs:ned-id/ncs:config" {
    // NCS drop config false container 'clocksync-comm'
  }
  augment "/ncs:devices/ncs:template/ncs:ned-id/ncs:config/ifm:ifm/ifm:interfaces/ifm:interface" {
    description
      "Interface.";
    container clocksync-flexe {
      description
        "Configure clock synchronization on FlexE interfaces.";
      container phy-ports {
        description
          "Configure physical FlexE interface.";
        container phy-port {
          description
            "Configure physical FlexE interface.";
          leaf lgc-port-name {
            type string;
            // NCS drop must statement
            description
              "Logical FlexE interface name.";
          }
        }
      }
    }
  }
  augment "/ncs:devices/ncs:device/ncs:live-status/ifm:ifm/ifm:interfaces/ifm:interface" {
    description
      "Interface.";
    container clocksync-flexe {
      tailf:ncs-device-type "netconf";
      tailf:display-when "not(../../../../../ncs:module) or ../../../../../ncs:module[ncs:name='huawei-clocksync-comm'] or (../../../../../ncs:live-status-protocol[not(ncs:capability)]) or (../../../../../ncs:live-status-protocol/ncs:capability/ncs:module[.='huawei-clocksync-comm'])";
      description
        "Configure clock synchronization on FlexE interfaces.";
      container phy-ports {
        description
          "Configure physical FlexE interface.";
        container phy-port {
          description
            "Configure physical FlexE interface.";
          leaf lgc-port-name {
            type leafref {
              path "/ncs:devices/ncs:device/ncs:live-status/ifm:ifm/ifm:interfaces/ifm:interface/ifm:name" {
                tailf:xpath-root 3;
              }
            }
            // NCS drop must statement
            description
              "Logical FlexE interface name.";
          }
        }
      }
    }
  }
  augment "/ncs:devices/ncs:device/ncs:config/ifm:ifm/ifm:interfaces/ifm:interface" {
    description
      "Interface.";
    container clocksync-flexe {
      tailf:ncs-device-type "netconf";
      tailf:display-when "not(../../../../../ncs:module) or ../../../../../ncs:module[ncs:name='huawei-clocksync-comm']";
      description
        "Configure clock synchronization on FlexE interfaces.";
      container phy-ports {
        description
          "Configure physical FlexE interface.";
        container phy-port {
          description
            "Configure physical FlexE interface.";
          leaf lgc-port-name {
            type leafref {
              path "/ncs:devices/ncs:device/ncs:config/ifm:ifm/ifm:interfaces/ifm:interface/ifm:name" {
                tailf:xpath-root 3;
              }
            }
            must "/ifm:ifm/ifm:interfaces/ifm:interface[ifm:name=current()]/ifm:type='FlexE'" {
              tailf:xpath-root 3;
            }
            description
              "Logical FlexE interface name.";
          }
        }
      }
    }
  }
}
