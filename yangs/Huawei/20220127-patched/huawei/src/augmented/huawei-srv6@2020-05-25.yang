module huawei-srv6 {
  // Generated by yanger -t ncs
  tailf:mount-id "huawei-nc-1.0:huawei-nc-1.0";
  tailf:ncs-device-type "netconf";

  namespace "urn:huawei:yang:huawei-srv6";
  prefix srv6;

  import huawei-network-instance {
    prefix ni;
  }
  import ietf-inet-types {
    prefix inet;
  }
  import huawei-extension {
    prefix ext;
  }
  import huawei-ifm {
    prefix ifm;
  }
  import huawei-evpl {
    prefix evpl;
  }
  import huawei-bd {
    prefix bd;
  }
  import huawei-pub-type {
    prefix pub-type;
  }
  include huawei-srv6-type;
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Segment routing IPv6.";

  revision 2020-05-25 {
    description
      "Add mapping-policys container.";
    reference "Huawei private.";
  }
  revision 2020-05-10 {
    description
      "Modify the description.";
    reference "Huawei private.";
  }
  revision 2020-03-09 {
    description
      "Modify the description.";
    reference "Huawei private.";
  }
  revision 2020-02-24 {
    description
      "Add end-ass container.";
    reference "Huawei private.";
  }
  revision 2020-02-04 {
    description
      "Add new leaf.";
    reference "Huawei private.";
  }
  revision 2019-11-22 {
    description
      "Reconstructing Yang file by yin mechanism.";
    reference "Huawei private.";
  }
  revision 2019-04-04 {
    description
      "Initial revision.";
    reference "Huawei private.";
  }
  ext:task-name "segr";

  augment "/ncs:devices/ncs:device/ncs:rpc" {
    container rpc-get-available-static-sid {
      tailf:ncs-device-type "netconf";
      tailf:display-when "not(../../ncs:module) or ../../ncs:module[ncs:name='huawei-srv6']";
      tailf:action get-available-static-sid {
        tailf:actionpoint ncsproxy {
          tailf:internal;
        }
        description
          "Query a maximum of 10 available SRv6 static SIDs for a specified locator name.";
        input {
          leaf locator-name {
            type string {
              length "1..32";
            }
            mandatory true;
            description
              "Locator name.";
          }
          leaf begin-value {
            type inet:ipv6-address-no-zone;
            description
              "Start value in the range of available SRv6 static SIDs.";
          }
        }
        output {
          leaf sid-value1 {
            type inet:ipv6-address-no-zone;
            description
              "The first available SRv6 static SID.";
          }
          leaf sid-value2 {
            type inet:ipv6-address-no-zone;
            description
              "The second available SRv6 static SID.";
          }
          leaf sid-value3 {
            type inet:ipv6-address-no-zone;
            description
              "The third available SRv6 static SID.";
          }
          leaf sid-value4 {
            type inet:ipv6-address-no-zone;
            description
              "The fourth available SRv6 static SID.";
          }
          leaf sid-value5 {
            type inet:ipv6-address-no-zone;
            description
              "The fifth available SRv6 static SID.";
          }
          leaf sid-value6 {
            type inet:ipv6-address-no-zone;
            description
              "The sixth available SRv6 static SID.";
          }
          leaf sid-value7 {
            type inet:ipv6-address-no-zone;
            description
              "The seventh available SRv6 static SID.";
          }
          leaf sid-value8 {
            type inet:ipv6-address-no-zone;
            description
              "The eighth available SRv6 static SID.";
          }
          leaf sid-value9 {
            type inet:ipv6-address-no-zone;
            description
              "The ninth available SRv6 static SID.";
          }
          leaf sid-value10 {
            type inet:ipv6-address-no-zone;
            description
              "The tenth available SRv6 static SID.";
          }
        }
      }
    }
  }
  augment "/ncs:devices/ncs:device-group/ncs:ned-id/ncs:rpc" {
    container rpc-get-available-static-sid {
      tailf:ncs-device-type "netconf";
      tailf:display-when "/ncs:devices/ncs:device[ncs:name=current()/../../../ncs:member]/ncs:module[ncs:name='huawei-srv6']";
      tailf:action get-available-static-sid {
        tailf:actionpoint ncsproxy {
          tailf:internal;
        }
        description
          "Query a maximum of 10 available SRv6 static SIDs for a specified locator name.";
        input {
          leaf locator-name {
            type string {
              length "1..32";
            }
            mandatory true;
            description
              "Locator name.";
          }
          leaf begin-value {
            type inet:ipv6-address-no-zone;
            description
              "Start value in the range of available SRv6 static SIDs.";
          }
        }
        output {
          container "device" {
            leaf "name" {
              type string;
            }
            leaf "info" {
              type string;
            }
            container "result" {
              leaf sid-value1 {
                type inet:ipv6-address-no-zone;
                description
                  "The first available SRv6 static SID.";
              }
              leaf sid-value2 {
                type inet:ipv6-address-no-zone;
                description
                  "The second available SRv6 static SID.";
              }
              leaf sid-value3 {
                type inet:ipv6-address-no-zone;
                description
                  "The third available SRv6 static SID.";
              }
              leaf sid-value4 {
                type inet:ipv6-address-no-zone;
                description
                  "The fourth available SRv6 static SID.";
              }
              leaf sid-value5 {
                type inet:ipv6-address-no-zone;
                description
                  "The fifth available SRv6 static SID.";
              }
              leaf sid-value6 {
                type inet:ipv6-address-no-zone;
                description
                  "The sixth available SRv6 static SID.";
              }
              leaf sid-value7 {
                type inet:ipv6-address-no-zone;
                description
                  "The seventh available SRv6 static SID.";
              }
              leaf sid-value8 {
                type inet:ipv6-address-no-zone;
                description
                  "The eighth available SRv6 static SID.";
              }
              leaf sid-value9 {
                type inet:ipv6-address-no-zone;
                description
                  "The ninth available SRv6 static SID.";
              }
              leaf sid-value10 {
                type inet:ipv6-address-no-zone;
                description
                  "The tenth available SRv6 static SID.";
              }
            }
          }
        }
      }
    }
  }
  augment "/ncs:devices/ncs:template/ncs:ned-id/ncs:config/ni:network-instance/ni:instances/ni:instance" {
    description
      "Segment routing IPv6 augment to L3VPN.";
    container srv6 {
      // NCS drop when statement
      description
        "Configure segment routing IPv6.";
      leaf enable {
        type string;
        // NCS drop default statement
        description
          "Enable/disable segment routing IPv6.";
      }
      leaf te-frr-enable {
        type string;
        // NCS drop must statement
        // NCS drop default statement
        description
          "Enable/disable SR TE FRR.";
      }
      leaf end-x-delay-time {
        // NCS drop when statement
        type string;
        units "ms";
        // NCS drop default statement
        description
          "End.X delay time.";
      }
      leaf path-mtu {
        // NCS drop when statement
        type string;
        // NCS drop must statement
        // NCS drop default statement
        description
          "Path MTU value.";
      }
      leaf path-mtu-reserved {
        // NCS drop when statement
        type string;
        // NCS drop must statement
        description
          "Path MTU reserved value.";
      }
      leaf proxy-peer-sid {
        // NCS drop when statement
        type string;
        description
          "Peer SID of SFC for anycast.";
      }
      leaf reduce-srh-enable {
        // NCS drop when statement
        type string;
        // NCS drop default statement
        description
          "Enable/disable reduce SRH.";
      }
      container encapsulation {
        // NCS drop when statement
        description
          "Configure IPv6 encapsulation configuation.";
        leaf source-address {
          type string;
          description
            "SRv6 VPN encapsulation source address.";
        }
        leaf hop-limit {
          // NCS drop when statement
          type string;
          // NCS drop default statement
          description
            "Encapsulation IPv6 header TTL value.";
        }
      }
      container locators {
        // NCS drop when statement
        description
          "List of SRv6 locator configuration.";
        list locator {
          // NCS patched for predictable order
          ordered-by user;
          key "name";
          unique "prefix";
          description
            "Configure SRv6 locator configuration.";
          leaf name {
            type string;
            description
              "Locator name.";
          }
          leaf prefix {
            ext:operation-exclude "update";
            type string;
            // NCS drop mandatory statement
            description
              "IPv6 prefix.";
          }
          leaf prefix-length {
            ext:operation-exclude "update";
            type string;
            // NCS drop must statement
            // NCS drop mandatory statement
            description
              "Mask length. The maximum sum value of the mask length, static segment length, and argument segment length is 128.";
          }
          leaf static-length {
            ext:operation-exclude "update";
            type string;
            // NCS drop must statement
            // NCS drop default statement
            description
              "The static segment length determines the range of opcode. The maximum sum value of the mask length, static segment length, and argument segment length is 128.";
          }
          leaf args-length {
            ext:operation-exclude "update";
            type string;
            // NCS drop must statement
            // NCS drop default statement
            description
              "Argument segment length. The maximum sum value of the mask length, static segment length, and argument segment length is 128.";
          }
          container opcodes {
            // NCS drop when statement
            description
              "Configure SRv6 opcodes configuration.";
            container ends {
              description
                "List of End type opcode configuration.";
              list end {
                // NCS patched for predictable order
                ordered-by user;
                key "value";
                // NCS drop max-elements statement
                description
                  "Configure End type opcode configuration.";
                leaf value {
                  type string;
                  description
                    "Opcode value. The value ranges from ::1 to ::XX, in which XX is an IPv6 address translated from 2^static-length minus 1.";
                }
              }
            }
            container end-psps {
              description
                "List of End psp type opcode configuration.";
              list end-psp {
                // NCS patched for predictable order
                ordered-by user;
                key "value";
                // NCS drop max-elements statement
                description
                  "Configure End psp type opcode configuration.";
                leaf value {
                  type string;
                  description
                    "Opcode value. The value ranges from ::1 to ::XX, in which XX is an IPv6 address translated from 2^static-length minus 1.";
                }
              }
            }
            container end-ops {
              description
                "List of End.OP type opcode configuration.";
              list end-op {
                // NCS patched for predictable order
                ordered-by user;
                key "value";
                // NCS drop max-elements statement
                description
                  "Configure End.OP type opcode configuration.";
                leaf value {
                  type string;
                  description
                    "Opcode value. The value ranges from ::1 to ::XX, in which XX is an IPv6 address translated from 2^static-length minus 1.";
                }
              }
            }
            container end-xs {
              description
                "List of End.X type opcode configuration.";
              list end-x {
                // NCS patched for predictable order
                ordered-by user;
                key "value if-name next-hop";
                description
                  "Configure End.X type opcode configuration.";
                leaf value {
                  type string;
                  description
                    "Opcode value. The value ranges from ::1 to ::XX, in which XX is an IPv6 address translated from 2^static-length minus 1.";
                }
                leaf if-name {
                  type string;
                  description
                    "Interface name.";
                }
                leaf next-hop {
                  type string;
                  description
                    "Nexthop address.";
                }
              }
            }
            container end-x-psps {
              description
                "List of End.X psp type opcode configuration.";
              list end-x-psp {
                // NCS patched for predictable order
                ordered-by user;
                key "value if-name next-hop";
                description
                  "Configure End.X psp type opcode configuration.";
                leaf value {
                  type string;
                  description
                    "Opcode value. The value ranges from ::1 to ::XX, in which XX is an IPv6 address translated from 2^static-length minus 1.";
                }
                leaf if-name {
                  type string;
                  description
                    "Interface name.";
                }
                leaf next-hop {
                  type string;
                  description
                    "NextHop address.";
                }
              }
            }
            container end-dt2us {
              description
                "List of End.DT2U type opcode configuration.";
              list end-dt2u {
                // NCS patched for predictable order
                ordered-by user;
                key "value";
                unique "bd-id";
                description
                  "Configure End.DT2U type opcode configuration.";
                leaf value {
                  type string;
                  description
                    "Opcode value. The value ranges from ::1 to ::XX, in which XX is an IPv6 address translated from 2^static-length minus 1.";
                }
                leaf bd-id {
                  type string;
                  // NCS drop mandatory statement
                  description
                    "Bridge domain ID.";
                  ext:support-filter "true";
                }
              }
            }
            container end-dt2uls {
              description
                "List of End.DT2UL type opcode configuration.";
              list end-dt2ul {
                // NCS patched for predictable order
                ordered-by user;
                key "value";
                unique "bd-id";
                description
                  "Configure End.DT2UL type opcode configuration.";
                leaf value {
                  type string;
                  description
                    "Opcode value. The value ranges from ::1 to ::XX, in which XX is an IPv6 address translated from 2^static-length minus 1.";
                }
                leaf bd-id {
                  type string;
                  // NCS drop mandatory statement
                  description
                    "Bridge domain ID.";
                  ext:support-filter "true";
                }
              }
            }
            container end-dt2ms {
              description
                "List of End.DT2M type opcode configuration.";
              list end-dt2m {
                // NCS patched for predictable order
                ordered-by user;
                key "value";
                unique "bd-id";
                description
                  "Configure End.DT2M type opcode configuration.";
                leaf value {
                  type string;
                  description
                    "Opcode value. The value ranges from ::1 to ::XX, in which XX is an IPv6 address translated from 2^static-length minus 1.";
                }
                leaf bd-id {
                  type string;
                  // NCS drop mandatory statement
                  description
                    "Bridge domain ID.";
                  ext:support-filter "true";
                }
              }
            }
            container end-dx2s {
              description
                "List of End.DX2 type opcode configuration.";
              list end-dx2 {
                // NCS patched for predictable order
                ordered-by user;
                key "value";
                unique "evpl-id";
                description
                  "Configure End.DX2 type opcode configuration.";
                leaf value {
                  type string;
                  description
                    "Opcode value. The value ranges from ::1 to ::XX, in which XX is an IPv6 address translated from 2^static-length minus 1.";
                }
                leaf evpl-id {
                  type string;
                  // NCS drop must statement
                  // NCS drop mandatory statement
                  description
                    "EVPL instance ID.";
                }
              }
            }
            container end-dx2ls {
              description
                "List of End.DX2L type opcode configuration.";
              list end-dx2l {
                // NCS patched for predictable order
                ordered-by user;
                key "value";
                unique "evpl-id";
                description
                  "Configure End.DX2L type opcode configuration.";
                leaf value {
                  type string;
                  description
                    "Opcode value. The value ranges from ::1 to ::XX, in which XX is an IPv6 address translated from 2^static-length minus 1.";
                }
                leaf evpl-id {
                  type string;
                  // NCS drop must statement
                  // NCS drop mandatory statement
                  description
                    "EVPL instance ID.";
                }
              }
            }
            container end-dt4s {
              description
                "List of End.DT4 type opcode configuration.";
              list end-dt4 {
                // NCS patched for predictable order
                ordered-by user;
                key "value";
                unique "vpn-name";
                description
                  "Configure End.DT4 type opcode configuration.";
                leaf value {
                  type string;
                  description
                    "Opcode value. The value ranges from ::1 to ::XX, in which XX is an IPv6 address translated from 2^static-length minus 1.";
                }
                leaf vpn-name {
                  type string;
                  // NCS drop default statement
                  description
                    "VPN name.";
                }
                leaf protocol {
                  type ncs_template_protocol-type;
                  // NCS drop must statement
                  // NCS drop default statement
                  description
                    "Protocol type.";
                }
              }
            }
            container end-dt6s {
              description
                "List of End.DT6 type opcode configuration.";
              list end-dt6 {
                // NCS patched for predictable order
                ordered-by user;
                key "value";
                unique "vpn-name";
                description
                  "Configure End.DT6 type opcode configuration.";
                leaf value {
                  type string;
                  description
                    "Opcode value. The value ranges from ::1 to ::XX, in which XX is an IPv6 address translated from 2^static-length minus 1.";
                }
                leaf vpn-name {
                  type string;
                  // NCS drop default statement
                  description
                    "VPN name.";
                }
                leaf protocol {
                  type ncs_template_protocol-type;
                  // NCS drop must statement
                  // NCS drop default statement
                  description
                    "Protocol type.";
                }
              }
            }
            container end-ms {
              description
                "List of End.M type opcode configuration.";
              list end-m {
                // NCS patched for predictable order
                ordered-by user;
                key "value mirror-prefix mirror-mask";
                description
                  "Configure End.M type opcode configuration.";
                leaf value {
                  type string;
                  description
                    "Opcode value. The value ranges from ::1 to ::XX, in which XX is an IPv6 address translated from 2^static-length minus 1.";
                }
                leaf mirror-prefix {
                  type string;
                  description
                    "Mirror locator prefix.";
                }
                leaf mirror-mask {
                  type string;
                  description
                    "Mirror locator mask.";
                }
              }
            }
            container end-dx4s {
              description
                "List of End.DX4 type opcode configuration.";
              list end-dx4 {
                // NCS patched for predictable order
                ordered-by user;
                key "value vpn-name if-name next-hop";
                description
                  "Configure End.DX4 type opcode configuration.";
                leaf value {
                  type string;
                  description
                    "Opcode value. The value ranges from ::1 to ::XX, in which XX is an IPv6 address translated from 2^static-length minus 1.";
                }
                leaf vpn-name {
                  type string;
                  // NCS drop must statement
                  description
                    "VPN name.";
                }
                leaf if-name {
                  type string;
                  description
                    "Interface name. Only support physical port.";
                }
                leaf next-hop {
                  type string;
                  description
                    "NextHop address.";
                }
                leaf protocol {
                  type ncs_template_protocol-type;
                  // NCS drop mandatory statement
                  description
                    "Protocol type.";
                }
              }
            }
            container end-dx6s {
              description
                "List of End.DX6 type opcode configuration.";
              list end-dx6 {
                // NCS patched for predictable order
                ordered-by user;
                key "value vpn-name if-name next-hop";
                description
                  "Configure End.DX6 type opcode configuration.";
                leaf value {
                  type string;
                  description
                    "Opcode value. The value ranges from ::1 to ::XX, in which XX is an IPv6 address translated from 2^static-length minus 1.";
                }
                leaf vpn-name {
                  type string;
                  // NCS drop must statement
                  description
                    "VPN name.";
                }
                leaf if-name {
                  type string;
                  description
                    "Interface name. Only support physical port.";
                }
                leaf next-hop {
                  type string;
                  description
                    "Nexthop address.";
                }
                leaf protocol {
                  type ncs_template_protocol-type;
                  // NCS drop mandatory statement
                  description
                    "Protocol type.";
                }
              }
            }
            container end-ass {
              description
                "List of End.AS type opcode.";
              list end-as {
                // NCS patched for predictable order
                ordered-by user;
                // NCS drop must statement
                key "value";
                description
                  "Configure End.AS type opcode.";
                leaf value {
                  type string;
                  description
                    "Opcode value. The value ranges from ::1 to ::XX, in which XX is an IPv6 address translated from 2^static-length minus 1.";
                }
                leaf backup-value {
                  type string;
                  description
                    "Backup proxy SID function opcode value. The value ranges from ::1 to ::XX, in which XX is an IPv6 address translated from 2^static-length minus 1.";
                }
                leaf inner-type {
                  type ncs_template_inner-type;
                  // NCS drop default statement
                  description
                    "Inner packet type.";
                }
                leaf bypass-enable {
                  type string;
                  // NCS drop default statement
                  description
                    "Enable/disable bypass function of SFC.";
                }
                leaf bypass-sid {
                  // NCS drop when statement
                  type string;
                  description
                    "Bypass SID, that must be a valid SID of other protection device in the SF group.";
                }
                choice service-mode {
                  // NCS drop default statement
                  description
                    "Configure differenciated service mode.";
                  case pipe {
                    description
                      "Pipe mode.";
                    leaf service-class {
                      type ncs_template_service-class;
                      description
                        "Class of service.";
                    }
                    leaf color {
                      type ncs_template_color;
                      description
                        "Packet color.";
                    }
                  }
                  case uniform {
                    description
                      "Uniform mode.";
                    leaf diffserv-uniform {
                      type empty;
                      description
                        "Uniform mode.";
                    }
                  }
                }
                choice ttl-mode {
                  // NCS drop default statement
                  description
                    "Configure TTL mode.";
                  case pipe {
                    description
                      "Pipe mode.";
                    leaf ttl-value {
                      type string;
                      description
                        "TTL value.";
                    }
                  }
                  case uniform {
                    description
                      "Uniform mode.";
                    leaf ttl-uniform {
                      type empty;
                      description
                        "Uniform mode.";
                    }
                  }
                }
                container l2-fwds {
                  description
                    "List of encapsulation for layer 2 packet forwarding.";
                  list l2-fwd {
                    // NCS patched for predictable order
                    ordered-by user;
                    key "out-ifname in-ifname out-vlan in-vlan out-ce-vlan in-ce-vlan";
                    // NCS drop max-elements statement
                    description
                      "Configure encapsulation for layer 2 packet forwarding.";
                    leaf out-ifname {
                      type string;
                      // NCS drop must statement
                      description
                        "Outbound interface from SFF to SF, this interface must be exclusively used by SFC.";
                    }
                    leaf in-ifname {
                      type string;
                      // NCS drop must statement
                      description
                        "Inbound interface from SF to SFF, this interface must be exclusively used by SFC.";
                    }
                    leaf out-vlan {
                      type string;
                      description
                        "Outer VLAN ID of the outbound interface from SFF to SF.";
                    }
                    leaf in-vlan {
                      type string;
                      description
                        "Outer VLAN ID of the inbound interface from SF to SFF.";
                    }
                    leaf out-ce-vlan {
                      type string;
                      // NCS drop must statement
                      description
                        "Inner VLAN ID of the outbound interface from SFF to SF.";
                    }
                    leaf in-ce-vlan {
                      type string;
                      // NCS drop must statement
                      description
                        "Inner VLAN ID of the inbound interface from SF to SFF.";
                    }
                    leaf dest-mac {
                      type pub-type:ncs_template_mac-address;
                      description
                        "MAC address of destination for the inbound interface, that is H-H-H.";
                    }
                  }
                }
                container l3-fwds {
                  description
                    "List of encapsulation for layer 3 packet forwarding.";
                  list l3-fwd {
                    // NCS patched for predictable order
                    ordered-by user;
                    key "next-hop in-ifname out-ifname";
                    description
                      "Configure encapsulation for layer 3 packet forwarding.";
                    leaf next-hop {
                      type string;
                      description
                        "IPv4 next hop address.";
                    }
                    leaf in-ifname {
                      type string;
                      // NCS drop must statement
                      description
                        "Inbound interface from SF to SFF, this interface must be exclusively used by SFC.";
                    }
                    leaf out-ifname {
                      type string;
                      // NCS drop must statement
                      description
                        "Outbound interface from SFF to SF, this interface must be exclusively used by SFC.";
                    }
                    leaf symmetric-index {
                      type string;
                      description
                        "Symmetric index for the forward and reverse traffic on the same VM.";
                    }
                  }
                }
                container cache {
                  description
                    "Configure SR information to be attached on the traffic coming back from SF.";
                  leaf source-address {
                    type string;
                    description
                      "IPv6 source address that encapsulated on the traffic coming back from SF.";
                  }
                  // NCS drop config false leaf 'sl-num'
                  container ipv6addrs {
                    description
                      "List of IPv6 address for encapsulating on the traffic coming back from SF. The local End.AS SID must be in the address list except the first address.";
                    list ipv6addr {
                      // NCS patched for predictable order
                      ordered-by user;
                      key "ipv6-address";
                      // NCS drop max-elements statement
                      description
                        "Configure the IPv6 address for encapsulating on the traffic coming back from SF.";
                      leaf ipv6-address {
                        type string;
                        description
                          "Configure the IPv6 address for encapsulating on the traffic coming back from SF.";
                      }
                    }
                  }
                }
              }
            }
          }
        }
      }
      container remote-end-ops {
        // NCS drop when statement
        description
          "List of remote End.OTP configuration.";
        list remote-end-op {
          // NCS patched for predictable order
          ordered-by user;
          key "sid";
          description
            "Configure remote End.OTP configuration.";
          leaf sid {
            type string;
            description
              "Remote End.OTP SID.";
          }
          leaf prefix-length {
            type string;
            // NCS drop mandatory statement
            description
              "Remote End.OTP SID prefix length.";
          }
        }
      }
      // NCS drop config false container 'local-sids'
      container mapping-policys {
        // NCS drop when statement
        description
          "List of mapping policies.";
        list mapping-policy {
          // NCS patched for predictable order
          ordered-by user;
          key "color";
          description
            "Configure a mapping policy.";
          leaf color {
            type string;
            description
              "Color of a mapping policy.";
          }
          leaf description {
            type string;
            description
              "Description of a mapping policy.";
          }
          leaf type {
            type ncs_template_match-type;
            // NCS drop default statement
            description
              "Type of a mapping policy.";
          }
        }
      }
    }
  }
  augment "/ncs:devices/ncs:device/ncs:live-status/ni:network-instance/ni:instances/ni:instance" {
    description
      "Segment routing IPv6 augment to L3VPN.";
    container srv6 {
      tailf:ncs-device-type "netconf";
      tailf:display-when "not(../../../../../ncs:module) or ../../../../../ncs:module[ncs:name='huawei-srv6'] or (../../../../../ncs:live-status-protocol[not(ncs:capability)]) or (../../../../../ncs:live-status-protocol/ncs:capability/ncs:module[.='huawei-srv6'])";
      // NCS drop when statement
      description
        "Configure segment routing IPv6.";
      leaf enable {
        type boolean;
        // NCS drop default statement
        description
          "Enable/disable segment routing IPv6.";
      }
      leaf te-frr-enable {
        type boolean;
        // NCS drop must statement
        // NCS drop default statement
        description
          "Enable/disable SR TE FRR.";
      }
      leaf end-x-delay-time {
        // NCS drop when statement
        type uint32 {
          range "0..600000";
        }
        units "ms";
        // NCS drop default statement
        description
          "End.X delay time.";
      }
      leaf path-mtu {
        // NCS drop when statement
        type uint32 {
          range "1280..9600";
        }
        // NCS drop must statement
        // NCS drop default statement
        description
          "Path MTU value.";
      }
      leaf path-mtu-reserved {
        // NCS drop when statement
        type uint32 {
          range "1..9600";
        }
        // NCS drop must statement
        description
          "Path MTU reserved value.";
      }
      leaf proxy-peer-sid {
        // NCS drop when statement
        type inet:ipv6-address-no-zone;
        description
          "Peer SID of SFC for anycast.";
      }
      leaf reduce-srh-enable {
        // NCS drop when statement
        type boolean;
        // NCS drop default statement
        description
          "Enable/disable reduce SRH.";
      }
      container encapsulation {
        // NCS drop when statement
        description
          "Configure IPv6 encapsulation configuation.";
        leaf source-address {
          type inet:ipv6-address-no-zone;
          description
            "SRv6 VPN encapsulation source address.";
        }
        leaf hop-limit {
          // NCS drop when statement
          type uint8 {
            range "1..255";
          }
          // NCS drop default statement
          description
            "Encapsulation IPv6 header TTL value.";
        }
      }
      container locators {
        // NCS drop when statement
        description
          "List of SRv6 locator configuration.";
        list locator {
          key "name";
          unique "prefix";
          description
            "Configure SRv6 locator configuration.";
          leaf name {
            type string {
              length "1..31";
            }
            description
              "Locator name.";
          }
          leaf prefix {
            ext:operation-exclude "update";
            type inet:ipv6-address-no-zone;
            // NCS drop mandatory statement
            description
              "IPv6 prefix.";
          }
          leaf prefix-length {
            ext:operation-exclude "update";
            type uint8 {
              range "32..120";
            }
            // NCS drop must statement
            // NCS drop mandatory statement
            description
              "Mask length. The maximum sum value of the mask length, static segment length, and argument segment length is 128.";
          }
          leaf static-length {
            ext:operation-exclude "update";
            type uint8 {
              range "0..96";
            }
            // NCS drop must statement
            // NCS drop default statement
            description
              "The static segment length determines the range of opcode. The maximum sum value of the mask length, static segment length, and argument segment length is 128.";
          }
          leaf args-length {
            ext:operation-exclude "update";
            type uint8 {
              range "0..64";
            }
            // NCS drop must statement
            // NCS drop default statement
            description
              "Argument segment length. The maximum sum value of the mask length, static segment length, and argument segment length is 128.";
          }
          container opcodes {
            // NCS drop when statement
            description
              "Configure SRv6 opcodes configuration.";
            container ends {
              description
                "List of End type opcode configuration.";
              list end {
                key "value";
                // NCS drop max-elements statement
                description
                  "Configure End type opcode configuration.";
                leaf value {
                  type inet:ipv6-address-no-zone;
                  description
                    "Opcode value. The value ranges from ::1 to ::XX, in which XX is an IPv6 address translated from 2^static-length minus 1.";
                }
              }
            }
            container end-psps {
              description
                "List of End psp type opcode configuration.";
              list end-psp {
                key "value";
                // NCS drop max-elements statement
                description
                  "Configure End psp type opcode configuration.";
                leaf value {
                  type inet:ipv6-address-no-zone;
                  description
                    "Opcode value. The value ranges from ::1 to ::XX, in which XX is an IPv6 address translated from 2^static-length minus 1.";
                }
              }
            }
            container end-ops {
              description
                "List of End.OP type opcode configuration.";
              list end-op {
                key "value";
                // NCS drop max-elements statement
                description
                  "Configure End.OP type opcode configuration.";
                leaf value {
                  type inet:ipv6-address-no-zone;
                  description
                    "Opcode value. The value ranges from ::1 to ::XX, in which XX is an IPv6 address translated from 2^static-length minus 1.";
                }
              }
            }
            container end-xs {
              description
                "List of End.X type opcode configuration.";
              list end-x {
                key "value if-name next-hop";
                description
                  "Configure End.X type opcode configuration.";
                leaf value {
                  type inet:ipv6-address-no-zone;
                  description
                    "Opcode value. The value ranges from ::1 to ::XX, in which XX is an IPv6 address translated from 2^static-length minus 1.";
                }
                leaf if-name {
                  type leafref {
                    path "/ncs:devices/ncs:device/ncs:live-status/ifm:ifm/ifm:interfaces/ifm:interface/ifm:name" {
                      tailf:xpath-root 3;
                    }
                  }
                  description
                    "Interface name.";
                }
                leaf next-hop {
                  type inet:ipv6-address-no-zone;
                  description
                    "Nexthop address.";
                }
              }
            }
            container end-x-psps {
              description
                "List of End.X psp type opcode configuration.";
              list end-x-psp {
                key "value if-name next-hop";
                description
                  "Configure End.X psp type opcode configuration.";
                leaf value {
                  type inet:ipv6-address-no-zone;
                  description
                    "Opcode value. The value ranges from ::1 to ::XX, in which XX is an IPv6 address translated from 2^static-length minus 1.";
                }
                leaf if-name {
                  type leafref {
                    path "/ncs:devices/ncs:device/ncs:live-status/ifm:ifm/ifm:interfaces/ifm:interface/ifm:name" {
                      tailf:xpath-root 3;
                    }
                  }
                  description
                    "Interface name.";
                }
                leaf next-hop {
                  type inet:ipv6-address-no-zone;
                  description
                    "NextHop address.";
                }
              }
            }
            container end-dt2us {
              description
                "List of End.DT2U type opcode configuration.";
              list end-dt2u {
                key "value";
                unique "bd-id";
                description
                  "Configure End.DT2U type opcode configuration.";
                leaf value {
                  type inet:ipv6-address-no-zone;
                  description
                    "Opcode value. The value ranges from ::1 to ::XX, in which XX is an IPv6 address translated from 2^static-length minus 1.";
                }
                leaf bd-id {
                  type leafref {
                    path "/ncs:devices/ncs:device/ncs:live-status/bd:bd/bd:instances/bd:instance/bd:id" {
                      tailf:xpath-root 3;
                    }
                  }
                  // NCS drop mandatory statement
                  description
                    "Bridge domain ID.";
                  ext:support-filter "true";
                }
              }
            }
            container end-dt2uls {
              description
                "List of End.DT2UL type opcode configuration.";
              list end-dt2ul {
                key "value";
                unique "bd-id";
                description
                  "Configure End.DT2UL type opcode configuration.";
                leaf value {
                  type inet:ipv6-address-no-zone;
                  description
                    "Opcode value. The value ranges from ::1 to ::XX, in which XX is an IPv6 address translated from 2^static-length minus 1.";
                }
                leaf bd-id {
                  type leafref {
                    path "/ncs:devices/ncs:device/ncs:live-status/bd:bd/bd:instances/bd:instance/bd:id" {
                      tailf:xpath-root 3;
                    }
                  }
                  // NCS drop mandatory statement
                  description
                    "Bridge domain ID.";
                  ext:support-filter "true";
                }
              }
            }
            container end-dt2ms {
              description
                "List of End.DT2M type opcode configuration.";
              list end-dt2m {
                key "value";
                unique "bd-id";
                description
                  "Configure End.DT2M type opcode configuration.";
                leaf value {
                  type inet:ipv6-address-no-zone;
                  description
                    "Opcode value. The value ranges from ::1 to ::XX, in which XX is an IPv6 address translated from 2^static-length minus 1.";
                }
                leaf bd-id {
                  type leafref {
                    path "/ncs:devices/ncs:device/ncs:live-status/bd:bd/bd:instances/bd:instance/bd:id" {
                      tailf:xpath-root 3;
                    }
                  }
                  // NCS drop mandatory statement
                  description
                    "Bridge domain ID.";
                  ext:support-filter "true";
                }
              }
            }
            container end-dx2s {
              description
                "List of End.DX2 type opcode configuration.";
              list end-dx2 {
                key "value";
                unique "evpl-id";
                description
                  "Configure End.DX2 type opcode configuration.";
                leaf value {
                  type inet:ipv6-address-no-zone;
                  description
                    "Opcode value. The value ranges from ::1 to ::XX, in which XX is an IPv6 address translated from 2^static-length minus 1.";
                }
                leaf evpl-id {
                  type leafref {
                    path "/ncs:devices/ncs:device/ncs:live-status/evpl:evpl/evpl:instances/evpl:instance/evpl:id" {
                      tailf:xpath-root 3;
                    }
                  }
                  // NCS drop must statement
                  // NCS drop mandatory statement
                  description
                    "EVPL instance ID.";
                }
              }
            }
            container end-dx2ls {
              description
                "List of End.DX2L type opcode configuration.";
              list end-dx2l {
                key "value";
                unique "evpl-id";
                description
                  "Configure End.DX2L type opcode configuration.";
                leaf value {
                  type inet:ipv6-address-no-zone;
                  description
                    "Opcode value. The value ranges from ::1 to ::XX, in which XX is an IPv6 address translated from 2^static-length minus 1.";
                }
                leaf evpl-id {
                  type leafref {
                    path "/ncs:devices/ncs:device/ncs:live-status/evpl:evpl/evpl:instances/evpl:instance/evpl:id" {
                      tailf:xpath-root 3;
                    }
                  }
                  // NCS drop must statement
                  // NCS drop mandatory statement
                  description
                    "EVPL instance ID.";
                }
              }
            }
            container end-dt4s {
              description
                "List of End.DT4 type opcode configuration.";
              list end-dt4 {
                key "value";
                unique "vpn-name";
                description
                  "Configure End.DT4 type opcode configuration.";
                leaf value {
                  type inet:ipv6-address-no-zone;
                  description
                    "Opcode value. The value ranges from ::1 to ::XX, in which XX is an IPv6 address translated from 2^static-length minus 1.";
                }
                leaf vpn-name {
                  type leafref {
                    path "/ncs:devices/ncs:device/ncs:live-status/ni:network-instance/ni:instances/ni:instance/ni:name" {
                      tailf:xpath-root 3;
                    }
                  }
                  // NCS drop default statement
                  description
                    "VPN name.";
                }
                leaf protocol {
                  type live_ncs_protocol-type;
                  // NCS drop must statement
                  // NCS drop default statement
                  description
                    "Protocol type.";
                }
              }
            }
            container end-dt6s {
              description
                "List of End.DT6 type opcode configuration.";
              list end-dt6 {
                key "value";
                unique "vpn-name";
                description
                  "Configure End.DT6 type opcode configuration.";
                leaf value {
                  type inet:ipv6-address-no-zone;
                  description
                    "Opcode value. The value ranges from ::1 to ::XX, in which XX is an IPv6 address translated from 2^static-length minus 1.";
                }
                leaf vpn-name {
                  type leafref {
                    path "/ncs:devices/ncs:device/ncs:live-status/ni:network-instance/ni:instances/ni:instance/ni:name" {
                      tailf:xpath-root 3;
                    }
                  }
                  // NCS drop default statement
                  description
                    "VPN name.";
                }
                leaf protocol {
                  type live_ncs_protocol-type;
                  // NCS drop must statement
                  // NCS drop default statement
                  description
                    "Protocol type.";
                }
              }
            }
            container end-ms {
              description
                "List of End.M type opcode configuration.";
              list end-m {
                key "value mirror-prefix mirror-mask";
                description
                  "Configure End.M type opcode configuration.";
                leaf value {
                  type inet:ipv6-address-no-zone;
                  description
                    "Opcode value. The value ranges from ::1 to ::XX, in which XX is an IPv6 address translated from 2^static-length minus 1.";
                }
                leaf mirror-prefix {
                  type inet:ipv6-address-no-zone;
                  description
                    "Mirror locator prefix.";
                }
                leaf mirror-mask {
                  type uint8 {
                    range "32..120";
                  }
                  description
                    "Mirror locator mask.";
                }
              }
            }
            container end-dx4s {
              description
                "List of End.DX4 type opcode configuration.";
              list end-dx4 {
                key "value vpn-name if-name next-hop";
                description
                  "Configure End.DX4 type opcode configuration.";
                leaf value {
                  type inet:ipv6-address-no-zone;
                  description
                    "Opcode value. The value ranges from ::1 to ::XX, in which XX is an IPv6 address translated from 2^static-length minus 1.";
                }
                leaf vpn-name {
                  type leafref {
                    path "/ncs:devices/ncs:device/ncs:live-status/ni:network-instance/ni:instances/ni:instance/ni:name" {
                      tailf:xpath-root 3;
                    }
                  }
                  // NCS drop must statement
                  description
                    "VPN name.";
                }
                leaf if-name {
                  type leafref {
                    path "/ncs:devices/ncs:device/ncs:live-status/ifm:ifm/ifm:interfaces/ifm:interface/ifm:name" {
                      tailf:xpath-root 3;
                    }
                  }
                  description
                    "Interface name. Only support physical port.";
                }
                leaf next-hop {
                  type inet:ipv4-address-no-zone;
                  description
                    "NextHop address.";
                }
                leaf protocol {
                  type live_ncs_protocol-type;
                  // NCS drop mandatory statement
                  description
                    "Protocol type.";
                }
              }
            }
            container end-dx6s {
              description
                "List of End.DX6 type opcode configuration.";
              list end-dx6 {
                key "value vpn-name if-name next-hop";
                description
                  "Configure End.DX6 type opcode configuration.";
                leaf value {
                  type inet:ipv6-address-no-zone;
                  description
                    "Opcode value. The value ranges from ::1 to ::XX, in which XX is an IPv6 address translated from 2^static-length minus 1.";
                }
                leaf vpn-name {
                  type leafref {
                    path "/ncs:devices/ncs:device/ncs:live-status/ni:network-instance/ni:instances/ni:instance/ni:name" {
                      tailf:xpath-root 3;
                    }
                  }
                  // NCS drop must statement
                  description
                    "VPN name.";
                }
                leaf if-name {
                  type leafref {
                    path "/ncs:devices/ncs:device/ncs:live-status/ifm:ifm/ifm:interfaces/ifm:interface/ifm:name" {
                      tailf:xpath-root 3;
                    }
                  }
                  description
                    "Interface name. Only support physical port.";
                }
                leaf next-hop {
                  type inet:ipv6-address-no-zone;
                  description
                    "Nexthop address.";
                }
                leaf protocol {
                  type live_ncs_protocol-type;
                  // NCS drop mandatory statement
                  description
                    "Protocol type.";
                }
              }
            }
            container end-ass {
              description
                "List of End.AS type opcode.";
              list end-as {
                // NCS drop must statement
                key "value";
                description
                  "Configure End.AS type opcode.";
                leaf value {
                  type inet:ipv6-address-no-zone;
                  description
                    "Opcode value. The value ranges from ::1 to ::XX, in which XX is an IPv6 address translated from 2^static-length minus 1.";
                }
                leaf backup-value {
                  type inet:ipv6-address-no-zone;
                  description
                    "Backup proxy SID function opcode value. The value ranges from ::1 to ::XX, in which XX is an IPv6 address translated from 2^static-length minus 1.";
                }
                leaf inner-type {
                  type live_ncs_inner-type;
                  // NCS drop default statement
                  description
                    "Inner packet type.";
                }
                leaf bypass-enable {
                  type boolean;
                  // NCS drop default statement
                  description
                    "Enable/disable bypass function of SFC.";
                }
                leaf bypass-sid {
                  // NCS drop when statement
                  type inet:ipv6-address-no-zone;
                  description
                    "Bypass SID, that must be a valid SID of other protection device in the SF group.";
                }
                choice service-mode {
                  // NCS drop default statement
                  description
                    "Configure differenciated service mode.";
                  case pipe {
                    description
                      "Pipe mode.";
                    leaf service-class {
                      type live_ncs_service-class;
                      description
                        "Class of service.";
                    }
                    leaf color {
                      type live_ncs_color;
                      description
                        "Packet color.";
                    }
                  }
                  case uniform {
                    description
                      "Uniform mode.";
                    leaf diffserv-uniform {
                      type empty;
                      description
                        "Uniform mode.";
                    }
                  }
                }
                choice ttl-mode {
                  // NCS drop default statement
                  description
                    "Configure TTL mode.";
                  case pipe {
                    description
                      "Pipe mode.";
                    leaf ttl-value {
                      type uint8 {
                        range "1..255";
                      }
                      description
                        "TTL value.";
                    }
                  }
                  case uniform {
                    description
                      "Uniform mode.";
                    leaf ttl-uniform {
                      type empty;
                      description
                        "Uniform mode.";
                    }
                  }
                }
                container l2-fwds {
                  description
                    "List of encapsulation for layer 2 packet forwarding.";
                  list l2-fwd {
                    key "out-ifname in-ifname out-vlan in-vlan out-ce-vlan in-ce-vlan";
                    // NCS drop max-elements statement
                    description
                      "Configure encapsulation for layer 2 packet forwarding.";
                    leaf out-ifname {
                      type leafref {
                        path "/ncs:devices/ncs:device/ncs:live-status/ifm:ifm/ifm:interfaces/ifm:interface/ifm:name" {
                          tailf:xpath-root 3;
                        }
                      }
                      // NCS drop must statement
                      description
                        "Outbound interface from SFF to SF, this interface must be exclusively used by SFC.";
                    }
                    leaf in-ifname {
                      type leafref {
                        path "/ncs:devices/ncs:device/ncs:live-status/ifm:ifm/ifm:interfaces/ifm:interface/ifm:name" {
                          tailf:xpath-root 3;
                        }
                      }
                      // NCS drop must statement
                      description
                        "Inbound interface from SF to SFF, this interface must be exclusively used by SFC.";
                    }
                    leaf out-vlan {
                      type uint32 {
                        range "0..4094";
                        ext:value-meaning {
                          ext:item "0" {
                            ext:meaning "no-set";
                            description
                              "Value 0 means that the VLAN ID is not set.";
                          }
                        }
                      }
                      description
                        "Outer VLAN ID of the outbound interface from SFF to SF.";
                    }
                    leaf in-vlan {
                      type uint32 {
                        range "0..4094";
                        ext:value-meaning {
                          ext:item "0" {
                            ext:meaning "no-set";
                            description
                              "Value 0 means that the VLAN ID is not set.";
                          }
                        }
                      }
                      description
                        "Outer VLAN ID of the inbound interface from SF to SFF.";
                    }
                    leaf out-ce-vlan {
                      type uint32 {
                        range "0..4094";
                        ext:value-meaning {
                          ext:item "0" {
                            ext:meaning "no-set";
                            description
                              "Value 0 means that the VLAN ID is not set.";
                          }
                        }
                      }
                      // NCS drop must statement
                      description
                        "Inner VLAN ID of the outbound interface from SFF to SF.";
                    }
                    leaf in-ce-vlan {
                      type uint32 {
                        range "0..4094";
                        ext:value-meaning {
                          ext:item "0" {
                            ext:meaning "no-set";
                            description
                              "Value 0 means that the VLAN ID is not set.";
                          }
                        }
                      }
                      // NCS drop must statement
                      description
                        "Inner VLAN ID of the inbound interface from SF to SFF.";
                    }
                    leaf dest-mac {
                      type pub-type:live_ncs_mac-address;
                      description
                        "MAC address of destination for the inbound interface, that is H-H-H.";
                    }
                  }
                }
                container l3-fwds {
                  description
                    "List of encapsulation for layer 3 packet forwarding.";
                  list l3-fwd {
                    key "next-hop in-ifname out-ifname";
                    description
                      "Configure encapsulation for layer 3 packet forwarding.";
                    leaf next-hop {
                      type inet:ipv4-address-no-zone;
                      description
                        "IPv4 next hop address.";
                    }
                    leaf in-ifname {
                      type leafref {
                        path "/ncs:devices/ncs:device/ncs:live-status/ifm:ifm/ifm:interfaces/ifm:interface/ifm:name" {
                          tailf:xpath-root 3;
                        }
                      }
                      // NCS drop must statement
                      description
                        "Inbound interface from SF to SFF, this interface must be exclusively used by SFC.";
                    }
                    leaf out-ifname {
                      type leafref {
                        path "/ncs:devices/ncs:device/ncs:live-status/ifm:ifm/ifm:interfaces/ifm:interface/ifm:name" {
                          tailf:xpath-root 3;
                        }
                      }
                      // NCS drop must statement
                      description
                        "Outbound interface from SFF to SF, this interface must be exclusively used by SFC.";
                    }
                    leaf symmetric-index {
                      type uint32 {
                        range "1..4294967295";
                      }
                      description
                        "Symmetric index for the forward and reverse traffic on the same VM.";
                    }
                  }
                }
                container cache {
                  description
                    "Configure SR information to be attached on the traffic coming back from SF.";
                  leaf source-address {
                    type inet:ipv6-address-no-zone;
                    description
                      "IPv6 source address that encapsulated on the traffic coming back from SF.";
                  }
                  leaf sl-num {
                    type uint32 {
                      range "0..10";
                    }
                    description
                      "Number of route segments remaining.";
                  }
                  container ipv6addrs {
                    description
                      "List of IPv6 address for encapsulating on the traffic coming back from SF. The local End.AS SID must be in the address list except the first address.";
                    list ipv6addr {
                      key "ipv6-address";
                      // NCS drop max-elements statement
                      ordered-by user;
                      description
                        "Configure the IPv6 address for encapsulating on the traffic coming back from SF.";
                      leaf ipv6-address {
                        type inet:ipv6-address-no-zone;
                        description
                          "Configure the IPv6 address for encapsulating on the traffic coming back from SF.";
                      }
                    }
                  }
                }
              }
            }
          }
        }
      }
      container remote-end-ops {
        // NCS drop when statement
        description
          "List of remote End.OTP configuration.";
        list remote-end-op {
          key "sid";
          description
            "Configure remote End.OTP configuration.";
          leaf sid {
            type inet:ipv6-address-no-zone;
            description
              "Remote End.OTP SID.";
          }
          leaf prefix-length {
            type uint8 {
              range "1..128";
            }
            // NCS drop mandatory statement
            description
              "Remote End.OTP SID prefix length.";
          }
        }
      }
      container local-sids {
        description
          "Statistics of segment routing IPv6 local SID list.";
        container ends {
          description
            "List of segment routing IPv6 End local SID list.";
          list end {
            key "value";
            description
              "Statistics of segment routing IPv6 End local SID list.";
            leaf value {
              type inet:ipv6-address-no-zone;
              description
                "End SID value.";
            }
            leaf locator-name {
              type string {
                length "1..32";
              }
              description
                "Locator name.";
            }
          }
        }
        container end-psps {
          description
            "List of segment routing IPv6 End psp local SID list.";
          list end-psp {
            key "value";
            description
              "Statistics of segment routing IPv6 End psp local SID list.";
            leaf value {
              type inet:ipv6-address-no-zone;
              description
                "End SID value.";
            }
            leaf locator-name {
              type string {
                length "1..32";
              }
              description
                "Locator name.";
            }
          }
        }
        container end-ops {
          description
            "List of segment routing IPv6 End.OP local SID list.";
          list end-op {
            key "value";
            description
              "Statistics of segment routing IPv6 End.OP local SID list.";
            leaf value {
              type inet:ipv6-address-no-zone;
              description
                "End.OP SID value.";
            }
            leaf locator-name {
              type string {
                length "1..32";
              }
              description
                "Locator name.";
            }
          }
        }
        container end-xs {
          description
            "List of segment routing IPv6 End.X local SID list.";
          list end-x {
            key "value";
            description
              "Statistics of segment routing IPv6 End.X local SID list.";
            leaf value {
              type inet:ipv6-address-no-zone;
              description
                "End.X SID value.";
            }
            leaf locator-name {
              type string {
                length "1..32";
              }
              description
                "Locator name.";
            }
            container next-hops {
              description
                "List of next hop information.";
              list next-hop {
                key "if-name next-hop";
                description
                  "Statistics of next hop information.";
                leaf if-name {
                  type leafref {
                    path "/ncs:devices/ncs:device/ncs:live-status/ifm:ifm/ifm:interfaces/ifm:interface/ifm:name" {
                      tailf:xpath-root 3;
                    }
                  }
                  description
                    "Exit interface.";
                }
                leaf next-hop {
                  type inet:ipv6-address-no-zone;
                  description
                    "Next hop IPv6 address.";
                }
              }
            }
          }
        }
        container end-x-psps {
          description
            "List of segment routing IPv6 End.X psp local SID list.";
          list end-x-psp {
            key "value";
            description
              "Statistics of segment routing IPv6 End.X psp local SID list.";
            leaf value {
              type inet:ipv6-address-no-zone;
              description
                "End.X SID value.";
            }
            leaf locator-name {
              type string {
                length "1..32";
              }
              description
                "Locator name.";
            }
            container next-hops {
              description
                "List of next hop information.";
              list next-hop {
                key "if-name next-hop";
                description
                  "Statistics of next hop information.";
                leaf if-name {
                  type leafref {
                    path "/ncs:devices/ncs:device/ncs:live-status/ifm:ifm/ifm:interfaces/ifm:interface/ifm:name" {
                      tailf:xpath-root 3;
                    }
                  }
                  description
                    "Exit interface.";
                }
                leaf next-hop {
                  type inet:ipv6-address-no-zone;
                  description
                    "Next hop IPv6 address.";
                }
              }
            }
          }
        }
        container end-dt4s {
          description
            "List of segment routing IPv6 End.DT4 local SID list.";
          list end-dt4 {
            key "value";
            description
              "Statistics of segment routing IPv6 End.DT4 local SID list.";
            leaf value {
              type inet:ipv6-address-no-zone;
              description
                "End.DT4 SID value.";
            }
            leaf vpn-name {
              type string {
                length "1..32";
              }
              description
                "VPN name.";
            }
            leaf locator-name {
              type string {
                length "1..32";
              }
              description
                "Locator name.";
            }
          }
        }
        container end-dt6s {
          description
            "List of segment routing IPv6 End.DT6 local SID list.";
          list end-dt6 {
            key "value";
            description
              "Statistics of segment routing IPv6 End.DT6 local SID list.";
            leaf value {
              type inet:ipv6-address-no-zone;
              description
                "End.DT6 SID value.";
            }
            leaf vpn-name {
              type string {
                length "1..32";
              }
              description
                "VPN name.";
            }
            leaf locator-name {
              type string {
                length "1..32";
              }
              description
                "Locator name.";
            }
          }
        }
        container end-ms {
          description
            "List of segment routing IPv6 End.M local SID list.";
          list end-m {
            key "value";
            description
              "Statistics of segment routing IPv6 End.M local SID list.";
            leaf value {
              type inet:ipv6-address-no-zone;
              description
                "End.M SID value.";
            }
            leaf flavor {
              type string {
                length "1..64";
              }
              description
                "End SID flavor value.";
            }
            leaf locator-name {
              type string {
                length "1..32";
              }
              description
                "Locator name.";
            }
            leaf mirror-locator-number {
              type uint32;
              description
                "Mirror locator number.";
            }
            leaf mirror-locator-set {
              type string {
                length "1..360";
              }
              description
                "Mirror locator address set.";
            }
          }
        }
        container end-dx4s {
          description
            "List of segment routing IPv6 End.DX4 local SID list.";
          list end-dx4 {
            key "value";
            description
              "Statistics of segment routing IPv6 End.DX4 local SID list.";
            leaf value {
              type inet:ipv6-address-no-zone;
              description
                "End.DX4 SID value.";
            }
            leaf vpn-name {
              type string {
                length "1..32";
              }
              description
                "VPN name.";
            }
            leaf locator-name {
              type string {
                length "1..32";
              }
              description
                "Locator name.";
            }
            leaf if-name {
              type string {
                length "1..32";
              }
              description
                "Exit interface.";
            }
            leaf next-hop {
              type inet:ipv4-address-no-zone;
              description
                "Next hop IPv4 address.";
            }
          }
        }
        container end-dx6s {
          description
            "List of segment routing IPv6 End.DX6 local SID list.";
          list end-dx6 {
            key "value";
            description
              "Statistics of segment routing IPv6 End.DX6 local SID list.";
            leaf value {
              type inet:ipv6-address-no-zone;
              description
                "End.DX6 SID value.";
            }
            leaf vpn-name {
              type string {
                length "1..32";
              }
              description
                "VPN name.";
            }
            leaf locator-name {
              type string {
                length "1..32";
              }
              description
                "Locator name.";
            }
            leaf if-name {
              type string {
                length "1..32";
              }
              description
                "Exit interface.";
            }
            leaf next-hop {
              type inet:ipv6-address-no-zone;
              description
                "Next hop IPv6 address.";
            }
          }
        }
      }
      container mapping-policys {
        // NCS drop when statement
        description
          "List of mapping policies.";
        list mapping-policy {
          key "color";
          description
            "Configure a mapping policy.";
          leaf color {
            type uint32 {
              range "0..4294967295";
            }
            description
              "Color of a mapping policy.";
          }
          leaf description {
            type string {
              length "1..242";
            }
            description
              "Description of a mapping policy.";
          }
          leaf type {
            type live_ncs_match-type;
            // NCS drop default statement
            description
              "Type of a mapping policy.";
          }
        }
      }
    }
  }
  augment "/ncs:devices/ncs:device/ncs:config/ni:network-instance/ni:instances/ni:instance" {
    description
      "Segment routing IPv6 augment to L3VPN.";
    container srv6 {
      tailf:ncs-device-type "netconf";
      tailf:display-when "not(../../../../../ncs:module) or ../../../../../ncs:module[ncs:name='huawei-srv6']";
      when "../ni:name='_public_'" {
        tailf:xpath-root 3;
      }
      description
        "Configure segment routing IPv6.";
      leaf enable {
        type boolean;
        default "false";
        description
          "Enable/disable segment routing IPv6.";
      }
      leaf te-frr-enable {
        type boolean;
        must "../te-frr-enable='false' or ../enable='true'" {
          tailf:xpath-root 3;
        }
        default "false";
        description
          "Enable/disable SR TE FRR.";
      }
      leaf end-x-delay-time {
        when "../enable='true'" {
          tailf:xpath-root 3;
        }
        type uint32 {
          range "0..600000";
        }
        units "ms";
        default "0";
        description
          "End.X delay time.";
      }
      leaf path-mtu {
        when "../enable='true'" {
          tailf:xpath-root 3;
        }
        type uint32 {
          range "1280..9600";
        }
        must '(../path-mtu-reserved and (../path-mtu)-(../path-mtu-reserved)>=1280) or not(../path-mtu-reserved)' {
          tailf:xpath-root 3;
        }
        default "9600";
        description
          "Path MTU value.";
      }
      leaf path-mtu-reserved {
        when "../enable='true'" {
          tailf:xpath-root 3;
        }
        type uint32 {
          range "1..9600";
        }
        must '(../path-mtu)-(../path-mtu-reserved)>=1280' {
          tailf:xpath-root 3;
        }
        description
          "Path MTU reserved value.";
      }
      leaf proxy-peer-sid {
        when "../enable='true'" {
          tailf:xpath-root 3;
        }
        type inet:ipv6-address-no-zone;
        description
          "Peer SID of SFC for anycast.";
      }
      leaf reduce-srh-enable {
        when "../enable='true'" {
          tailf:xpath-root 3;
        }
        type boolean;
        default "false";
        description
          "Enable/disable reduce SRH.";
      }
      container encapsulation {
        when "../enable='true'" {
          tailf:xpath-root 3;
        }
        description
          "Configure IPv6 encapsulation configuation.";
        leaf source-address {
          type inet:ipv6-address-no-zone;
          description
            "SRv6 VPN encapsulation source address.";
        }
        leaf hop-limit {
          when '../source-address' {
            tailf:xpath-root 3;
          }
          type uint8 {
            range "1..255";
          }
          default "255";
          description
            "Encapsulation IPv6 header TTL value.";
        }
      }
      container locators {
        when "../enable='true'" {
          tailf:xpath-root 3;
        }
        description
          "List of SRv6 locator configuration.";
        list locator {
          key "name";
          unique "prefix";
          description
            "Configure SRv6 locator configuration.";
          leaf name {
            type string {
              length "1..31";
            }
            description
              "Locator name.";
          }
          leaf prefix {
            ext:operation-exclude "update";
            type inet:ipv6-address-no-zone;
            mandatory true;
            description
              "IPv6 prefix.";
          }
          leaf prefix-length {
            ext:operation-exclude "update";
            type uint8 {
              range "32..120";
            }
            must '../prefix-length+../static-length+../args-length<=128' {
              tailf:xpath-root 3;
            }
            mandatory true;
            description
              "Mask length. The maximum sum value of the mask length, static segment length, and argument segment length is 128.";
          }
          leaf static-length {
            ext:operation-exclude "update";
            type uint8 {
              range "0..96";
            }
            must '../prefix-length+../static-length+../args-length<=128' {
              tailf:xpath-root 3;
            }
            default "0";
            description
              "The static segment length determines the range of opcode. The maximum sum value of the mask length, static segment length, and argument segment length is 128.";
          }
          leaf args-length {
            ext:operation-exclude "update";
            type uint8 {
              range "0..64";
            }
            must '../prefix-length+../static-length+../args-length<=128' {
              tailf:xpath-root 3;
            }
            default "0";
            description
              "Argument segment length. The maximum sum value of the mask length, static segment length, and argument segment length is 128.";
          }
          container opcodes {
            when '../static-length>0' {
              tailf:xpath-root 3;
            }
            description
              "Configure SRv6 opcodes configuration.";
            container ends {
              description
                "List of End type opcode configuration.";
              list end {
                key "value";
                max-elements 1;
                description
                  "Configure End type opcode configuration.";
                leaf value {
                  type inet:ipv6-address-no-zone;
                  description
                    "Opcode value. The value ranges from ::1 to ::XX, in which XX is an IPv6 address translated from 2^static-length minus 1.";
                }
              }
            }
            container end-psps {
              description
                "List of End psp type opcode configuration.";
              list end-psp {
                key "value";
                max-elements 1;
                description
                  "Configure End psp type opcode configuration.";
                leaf value {
                  type inet:ipv6-address-no-zone;
                  description
                    "Opcode value. The value ranges from ::1 to ::XX, in which XX is an IPv6 address translated from 2^static-length minus 1.";
                }
              }
            }
            container end-ops {
              description
                "List of End.OP type opcode configuration.";
              list end-op {
                key "value";
                max-elements 1;
                description
                  "Configure End.OP type opcode configuration.";
                leaf value {
                  type inet:ipv6-address-no-zone;
                  description
                    "Opcode value. The value ranges from ::1 to ::XX, in which XX is an IPv6 address translated from 2^static-length minus 1.";
                }
              }
            }
            container end-xs {
              description
                "List of End.X type opcode configuration.";
              list end-x {
                key "value if-name next-hop";
                description
                  "Configure End.X type opcode configuration.";
                leaf value {
                  type inet:ipv6-address-no-zone;
                  description
                    "Opcode value. The value ranges from ::1 to ::XX, in which XX is an IPv6 address translated from 2^static-length minus 1.";
                }
                leaf if-name {
                  type leafref {
                    path "/ncs:devices/ncs:device/ncs:config/ifm:ifm/ifm:interfaces/ifm:interface/ifm:name" {
                      tailf:xpath-root 3;
                    }
                  }
                  description
                    "Interface name.";
                }
                leaf next-hop {
                  type inet:ipv6-address-no-zone;
                  description
                    "Nexthop address.";
                }
              }
            }
            container end-x-psps {
              description
                "List of End.X psp type opcode configuration.";
              list end-x-psp {
                key "value if-name next-hop";
                description
                  "Configure End.X psp type opcode configuration.";
                leaf value {
                  type inet:ipv6-address-no-zone;
                  description
                    "Opcode value. The value ranges from ::1 to ::XX, in which XX is an IPv6 address translated from 2^static-length minus 1.";
                }
                leaf if-name {
                  type leafref {
                    path "/ncs:devices/ncs:device/ncs:config/ifm:ifm/ifm:interfaces/ifm:interface/ifm:name" {
                      tailf:xpath-root 3;
                    }
                  }
                  description
                    "Interface name.";
                }
                leaf next-hop {
                  type inet:ipv6-address-no-zone;
                  description
                    "NextHop address.";
                }
              }
            }
            container end-dt2us {
              description
                "List of End.DT2U type opcode configuration.";
              list end-dt2u {
                key "value";
                unique "bd-id";
                description
                  "Configure End.DT2U type opcode configuration.";
                leaf value {
                  type inet:ipv6-address-no-zone;
                  description
                    "Opcode value. The value ranges from ::1 to ::XX, in which XX is an IPv6 address translated from 2^static-length minus 1.";
                }
                leaf bd-id {
                  type leafref {
                    path "/ncs:devices/ncs:device/ncs:config/bd:bd/bd:instances/bd:instance/bd:id" {
                      tailf:xpath-root 3;
                    }
                  }
                  mandatory true;
                  description
                    "Bridge domain ID.";
                  ext:support-filter "true";
                }
              }
            }
            container end-dt2uls {
              description
                "List of End.DT2UL type opcode configuration.";
              list end-dt2ul {
                key "value";
                unique "bd-id";
                description
                  "Configure End.DT2UL type opcode configuration.";
                leaf value {
                  type inet:ipv6-address-no-zone;
                  description
                    "Opcode value. The value ranges from ::1 to ::XX, in which XX is an IPv6 address translated from 2^static-length minus 1.";
                }
                leaf bd-id {
                  type leafref {
                    path "/ncs:devices/ncs:device/ncs:config/bd:bd/bd:instances/bd:instance/bd:id" {
                      tailf:xpath-root 3;
                    }
                  }
                  mandatory true;
                  description
                    "Bridge domain ID.";
                  ext:support-filter "true";
                }
              }
            }
            container end-dt2ms {
              description
                "List of End.DT2M type opcode configuration.";
              list end-dt2m {
                key "value";
                unique "bd-id";
                description
                  "Configure End.DT2M type opcode configuration.";
                leaf value {
                  type inet:ipv6-address-no-zone;
                  description
                    "Opcode value. The value ranges from ::1 to ::XX, in which XX is an IPv6 address translated from 2^static-length minus 1.";
                }
                leaf bd-id {
                  type leafref {
                    path "/ncs:devices/ncs:device/ncs:config/bd:bd/bd:instances/bd:instance/bd:id" {
                      tailf:xpath-root 3;
                    }
                  }
                  mandatory true;
                  description
                    "Bridge domain ID.";
                  ext:support-filter "true";
                }
              }
            }
            container end-dx2s {
              description
                "List of End.DX2 type opcode configuration.";
              list end-dx2 {
                key "value";
                unique "evpl-id";
                description
                  "Configure End.DX2 type opcode configuration.";
                leaf value {
                  type inet:ipv6-address-no-zone;
                  description
                    "Opcode value. The value ranges from ::1 to ::XX, in which XX is an IPv6 address translated from 2^static-length minus 1.";
                }
                leaf evpl-id {
                  type leafref {
                    path "/ncs:devices/ncs:device/ncs:config/evpl:evpl/evpl:instances/evpl:instance/evpl:id" {
                      tailf:xpath-root 3;
                    }
                  }
                  must "/evpl:evpl/evpl:instances/evpl:instance[evpl:id=current()]/evpl:mode='srv6-mode'" {
                    tailf:xpath-root 3;
                  }
                  mandatory true;
                  description
                    "EVPL instance ID.";
                }
              }
            }
            container end-dx2ls {
              description
                "List of End.DX2L type opcode configuration.";
              list end-dx2l {
                key "value";
                unique "evpl-id";
                description
                  "Configure End.DX2L type opcode configuration.";
                leaf value {
                  type inet:ipv6-address-no-zone;
                  description
                    "Opcode value. The value ranges from ::1 to ::XX, in which XX is an IPv6 address translated from 2^static-length minus 1.";
                }
                leaf evpl-id {
                  type leafref {
                    path "/ncs:devices/ncs:device/ncs:config/evpl:evpl/evpl:instances/evpl:instance/evpl:id" {
                      tailf:xpath-root 3;
                    }
                  }
                  must "/evpl:evpl/evpl:instances/evpl:instance[evpl:id=current()]/evpl:mode='srv6-mode'" {
                    tailf:xpath-root 3;
                  }
                  mandatory true;
                  description
                    "EVPL instance ID.";
                }
              }
            }
            container end-dt4s {
              description
                "List of End.DT4 type opcode configuration.";
              list end-dt4 {
                key "value";
                unique "vpn-name";
                description
                  "Configure End.DT4 type opcode configuration.";
                leaf value {
                  type inet:ipv6-address-no-zone;
                  description
                    "Opcode value. The value ranges from ::1 to ::XX, in which XX is an IPv6 address translated from 2^static-length minus 1.";
                }
                leaf vpn-name {
                  type leafref {
                    path "/ncs:devices/ncs:device/ncs:config/ni:network-instance/ni:instances/ni:instance/ni:name" {
                      tailf:xpath-root 3;
                    }
                  }
                  default "_public_";
                  description
                    "VPN name.";
                }
                leaf protocol {
                  type protocol-type;
                  must "(../vpn-name='_public_' and ../protocol='null') or (../vpn-name!='_public_' and ../protocol!='null')" {
                    tailf:xpath-root 3;
                  }
                  default "null";
                  description
                    "Protocol type.";
                }
              }
            }
            container end-dt6s {
              description
                "List of End.DT6 type opcode configuration.";
              list end-dt6 {
                key "value";
                unique "vpn-name";
                description
                  "Configure End.DT6 type opcode configuration.";
                leaf value {
                  type inet:ipv6-address-no-zone;
                  description
                    "Opcode value. The value ranges from ::1 to ::XX, in which XX is an IPv6 address translated from 2^static-length minus 1.";
                }
                leaf vpn-name {
                  type leafref {
                    path "/ncs:devices/ncs:device/ncs:config/ni:network-instance/ni:instances/ni:instance/ni:name" {
                      tailf:xpath-root 3;
                    }
                  }
                  default "_public_";
                  description
                    "VPN name.";
                }
                leaf protocol {
                  type protocol-type;
                  must "(../vpn-name='_public_' and ../protocol='null') or (../vpn-name!='_public_' and ../protocol!='null')" {
                    tailf:xpath-root 3;
                  }
                  default "null";
                  description
                    "Protocol type.";
                }
              }
            }
            container end-ms {
              description
                "List of End.M type opcode configuration.";
              list end-m {
                key "value mirror-prefix mirror-mask";
                description
                  "Configure End.M type opcode configuration.";
                leaf value {
                  type inet:ipv6-address-no-zone;
                  description
                    "Opcode value. The value ranges from ::1 to ::XX, in which XX is an IPv6 address translated from 2^static-length minus 1.";
                }
                leaf mirror-prefix {
                  type inet:ipv6-address-no-zone;
                  description
                    "Mirror locator prefix.";
                }
                leaf mirror-mask {
                  type uint8 {
                    range "32..120";
                  }
                  description
                    "Mirror locator mask.";
                }
              }
            }
            container end-dx4s {
              description
                "List of End.DX4 type opcode configuration.";
              list end-dx4 {
                key "value vpn-name if-name next-hop";
                description
                  "Configure End.DX4 type opcode configuration.";
                leaf value {
                  type inet:ipv6-address-no-zone;
                  description
                    "Opcode value. The value ranges from ::1 to ::XX, in which XX is an IPv6 address translated from 2^static-length minus 1.";
                }
                leaf vpn-name {
                  type leafref {
                    path "/ncs:devices/ncs:device/ncs:config/ni:network-instance/ni:instances/ni:instance/ni:name" {
                      tailf:xpath-root 3;
                    }
                  }
                  must "../vpn-name!='_public_'" {
                    tailf:xpath-root 3;
                  }
                  description
                    "VPN name.";
                }
                leaf if-name {
                  type leafref {
                    path "/ncs:devices/ncs:device/ncs:config/ifm:ifm/ifm:interfaces/ifm:interface/ifm:name" {
                      tailf:xpath-root 3;
                    }
                  }
                  description
                    "Interface name. Only support physical port.";
                }
                leaf next-hop {
                  type inet:ipv4-address-no-zone;
                  description
                    "NextHop address.";
                }
                leaf protocol {
                  type protocol-type;
                  mandatory true;
                  description
                    "Protocol type.";
                }
              }
            }
            container end-dx6s {
              description
                "List of End.DX6 type opcode configuration.";
              list end-dx6 {
                key "value vpn-name if-name next-hop";
                description
                  "Configure End.DX6 type opcode configuration.";
                leaf value {
                  type inet:ipv6-address-no-zone;
                  description
                    "Opcode value. The value ranges from ::1 to ::XX, in which XX is an IPv6 address translated from 2^static-length minus 1.";
                }
                leaf vpn-name {
                  type leafref {
                    path "/ncs:devices/ncs:device/ncs:config/ni:network-instance/ni:instances/ni:instance/ni:name" {
                      tailf:xpath-root 3;
                    }
                  }
                  must "../vpn-name!='_public_'" {
                    tailf:xpath-root 3;
                  }
                  description
                    "VPN name.";
                }
                leaf if-name {
                  type leafref {
                    path "/ncs:devices/ncs:device/ncs:config/ifm:ifm/ifm:interfaces/ifm:interface/ifm:name" {
                      tailf:xpath-root 3;
                    }
                  }
                  description
                    "Interface name. Only support physical port.";
                }
                leaf next-hop {
                  type inet:ipv6-address-no-zone;
                  description
                    "Nexthop address.";
                }
                leaf protocol {
                  type protocol-type;
                  mandatory true;
                  description
                    "Protocol type.";
                }
              }
            }
            container end-ass {
              description
                "List of End.AS type opcode.";
              list end-as {
                must '(service-class and color) or (not(service-class) and not(color))' {
                  tailf:xpath-root 3;
                }
                key "value";
                description
                  "Configure End.AS type opcode.";
                leaf value {
                  type inet:ipv6-address-no-zone;
                  description
                    "Opcode value. The value ranges from ::1 to ::XX, in which XX is an IPv6 address translated from 2^static-length minus 1.";
                }
                leaf backup-value {
                  type inet:ipv6-address-no-zone;
                  description
                    "Backup proxy SID function opcode value. The value ranges from ::1 to ::XX, in which XX is an IPv6 address translated from 2^static-length minus 1.";
                }
                leaf inner-type {
                  type inner-type;
                  default "null";
                  description
                    "Inner packet type.";
                }
                leaf bypass-enable {
                  type boolean;
                  default "false";
                  description
                    "Enable/disable bypass function of SFC.";
                }
                leaf bypass-sid {
                  when "../bypass-enable='true'" {
                    tailf:xpath-root 3;
                  }
                  type inet:ipv6-address-no-zone;
                  description
                    "Bypass SID, that must be a valid SID of other protection device in the SF group.";
                }
                choice service-mode {
                  default "uniform";
                  description
                    "Configure differenciated service mode.";
                  case pipe {
                    description
                      "Pipe mode.";
                    leaf service-class {
                      type service-class;
                      description
                        "Class of service.";
                    }
                    leaf color {
                      type color;
                      description
                        "Packet color.";
                    }
                  }
                  case uniform {
                    description
                      "Uniform mode.";
                    leaf diffserv-uniform {
                      type empty;
                      description
                        "Uniform mode.";
                    }
                  }
                }
                choice ttl-mode {
                  default "uniform";
                  description
                    "Configure TTL mode.";
                  case pipe {
                    description
                      "Pipe mode.";
                    leaf ttl-value {
                      type uint8 {
                        range "1..255";
                      }
                      description
                        "TTL value.";
                    }
                  }
                  case uniform {
                    description
                      "Uniform mode.";
                    leaf ttl-uniform {
                      type empty;
                      description
                        "Uniform mode.";
                    }
                  }
                }
                container l2-fwds {
                  description
                    "List of encapsulation for layer 2 packet forwarding.";
                  list l2-fwd {
                    key "out-ifname in-ifname out-vlan in-vlan out-ce-vlan in-ce-vlan";
                    max-elements 1;
                    description
                      "Configure encapsulation for layer 2 packet forwarding.";
                    leaf out-ifname {
                      type leafref {
                        path "/ncs:devices/ncs:device/ncs:config/ifm:ifm/ifm:interfaces/ifm:interface/ifm:name" {
                          tailf:xpath-root 3;
                        }
                      }
                      must "/ifm:ifm/ifm:interfaces/ifm:interface[ifm:name=current()]/ifm:l2-mode-enable='true'" {
                        tailf:xpath-root 3;
                      }
                      description
                        "Outbound interface from SFF to SF, this interface must be exclusively used by SFC.";
                    }
                    leaf in-ifname {
                      type leafref {
                        path "/ncs:devices/ncs:device/ncs:config/ifm:ifm/ifm:interfaces/ifm:interface/ifm:name" {
                          tailf:xpath-root 3;
                        }
                      }
                      must "/ifm:ifm/ifm:interfaces/ifm:interface[ifm:name=current()]/ifm:l2-mode-enable='true'" {
                        tailf:xpath-root 3;
                      }
                      description
                        "Inbound interface from SF to SFF, this interface must be exclusively used by SFC.";
                    }
                    leaf out-vlan {
                      type uint32 {
                        range "0..4094";
                        ext:value-meaning {
                          ext:item "0" {
                            ext:meaning "no-set";
                            description
                              "Value 0 means that the VLAN ID is not set.";
                          }
                        }
                      }
                      description
                        "Outer VLAN ID of the outbound interface from SFF to SF.";
                    }
                    leaf in-vlan {
                      type uint32 {
                        range "0..4094";
                        ext:value-meaning {
                          ext:item "0" {
                            ext:meaning "no-set";
                            description
                              "Value 0 means that the VLAN ID is not set.";
                          }
                        }
                      }
                      description
                        "Outer VLAN ID of the inbound interface from SF to SFF.";
                    }
                    leaf out-ce-vlan {
                      type uint32 {
                        range "0..4094";
                        ext:value-meaning {
                          ext:item "0" {
                            ext:meaning "no-set";
                            description
                              "Value 0 means that the VLAN ID is not set.";
                          }
                        }
                      }
                      must '../out-vlan!=0' {
                        tailf:xpath-root 3;
                      }
                      description
                        "Inner VLAN ID of the outbound interface from SFF to SF.";
                    }
                    leaf in-ce-vlan {
                      type uint32 {
                        range "0..4094";
                        ext:value-meaning {
                          ext:item "0" {
                            ext:meaning "no-set";
                            description
                              "Value 0 means that the VLAN ID is not set.";
                          }
                        }
                      }
                      must '../in-vlan!=0' {
                        tailf:xpath-root 3;
                      }
                      description
                        "Inner VLAN ID of the inbound interface from SF to SFF.";
                    }
                    leaf dest-mac {
                      type pub-type:mac-address;
                      description
                        "MAC address of destination for the inbound interface, that is H-H-H.";
                    }
                  }
                }
                container l3-fwds {
                  description
                    "List of encapsulation for layer 3 packet forwarding.";
                  list l3-fwd {
                    key "next-hop in-ifname out-ifname";
                    description
                      "Configure encapsulation for layer 3 packet forwarding.";
                    leaf next-hop {
                      type inet:ipv4-address-no-zone;
                      description
                        "IPv4 next hop address.";
                    }
                    leaf in-ifname {
                      type leafref {
                        path "/ncs:devices/ncs:device/ncs:config/ifm:ifm/ifm:interfaces/ifm:interface/ifm:name" {
                          tailf:xpath-root 3;
                        }
                      }
                      must "/ifm:ifm/ifm:interfaces/ifm:interface[ifm:name=current()]/ifm:type='Vbdif'" {
                        tailf:xpath-root 3;
                      }
                      description
                        "Inbound interface from SF to SFF, this interface must be exclusively used by SFC.";
                    }
                    leaf out-ifname {
                      type leafref {
                        path "/ncs:devices/ncs:device/ncs:config/ifm:ifm/ifm:interfaces/ifm:interface/ifm:name" {
                          tailf:xpath-root 3;
                        }
                      }
                      must "/ifm:ifm/ifm:interfaces/ifm:interface[ifm:name=current()]/ifm:type='Vbdif'" {
                        tailf:xpath-root 3;
                      }
                      description
                        "Outbound interface from SFF to SF, this interface must be exclusively used by SFC.";
                    }
                    leaf symmetric-index {
                      type uint32 {
                        range "1..4294967295";
                      }
                      description
                        "Symmetric index for the forward and reverse traffic on the same VM.";
                    }
                  }
                }
                container cache {
                  description
                    "Configure SR information to be attached on the traffic coming back from SF.";
                  leaf source-address {
                    type inet:ipv6-address-no-zone;
                    description
                      "IPv6 source address that encapsulated on the traffic coming back from SF.";
                  }
                  // NCS drop config false leaf 'sl-num'
                  container ipv6addrs {
                    description
                      "List of IPv6 address for encapsulating on the traffic coming back from SF. The local End.AS SID must be in the address list except the first address.";
                    list ipv6addr {
                      key "ipv6-address";
                      max-elements 11;
                      ordered-by user;
                      description
                        "Configure the IPv6 address for encapsulating on the traffic coming back from SF.";
                      leaf ipv6-address {
                        type inet:ipv6-address-no-zone;
                        description
                          "Configure the IPv6 address for encapsulating on the traffic coming back from SF.";
                      }
                    }
                  }
                }
              }
            }
          }
        }
      }
      container remote-end-ops {
        when "../enable='true'" {
          tailf:xpath-root 3;
        }
        description
          "List of remote End.OTP configuration.";
        list remote-end-op {
          key "sid";
          description
            "Configure remote End.OTP configuration.";
          leaf sid {
            type inet:ipv6-address-no-zone;
            description
              "Remote End.OTP SID.";
          }
          leaf prefix-length {
            type uint8 {
              range "1..128";
            }
            mandatory true;
            description
              "Remote End.OTP SID prefix length.";
          }
        }
      }
      // NCS drop config false container 'local-sids'
      container mapping-policys {
        when "../enable='true'" {
          tailf:xpath-root 3;
        }
        description
          "List of mapping policies.";
        list mapping-policy {
          key "color";
          description
            "Configure a mapping policy.";
          leaf color {
            type uint32 {
              range "0..4294967295";
            }
            description
              "Color of a mapping policy.";
          }
          leaf description {
            type string {
              length "1..242";
            }
            description
              "Description of a mapping policy.";
          }
          leaf type {
            type match-type;
            default "none";
            description
              "Type of a mapping policy.";
          }
        }
      }
    }
  }
}
