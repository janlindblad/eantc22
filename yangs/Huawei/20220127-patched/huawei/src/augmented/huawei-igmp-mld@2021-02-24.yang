module huawei-igmp-mld {
  // Generated by yanger -t ncs
  tailf:mount-id "huawei-nc-1.0:huawei-nc-1.0";
  tailf:ncs-device-type "netconf";

  namespace "urn:huawei:yang:huawei-igmp-mld";
  prefix igmp-mld;

  import huawei-acl {
    prefix acl;
  }
  import huawei-ethernet {
    prefix ethernet;
  }
  import huawei-ifm {
    prefix ifm;
  }
  import huawei-network-instance {
    prefix ni;
  }
  import huawei-l3-multicast {
    prefix l3mc;
  }
  import huawei-pub-type {
    prefix pub-type;
  }
  import ietf-inet-types {
    prefix inet;
  }
  import huawei-extension {
    prefix ext;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "The module defines the configuration and operational state for
     the Internet Group Management Protocol (IGMP) and Multicast
     Listener Discovery (MLD) protocols.";

  revision 2021-02-24 {
    description
      "Add mld access-limit node.";
    reference "Huawei private.";
  }
  revision 2020-06-21 {
    description
      "Modify must restrictions for static-group configurations.";
    reference "Huawei private.";
  }
  revision 2020-03-04 {
    description
      "Add units for some nodes.";
    reference "Huawei private.";
  }
  revision 2020-01-08 {
    description
      "Modify description; Add ssm-mapping-policy node; Add must for some nodes.";
    reference "Huawei private.";
  }
  revision 2019-03-30 {
    description
      "Initial revision.";
    reference "Huawei private.";
  }
  ext:task-name "igmp";

  typedef ncs_template_querier-local-or-not {
    type string;
    description
      "Whether a query is a local query.";
  }

  typedef ncs_template_timer-state-type {
    type string;
    description
      "The status of a timer.";
  }

  typedef ncs_template_remote-backup-state-type {
    type string;
    description
      "Remote backup state.";
  }

  typedef ncs_template_filter-mode-type {
    type string;
    description
      "Source filter mode.";
  }

  typedef ncs_template_if-state {
    type string;
    description
      "The status of an interface enabled with IGMP or MLD.";
  }

  typedef ncs_rpc_notif_querier-local-or-not {
    type enumeration {
      enum "reserved" {
        value 0;
        description
          "Reserved.";
      }
      enum "no-querier" {
        value 1;
        description
          "Not a querier.";
      }
      enum "this-router" {
        value 2;
        description
          "A local querier.";
      }
      enum "other-router" {
        value 3;
        description
          "Any querier instead of a local querier.";
      }
    }
    description
      "Whether a query is a local query.";
  }

  typedef ncs_rpc_notif_timer-state-type {
    type enumeration {
      enum "off" {
        value 0;
        description
          "The off state.";
      }
      enum "on" {
        value 1;
        description
          "The on state.";
      }
      enum "reserved" {
        value 255;
        description
          "Reserved.";
      }
    }
    description
      "The status of a timer.";
  }

  typedef ncs_rpc_notif_remote-backup-state-type {
    type enumeration {
      enum "remote-backup-disabled" {
        value 0;
        description
          "Remote Backup is disabled.";
      }
      enum "remote-backup-master" {
        value 1;
        description
          "Master state.";
      }
      enum "remote-backup-slave" {
        value 2;
        description
          "Backup state.";
      }
    }
    description
      "Remote backup state.";
  }

  typedef ncs_rpc_notif_filter-mode-type {
    type enumeration {
      enum "include" {
        value 1;
        description
          "The Include mode.";
      }
      enum "exclude" {
        value 2;
        description
          "The Exclude mode.";
      }
      enum "reserved" {
        value 1610612735;
        description
          "Reserved.";
      }
    }
    description
      "Source filter mode.";
  }

  typedef ncs_rpc_notif_if-state {
    type enumeration {
      enum "down" {
        value 1;
        description
          "The interface is Down.";
      }
      enum "up" {
        value 2;
        description
          "The interface is Up.";
      }
    }
    description
      "The status of an interface enabled with IGMP or MLD.";
  }

  typedef live_ncs_querier-local-or-not {
    type enumeration {
      enum "reserved" {
        value 0;
        description
          "Reserved.";
      }
      enum "no-querier" {
        value 1;
        description
          "Not a querier.";
      }
      enum "this-router" {
        value 2;
        description
          "A local querier.";
      }
      enum "other-router" {
        value 3;
        description
          "Any querier instead of a local querier.";
      }
    }
    description
      "Whether a query is a local query.";
  }

  typedef live_ncs_timer-state-type {
    type enumeration {
      enum "off" {
        value 0;
        description
          "The off state.";
      }
      enum "on" {
        value 1;
        description
          "The on state.";
      }
      enum "reserved" {
        value 255;
        description
          "Reserved.";
      }
    }
    description
      "The status of a timer.";
  }

  typedef live_ncs_remote-backup-state-type {
    type enumeration {
      enum "remote-backup-disabled" {
        value 0;
        description
          "Remote Backup is disabled.";
      }
      enum "remote-backup-master" {
        value 1;
        description
          "Master state.";
      }
      enum "remote-backup-slave" {
        value 2;
        description
          "Backup state.";
      }
    }
    description
      "Remote backup state.";
  }

  typedef live_ncs_filter-mode-type {
    type enumeration {
      enum "include" {
        value 1;
        description
          "The Include mode.";
      }
      enum "exclude" {
        value 2;
        description
          "The Exclude mode.";
      }
      enum "reserved" {
        value 1610612735;
        description
          "Reserved.";
      }
    }
    description
      "Source filter mode.";
  }

  typedef live_ncs_if-state {
    type enumeration {
      enum "down" {
        value 1;
        description
          "The interface is Down.";
      }
      enum "up" {
        value 2;
        description
          "The interface is Up.";
      }
    }
    description
      "The status of an interface enabled with IGMP or MLD.";
  }

  typedef querier-local-or-not {
    type enumeration {
      enum "reserved" {
        value 0;
        description
          "Reserved.";
      }
      enum "no-querier" {
        value 1;
        description
          "Not a querier.";
      }
      enum "this-router" {
        value 2;
        description
          "A local querier.";
      }
      enum "other-router" {
        value 3;
        description
          "Any querier instead of a local querier.";
      }
    }
    description
      "Whether a query is a local query.";
  }

  typedef timer-state-type {
    type enumeration {
      enum "off" {
        value 0;
        description
          "The off state.";
      }
      enum "on" {
        value 1;
        description
          "The on state.";
      }
      enum "reserved" {
        value 255;
        description
          "Reserved.";
      }
    }
    description
      "The status of a timer.";
  }

  typedef remote-backup-state-type {
    type enumeration {
      enum "remote-backup-disabled" {
        value 0;
        description
          "Remote Backup is disabled.";
      }
      enum "remote-backup-master" {
        value 1;
        description
          "Master state.";
      }
      enum "remote-backup-slave" {
        value 2;
        description
          "Backup state.";
      }
    }
    description
      "Remote backup state.";
  }

  typedef filter-mode-type {
    type enumeration {
      enum "include" {
        value 1;
        description
          "The Include mode.";
      }
      enum "exclude" {
        value 2;
        description
          "The Exclude mode.";
      }
      enum "reserved" {
        value 1610612735;
        description
          "Reserved.";
      }
    }
    description
      "Source filter mode.";
  }

  typedef if-state {
    type enumeration {
      enum "down" {
        value 1;
        description
          "The interface is Down.";
      }
      enum "up" {
        value 2;
        description
          "The interface is Up.";
      }
    }
    description
      "The status of an interface enabled with IGMP or MLD.";
  }

  grouping ncs_template_interface-status {
    description
      "Display IGMP/MLD status information on interfaces.";
    // NCS drop config false container status
  }

  grouping ncs_template_display-static-group {
    description
      "Display static multicast group information.";
    // NCS drop config false container 'display-static-groups'
  }

  grouping ncs_template_display-group {
    description
      "Display multicast group information.";
    // NCS drop config false container groups
  }

  grouping ncs_rpc_notif_interface-status {
    description
      "Display IGMP/MLD status information on interfaces.";
    container status {
      config false;
      description
        "Operational state of IGMP/MLD on interfaces.";
      leaf address {
        type inet:ip-address-no-zone;
        description
          "Specify the IP address of an interface.";
      }
      leaf state {
        type ncs_rpc_notif_if-state;
        description
          "Specify the status of an interface enabled with a protocol.";
      }
      leaf negotiate-query-interval {
        type uint32 {
          ext:value-meaning {
            ext:item "1627389951" {
              ext:meaning "-";
            }
          }
        }
        units "s";
        description
          "Interval negotiated by non-queriers for sending query messages. The negotiated value is supported by IGMPv3 only.";
      }
      leaf other-querier-timeout {
        type uint32 {
          ext:value-meaning {
            ext:item "1627389951" {
              ext:meaning "-";
            }
          }
        }
        units "s";
        description
          "Specify the timeout period of other queriers. The value is 0 on the interface that acts as the querier.";
      }
      leaf maximum-response-time {
        type uint32;
        units "s";
        description
          "Specify the maximum response time carried in a query message.";
      }
      leaf last-member-query-time {
        type uint32;
        units "s";
        description
          "Specify the timeout period for sending the last-member query message.";
      }
      leaf startup-query-interval {
        type uint32 {
          ext:value-meaning {
            ext:item "1627389951" {
              ext:meaning "-";
            }
          }
        }
        units "s";
        description
          "Specify the interval at which an interface functioning as the querier sends query messages when it is started.";
      }
      leaf startup-query-count {
        type uint32 {
          ext:value-meaning {
            ext:item "1627389951" {
              ext:meaning "-";
            }
          }
        }
        description
          "Specify the number of times that an interface functioning as the querier sends query messages when it is started.";
      }
      leaf querier-address {
        type inet:ip-address-no-zone;
        description
          "Specify the address of a querier.";
      }
      leaf is-local-querier {
        type ncs_rpc_notif_querier-local-or-not;
        description
          "Whether a query is a local query.";
      }
      leaf joins {
        type uint32;
        description
          "Specify the number of groups that an interface has joined. When the interface joins a new group, the value increases by one; when the interface leaves a group, the value remains unchanged.";
      }
      leaf leaves {
        type uint32;
        description
          "Specify the number of groups that the interface leaves. Each time when the interface leaves a group, the value increases by one.";
      }
      leaf negotiated-robustness {
        type uint32 {
          ext:value-meaning {
            ext:item "1627389951" {
              ext:meaning "-";
            }
          }
        }
        description
          "Specify the robustness variable negotiated by non-queriers. The value is supported by IGMPv3 only.";
      }
      leaf startup-query-timer-state {
        type ncs_rpc_notif_timer-state-type;
        description
          "Specify the status of the timer for the interface functioning as the querier after being started. off: The interface immediately sends a query message after being started. on: The interface does not send a query message after being started.";
      }
      leaf other-querier-present-timer-state {
        type ncs_rpc_notif_timer-state-type;
        description
          "Specify the status of the timer identifying whether another querier is present. Off: The interface considers itself as a querier and that no other queriers exist.";
      }
      leaf total-group-reported {
        type uint32;
        description
          "Specify the number of groups that the interface dynamically joins. When an interface dynamically joins a new multicast group, the value increases by one.";
      }
      leaf remote-backup-state {
        type ncs_rpc_notif_remote-backup-state-type;
        description
          "Remote backup state.";
      }
    }
  }

  grouping ncs_rpc_notif_display-static-group {
    description
      "Display static multicast group information.";
    container display-static-groups {
      config false;
      description
        "List of static multicast group information.";
      list display-static-group {
        key "interface group-address";
        description
          "Operational state of static multicast group.";
        leaf interface {
          type string;
          description
            "Specify the name of an interface.";
        }
        leaf group-address {
          type inet:ip-address-no-zone;
          description
            "Specify a multicast group address. In the case of an IPv4, the value is in dotted decimal notation and ranges from 224.0.1.0 to 239.255.255.255; in the case of an IPv6 address, the value is in hexadecimal notation and in the format of FFxA:xxxx:xxxx::xxxx (x ranges from 0 to F and A can be 0, or in the range of 3 to F).";
        }
        leaf source-address {
          type inet:ip-address-no-zone;
          description
            "Specify the address of a multicast source.";
        }
        leaf is-configured-boundary {
          type boolean;
          description
            "Whether the multicast forwarding boundary is configured.";
        }
      }
    }
  }

  grouping ncs_rpc_notif_display-group {
    description
      "Display multicast group information.";
    container groups {
      config false;
      description
        "List of dynamic multicast group.";
      list group {
        key "interface group-address";
        description
          "Multicast group state.";
        leaf interface {
          type string;
          description
            "Specify the name of an interface.";
        }
        leaf group-address {
          type inet:ip-address-no-zone;
          description
            "Specify a multicast group address. In the case of an IPv4 address, the value is in dotted decimal notation and ranges from 224.0.1.0 to 239.255.255.255; in the case of an IPv6 address, the value in hexadecimal notation and in the format of FFxA:xxxx:xxxx::xxxx (x ranges from 0 to F and A can be 0, or in the range of 3 to F).";
        }
        leaf last-report-address {
          type inet:ip-address-no-zone {
            ext:value-meaning {
              ext:item "0.0.0.0" {
                ext:meaning "--";
              }
            }
          }
          description
            "Specify the host that sends the last report message.";
        }
        leaf up-time {
          type pub-type:ncs_rpc_notif_time-tick;
          description
            "Specify the time when a multicast group is discovered, in seconds.";
        }
        leaf expire-time {
          type pub-type:ncs_rpc_notif_time-tick;
          description
            "Specify the scheduled time to remove a group from the group table. The value is expressed in seconds.";
        }
        leaf last-member-query-counter {
          type uint32;
          description
            "Specify the number of times that the last member query message is transmitted.";
        }
        leaf last-member-query-timer {
          type pub-type:ncs_rpc_notif_time-tick;
          description
            "Specify the timeout period for sending last member query messages.";
        }
        leaf source-filter-mode {
          type ncs_rpc_notif_filter-mode-type;
          description
            "Specify the group mode, exclude or include.";
        }
        leaf v1-host-timer {
          type pub-type:ncs_rpc_notif_time-tick;
          description
            "Specify the timeout period of an v1 host.";
        }
        leaf v2-host-timer {
          type pub-type:ncs_rpc_notif_time-tick;
          description
            "Specify the timeout period of an v2 host.";
        }
        leaf is-ssm-mapping {
          type boolean;
          description
            "Identifies an SSM mapping-enabled group.";
        }
        container sources {
          description
            "List of dynamic multicast source.";
          list source {
            key "source-address";
            description
              "Dynamic multicast source state.";
            leaf source-address {
              type inet:ip-address-no-zone;
              description
                "Specify the address of a multicast source.";
            }
            leaf up-time {
              type pub-type:ncs_rpc_notif_time-tick;
              description
                "Specify the time when a multicast source is discovered.";
            }
            leaf expire-time {
              type pub-type:ncs_rpc_notif_time-tick;
              description
                "Specify the time left to delete records from the source table.";
            }
            leaf last-member-query-counter {
              type uint32;
              description
                "Specify the number of times that the last member query message is transmitted.";
            }
            leaf last-member-query-timer {
              type pub-type:ncs_rpc_notif_time-tick;
              description
                "Specify the timeout period for sending last member query messages.";
            }
          }
        }
      }
    }
  }

  grouping live_ncs_interface-status {
    description
      "Display IGMP/MLD status information on interfaces.";
    container status {
      description
        "Operational state of IGMP/MLD on interfaces.";
      leaf address {
        type inet:ip-address-no-zone;
        description
          "Specify the IP address of an interface.";
      }
      leaf state {
        type live_ncs_if-state;
        description
          "Specify the status of an interface enabled with a protocol.";
      }
      leaf negotiate-query-interval {
        type uint32 {
          ext:value-meaning {
            ext:item "1627389951" {
              ext:meaning "-";
            }
          }
        }
        units "s";
        description
          "Interval negotiated by non-queriers for sending query messages. The negotiated value is supported by IGMPv3 only.";
      }
      leaf other-querier-timeout {
        type uint32 {
          ext:value-meaning {
            ext:item "1627389951" {
              ext:meaning "-";
            }
          }
        }
        units "s";
        description
          "Specify the timeout period of other queriers. The value is 0 on the interface that acts as the querier.";
      }
      leaf maximum-response-time {
        type uint32;
        units "s";
        description
          "Specify the maximum response time carried in a query message.";
      }
      leaf last-member-query-time {
        type uint32;
        units "s";
        description
          "Specify the timeout period for sending the last-member query message.";
      }
      leaf startup-query-interval {
        type uint32 {
          ext:value-meaning {
            ext:item "1627389951" {
              ext:meaning "-";
            }
          }
        }
        units "s";
        description
          "Specify the interval at which an interface functioning as the querier sends query messages when it is started.";
      }
      leaf startup-query-count {
        type uint32 {
          ext:value-meaning {
            ext:item "1627389951" {
              ext:meaning "-";
            }
          }
        }
        description
          "Specify the number of times that an interface functioning as the querier sends query messages when it is started.";
      }
      leaf querier-address {
        type inet:ip-address-no-zone;
        description
          "Specify the address of a querier.";
      }
      leaf is-local-querier {
        type live_ncs_querier-local-or-not;
        description
          "Whether a query is a local query.";
      }
      leaf joins {
        type uint32;
        description
          "Specify the number of groups that an interface has joined. When the interface joins a new group, the value increases by one; when the interface leaves a group, the value remains unchanged.";
      }
      leaf leaves {
        type uint32;
        description
          "Specify the number of groups that the interface leaves. Each time when the interface leaves a group, the value increases by one.";
      }
      leaf negotiated-robustness {
        type uint32 {
          ext:value-meaning {
            ext:item "1627389951" {
              ext:meaning "-";
            }
          }
        }
        description
          "Specify the robustness variable negotiated by non-queriers. The value is supported by IGMPv3 only.";
      }
      leaf startup-query-timer-state {
        type live_ncs_timer-state-type;
        description
          "Specify the status of the timer for the interface functioning as the querier after being started. off: The interface immediately sends a query message after being started. on: The interface does not send a query message after being started.";
      }
      leaf other-querier-present-timer-state {
        type live_ncs_timer-state-type;
        description
          "Specify the status of the timer identifying whether another querier is present. Off: The interface considers itself as a querier and that no other queriers exist.";
      }
      leaf total-group-reported {
        type uint32;
        description
          "Specify the number of groups that the interface dynamically joins. When an interface dynamically joins a new multicast group, the value increases by one.";
      }
      leaf remote-backup-state {
        type live_ncs_remote-backup-state-type;
        description
          "Remote backup state.";
      }
    }
  }

  grouping live_ncs_display-static-group {
    description
      "Display static multicast group information.";
    container display-static-groups {
      description
        "List of static multicast group information.";
      list display-static-group {
        key "interface group-address";
        description
          "Operational state of static multicast group.";
        leaf interface {
          type leafref {
            path "/ncs:devices/ncs:device/ncs:live-status/ifm:ifm/ifm:interfaces/ifm:interface/ifm:name" {
              tailf:xpath-root 3;
            }
          }
          description
            "Specify the name of an interface.";
        }
        leaf group-address {
          type inet:ip-address-no-zone;
          description
            "Specify a multicast group address. In the case of an IPv4, the value is in dotted decimal notation and ranges from 224.0.1.0 to 239.255.255.255; in the case of an IPv6 address, the value is in hexadecimal notation and in the format of FFxA:xxxx:xxxx::xxxx (x ranges from 0 to F and A can be 0, or in the range of 3 to F).";
        }
        leaf source-address {
          type inet:ip-address-no-zone;
          description
            "Specify the address of a multicast source.";
        }
        leaf is-configured-boundary {
          type boolean;
          description
            "Whether the multicast forwarding boundary is configured.";
        }
      }
    }
  }

  grouping live_ncs_display-group {
    description
      "Display multicast group information.";
    container groups {
      description
        "List of dynamic multicast group.";
      list group {
        key "interface group-address";
        description
          "Multicast group state.";
        leaf interface {
          type leafref {
            path "/ncs:devices/ncs:device/ncs:live-status/ifm:ifm/ifm:interfaces/ifm:interface/ifm:name" {
              tailf:xpath-root 3;
            }
          }
          description
            "Specify the name of an interface.";
        }
        leaf group-address {
          type inet:ip-address-no-zone;
          description
            "Specify a multicast group address. In the case of an IPv4 address, the value is in dotted decimal notation and ranges from 224.0.1.0 to 239.255.255.255; in the case of an IPv6 address, the value in hexadecimal notation and in the format of FFxA:xxxx:xxxx::xxxx (x ranges from 0 to F and A can be 0, or in the range of 3 to F).";
        }
        leaf last-report-address {
          type inet:ip-address-no-zone {
            ext:value-meaning {
              ext:item "0.0.0.0" {
                ext:meaning "--";
              }
            }
          }
          description
            "Specify the host that sends the last report message.";
        }
        leaf up-time {
          type pub-type:live_ncs_time-tick;
          description
            "Specify the time when a multicast group is discovered, in seconds.";
        }
        leaf expire-time {
          type pub-type:live_ncs_time-tick;
          description
            "Specify the scheduled time to remove a group from the group table. The value is expressed in seconds.";
        }
        leaf last-member-query-counter {
          type uint32;
          description
            "Specify the number of times that the last member query message is transmitted.";
        }
        leaf last-member-query-timer {
          type pub-type:live_ncs_time-tick;
          description
            "Specify the timeout period for sending last member query messages.";
        }
        leaf source-filter-mode {
          type live_ncs_filter-mode-type;
          description
            "Specify the group mode, exclude or include.";
        }
        leaf v1-host-timer {
          type pub-type:live_ncs_time-tick;
          description
            "Specify the timeout period of an v1 host.";
        }
        leaf v2-host-timer {
          type pub-type:live_ncs_time-tick;
          description
            "Specify the timeout period of an v2 host.";
        }
        leaf is-ssm-mapping {
          type boolean;
          description
            "Identifies an SSM mapping-enabled group.";
        }
        container sources {
          description
            "List of dynamic multicast source.";
          list source {
            key "source-address";
            description
              "Dynamic multicast source state.";
            leaf source-address {
              type inet:ip-address-no-zone;
              description
                "Specify the address of a multicast source.";
            }
            leaf up-time {
              type pub-type:live_ncs_time-tick;
              description
                "Specify the time when a multicast source is discovered.";
            }
            leaf expire-time {
              type pub-type:live_ncs_time-tick;
              description
                "Specify the time left to delete records from the source table.";
            }
            leaf last-member-query-counter {
              type uint32;
              description
                "Specify the number of times that the last member query message is transmitted.";
            }
            leaf last-member-query-timer {
              type pub-type:live_ncs_time-tick;
              description
                "Specify the timeout period for sending last member query messages.";
            }
          }
        }
      }
    }
  }

  grouping interface-status {
    description
      "Display IGMP/MLD status information on interfaces.";
    // NCS drop config false container status
  }

  grouping display-static-group {
    description
      "Display static multicast group information.";
    // NCS drop config false container 'display-static-groups'
  }

  grouping display-group {
    description
      "Display multicast group information.";
    // NCS drop config false container groups
  }

  augment "/ncs:devices/ncs:template/ncs:ned-id/ncs:config/ni:network-instance/ni:instances/ni:instance" {
    description
      "Adds igmp/mld configuration to the l3vpn module.";
    container igmp {
      // NCS drop when statement
      description
        "Configure IGMP configurations.";
      container global {
        presence "Create IGMP.";
        description
          "Enable/disable IGMP in an instance.";
        leaf query-interval {
          type string;
          units "s";
          // NCS drop default statement
          description
            "Specify the interval at which the router sends general query messages.";
        }
        leaf query-response-interval {
          type string;
          units "s";
          // NCS drop default statement
          description
            "Specify the maximum response time for a query message.";
        }
        leaf robustness {
          type string;
          // NCS drop default statement
          description
            "Specify the number of times for retransmitting a message to avoid the packet loss.";
        }
        leaf last-member-query-interval {
          type string;
          units "s";
          // NCS drop default statement
          description
            "Specify the interval at which the querier sends last-member query messages. This parameter makes sense only when the current querier runs IGMPv2, IGMPv3 or MLD.";
        }
        leaf require-router-alert {
          type string;
          // NCS drop default statement
          description
            "Enable/disable the router to process the messages whose IP headers contain Router-Alert options globally.";
        }
        leaf send-router-alert {
          type string;
          // NCS drop default statement
          description
            "Enable/disable the router to send the messages with Router-Alert options in the IP headers globally.";
        }
        leaf other-querier-present-time {
          type string;
          units "s";
          description
            "Set the global Keepalive period for other queriers.";
        }
        leaf ssm-mapping-dns-domain {
          type string;
          // NCS drop default statement
          description
            "Specify the name extension of DNS.";
        }
        leaf ssm-mapping-query-dns {
          type string;
          // NCS drop default statement
          description
            "Enable/disable that whether SSM-mapping is based on DNS.";
        }
        leaf ssm-mapping-query-dns-policy {
          // NCS drop when statement
          type string;
          // NCS drop must statement
          description
            "Configure and filter the acl name of DNS ssm-mapping.";
        }
        container ssm-mappings {
          description
            "List of SSM-mapping rules.";
          list ssm-mapping {
            // NCS patched for predictable order
            ordered-by user;
            key "group-address mask-length source-address";
            description
              "Configure SSM-mapping rules.";
            leaf group-address {
              type string;
              description
                "Specify the address of a multicast group. In the case of an IPv4 address, the value ranges from 224.0.1.0 to 239.255.255.255, in dotted decimal notation. In the case of an IPv6 address, the value ranges from FF00:: to FFFF:FFFF:FFFF:FFFF:FFFF:FFFF:FFFF:FFFF, in the hexadecimal format.";
            }
            leaf mask-length {
              type string;
              description
                "Specify the mask length of a multicast group address.";
            }
            leaf source-address {
              type string;
              description
                "Specify the address of a multicast source. In the case of an IPv4 address, the value is in dotted decimal notation; in the case of an IPv6 address, the value ranges from FF00:: to FFFF:FFFF:FFFF:FFFF:FFFF:FFFF:FFFF:FFFF, in hexadecimal notation.";
            }
          }
        }
      }
      container interfaces {
        description
          "List of MGMD configurations on interfaces.";
        list interface {
          // NCS patched for predictable order
          ordered-by user;
          // NCS drop must statement
          key "name";
          description
            "Configure MGMD on an interface.";
          leaf name {
            type string;
            description
              "Specify the type and number of an interface.";
          }
          leaf enable {
            type string;
            // NCS drop default statement
            description
              "Enable/disable protocols on an interface.";
          }
          leaf ip-source-policy-enable {
            type string;
            // NCS drop default statement
            description
              "Enable/disable a policy for filtering IGMP Report messages based on host addresses. By default, no policy is configured for filtering IGMP Report messages based on host addresses.";
          }
          leaf ip-source-policy-name {
            // NCS drop when statement
            type string;
            // NCS drop must statement
            description
              "Configure an ACL that defines a host addresses range. The value is an integer ranging from 2000 to 2999, or a case-sensitive string.";
          }
          leaf query-interval {
            type string;
            units "s";
            // NCS drop default statement
            description
              "Specify the interval at which the router sends general query messages.";
          }
          leaf query-response-interval {
            type string;
            units "s";
            // NCS drop default statement
            description
              "Specify the maximum time for the response to a query message. This time is used to control the deadline of a host's group membership feedback.";
          }
          leaf robustness {
            type string;
            // NCS drop default statement
            description
              "Specify the number of times for retransmitting messages to avoid packet loss.";
          }
          leaf version {
            ext:operation-exclude "update" {
              // NCS drop when statement
              description
                "The version configuration cannot be changed when On-Demand is running on the interface.";
            }
            type string;
            // NCS drop default statement
            description
              "Specify the version of IGMP or MLD running on an interface.";
          }
          leaf last-member-query-interval {
            type string;
            units "s";
            // NCS drop default statement
            description
              "Specify the interval at which the querier sends last-member query messages. This parameter makes sense only when the current querier runs IGMPv2, IGMPv3 or MLD.";
          }
          leaf require-router-alert {
            type string;
            // NCS drop default statement
            description
              "Enable/disable an interface to process messages whose IP headers contain Router-Alert options.";
          }
          leaf send-router-alert {
            type string;
            // NCS drop default statement
            description
              "Enable/disable an interface to send the messages with Router-Alert options in the IP headers.";
          }
          leaf other-querier-present-time {
            type string;
            units "s";
            description
              "Set the Keepalive period for other queriers on an interface.";
          }
          leaf immediately-leave {
            type string;
            // NCS drop default statement
            description
              "Enable/disable an interface that receives a leave message of a certain group to immediately delete the corresponding group records, without sending a last-member query message.";
          }
          leaf immediately-leave-policy {
            // NCS drop when statement
            type string;
            // NCS drop must statement
            description
              "Configure an ACL that defines a multicast group range. The basic ACL number ranges from 2000 to 2999, and the advanced ACL number ranges from 3000 to 3999. The name is a case-sensitive string.";
          }
          leaf on-demand-enable {
            type string;
            // NCS drop must statement
            // NCS drop must statement
            // NCS drop default statement
            description
              "Enable/disable records about the groups that the interface joins never to age. By default, the group records age periodically. 1. This command is applicable to IGMPv2, IGMPv3, and MLD only. 2. This command can be used on the querier only.";
          }
          leaf entry-limit {
            type string;
            description
              "Specify the maximum number of entries that the current interface can create.";
          }
          leaf entry-limit-acl-name {
            // NCS drop when statement
            type string;
            // NCS drop must statement
            description
              "Specify the range of multicast groups, the number of IGMP entries corresponding to which needs not be limited. The basic ACL number ranges from 2000 to 2999. The basic ACL filters group addresses only, without distinguishing (*, G) entries and (S, G) entries; the advanced ACL number ranges from 3000 to 3999. The advanced ACL filters (S, G) entries of the interface only. The name is a case-sensitive string.";
          }
          leaf ssm-mapping-enable {
            type string;
            // NCS drop default statement
            description
              "Enable/disable SSM mapping on an interface.";
          }
          leaf ssm-mapping-policy {
            // NCS drop when statement
            type string;
            description
              "Configure a policy for SSM Mapping on an interface.";
          }
          leaf group-acl-name {
            type string;
            // NCS drop must statement
            description
              "Set a filter for multicast groups on an interface to control the range of multicast groups that hosts can join. The basic ACL number ranges from 2000 to 2999, and the advanced ACL number ranges from 3000 to 3999. The name is a case-sensitive string.";
          }
          leaf group-acl-version {
            // NCS drop when statement
            type string;
            description
              "Forbids hosts that use a specified version to join the multicast group. The version can be specified in this command only after a multicast filtering policy is configured.";
          }
          leaf query-acl-name {
            type string;
            // NCS drop must statement
            description
              "Configure an ACL that defines a host addresses range. The value is an integer ranging from 2000 to 2999, or a case-sensitive string.";
          }
          uses ncs_template_interface-status;
        }
      }
      container static-groups {
        description
          "List of static multicast groups configurations.";
        list static-group {
          // NCS patched for predictable order
          ordered-by user;
          // NCS drop must statement
          key "interface group-address is-source-address source-address is-inc-step-group-mask inc-step-group-mask is-source-dns-ssm-mapping";
          description
            "Configure a static multicast group.";
          leaf interface {
            type string;
            description
              "Specify the name of an interface.";
          }
          leaf group-address {
            type string;
            description
              "Specify the address of a multicast group. In batch configuration mode, this parameter specifies the start multicast group address. In the case of an IPv4 address, the value ranges from 224.0.1.0 to 239.255.255.255, in dotted decimal notation; in the case of an IPv6 address, the value is in hexadecimal notation and in the format of FFxA:xxxx:xxxx::xxxx, among which x ranges from 0 to F and A can be 0, or in the range of 3 to F.";
          }
          leaf is-source-address {
            type string;
            // NCS drop must statement
            description
              "Enable/disable a device to configure an address for the multicast source.";
          }
          leaf source-address {
            type string;
            // NCS drop must statement
            description
              "Specify the address of a multicast source. In the case of an IPv4 address, the value is in dotted decimal notation. In the case of an IPv6 address, the value is in hexadecimal notation.";
          }
          leaf is-inc-step-group-mask {
            type string;
            // NCS drop must statement
            description
              "Enable/disable a device to specify the step mask in batch configuration mode.";
          }
          leaf inc-step-group-mask {
            type string;
            // NCS drop must statement
            description
              "Specify the step mask of a group address in batch configuration mode. It refers to the step between two neighboring multicast group addresses. The value is expressed in wildcard-mask mode and in dotted decimal notation, ranging from 0.0.0.1 to 15.255.255.255.";
          }
          leaf is-source-dns-ssm-mapping {
            type string;
            // NCS drop must statement
            description
              "Enable/disable an DNS based SSM mapping.";
          }
          leaf group-number {
            // NCS drop when statement
            type string;
            // NCS drop mandatory statement
            description
              "Specify the number of multicast group addresses in batch configuration mode.";
          }
        }
      }
      container dot1q-static-groups {
        description
          "List of static multicast groups in dot1q-termination interface.";
        list dot1q-static-group {
          // NCS patched for predictable order
          ordered-by user;
          // NCS drop must statement
          // NCS drop must statement
          // NCS drop must statement
          key "interface group-address is-source-address source-address is-inc-step-group-mask inc-step-group-mask begin-vid end-vid";
          description
            "Configure a static multicast group in a dot1q-termination interface.";
          leaf interface {
            type string;
            description
              "Specify the name of an interface.";
          }
          leaf group-address {
            type string;
            description
              "Specify the address of a multicast group. In batch configuration mode, this parameter specifies the start multicast group address. In the case of an IPv4 address, the value ranges from 224.0.1.0 to 239.255.255.255, in dotted decimal notation; in the case of an IPv6 address, the value is in hexadecimal notation and in the format of FFxA:xxxx:xxxx::xxxx, among which x ranges from 0 to F and A can be 0, or in the range of 3 to F.";
          }
          leaf is-source-address {
            type string;
            description
              "Enable/disable a device to configure an address for the multicast source.";
          }
          leaf source-address {
            type string;
            // NCS drop must statement
            // NCS drop must statement
            description
              "Specify the address of a multicast source. In the case of an IPv4 address, the value is in dotted decimal notation. In the case of an IPv6 address, the value is in hexadecimal notation.";
          }
          leaf is-inc-step-group-mask {
            type string;
            description
              "Enable/disable a device to specify the step mask in batch configuration mode.";
          }
          leaf inc-step-group-mask {
            type string;
            // NCS drop must statement
            description
              "Specify the step mask of a group address in batch configuration mode. It refers to the step between two neighboring multicast group addresses. The value is expressed in wildcard-mask mode and in dotted decimal notation, ranging from 0.0.0.1 to 15.255.255.255.";
          }
          leaf begin-vid {
            type string;
            description
              "Specify the start DOT1Q tag.";
          }
          leaf end-vid {
            type string;
            description
              "Specify the end DOT1Q tag.";
          }
          leaf group-number {
            // NCS drop when statement
            type string;
            // NCS drop mandatory statement
            description
              "Specify the number of multicast group addresses configured in a batch.";
          }
        }
      }
      container qinq-static-groups {
        description
          "List of static multicast groups configuration on qinq-termination interface.";
        list qinq-static-group {
          // NCS patched for predictable order
          ordered-by user;
          // NCS drop must statement
          // NCS drop must statement
          // NCS drop must statement
          key "interface group-address is-source-address source-address is-inc-step-group-mask inc-step-group-mask pe-vid ce-begin-vid ce-end-vid";
          description
            "Configure a static multicast group on a qinq-termination interface.";
          leaf interface {
            type string;
            description
              "Specify the name of an interface.";
          }
          leaf group-address {
            type string;
            description
              "Specify the address of a multicast group. In batch configuration mode, this parameter specifies the start multicast group address. In the case of an IPv4 address, the value ranges from 224.0.1.0 to 239.255.255.255, in dotted decimal notation; in the case of an IPv6 address, the value is in hexadecimal notation and in the format of FFxA:xxxx:xxxx::xxxx, among which x ranges from 0 to F and A can be 0, or in the range of 3 to F.";
          }
          leaf is-source-address {
            type string;
            description
              "Enable/disable a device to configure an address for the multicast source.";
          }
          leaf source-address {
            type string;
            // NCS drop must statement
            // NCS drop must statement
            description
              "Specify the address of a multicast source. In the case of an IPv4 address, the value is in dotted decimal notation. In the case of an IPv6 address, the value is in hexadecimal notation.";
          }
          leaf is-inc-step-group-mask {
            type string;
            description
              "Enable/disable a device to specify the step mask in batch configuration mode.";
          }
          leaf inc-step-group-mask {
            type string;
            // NCS drop must statement
            description
              "Specify the step mask of a group address in batch configuration mode. It refers to the step between two neighboring multicast group addresses. The value is expressed in wildcard-mask mode and in dotted decimal notation, ranging from 0.0.0.1 to 15.255.255.255.";
          }
          leaf pe-vid {
            type string;
            description
              "QINQ PE ID in an outer VLAN tag.";
          }
          leaf ce-begin-vid {
            type string;
            description
              "Specify the start QINQ CE ID.";
          }
          leaf ce-end-vid {
            type string;
            description
              "Specify the end QINQ CE ID.";
          }
          leaf group-number {
            // NCS drop when statement
            type string;
            // NCS drop mandatory statement
            description
              "Specify the number of multicast group addresses configured in a batch.";
          }
        }
      }
      uses ncs_template_display-static-group;
      uses ncs_template_display-group;
    }
    container mld {
      // NCS drop when statement
      description
        "Configure MLD configurations.";
      container global {
        presence "Create MLD.";
        description
          "Enable/disable MLD in an instance.";
        leaf query-interval {
          type string;
          units "s";
          // NCS drop default statement
          description
            "Specify the interval at which the router sends general query messages.";
        }
        leaf query-response-interval {
          type string;
          units "s";
          // NCS drop default statement
          description
            "Specify the maximum response time for a query message.";
        }
        leaf robustness {
          type string;
          // NCS drop default statement
          description
            "Specify the number of times for retransmitting a message to avoid the packet loss.";
        }
        leaf last-member-query-interval {
          type string;
          units "s";
          // NCS drop default statement
          description
            "Specify the interval at which the querier sends last-member query messages. This parameter makes sense only when the current querier runs IGMPv2, IGMPv3 or MLD.";
        }
        leaf require-router-alert {
          type string;
          // NCS drop default statement
          description
            "Enable/disable the router to process the messages whose IP headers contain Router-Alert options globally.";
        }
        leaf send-router-alert {
          type string;
          // NCS drop default statement
          description
            "Enable/disable the router to send the messages with Router-Alert options in the IP headers globally.";
        }
        leaf other-querier-present-time {
          type string;
          units "s";
          description
            "Set the global Keepalive period for other queriers.";
        }
        container ssm-mappings {
          description
            "List of SSM-mapping rules configurations.";
          list ssm-mapping {
            // NCS patched for predictable order
            ordered-by user;
            key "group-address mask-length source-address";
            description
              "Configure a SSM-mapping rule.";
            leaf group-address {
              type string;
              description
                "Specify the address of a multicast group. In the case of an IPv6 address, the value ranges from FF00:: to FFFF:FFFF:FFFF:FFFF:FFFF:FFFF:FFFF:FFFF, in the hexadecimal format.";
            }
            leaf mask-length {
              type string;
              description
                "Specify the mask length of a multicast group address.";
            }
            leaf source-address {
              type string;
              description
                "Specify the address of a multicast source. In the case of an IPv6 address, the value ranges from FF00:: to FFFF:FFFF:FFFF:FFFF:FFFF:FFFF:FFFF:FFFF, in hexadecimal notation.";
            }
          }
        }
      }
      container interfaces {
        description
          "List of MGMD configurations on all interfaces.";
        list interface {
          // NCS patched for predictable order
          ordered-by user;
          // NCS drop must statement
          key "name";
          description
            "Configure MGMD on an interface.";
          leaf name {
            type string;
            description
              "Specify the type and number of an interface.";
          }
          leaf enable {
            type string;
            // NCS drop default statement
            description
              "Enable/disable protocols on an interface.";
          }
          leaf ip-source-policy-enable {
            type string;
            // NCS drop must statement
            // NCS drop default statement
            description
              "Enable/disable a policy for filtering IGMP Report messages based on host addresses.";
          }
          leaf ip-source-policy-name {
            // NCS drop when statement
            type string;
            // NCS drop must statement
            description
              "Configure an ACL that defines a host addresses range. The value is an integer ranging from 2000 to 2999, or a case-sensitive string.";
          }
          leaf query-interval {
            type string;
            units "s";
            // NCS drop default statement
            description
              "Specify the interval at which the router sends general query messages.";
          }
          leaf query-response-interval {
            type string;
            units "s";
            // NCS drop default statement
            description
              "Specify the maximum time for the response to a query message. This time is used to control the deadline of a host's group membership feedback.";
          }
          leaf robustness {
            type string;
            // NCS drop default statement
            description
              "Specify the number of times for retransmitting messages to avoid packet loss.";
          }
          leaf version {
            ext:operation-exclude "update" {
              // NCS drop when statement
              description
                "The version configuration cannot be changed when On-Demand is running on the interface.";
            }
            type string;
            // NCS drop default statement
            description
              "Specify the version of IGMP or MLD running on an interface.";
          }
          leaf last-member-query-interval {
            type string;
            units "s";
            // NCS drop default statement
            description
              "Specify the interval at which the querier sends last-member query messages. This parameter makes sense only when the current querier runs IGMPv2, IGMPv3 or MLD.";
          }
          leaf require-router-alert {
            type string;
            // NCS drop default statement
            description
              "Enable/disable an interface to process messages whose IP headers contain Router-Alert options.";
          }
          leaf send-router-alert {
            type string;
            // NCS drop default statement
            description
              "Enable/disable an interface to send the messages with Router-Alert options in the IP headers.";
          }
          leaf other-querier-present-time {
            type string;
            units "s";
            description
              "Set the Keepalive period for other queriers on an interface. The value ranges from 60 to 300, in second.";
          }
          leaf immediately-leave {
            type string;
            // NCS drop default statement
            description
              "Enable/disable an interface that receives a leave message of a certain group to immediately delete the corresponding group records, without sending a last-member query message.";
          }
          leaf immediately-leave-policy {
            // NCS drop when statement
            type string;
            // NCS drop must statement
            description
              "Configure an ACL that defines a multicast group range. The basic ACL number ranges from 2000 to 2999, and the advanced ACL number ranges from 3000 to 3999. The name is a case-sensitive string.";
          }
          leaf on-demand-enable {
            type string;
            // NCS drop default statement
            description
              "Enable/disable records about the groups that the interface joins never to age. By default, the group records age periodically. 1. This command is applicable to IGMPv2, IGMPv3, and MLD only. 2. This command can be used on the querier only.";
          }
          leaf entry-limit {
            type string;
            description
              "Specify the maximum number of entries that the current interface can create.";
          }
          leaf entry-limit-acl-name {
            // NCS drop when statement
            type string;
            // NCS drop must statement
            description
              "Specify the range of multicast groups, the number of MLD entries corresponding to which needs not be limited. The basic ACL number ranges from 2000 to 2999. The basic ACL filters group addresses only, without distinguishing (*, G) entries and (S, G) entries; the advanced ACL number ranges from 3000 to 3999. The advanced ACL filters (S, G) entries of the interface only. The name is a case-sensitive string.";
          }
          leaf ssm-mapping-enable {
            type string;
            // NCS drop default statement
            description
              "Enable/disable SSM mapping on an interface.";
          }
          leaf group-acl-name {
            type string;
            // NCS drop must statement
            description
              "Set a filter for multicast groups on an interface to control the range of multicast groups that hosts can join. The basic ACL number ranges from 2000 to 2999, and the advanced ACL number ranges from 3000 to 3999. The name is a case-sensitive string.";
          }
          leaf group-acl-version {
            // NCS drop when statement
            type string;
            description
              "Forbids hosts that use a specified version to join the multicast group. The version can be specified in this command only after a multicast filtering policy is configured.";
          }
          leaf query-acl-name {
            type string;
            // NCS drop must statement
            description
              "Configure an ACL that defines a host addresses range. The value is an integer ranging from 2000 to 2999, or a case-sensitive string.";
          }
          uses ncs_template_interface-status;
        }
      }
      container static-groups {
        description
          "List of static multicast groups configurations on interfaces.";
        list static-group {
          // NCS patched for predictable order
          ordered-by user;
          // NCS drop must statement
          key "interface group-address is-source-address source-address is-mask-length mask-length";
          description
            "Configure a static multicast group.";
          leaf interface {
            type string;
            description
              "Specify the name of an interface.";
          }
          leaf group-address {
            type string;
            description
              "Specify the address of a multicast group. In batch configuration mode, this parameter specifies the start multicast group address. In the case of an IPv6 address, the value is in hexadecimal notation and in the format of FFxA:xxxx:xxxx::xxxx, among which x ranges from 0 to F and A can be 0, or in the range of 3 to F.";
          }
          leaf is-source-address {
            type string;
            description
              "Enable/disable a device to configure an address for the multicast source.";
          }
          leaf source-address {
            type string;
            // NCS drop must statement
            // NCS drop must statement
            description
              "Specify the address of a multicast source.";
          }
          leaf is-mask-length {
            type string;
            description
              "Enable/disable a device to specify the length for the step mask of a multicast group address in batch configuration mode.";
          }
          leaf mask-length {
            type string;
            // NCS drop must statement
            description
              "Specify the mask length of a multicast group address. In the case of an IPv6 address, the mask length is 16/32/64/128.";
          }
          leaf total-number {
            // NCS drop when statement
            type string;
            // NCS drop mandatory statement
            description
              "Specify the number of multicast group addresses in batch configuration mode.";
          }
        }
      }
      container dot1q-static-groups {
        description
          "List of static multicast groups on dot1q-termination interfaces.";
        list dot1q-static-group {
          // NCS patched for predictable order
          ordered-by user;
          // NCS drop must statement
          // NCS drop must statement
          // NCS drop must statement
          key "interface group-address is-source-address source-address is-mask-length mask-length begin-vid end-vid";
          description
            "Configure a static multicast group on a dot1q-termination interface.";
          leaf interface {
            type string;
            description
              "Specify the name of an interface.";
          }
          leaf group-address {
            type string;
            description
              "Specify the address of a multicast group. In batch configuration mode, this parameter specifies the start multicast group address. In the case of an IPv6 address, the value is in hexadecimal notation and in the format of FFxA:xxxx:xxxx::xxxx, among which x ranges from 0 to F and A can be 0, or in the range of 3 to F.";
          }
          leaf is-source-address {
            type string;
            description
              "Enable/disable a device to configure an address for the multicast source.";
          }
          leaf source-address {
            type string;
            // NCS drop must statement
            // NCS drop must statement
            description
              "Specify the address of a multicast source.";
          }
          leaf is-mask-length {
            type string;
            description
              "Enable/disable a device to specify the length for the step mask of a multicast group address in batch configuration mode.";
          }
          leaf mask-length {
            type string;
            // NCS drop must statement
            description
              "Specify the step mask length of a multicast group address. An IPv4 address uses a mask with a length from 4 to 32 bits. An IPv6 address uses a mask with a length of 16, 32, 64, or 128 bits.";
          }
          leaf begin-vid {
            type string;
            description
              "Specify the start DOT1Q tag.";
          }
          leaf end-vid {
            type string;
            description
              "Specify the end DOT1Q tag.";
          }
          leaf group-number {
            // NCS drop when statement
            type string;
            // NCS drop mandatory statement
            description
              "Specify the number of multicast group addresses configured in a batch.";
          }
        }
      }
      container qinq-static-groups {
        description
          "List of static multicast groups configuration on qinq-termination interfaces.";
        list qinq-static-group {
          // NCS patched for predictable order
          ordered-by user;
          // NCS drop must statement
          // NCS drop must statement
          // NCS drop must statement
          key "interface group-address is-source-address source-address is-mask-length mask-length pe-vid ce-begin-vid ce-end-vid";
          description
            "Configure a static multicast group.";
          leaf interface {
            type string;
            description
              "Specify the name of an interface.";
          }
          leaf group-address {
            type string;
            description
              "Specify the address of a multicast group. In batch configuration mode, this parameter specifies the start multicast group address. In the case of an IPv6 address, the value is in hexadecimal notation and in the format of FFxA:xxxx:xxxx::xxxx, among which x ranges from 0 to F and A can be 0, or in the range of 3 to F.";
          }
          leaf is-source-address {
            type string;
            description
              "Enable/disable a device to configure an address for the multicast source.";
          }
          leaf source-address {
            type string;
            // NCS drop must statement
            // NCS drop must statement
            description
              "Specify the address of a multicast source.";
          }
          leaf is-mask-length {
            type string;
            description
              "Enable/disable a device to specify the length for the step mask of a multicast group address in batch configuration mode.";
          }
          leaf mask-length {
            type string;
            // NCS drop must statement
            description
              "Specify the step mask length of a multicast group address. An IPv4 address uses a mask with a length from 4 to 32 bits. An IPv6 address uses a mask with a length of 16, 32, 64, or 128 bits.";
          }
          leaf pe-vid {
            type string;
            description
              "QINQ PE ID in an outer VLAN tag.";
          }
          leaf ce-begin-vid {
            type string;
            description
              "Specify the start QINQ CE ID.";
          }
          leaf ce-end-vid {
            type string;
            description
              "Specify the end QINQ CE ID.";
          }
          leaf group-number {
            // NCS drop when statement
            type string;
            // NCS drop mandatory statement
            description
              "Specify the number of multicast group addresses configured in a batch.";
          }
        }
      }
      uses ncs_template_display-static-group;
      uses ncs_template_display-group;
    }
  }
  augment "/ncs:devices/ncs:device/ncs:live-status/ni:network-instance/ni:instances/ni:instance" {
    description
      "Adds igmp/mld configuration to the l3vpn module.";
    container igmp {
      tailf:ncs-device-type "netconf";
      tailf:display-when "not(../../../../../ncs:module) or ../../../../../ncs:module[ncs:name='huawei-igmp-mld'] or (../../../../../ncs:live-status-protocol[not(ncs:capability)]) or (../../../../../ncs:live-status-protocol/ncs:capability/ncs:module[.='huawei-igmp-mld'])";
      // NCS drop when statement
      description
        "Configure IGMP configurations.";
      container global {
        presence "Create IGMP.";
        description
          "Enable/disable IGMP in an instance.";
        leaf query-interval {
          type uint32 {
            range "1..18000";
          }
          units "s";
          // NCS drop default statement
          description
            "Specify the interval at which the router sends general query messages.";
        }
        leaf query-response-interval {
          type uint32 {
            range "1..125";
          }
          units "s";
          // NCS drop default statement
          description
            "Specify the maximum response time for a query message.";
        }
        leaf robustness {
          type uint32 {
            range "2..5";
          }
          // NCS drop default statement
          description
            "Specify the number of times for retransmitting a message to avoid the packet loss.";
        }
        leaf last-member-query-interval {
          type uint32 {
            range "1..25";
          }
          units "s";
          // NCS drop default statement
          description
            "Specify the interval at which the querier sends last-member query messages. This parameter makes sense only when the current querier runs IGMPv2, IGMPv3 or MLD.";
        }
        leaf require-router-alert {
          type boolean;
          // NCS drop default statement
          description
            "Enable/disable the router to process the messages whose IP headers contain Router-Alert options globally.";
        }
        leaf send-router-alert {
          type boolean;
          // NCS drop default statement
          description
            "Enable/disable the router to send the messages with Router-Alert options in the IP headers globally.";
        }
        leaf other-querier-present-time {
          type uint32 {
            range "60..300";
          }
          units "s";
          description
            "Set the global Keepalive period for other queriers.";
        }
        leaf ssm-mapping-dns-domain {
          type string {
            length "1..63";
          }
          // NCS drop default statement
          description
            "Specify the name extension of DNS.";
        }
        leaf ssm-mapping-query-dns {
          type boolean;
          // NCS drop default statement
          description
            "Enable/disable that whether SSM-mapping is based on DNS.";
        }
        leaf ssm-mapping-query-dns-policy {
          // NCS drop when statement
          type leafref {
            path "/ncs:devices/ncs:device/ncs:live-status/acl:acl/acl:groups/acl:group/acl:identity" {
              tailf:xpath-root 3;
            }
          }
          // NCS drop must statement
          description
            "Configure and filter the acl name of DNS ssm-mapping.";
        }
        container ssm-mappings {
          description
            "List of SSM-mapping rules.";
          list ssm-mapping {
            key "group-address mask-length source-address";
            description
              "Configure SSM-mapping rules.";
            leaf group-address {
              type inet:ipv4-address-no-zone {
                pattern '(22[4-9]|23\d)(\.(25[0-5]|2[0-4]\d|1\d\d|[1-9]?\d)){3}';
              }
              description
                "Specify the address of a multicast group. In the case of an IPv4 address, the value ranges from 224.0.1.0 to 239.255.255.255, in dotted decimal notation. In the case of an IPv6 address, the value ranges from FF00:: to FFFF:FFFF:FFFF:FFFF:FFFF:FFFF:FFFF:FFFF, in the hexadecimal format.";
            }
            leaf mask-length {
              type uint32 {
                range "5..32";
              }
              description
                "Specify the mask length of a multicast group address.";
            }
            leaf source-address {
              type inet:ipv4-address-no-zone {
                pattern '(12[0-6]|1[0-1]\d|[1-9]\d|[1-9])(\.(25[0-5]|2[0-4]\d|1\d\d|[1-9]?\d)){3}|(12[8-9]|1[3-9]\d|2[0-1]\d|22[0-3])(\.(25[0-5]|2[0-4]\d|1\d\d|[1-9]?\d)){3}';
              }
              description
                "Specify the address of a multicast source. In the case of an IPv4 address, the value is in dotted decimal notation; in the case of an IPv6 address, the value ranges from FF00:: to FFFF:FFFF:FFFF:FFFF:FFFF:FFFF:FFFF:FFFF, in hexadecimal notation.";
            }
          }
        }
      }
      container interfaces {
        description
          "List of MGMD configurations on interfaces.";
        list interface {
          // NCS drop must statement
          key "name";
          description
            "Configure MGMD on an interface.";
          leaf name {
            type leafref {
              path "/ncs:devices/ncs:device/ncs:live-status/ifm:ifm/ifm:interfaces/ifm:interface/ifm:name" {
                tailf:xpath-root 3;
              }
            }
            description
              "Specify the type and number of an interface.";
          }
          leaf enable {
            type boolean;
            // NCS drop default statement
            description
              "Enable/disable protocols on an interface.";
          }
          leaf ip-source-policy-enable {
            type boolean;
            // NCS drop default statement
            description
              "Enable/disable a policy for filtering IGMP Report messages based on host addresses. By default, no policy is configured for filtering IGMP Report messages based on host addresses.";
          }
          leaf ip-source-policy-name {
            // NCS drop when statement
            type leafref {
              path "/ncs:devices/ncs:device/ncs:live-status/acl:acl/acl:groups/acl:group/acl:identity" {
                tailf:xpath-root 3;
              }
            }
            // NCS drop must statement
            description
              "Configure an ACL that defines a host addresses range. The value is an integer ranging from 2000 to 2999, or a case-sensitive string.";
          }
          leaf query-interval {
            type uint32 {
              range "1..18000";
            }
            units "s";
            // NCS drop default statement
            description
              "Specify the interval at which the router sends general query messages.";
          }
          leaf query-response-interval {
            type uint32 {
              range "1..125";
            }
            units "s";
            // NCS drop default statement
            description
              "Specify the maximum time for the response to a query message. This time is used to control the deadline of a host's group membership feedback.";
          }
          leaf robustness {
            type uint32 {
              range "2..5";
            }
            // NCS drop default statement
            description
              "Specify the number of times for retransmitting messages to avoid packet loss.";
          }
          leaf version {
            ext:operation-exclude "update" {
              // NCS drop when statement
              description
                "The version configuration cannot be changed when On-Demand is running on the interface.";
            }
            type uint32 {
              range "1..3";
            }
            // NCS drop default statement
            description
              "Specify the version of IGMP or MLD running on an interface.";
          }
          leaf last-member-query-interval {
            type uint32 {
              range "1..25";
            }
            units "s";
            // NCS drop default statement
            description
              "Specify the interval at which the querier sends last-member query messages. This parameter makes sense only when the current querier runs IGMPv2, IGMPv3 or MLD.";
          }
          leaf require-router-alert {
            type boolean;
            // NCS drop default statement
            description
              "Enable/disable an interface to process messages whose IP headers contain Router-Alert options.";
          }
          leaf send-router-alert {
            type boolean;
            // NCS drop default statement
            description
              "Enable/disable an interface to send the messages with Router-Alert options in the IP headers.";
          }
          leaf other-querier-present-time {
            type uint32 {
              range "60..300";
            }
            units "s";
            description
              "Set the Keepalive period for other queriers on an interface.";
          }
          leaf immediately-leave {
            type boolean;
            // NCS drop default statement
            description
              "Enable/disable an interface that receives a leave message of a certain group to immediately delete the corresponding group records, without sending a last-member query message.";
          }
          leaf immediately-leave-policy {
            // NCS drop when statement
            type leafref {
              path "/ncs:devices/ncs:device/ncs:live-status/acl:acl/acl:groups/acl:group/acl:identity" {
                tailf:xpath-root 3;
              }
            }
            // NCS drop must statement
            description
              "Configure an ACL that defines a multicast group range. The basic ACL number ranges from 2000 to 2999, and the advanced ACL number ranges from 3000 to 3999. The name is a case-sensitive string.";
          }
          leaf on-demand-enable {
            type boolean;
            // NCS drop must statement
            // NCS drop must statement
            // NCS drop default statement
            description
              "Enable/disable records about the groups that the interface joins never to age. By default, the group records age periodically. 1. This command is applicable to IGMPv2, IGMPv3, and MLD only. 2. This command can be used on the querier only.";
          }
          leaf entry-limit {
            type uint32 {
              range "1..16384";
            }
            description
              "Specify the maximum number of entries that the current interface can create.";
          }
          leaf entry-limit-acl-name {
            // NCS drop when statement
            type leafref {
              path "/ncs:devices/ncs:device/ncs:live-status/acl:acl/acl:groups/acl:group/acl:identity" {
                tailf:xpath-root 3;
              }
            }
            // NCS drop must statement
            description
              "Specify the range of multicast groups, the number of IGMP entries corresponding to which needs not be limited. The basic ACL number ranges from 2000 to 2999. The basic ACL filters group addresses only, without distinguishing (*, G) entries and (S, G) entries; the advanced ACL number ranges from 3000 to 3999. The advanced ACL filters (S, G) entries of the interface only. The name is a case-sensitive string.";
          }
          leaf ssm-mapping-enable {
            type boolean;
            // NCS drop default statement
            description
              "Enable/disable SSM mapping on an interface.";
          }
          leaf ssm-mapping-policy {
            // NCS drop when statement
            type string {
              length "1..31";
            }
            description
              "Configure a policy for SSM Mapping on an interface.";
          }
          leaf group-acl-name {
            type leafref {
              path "/ncs:devices/ncs:device/ncs:live-status/acl:acl/acl:groups/acl:group/acl:identity" {
                tailf:xpath-root 3;
              }
            }
            // NCS drop must statement
            description
              "Set a filter for multicast groups on an interface to control the range of multicast groups that hosts can join. The basic ACL number ranges from 2000 to 2999, and the advanced ACL number ranges from 3000 to 3999. The name is a case-sensitive string.";
          }
          leaf group-acl-version {
            // NCS drop when statement
            type uint32 {
              range "1..3";
            }
            description
              "Forbids hosts that use a specified version to join the multicast group. The version can be specified in this command only after a multicast filtering policy is configured.";
          }
          leaf query-acl-name {
            type leafref {
              path "/ncs:devices/ncs:device/ncs:live-status/acl:acl/acl:groups/acl:group/acl:identity" {
                tailf:xpath-root 3;
              }
            }
            // NCS drop must statement
            description
              "Configure an ACL that defines a host addresses range. The value is an integer ranging from 2000 to 2999, or a case-sensitive string.";
          }
          uses live_ncs_interface-status;
        }
      }
      container static-groups {
        description
          "List of static multicast groups configurations.";
        list static-group {
          // NCS drop must statement
          key "interface group-address is-source-address source-address is-inc-step-group-mask inc-step-group-mask is-source-dns-ssm-mapping";
          description
            "Configure a static multicast group.";
          leaf interface {
            type leafref {
              path "/ncs:devices/ncs:device/ncs:live-status/ifm:ifm/ifm:interfaces/ifm:interface/ifm:name" {
                tailf:xpath-root 3;
              }
            }
            description
              "Specify the name of an interface.";
          }
          leaf group-address {
            type inet:ipv4-address-no-zone {
              pattern '(22[5-9]|23\d)(\.(25[0-5]|2[0-4]\d|1\d\d|[1-9]?\d)){3}|224(\.(25[0-5]|2[0-4]\d|1\d\d|[1-9]\d|[1-9]))(\.(25[0-5]|2[0-4]\d|1\d\d|[1-9]?\d)){2}|224\.0(\.(25[0-5]|2[0-4]\d|1\d\d|[1-9]\d|[1-9]))(\.(25[0-5]|2[0-4]\d|1\d\d|[1-9]?\d))';
            }
            description
              "Specify the address of a multicast group. In batch configuration mode, this parameter specifies the start multicast group address. In the case of an IPv4 address, the value ranges from 224.0.1.0 to 239.255.255.255, in dotted decimal notation; in the case of an IPv6 address, the value is in hexadecimal notation and in the format of FFxA:xxxx:xxxx::xxxx, among which x ranges from 0 to F and A can be 0, or in the range of 3 to F.";
          }
          leaf is-source-address {
            type boolean;
            // NCS drop must statement
            description
              "Enable/disable a device to configure an address for the multicast source.";
          }
          leaf source-address {
            type inet:ipv4-address-no-zone;
            // NCS drop must statement
            description
              "Specify the address of a multicast source. In the case of an IPv4 address, the value is in dotted decimal notation. In the case of an IPv6 address, the value is in hexadecimal notation.";
          }
          leaf is-inc-step-group-mask {
            type boolean;
            // NCS drop must statement
            description
              "Enable/disable a device to specify the step mask in batch configuration mode.";
          }
          leaf inc-step-group-mask {
            type inet:ipv4-address-no-zone;
            // NCS drop must statement
            description
              "Specify the step mask of a group address in batch configuration mode. It refers to the step between two neighboring multicast group addresses. The value is expressed in wildcard-mask mode and in dotted decimal notation, ranging from 0.0.0.1 to 15.255.255.255.";
          }
          leaf is-source-dns-ssm-mapping {
            type boolean;
            // NCS drop must statement
            description
              "Enable/disable an DNS based SSM mapping.";
          }
          leaf group-number {
            // NCS drop when statement
            type uint32 {
              range "2..512";
            }
            // NCS drop mandatory statement
            description
              "Specify the number of multicast group addresses in batch configuration mode.";
          }
        }
      }
      container dot1q-static-groups {
        description
          "List of static multicast groups in dot1q-termination interface.";
        list dot1q-static-group {
          // NCS drop must statement
          // NCS drop must statement
          // NCS drop must statement
          key "interface group-address is-source-address source-address is-inc-step-group-mask inc-step-group-mask begin-vid end-vid";
          description
            "Configure a static multicast group in a dot1q-termination interface.";
          leaf interface {
            type leafref {
              path "/ncs:devices/ncs:device/ncs:live-status/ifm:ifm/ifm:interfaces/ifm:interface/ifm:name" {
                tailf:xpath-root 3;
              }
            }
            description
              "Specify the name of an interface.";
          }
          leaf group-address {
            type inet:ipv4-address-no-zone {
              pattern '(22[5-9]|23\d)(\.(25[0-5]|2[0-4]\d|1\d\d|[1-9]?\d)){3}|224(\.(25[0-5]|2[0-4]\d|1\d\d|[1-9]\d|[1-9]))(\.(25[0-5]|2[0-4]\d|1\d\d|[1-9]?\d)){2}|224\.0(\.(25[0-5]|2[0-4]\d|1\d\d|[1-9]\d|[1-9]))(\.(25[0-5]|2[0-4]\d|1\d\d|[1-9]?\d))';
            }
            description
              "Specify the address of a multicast group. In batch configuration mode, this parameter specifies the start multicast group address. In the case of an IPv4 address, the value ranges from 224.0.1.0 to 239.255.255.255, in dotted decimal notation; in the case of an IPv6 address, the value is in hexadecimal notation and in the format of FFxA:xxxx:xxxx::xxxx, among which x ranges from 0 to F and A can be 0, or in the range of 3 to F.";
          }
          leaf is-source-address {
            type boolean;
            description
              "Enable/disable a device to configure an address for the multicast source.";
          }
          leaf source-address {
            type inet:ipv4-address-no-zone;
            // NCS drop must statement
            // NCS drop must statement
            description
              "Specify the address of a multicast source. In the case of an IPv4 address, the value is in dotted decimal notation. In the case of an IPv6 address, the value is in hexadecimal notation.";
          }
          leaf is-inc-step-group-mask {
            type boolean;
            description
              "Enable/disable a device to specify the step mask in batch configuration mode.";
          }
          leaf inc-step-group-mask {
            type inet:ipv4-address-no-zone;
            // NCS drop must statement
            description
              "Specify the step mask of a group address in batch configuration mode. It refers to the step between two neighboring multicast group addresses. The value is expressed in wildcard-mask mode and in dotted decimal notation, ranging from 0.0.0.1 to 15.255.255.255.";
          }
          leaf begin-vid {
            type uint32 {
              range "1..4094";
            }
            description
              "Specify the start DOT1Q tag.";
          }
          leaf end-vid {
            type uint32 {
              range "1..4094";
            }
            description
              "Specify the end DOT1Q tag.";
          }
          leaf group-number {
            // NCS drop when statement
            type uint32 {
              range "2..512";
            }
            // NCS drop mandatory statement
            description
              "Specify the number of multicast group addresses configured in a batch.";
          }
        }
      }
      container qinq-static-groups {
        description
          "List of static multicast groups configuration on qinq-termination interface.";
        list qinq-static-group {
          // NCS drop must statement
          // NCS drop must statement
          // NCS drop must statement
          key "interface group-address is-source-address source-address is-inc-step-group-mask inc-step-group-mask pe-vid ce-begin-vid ce-end-vid";
          description
            "Configure a static multicast group on a qinq-termination interface.";
          leaf interface {
            type leafref {
              path "/ncs:devices/ncs:device/ncs:live-status/ifm:ifm/ifm:interfaces/ifm:interface/ifm:name" {
                tailf:xpath-root 3;
              }
            }
            description
              "Specify the name of an interface.";
          }
          leaf group-address {
            type inet:ipv4-address-no-zone {
              pattern '(22[5-9]|23\d)(\.(25[0-5]|2[0-4]\d|1\d\d|[1-9]?\d)){3}|224(\.(25[0-5]|2[0-4]\d|1\d\d|[1-9]\d|[1-9]))(\.(25[0-5]|2[0-4]\d|1\d\d|[1-9]?\d)){2}|224\.0(\.(25[0-5]|2[0-4]\d|1\d\d|[1-9]\d|[1-9]))(\.(25[0-5]|2[0-4]\d|1\d\d|[1-9]?\d))';
            }
            description
              "Specify the address of a multicast group. In batch configuration mode, this parameter specifies the start multicast group address. In the case of an IPv4 address, the value ranges from 224.0.1.0 to 239.255.255.255, in dotted decimal notation; in the case of an IPv6 address, the value is in hexadecimal notation and in the format of FFxA:xxxx:xxxx::xxxx, among which x ranges from 0 to F and A can be 0, or in the range of 3 to F.";
          }
          leaf is-source-address {
            type boolean;
            description
              "Enable/disable a device to configure an address for the multicast source.";
          }
          leaf source-address {
            type inet:ipv4-address-no-zone;
            // NCS drop must statement
            // NCS drop must statement
            description
              "Specify the address of a multicast source. In the case of an IPv4 address, the value is in dotted decimal notation. In the case of an IPv6 address, the value is in hexadecimal notation.";
          }
          leaf is-inc-step-group-mask {
            type boolean;
            description
              "Enable/disable a device to specify the step mask in batch configuration mode.";
          }
          leaf inc-step-group-mask {
            type inet:ipv4-address-no-zone;
            // NCS drop must statement
            description
              "Specify the step mask of a group address in batch configuration mode. It refers to the step between two neighboring multicast group addresses. The value is expressed in wildcard-mask mode and in dotted decimal notation, ranging from 0.0.0.1 to 15.255.255.255.";
          }
          leaf pe-vid {
            type uint32 {
              range "1..4094";
            }
            description
              "QINQ PE ID in an outer VLAN tag.";
          }
          leaf ce-begin-vid {
            type uint32 {
              range "1..4094";
            }
            description
              "Specify the start QINQ CE ID.";
          }
          leaf ce-end-vid {
            type uint32 {
              range "1..4094";
            }
            description
              "Specify the end QINQ CE ID.";
          }
          leaf group-number {
            // NCS drop when statement
            type uint32 {
              range "2..512";
            }
            // NCS drop mandatory statement
            description
              "Specify the number of multicast group addresses configured in a batch.";
          }
        }
      }
      uses live_ncs_display-static-group;
      uses live_ncs_display-group;
    }
    container mld {
      tailf:ncs-device-type "netconf";
      tailf:display-when "not(../../../../../ncs:module) or ../../../../../ncs:module[ncs:name='huawei-igmp-mld'] or (../../../../../ncs:live-status-protocol[not(ncs:capability)]) or (../../../../../ncs:live-status-protocol/ncs:capability/ncs:module[.='huawei-igmp-mld'])";
      // NCS drop when statement
      description
        "Configure MLD configurations.";
      container global {
        presence "Create MLD.";
        description
          "Enable/disable MLD in an instance.";
        leaf query-interval {
          type uint32 {
            range "1..18000";
          }
          units "s";
          // NCS drop default statement
          description
            "Specify the interval at which the router sends general query messages.";
        }
        leaf query-response-interval {
          type uint32 {
            range "1..125";
          }
          units "s";
          // NCS drop default statement
          description
            "Specify the maximum response time for a query message.";
        }
        leaf robustness {
          type uint32 {
            range "2..5";
          }
          // NCS drop default statement
          description
            "Specify the number of times for retransmitting a message to avoid the packet loss.";
        }
        leaf last-member-query-interval {
          type uint32 {
            range "1..25";
          }
          units "s";
          // NCS drop default statement
          description
            "Specify the interval at which the querier sends last-member query messages. This parameter makes sense only when the current querier runs IGMPv2, IGMPv3 or MLD.";
        }
        leaf require-router-alert {
          type boolean;
          // NCS drop default statement
          description
            "Enable/disable the router to process the messages whose IP headers contain Router-Alert options globally.";
        }
        leaf send-router-alert {
          type boolean;
          // NCS drop default statement
          description
            "Enable/disable the router to send the messages with Router-Alert options in the IP headers globally.";
        }
        leaf other-querier-present-time {
          type uint32 {
            range "60..300";
          }
          units "s";
          description
            "Set the global Keepalive period for other queriers.";
        }
        container ssm-mappings {
          description
            "List of SSM-mapping rules configurations.";
          list ssm-mapping {
            key "group-address mask-length source-address";
            description
              "Configure a SSM-mapping rule.";
            leaf group-address {
              type inet:ipv6-address-no-zone {
                pattern '([Ff]{2}[0-9a-fA-F]{2})[0-9a-fA-F:\.]*';
              }
              description
                "Specify the address of a multicast group. In the case of an IPv6 address, the value ranges from FF00:: to FFFF:FFFF:FFFF:FFFF:FFFF:FFFF:FFFF:FFFF, in the hexadecimal format.";
            }
            leaf mask-length {
              type uint32 {
                range "16 | 32 | 64 | 128";
              }
              description
                "Specify the mask length of a multicast group address.";
            }
            leaf source-address {
              type inet:ipv6-address-no-zone {
                pattern '(([1-9A-Ea-e][0-9A-Fa-f]{3}:)|([Ff][0-9A-Da-d][0-9A-Fa-f]{2}:)|([Ff][Ee][0-7C-Fc-f][0-9A-Fa-f]:)|((0)?[1-9A-Fa-f][0-9A-Fa-f]{2}:)|((00)?[1-9A-Fa-f][0-9A-Fa-f]:)|((000)?[1-9A-Fa-f]:)).+';
              }
              description
                "Specify the address of a multicast source. In the case of an IPv6 address, the value ranges from FF00:: to FFFF:FFFF:FFFF:FFFF:FFFF:FFFF:FFFF:FFFF, in hexadecimal notation.";
            }
          }
        }
      }
      container interfaces {
        description
          "List of MGMD configurations on all interfaces.";
        list interface {
          // NCS drop must statement
          key "name";
          description
            "Configure MGMD on an interface.";
          leaf name {
            type leafref {
              path "/ncs:devices/ncs:device/ncs:live-status/ifm:ifm/ifm:interfaces/ifm:interface/ifm:name" {
                tailf:xpath-root 3;
              }
            }
            description
              "Specify the type and number of an interface.";
          }
          leaf enable {
            type boolean;
            // NCS drop default statement
            description
              "Enable/disable protocols on an interface.";
          }
          leaf ip-source-policy-enable {
            type boolean;
            // NCS drop must statement
            // NCS drop default statement
            description
              "Enable/disable a policy for filtering IGMP Report messages based on host addresses.";
          }
          leaf ip-source-policy-name {
            // NCS drop when statement
            type leafref {
              path "/ncs:devices/ncs:device/ncs:live-status/acl:acl/acl:group6s/acl:group6/acl:identity" {
                tailf:xpath-root 3;
              }
            }
            // NCS drop must statement
            description
              "Configure an ACL that defines a host addresses range. The value is an integer ranging from 2000 to 2999, or a case-sensitive string.";
          }
          leaf query-interval {
            type uint32 {
              range "1..18000";
            }
            units "s";
            // NCS drop default statement
            description
              "Specify the interval at which the router sends general query messages.";
          }
          leaf query-response-interval {
            type uint32 {
              range "1..125";
            }
            units "s";
            // NCS drop default statement
            description
              "Specify the maximum time for the response to a query message. This time is used to control the deadline of a host's group membership feedback.";
          }
          leaf robustness {
            type uint32 {
              range "2..5";
            }
            // NCS drop default statement
            description
              "Specify the number of times for retransmitting messages to avoid packet loss.";
          }
          leaf version {
            ext:operation-exclude "update" {
              // NCS drop when statement
              description
                "The version configuration cannot be changed when On-Demand is running on the interface.";
            }
            type uint32 {
              range "1..2";
            }
            // NCS drop default statement
            description
              "Specify the version of IGMP or MLD running on an interface.";
          }
          leaf last-member-query-interval {
            type uint32 {
              range "1..25";
            }
            units "s";
            // NCS drop default statement
            description
              "Specify the interval at which the querier sends last-member query messages. This parameter makes sense only when the current querier runs IGMPv2, IGMPv3 or MLD.";
          }
          leaf require-router-alert {
            type boolean;
            // NCS drop default statement
            description
              "Enable/disable an interface to process messages whose IP headers contain Router-Alert options.";
          }
          leaf send-router-alert {
            type boolean;
            // NCS drop default statement
            description
              "Enable/disable an interface to send the messages with Router-Alert options in the IP headers.";
          }
          leaf other-querier-present-time {
            type uint32 {
              range "60..300";
            }
            units "s";
            description
              "Set the Keepalive period for other queriers on an interface. The value ranges from 60 to 300, in second.";
          }
          leaf immediately-leave {
            type boolean;
            // NCS drop default statement
            description
              "Enable/disable an interface that receives a leave message of a certain group to immediately delete the corresponding group records, without sending a last-member query message.";
          }
          leaf immediately-leave-policy {
            // NCS drop when statement
            type leafref {
              path "/ncs:devices/ncs:device/ncs:live-status/acl:acl/acl:group6s/acl:group6/acl:identity" {
                tailf:xpath-root 3;
              }
            }
            // NCS drop must statement
            description
              "Configure an ACL that defines a multicast group range. The basic ACL number ranges from 2000 to 2999, and the advanced ACL number ranges from 3000 to 3999. The name is a case-sensitive string.";
          }
          leaf on-demand-enable {
            type boolean;
            // NCS drop default statement
            description
              "Enable/disable records about the groups that the interface joins never to age. By default, the group records age periodically. 1. This command is applicable to IGMPv2, IGMPv3, and MLD only. 2. This command can be used on the querier only.";
          }
          leaf entry-limit {
            type uint32 {
              range "1..16384";
            }
            description
              "Specify the maximum number of entries that the current interface can create.";
          }
          leaf entry-limit-acl-name {
            // NCS drop when statement
            type leafref {
              path "/ncs:devices/ncs:device/ncs:live-status/acl:acl/acl:group6s/acl:group6/acl:identity" {
                tailf:xpath-root 3;
              }
            }
            // NCS drop must statement
            description
              "Specify the range of multicast groups, the number of MLD entries corresponding to which needs not be limited. The basic ACL number ranges from 2000 to 2999. The basic ACL filters group addresses only, without distinguishing (*, G) entries and (S, G) entries; the advanced ACL number ranges from 3000 to 3999. The advanced ACL filters (S, G) entries of the interface only. The name is a case-sensitive string.";
          }
          leaf ssm-mapping-enable {
            type boolean;
            // NCS drop default statement
            description
              "Enable/disable SSM mapping on an interface.";
          }
          leaf group-acl-name {
            type leafref {
              path "/ncs:devices/ncs:device/ncs:live-status/acl:acl/acl:group6s/acl:group6/acl:identity" {
                tailf:xpath-root 3;
              }
            }
            // NCS drop must statement
            description
              "Set a filter for multicast groups on an interface to control the range of multicast groups that hosts can join. The basic ACL number ranges from 2000 to 2999, and the advanced ACL number ranges from 3000 to 3999. The name is a case-sensitive string.";
          }
          leaf group-acl-version {
            // NCS drop when statement
            type uint32 {
              range "1..2";
            }
            description
              "Forbids hosts that use a specified version to join the multicast group. The version can be specified in this command only after a multicast filtering policy is configured.";
          }
          leaf query-acl-name {
            type leafref {
              path "/ncs:devices/ncs:device/ncs:live-status/acl:acl/acl:group6s/acl:group6/acl:identity" {
                tailf:xpath-root 3;
              }
            }
            // NCS drop must statement
            description
              "Configure an ACL that defines a host addresses range. The value is an integer ranging from 2000 to 2999, or a case-sensitive string.";
          }
          uses live_ncs_interface-status;
        }
      }
      container static-groups {
        description
          "List of static multicast groups configurations on interfaces.";
        list static-group {
          // NCS drop must statement
          key "interface group-address is-source-address source-address is-mask-length mask-length";
          description
            "Configure a static multicast group.";
          leaf interface {
            type leafref {
              path "/ncs:devices/ncs:device/ncs:live-status/ifm:ifm/ifm:interfaces/ifm:interface/ifm:name" {
                tailf:xpath-root 3;
              }
            }
            description
              "Specify the name of an interface.";
          }
          leaf group-address {
            type inet:ipv6-address-no-zone {
              pattern '[Ff]{2}[0-9A-Fa-f][03-9a-fA-F].+';
            }
            description
              "Specify the address of a multicast group. In batch configuration mode, this parameter specifies the start multicast group address. In the case of an IPv6 address, the value is in hexadecimal notation and in the format of FFxA:xxxx:xxxx::xxxx, among which x ranges from 0 to F and A can be 0, or in the range of 3 to F.";
          }
          leaf is-source-address {
            type boolean;
            description
              "Enable/disable a device to configure an address for the multicast source.";
          }
          leaf source-address {
            type inet:ipv6-address-no-zone;
            // NCS drop must statement
            // NCS drop must statement
            description
              "Specify the address of a multicast source.";
          }
          leaf is-mask-length {
            type boolean;
            description
              "Enable/disable a device to specify the length for the step mask of a multicast group address in batch configuration mode.";
          }
          leaf mask-length {
            type uint32 {
              range "0..128";
            }
            // NCS drop must statement
            description
              "Specify the mask length of a multicast group address. In the case of an IPv6 address, the mask length is 16/32/64/128.";
          }
          leaf total-number {
            // NCS drop when statement
            type uint32 {
              range "2..512";
            }
            // NCS drop mandatory statement
            description
              "Specify the number of multicast group addresses in batch configuration mode.";
          }
        }
      }
      container dot1q-static-groups {
        description
          "List of static multicast groups on dot1q-termination interfaces.";
        list dot1q-static-group {
          // NCS drop must statement
          // NCS drop must statement
          // NCS drop must statement
          key "interface group-address is-source-address source-address is-mask-length mask-length begin-vid end-vid";
          description
            "Configure a static multicast group on a dot1q-termination interface.";
          leaf interface {
            type leafref {
              path "/ncs:devices/ncs:device/ncs:live-status/ifm:ifm/ifm:interfaces/ifm:interface/ifm:name" {
                tailf:xpath-root 3;
              }
            }
            description
              "Specify the name of an interface.";
          }
          leaf group-address {
            type inet:ipv6-address-no-zone {
              pattern '[Ff]{2}[0-9A-Fa-f][03-9a-fA-F].+';
            }
            description
              "Specify the address of a multicast group. In batch configuration mode, this parameter specifies the start multicast group address. In the case of an IPv6 address, the value is in hexadecimal notation and in the format of FFxA:xxxx:xxxx::xxxx, among which x ranges from 0 to F and A can be 0, or in the range of 3 to F.";
          }
          leaf is-source-address {
            type boolean;
            description
              "Enable/disable a device to configure an address for the multicast source.";
          }
          leaf source-address {
            type inet:ipv6-address-no-zone;
            // NCS drop must statement
            // NCS drop must statement
            description
              "Specify the address of a multicast source.";
          }
          leaf is-mask-length {
            type boolean;
            description
              "Enable/disable a device to specify the length for the step mask of a multicast group address in batch configuration mode.";
          }
          leaf mask-length {
            type uint32 {
              range "0..128";
            }
            // NCS drop must statement
            description
              "Specify the step mask length of a multicast group address. An IPv4 address uses a mask with a length from 4 to 32 bits. An IPv6 address uses a mask with a length of 16, 32, 64, or 128 bits.";
          }
          leaf begin-vid {
            type uint32 {
              range "1..4094";
            }
            description
              "Specify the start DOT1Q tag.";
          }
          leaf end-vid {
            type uint32 {
              range "1..4094";
            }
            description
              "Specify the end DOT1Q tag.";
          }
          leaf group-number {
            // NCS drop when statement
            type uint32 {
              range "2..512";
            }
            // NCS drop mandatory statement
            description
              "Specify the number of multicast group addresses configured in a batch.";
          }
        }
      }
      container qinq-static-groups {
        description
          "List of static multicast groups configuration on qinq-termination interfaces.";
        list qinq-static-group {
          // NCS drop must statement
          // NCS drop must statement
          // NCS drop must statement
          key "interface group-address is-source-address source-address is-mask-length mask-length pe-vid ce-begin-vid ce-end-vid";
          description
            "Configure a static multicast group.";
          leaf interface {
            type leafref {
              path "/ncs:devices/ncs:device/ncs:live-status/ifm:ifm/ifm:interfaces/ifm:interface/ifm:name" {
                tailf:xpath-root 3;
              }
            }
            description
              "Specify the name of an interface.";
          }
          leaf group-address {
            type inet:ipv6-address-no-zone {
              pattern '[Ff]{2}[0-9A-Fa-f][03-9a-fA-F].+';
            }
            description
              "Specify the address of a multicast group. In batch configuration mode, this parameter specifies the start multicast group address. In the case of an IPv6 address, the value is in hexadecimal notation and in the format of FFxA:xxxx:xxxx::xxxx, among which x ranges from 0 to F and A can be 0, or in the range of 3 to F.";
          }
          leaf is-source-address {
            type boolean;
            description
              "Enable/disable a device to configure an address for the multicast source.";
          }
          leaf source-address {
            type inet:ipv6-address-no-zone;
            // NCS drop must statement
            // NCS drop must statement
            description
              "Specify the address of a multicast source.";
          }
          leaf is-mask-length {
            type boolean;
            description
              "Enable/disable a device to specify the length for the step mask of a multicast group address in batch configuration mode.";
          }
          leaf mask-length {
            type uint32 {
              range "0..128";
            }
            // NCS drop must statement
            description
              "Specify the step mask length of a multicast group address. An IPv4 address uses a mask with a length from 4 to 32 bits. An IPv6 address uses a mask with a length of 16, 32, 64, or 128 bits.";
          }
          leaf pe-vid {
            type uint32 {
              range "1..4094";
            }
            description
              "QINQ PE ID in an outer VLAN tag.";
          }
          leaf ce-begin-vid {
            type uint32 {
              range "1..4094";
            }
            description
              "Specify the start QINQ CE ID.";
          }
          leaf ce-end-vid {
            type uint32 {
              range "1..4094";
            }
            description
              "Specify the end QINQ CE ID.";
          }
          leaf group-number {
            // NCS drop when statement
            type uint32 {
              range "2..512";
            }
            // NCS drop mandatory statement
            description
              "Specify the number of multicast group addresses configured in a batch.";
          }
        }
      }
      uses live_ncs_display-static-group;
      uses live_ncs_display-group;
    }
  }
  augment "/ncs:devices/ncs:device/ncs:config/ni:network-instance/ni:instances/ni:instance" {
    description
      "Adds igmp/mld configuration to the l3vpn module.";
    container igmp {
      tailf:ncs-device-type "netconf";
      tailf:display-when "not(../../../../../ncs:module) or ../../../../../ncs:module[ncs:name='huawei-igmp-mld']";
      when '../l3mc:multicast/l3mc:ipv4' {
        tailf:xpath-root 3;
      }
      description
        "Configure IGMP configurations.";
      container global {
        presence "Create IGMP.";
        description
          "Enable/disable IGMP in an instance.";
        leaf query-interval {
          type uint32 {
            range "1..18000";
          }
          units "s";
          default "60";
          description
            "Specify the interval at which the router sends general query messages.";
        }
        leaf query-response-interval {
          type uint32 {
            range "1..125";
          }
          units "s";
          default "10";
          description
            "Specify the maximum response time for a query message.";
        }
        leaf robustness {
          type uint32 {
            range "2..5";
          }
          default "2";
          description
            "Specify the number of times for retransmitting a message to avoid the packet loss.";
        }
        leaf last-member-query-interval {
          type uint32 {
            range "1..25";
          }
          units "s";
          default "1";
          description
            "Specify the interval at which the querier sends last-member query messages. This parameter makes sense only when the current querier runs IGMPv2, IGMPv3 or MLD.";
        }
        leaf require-router-alert {
          type boolean;
          default "false";
          description
            "Enable/disable the router to process the messages whose IP headers contain Router-Alert options globally.";
        }
        leaf send-router-alert {
          type boolean;
          default "true";
          description
            "Enable/disable the router to send the messages with Router-Alert options in the IP headers globally.";
        }
        leaf other-querier-present-time {
          type uint32 {
            range "60..300";
          }
          units "s";
          description
            "Set the global Keepalive period for other queriers.";
        }
        leaf ssm-mapping-dns-domain {
          type string {
            length "1..63";
          }
          default "in-addr.arpa";
          description
            "Specify the name extension of DNS.";
        }
        leaf ssm-mapping-query-dns {
          type boolean;
          default "false";
          description
            "Enable/disable that whether SSM-mapping is based on DNS.";
        }
        leaf ssm-mapping-query-dns-policy {
          when "../ssm-mapping-query-dns='true'" {
            tailf:xpath-root 3;
          }
          type leafref {
            path "/ncs:devices/ncs:device/ncs:config/acl:acl/acl:groups/acl:group/acl:identity" {
              tailf:xpath-root 3;
            }
          }
          must "/acl:acl/acl:groups/acl:group[acl:identity=current()]/acl:type='basic'" {
            tailf:xpath-root 3;
          }
          description
            "Configure and filter the acl name of DNS ssm-mapping.";
        }
        container ssm-mappings {
          description
            "List of SSM-mapping rules.";
          list ssm-mapping {
            key "group-address mask-length source-address";
            description
              "Configure SSM-mapping rules.";
            leaf group-address {
              type inet:ipv4-address-no-zone {
                pattern '(22[4-9]|23\d)(\.(25[0-5]|2[0-4]\d|1\d\d|[1-9]?\d)){3}';
              }
              description
                "Specify the address of a multicast group. In the case of an IPv4 address, the value ranges from 224.0.1.0 to 239.255.255.255, in dotted decimal notation. In the case of an IPv6 address, the value ranges from FF00:: to FFFF:FFFF:FFFF:FFFF:FFFF:FFFF:FFFF:FFFF, in the hexadecimal format.";
            }
            leaf mask-length {
              type uint32 {
                range "5..32";
              }
              description
                "Specify the mask length of a multicast group address.";
            }
            leaf source-address {
              type inet:ipv4-address-no-zone {
                pattern '(12[0-6]|1[0-1]\d|[1-9]\d|[1-9])(\.(25[0-5]|2[0-4]\d|1\d\d|[1-9]?\d)){3}|(12[8-9]|1[3-9]\d|2[0-1]\d|22[0-3])(\.(25[0-5]|2[0-4]\d|1\d\d|[1-9]?\d)){3}';
              }
              description
                "Specify the address of a multicast source. In the case of an IPv4 address, the value is in dotted decimal notation; in the case of an IPv6 address, the value ranges from FF00:: to FFFF:FFFF:FFFF:FFFF:FFFF:FFFF:FFFF:FFFF, in hexadecimal notation.";
            }
          }
        }
      }
      container interfaces {
        description
          "List of MGMD configurations on interfaces.";
        list interface {
          must '../../../ni:name=/ifm:ifm/ifm:interfaces/ifm:interface[ifm:name=current()/name]/ifm:vrf-name' {
            tailf:xpath-root 3;
          }
          key "name";
          description
            "Configure MGMD on an interface.";
          leaf name {
            type leafref {
              path "/ncs:devices/ncs:device/ncs:config/ifm:ifm/ifm:interfaces/ifm:interface/ifm:name" {
                tailf:xpath-root 3;
              }
            }
            description
              "Specify the type and number of an interface.";
          }
          leaf enable {
            type boolean;
            default "false";
            description
              "Enable/disable protocols on an interface.";
          }
          leaf ip-source-policy-enable {
            type boolean;
            default "false";
            description
              "Enable/disable a policy for filtering IGMP Report messages based on host addresses. By default, no policy is configured for filtering IGMP Report messages based on host addresses.";
          }
          leaf ip-source-policy-name {
            when "../ip-source-policy-enable='true'" {
              tailf:xpath-root 3;
            }
            type leafref {
              path "/ncs:devices/ncs:device/ncs:config/acl:acl/acl:groups/acl:group/acl:identity" {
                tailf:xpath-root 3;
              }
            }
            must "/acl:acl/acl:groups/acl:group[acl:identity=current()]/acl:type='basic'" {
              tailf:xpath-root 3;
            }
            description
              "Configure an ACL that defines a host addresses range. The value is an integer ranging from 2000 to 2999, or a case-sensitive string.";
          }
          leaf query-interval {
            type uint32 {
              range "1..18000";
            }
            units "s";
            default "60";
            description
              "Specify the interval at which the router sends general query messages.";
          }
          leaf query-response-interval {
            type uint32 {
              range "1..125";
            }
            units "s";
            default "10";
            description
              "Specify the maximum time for the response to a query message. This time is used to control the deadline of a host's group membership feedback.";
          }
          leaf robustness {
            type uint32 {
              range "2..5";
            }
            default "2";
            description
              "Specify the number of times for retransmitting messages to avoid packet loss.";
          }
          leaf version {
            ext:operation-exclude "update" {
              when "../on-demand-enable='true'" {
                tailf:xpath-root 3;
              }
              description
                "The version configuration cannot be changed when On-Demand is running on the interface.";
            }
            type uint32 {
              range "1..3";
            }
            default "2";
            description
              "Specify the version of IGMP or MLD running on an interface.";
          }
          leaf last-member-query-interval {
            type uint32 {
              range "1..25";
            }
            units "s";
            default "1";
            description
              "Specify the interval at which the querier sends last-member query messages. This parameter makes sense only when the current querier runs IGMPv2, IGMPv3 or MLD.";
          }
          leaf require-router-alert {
            type boolean;
            default "false";
            description
              "Enable/disable an interface to process messages whose IP headers contain Router-Alert options.";
          }
          leaf send-router-alert {
            type boolean;
            default "true";
            description
              "Enable/disable an interface to send the messages with Router-Alert options in the IP headers.";
          }
          leaf other-querier-present-time {
            type uint32 {
              range "60..300";
            }
            units "s";
            description
              "Set the Keepalive period for other queriers on an interface.";
          }
          leaf immediately-leave {
            type boolean;
            default "false";
            description
              "Enable/disable an interface that receives a leave message of a certain group to immediately delete the corresponding group records, without sending a last-member query message.";
          }
          leaf immediately-leave-policy {
            when "../immediately-leave='true'" {
              tailf:xpath-root 3;
            }
            type leafref {
              path "/ncs:devices/ncs:device/ncs:config/acl:acl/acl:groups/acl:group/acl:identity" {
                tailf:xpath-root 3;
              }
            }
            must "/acl:acl/acl:groups/acl:group[acl:identity=current()]/acl:type='basic' or /acl:acl/acl:groups/acl:group[acl:identity=current()]/acl:type='advance'" {
              tailf:xpath-root 3;
            }
            description
              "Configure an ACL that defines a multicast group range. The basic ACL number ranges from 2000 to 2999, and the advanced ACL number ranges from 3000 to 3999. The name is a case-sensitive string.";
          }
          leaf on-demand-enable {
            type boolean;
            must "../on-demand-enable='false' or ../version!='1'" {
              tailf:xpath-root 3;
            }
            must "../on-demand-enable='false' or /ifm:ifm/ifm:interfaces/ifm:interface[ifm:name=current()/../name]/ifm:type!='Virtual-Template'" {
              tailf:xpath-root 3;
            }
            default "false";
            description
              "Enable/disable records about the groups that the interface joins never to age. By default, the group records age periodically. 1. This command is applicable to IGMPv2, IGMPv3, and MLD only. 2. This command can be used on the querier only.";
          }
          leaf entry-limit {
            type uint32 {
              range "1..16384";
            }
            description
              "Specify the maximum number of entries that the current interface can create.";
          }
          leaf entry-limit-acl-name {
            when '../entry-limit>0' {
              tailf:xpath-root 3;
            }
            type leafref {
              path "/ncs:devices/ncs:device/ncs:config/acl:acl/acl:groups/acl:group/acl:identity" {
                tailf:xpath-root 3;
              }
            }
            must "/acl:acl/acl:groups/acl:group[acl:identity=current()]/acl:type='basic' or /acl:acl/acl:groups/acl:group[acl:identity=current()]/acl:type='advance'" {
              tailf:xpath-root 3;
            }
            description
              "Specify the range of multicast groups, the number of IGMP entries corresponding to which needs not be limited. The basic ACL number ranges from 2000 to 2999. The basic ACL filters group addresses only, without distinguishing (*, G) entries and (S, G) entries; the advanced ACL number ranges from 3000 to 3999. The advanced ACL filters (S, G) entries of the interface only. The name is a case-sensitive string.";
          }
          leaf ssm-mapping-enable {
            type boolean;
            default "false";
            description
              "Enable/disable SSM mapping on an interface.";
          }
          leaf ssm-mapping-policy {
            when "../ssm-mapping-enable='true'" {
              tailf:xpath-root 3;
            }
            type string {
              length "1..31";
            }
            description
              "Configure a policy for SSM Mapping on an interface.";
          }
          leaf group-acl-name {
            type leafref {
              path "/ncs:devices/ncs:device/ncs:config/acl:acl/acl:groups/acl:group/acl:identity" {
                tailf:xpath-root 3;
              }
            }
            must "/acl:acl/acl:groups/acl:group[acl:identity=current()]/acl:type='basic' or /acl:acl/acl:groups/acl:group[acl:identity=current()]/acl:type='advance'" {
              tailf:xpath-root 3;
            }
            description
              "Set a filter for multicast groups on an interface to control the range of multicast groups that hosts can join. The basic ACL number ranges from 2000 to 2999, and the advanced ACL number ranges from 3000 to 3999. The name is a case-sensitive string.";
          }
          leaf group-acl-version {
            when '../group-acl-name' {
              tailf:xpath-root 3;
            }
            type uint32 {
              range "1..3";
            }
            description
              "Forbids hosts that use a specified version to join the multicast group. The version can be specified in this command only after a multicast filtering policy is configured.";
          }
          leaf query-acl-name {
            type leafref {
              path "/ncs:devices/ncs:device/ncs:config/acl:acl/acl:groups/acl:group/acl:identity" {
                tailf:xpath-root 3;
              }
            }
            must "/acl:acl/acl:groups/acl:group[acl:identity=current()]/acl:type='basic'" {
              tailf:xpath-root 3;
            }
            description
              "Configure an ACL that defines a host addresses range. The value is an integer ranging from 2000 to 2999, or a case-sensitive string.";
          }
          uses interface-status;
        }
      }
      container static-groups {
        description
          "List of static multicast groups configurations.";
        list static-group {
          must '../../../ni:name=/ifm:ifm/ifm:interfaces/ifm:interface[ifm:name=current()/interface]/ifm:vrf-name' {
            tailf:xpath-root 3;
          }
          key "interface group-address is-source-address source-address is-inc-step-group-mask inc-step-group-mask is-source-dns-ssm-mapping";
          description
            "Configure a static multicast group.";
          leaf interface {
            type leafref {
              path "/ncs:devices/ncs:device/ncs:config/ifm:ifm/ifm:interfaces/ifm:interface/ifm:name" {
                tailf:xpath-root 3;
              }
            }
            description
              "Specify the name of an interface.";
          }
          leaf group-address {
            type inet:ipv4-address-no-zone {
              pattern '(22[5-9]|23\d)(\.(25[0-5]|2[0-4]\d|1\d\d|[1-9]?\d)){3}|224(\.(25[0-5]|2[0-4]\d|1\d\d|[1-9]\d|[1-9]))(\.(25[0-5]|2[0-4]\d|1\d\d|[1-9]?\d)){2}|224\.0(\.(25[0-5]|2[0-4]\d|1\d\d|[1-9]\d|[1-9]))(\.(25[0-5]|2[0-4]\d|1\d\d|[1-9]?\d))';
            }
            description
              "Specify the address of a multicast group. In batch configuration mode, this parameter specifies the start multicast group address. In the case of an IPv4 address, the value ranges from 224.0.1.0 to 239.255.255.255, in dotted decimal notation; in the case of an IPv6 address, the value is in hexadecimal notation and in the format of FFxA:xxxx:xxxx::xxxx, among which x ranges from 0 to F and A can be 0, or in the range of 3 to F.";
          }
          leaf is-source-address {
            type boolean;
            must "../is-source-address='false' or (../is-source-dns-ssm-mapping='false' and ../source-address!='0.0.0.0')" {
              tailf:xpath-root 3;
            }
            description
              "Enable/disable a device to configure an address for the multicast source.";
          }
          leaf source-address {
            type inet:ipv4-address-no-zone;
            must "../source-address='0.0.0.0' or ../is-source-address='true'" {
              tailf:xpath-root 3;
            }
            description
              "Specify the address of a multicast source. In the case of an IPv4 address, the value is in dotted decimal notation. In the case of an IPv6 address, the value is in hexadecimal notation.";
          }
          leaf is-inc-step-group-mask {
            type boolean;
            must "../is-inc-step-group-mask='false' or (../is-source-dns-ssm-mapping='false' and ../inc-step-group-mask!='0.0.0.0')" {
              tailf:xpath-root 3;
            }
            description
              "Enable/disable a device to specify the step mask in batch configuration mode.";
          }
          leaf inc-step-group-mask {
            type inet:ipv4-address-no-zone;
            must "../inc-step-group-mask='0.0.0.0' or ../is-inc-step-group-mask='true'" {
              tailf:xpath-root 3;
            }
            description
              "Specify the step mask of a group address in batch configuration mode. It refers to the step between two neighboring multicast group addresses. The value is expressed in wildcard-mask mode and in dotted decimal notation, ranging from 0.0.0.1 to 15.255.255.255.";
          }
          leaf is-source-dns-ssm-mapping {
            type boolean;
            must "../is-source-dns-ssm-mapping='false' or (../is-source-address='false' and ../is-inc-step-group-mask='false')" {
              tailf:xpath-root 3;
            }
            description
              "Enable/disable an DNS based SSM mapping.";
          }
          leaf group-number {
            when "../is-inc-step-group-mask='true'" {
              tailf:xpath-root 3;
            }
            type uint32 {
              range "2..512";
            }
            mandatory true;
            description
              "Specify the number of multicast group addresses in batch configuration mode.";
          }
        }
      }
      container dot1q-static-groups {
        description
          "List of static multicast groups in dot1q-termination interface.";
        list dot1q-static-group {
          must '../../../ni:name=/ifm:ifm/ifm:interfaces/ifm:interface[ifm:name=current()/interface]/ifm:vrf-name' {
            tailf:xpath-root 3;
          }
          must '/ifm:ifm/ifm:interfaces/ifm:interface[ifm:name=current()/interface]/ethernet:ethernet/ethernet:l3-sub-interface/ethernet:dot1q-termination' {
            tailf:xpath-root 3;
          }
          must 'begin-vid<=end-vid' {
            tailf:xpath-root 3;
          }
          key "interface group-address is-source-address source-address is-inc-step-group-mask inc-step-group-mask begin-vid end-vid";
          description
            "Configure a static multicast group in a dot1q-termination interface.";
          leaf interface {
            type leafref {
              path "/ncs:devices/ncs:device/ncs:config/ifm:ifm/ifm:interfaces/ifm:interface/ifm:name" {
                tailf:xpath-root 3;
              }
            }
            description
              "Specify the name of an interface.";
          }
          leaf group-address {
            type inet:ipv4-address-no-zone {
              pattern '(22[5-9]|23\d)(\.(25[0-5]|2[0-4]\d|1\d\d|[1-9]?\d)){3}|224(\.(25[0-5]|2[0-4]\d|1\d\d|[1-9]\d|[1-9]))(\.(25[0-5]|2[0-4]\d|1\d\d|[1-9]?\d)){2}|224\.0(\.(25[0-5]|2[0-4]\d|1\d\d|[1-9]\d|[1-9]))(\.(25[0-5]|2[0-4]\d|1\d\d|[1-9]?\d))';
            }
            description
              "Specify the address of a multicast group. In batch configuration mode, this parameter specifies the start multicast group address. In the case of an IPv4 address, the value ranges from 224.0.1.0 to 239.255.255.255, in dotted decimal notation; in the case of an IPv6 address, the value is in hexadecimal notation and in the format of FFxA:xxxx:xxxx::xxxx, among which x ranges from 0 to F and A can be 0, or in the range of 3 to F.";
          }
          leaf is-source-address {
            type boolean;
            description
              "Enable/disable a device to configure an address for the multicast source.";
          }
          leaf source-address {
            type inet:ipv4-address-no-zone;
            must "../source-address='0.0.0.0' or ../is-source-address='true'" {
              tailf:xpath-root 3;
            }
            must "../source-address!='0.0.0.0' or ../is-source-address='false'" {
              tailf:xpath-root 3;
            }
            description
              "Specify the address of a multicast source. In the case of an IPv4 address, the value is in dotted decimal notation. In the case of an IPv6 address, the value is in hexadecimal notation.";
          }
          leaf is-inc-step-group-mask {
            type boolean;
            description
              "Enable/disable a device to specify the step mask in batch configuration mode.";
          }
          leaf inc-step-group-mask {
            type inet:ipv4-address-no-zone;
            must "(../is-inc-step-group-mask='true' and ../inc-step-group-mask!='0.0.0.0') or (../is-inc-step-group-mask='false' and ../inc-step-group-mask='0.0.0.0')" {
              tailf:xpath-root 3;
            }
            description
              "Specify the step mask of a group address in batch configuration mode. It refers to the step between two neighboring multicast group addresses. The value is expressed in wildcard-mask mode and in dotted decimal notation, ranging from 0.0.0.1 to 15.255.255.255.";
          }
          leaf begin-vid {
            type uint32 {
              range "1..4094";
            }
            description
              "Specify the start DOT1Q tag.";
          }
          leaf end-vid {
            type uint32 {
              range "1..4094";
            }
            description
              "Specify the end DOT1Q tag.";
          }
          leaf group-number {
            when "../is-inc-step-group-mask='true'" {
              tailf:xpath-root 3;
            }
            type uint32 {
              range "2..512";
            }
            mandatory true;
            description
              "Specify the number of multicast group addresses configured in a batch.";
          }
        }
      }
      container qinq-static-groups {
        description
          "List of static multicast groups configuration on qinq-termination interface.";
        list qinq-static-group {
          must '../../../ni:name=/ifm:ifm/ifm:interfaces/ifm:interface[ifm:name=current()/interface]/ifm:vrf-name' {
            tailf:xpath-root 3;
          }
          must '/ifm:ifm/ifm:interfaces/ifm:interface[ifm:name=current()/interface]/ethernet:ethernet/ethernet:l3-sub-interface/ethernet:qinq-termination' {
            tailf:xpath-root 3;
          }
          must 'ce-begin-vid<=ce-end-vid' {
            tailf:xpath-root 3;
          }
          key "interface group-address is-source-address source-address is-inc-step-group-mask inc-step-group-mask pe-vid ce-begin-vid ce-end-vid";
          description
            "Configure a static multicast group on a qinq-termination interface.";
          leaf interface {
            type leafref {
              path "/ncs:devices/ncs:device/ncs:config/ifm:ifm/ifm:interfaces/ifm:interface/ifm:name" {
                tailf:xpath-root 3;
              }
            }
            description
              "Specify the name of an interface.";
          }
          leaf group-address {
            type inet:ipv4-address-no-zone {
              pattern '(22[5-9]|23\d)(\.(25[0-5]|2[0-4]\d|1\d\d|[1-9]?\d)){3}|224(\.(25[0-5]|2[0-4]\d|1\d\d|[1-9]\d|[1-9]))(\.(25[0-5]|2[0-4]\d|1\d\d|[1-9]?\d)){2}|224\.0(\.(25[0-5]|2[0-4]\d|1\d\d|[1-9]\d|[1-9]))(\.(25[0-5]|2[0-4]\d|1\d\d|[1-9]?\d))';
            }
            description
              "Specify the address of a multicast group. In batch configuration mode, this parameter specifies the start multicast group address. In the case of an IPv4 address, the value ranges from 224.0.1.0 to 239.255.255.255, in dotted decimal notation; in the case of an IPv6 address, the value is in hexadecimal notation and in the format of FFxA:xxxx:xxxx::xxxx, among which x ranges from 0 to F and A can be 0, or in the range of 3 to F.";
          }
          leaf is-source-address {
            type boolean;
            description
              "Enable/disable a device to configure an address for the multicast source.";
          }
          leaf source-address {
            type inet:ipv4-address-no-zone;
            must "../source-address='0.0.0.0' or ../is-source-address='true'" {
              tailf:xpath-root 3;
            }
            must "../source-address!='0.0.0.0' or ../is-source-address='false'" {
              tailf:xpath-root 3;
            }
            description
              "Specify the address of a multicast source. In the case of an IPv4 address, the value is in dotted decimal notation. In the case of an IPv6 address, the value is in hexadecimal notation.";
          }
          leaf is-inc-step-group-mask {
            type boolean;
            description
              "Enable/disable a device to specify the step mask in batch configuration mode.";
          }
          leaf inc-step-group-mask {
            type inet:ipv4-address-no-zone;
            must "(../is-inc-step-group-mask='true' and ../inc-step-group-mask!='0.0.0.0')  or (../is-inc-step-group-mask='false' and ../inc-step-group-mask='0.0.0.0')" {
              tailf:xpath-root 3;
            }
            description
              "Specify the step mask of a group address in batch configuration mode. It refers to the step between two neighboring multicast group addresses. The value is expressed in wildcard-mask mode and in dotted decimal notation, ranging from 0.0.0.1 to 15.255.255.255.";
          }
          leaf pe-vid {
            type uint32 {
              range "1..4094";
            }
            description
              "QINQ PE ID in an outer VLAN tag.";
          }
          leaf ce-begin-vid {
            type uint32 {
              range "1..4094";
            }
            description
              "Specify the start QINQ CE ID.";
          }
          leaf ce-end-vid {
            type uint32 {
              range "1..4094";
            }
            description
              "Specify the end QINQ CE ID.";
          }
          leaf group-number {
            when "../is-inc-step-group-mask='true'" {
              tailf:xpath-root 3;
            }
            type uint32 {
              range "2..512";
            }
            mandatory true;
            description
              "Specify the number of multicast group addresses configured in a batch.";
          }
        }
      }
      uses display-static-group;
      uses display-group;
    }
    container mld {
      tailf:ncs-device-type "netconf";
      tailf:display-when "not(../../../../../ncs:module) or ../../../../../ncs:module[ncs:name='huawei-igmp-mld']";
      when '../l3mc:multicast/l3mc:ipv6' {
        tailf:xpath-root 3;
      }
      description
        "Configure MLD configurations.";
      container global {
        presence "Create MLD.";
        description
          "Enable/disable MLD in an instance.";
        leaf query-interval {
          type uint32 {
            range "1..18000";
          }
          units "s";
          default "125";
          description
            "Specify the interval at which the router sends general query messages.";
        }
        leaf query-response-interval {
          type uint32 {
            range "1..125";
          }
          units "s";
          default "10";
          description
            "Specify the maximum response time for a query message.";
        }
        leaf robustness {
          type uint32 {
            range "2..5";
          }
          default "2";
          description
            "Specify the number of times for retransmitting a message to avoid the packet loss.";
        }
        leaf last-member-query-interval {
          type uint32 {
            range "1..25";
          }
          units "s";
          default "1";
          description
            "Specify the interval at which the querier sends last-member query messages. This parameter makes sense only when the current querier runs IGMPv2, IGMPv3 or MLD.";
        }
        leaf require-router-alert {
          type boolean;
          default "false";
          description
            "Enable/disable the router to process the messages whose IP headers contain Router-Alert options globally.";
        }
        leaf send-router-alert {
          type boolean;
          default "true";
          description
            "Enable/disable the router to send the messages with Router-Alert options in the IP headers globally.";
        }
        leaf other-querier-present-time {
          type uint32 {
            range "60..300";
          }
          units "s";
          description
            "Set the global Keepalive period for other queriers.";
        }
        container ssm-mappings {
          description
            "List of SSM-mapping rules configurations.";
          list ssm-mapping {
            key "group-address mask-length source-address";
            description
              "Configure a SSM-mapping rule.";
            leaf group-address {
              type inet:ipv6-address-no-zone {
                pattern '([Ff]{2}[0-9a-fA-F]{2})[0-9a-fA-F:\.]*';
              }
              description
                "Specify the address of a multicast group. In the case of an IPv6 address, the value ranges from FF00:: to FFFF:FFFF:FFFF:FFFF:FFFF:FFFF:FFFF:FFFF, in the hexadecimal format.";
            }
            leaf mask-length {
              type uint32 {
                range "16 | 32 | 64 | 128";
              }
              description
                "Specify the mask length of a multicast group address.";
            }
            leaf source-address {
              type inet:ipv6-address-no-zone {
                pattern '(([1-9A-Ea-e][0-9A-Fa-f]{3}:)|([Ff][0-9A-Da-d][0-9A-Fa-f]{2}:)|([Ff][Ee][0-7C-Fc-f][0-9A-Fa-f]:)|((0)?[1-9A-Fa-f][0-9A-Fa-f]{2}:)|((00)?[1-9A-Fa-f][0-9A-Fa-f]:)|((000)?[1-9A-Fa-f]:)).+';
              }
              description
                "Specify the address of a multicast source. In the case of an IPv6 address, the value ranges from FF00:: to FFFF:FFFF:FFFF:FFFF:FFFF:FFFF:FFFF:FFFF, in hexadecimal notation.";
            }
          }
        }
      }
      container interfaces {
        description
          "List of MGMD configurations on all interfaces.";
        list interface {
          must '../../../ni:name=/ifm:ifm/ifm:interfaces/ifm:interface[ifm:name=current()/name]/ifm:vrf-name' {
            tailf:xpath-root 3;
          }
          key "name";
          description
            "Configure MGMD on an interface.";
          leaf name {
            type leafref {
              path "/ncs:devices/ncs:device/ncs:config/ifm:ifm/ifm:interfaces/ifm:interface/ifm:name" {
                tailf:xpath-root 3;
              }
            }
            description
              "Specify the type and number of an interface.";
          }
          leaf enable {
            type boolean;
            default "false";
            description
              "Enable/disable protocols on an interface.";
          }
          leaf ip-source-policy-enable {
            type boolean;
            must "../ip-source-policy-enable='false' or ../ip-source-policy-name" {
              tailf:xpath-root 3;
            }
            default "false";
            description
              "Enable/disable a policy for filtering IGMP Report messages based on host addresses.";
          }
          leaf ip-source-policy-name {
            when "../ip-source-policy-enable='true'" {
              tailf:xpath-root 3;
            }
            type leafref {
              path "/ncs:devices/ncs:device/ncs:config/acl:acl/acl:group6s/acl:group6/acl:identity" {
                tailf:xpath-root 3;
              }
            }
            must "/acl:acl/acl:group6s/acl:group6[acl:identity=current()]/acl:type='basic'" {
              tailf:xpath-root 3;
            }
            description
              "Configure an ACL that defines a host addresses range. The value is an integer ranging from 2000 to 2999, or a case-sensitive string.";
          }
          leaf query-interval {
            type uint32 {
              range "1..18000";
            }
            units "s";
            default "125";
            description
              "Specify the interval at which the router sends general query messages.";
          }
          leaf query-response-interval {
            type uint32 {
              range "1..125";
            }
            units "s";
            default "10";
            description
              "Specify the maximum time for the response to a query message. This time is used to control the deadline of a host's group membership feedback.";
          }
          leaf robustness {
            type uint32 {
              range "2..5";
            }
            default "2";
            description
              "Specify the number of times for retransmitting messages to avoid packet loss.";
          }
          leaf version {
            ext:operation-exclude "update" {
              when "../on-demand-enable='true'" {
                tailf:xpath-root 3;
              }
              description
                "The version configuration cannot be changed when On-Demand is running on the interface.";
            }
            type uint32 {
              range "1..2";
            }
            default "2";
            description
              "Specify the version of IGMP or MLD running on an interface.";
          }
          leaf last-member-query-interval {
            type uint32 {
              range "1..25";
            }
            units "s";
            default "1";
            description
              "Specify the interval at which the querier sends last-member query messages. This parameter makes sense only when the current querier runs IGMPv2, IGMPv3 or MLD.";
          }
          leaf require-router-alert {
            type boolean;
            default "false";
            description
              "Enable/disable an interface to process messages whose IP headers contain Router-Alert options.";
          }
          leaf send-router-alert {
            type boolean;
            default "true";
            description
              "Enable/disable an interface to send the messages with Router-Alert options in the IP headers.";
          }
          leaf other-querier-present-time {
            type uint32 {
              range "60..300";
            }
            units "s";
            description
              "Set the Keepalive period for other queriers on an interface. The value ranges from 60 to 300, in second.";
          }
          leaf immediately-leave {
            type boolean;
            default "false";
            description
              "Enable/disable an interface that receives a leave message of a certain group to immediately delete the corresponding group records, without sending a last-member query message.";
          }
          leaf immediately-leave-policy {
            when "../immediately-leave='true'" {
              tailf:xpath-root 3;
            }
            type leafref {
              path "/ncs:devices/ncs:device/ncs:config/acl:acl/acl:group6s/acl:group6/acl:identity" {
                tailf:xpath-root 3;
              }
            }
            must "/acl:acl/acl:group6s/acl:group6[acl:identity=current()]/acl:type='basic' or /acl:acl/acl:group6s/acl:group6[acl:identity=current()]/acl:type='advance'" {
              tailf:xpath-root 3;
            }
            description
              "Configure an ACL that defines a multicast group range. The basic ACL number ranges from 2000 to 2999, and the advanced ACL number ranges from 3000 to 3999. The name is a case-sensitive string.";
          }
          leaf on-demand-enable {
            type boolean;
            default "false";
            description
              "Enable/disable records about the groups that the interface joins never to age. By default, the group records age periodically. 1. This command is applicable to IGMPv2, IGMPv3, and MLD only. 2. This command can be used on the querier only.";
          }
          leaf entry-limit {
            type uint32 {
              range "1..16384";
            }
            description
              "Specify the maximum number of entries that the current interface can create.";
          }
          leaf entry-limit-acl-name {
            when '../entry-limit>0' {
              tailf:xpath-root 3;
            }
            type leafref {
              path "/ncs:devices/ncs:device/ncs:config/acl:acl/acl:group6s/acl:group6/acl:identity" {
                tailf:xpath-root 3;
              }
            }
            must "/acl:acl/acl:group6s/acl:group6[acl:identity=current()]/acl:type='basic' or /acl:acl/acl:group6s/acl:group6[acl:identity=current()]/acl:type='advance'" {
              tailf:xpath-root 3;
            }
            description
              "Specify the range of multicast groups, the number of MLD entries corresponding to which needs not be limited. The basic ACL number ranges from 2000 to 2999. The basic ACL filters group addresses only, without distinguishing (*, G) entries and (S, G) entries; the advanced ACL number ranges from 3000 to 3999. The advanced ACL filters (S, G) entries of the interface only. The name is a case-sensitive string.";
          }
          leaf ssm-mapping-enable {
            type boolean;
            default "false";
            description
              "Enable/disable SSM mapping on an interface.";
          }
          leaf group-acl-name {
            type leafref {
              path "/ncs:devices/ncs:device/ncs:config/acl:acl/acl:group6s/acl:group6/acl:identity" {
                tailf:xpath-root 3;
              }
            }
            must "/acl:acl/acl:group6s/acl:group6[acl:identity=current()]/acl:type='basic' or /acl:acl/acl:group6s/acl:group6[acl:identity=current()]/acl:type='advance'" {
              tailf:xpath-root 3;
            }
            description
              "Set a filter for multicast groups on an interface to control the range of multicast groups that hosts can join. The basic ACL number ranges from 2000 to 2999, and the advanced ACL number ranges from 3000 to 3999. The name is a case-sensitive string.";
          }
          leaf group-acl-version {
            when '../group-acl-name' {
              tailf:xpath-root 3;
            }
            type uint32 {
              range "1..2";
            }
            description
              "Forbids hosts that use a specified version to join the multicast group. The version can be specified in this command only after a multicast filtering policy is configured.";
          }
          leaf query-acl-name {
            type leafref {
              path "/ncs:devices/ncs:device/ncs:config/acl:acl/acl:group6s/acl:group6/acl:identity" {
                tailf:xpath-root 3;
              }
            }
            must "/acl:acl/acl:group6s/acl:group6[acl:identity=current()]/acl:type='basic'" {
              tailf:xpath-root 3;
            }
            description
              "Configure an ACL that defines a host addresses range. The value is an integer ranging from 2000 to 2999, or a case-sensitive string.";
          }
          uses interface-status;
        }
      }
      container static-groups {
        description
          "List of static multicast groups configurations on interfaces.";
        list static-group {
          must '../../../ni:name=/ifm:ifm/ifm:interfaces/ifm:interface[ifm:name=current()/interface]/ifm:vrf-name' {
            tailf:xpath-root 3;
          }
          key "interface group-address is-source-address source-address is-mask-length mask-length";
          description
            "Configure a static multicast group.";
          leaf interface {
            type leafref {
              path "/ncs:devices/ncs:device/ncs:config/ifm:ifm/ifm:interfaces/ifm:interface/ifm:name" {
                tailf:xpath-root 3;
              }
            }
            description
              "Specify the name of an interface.";
          }
          leaf group-address {
            type inet:ipv6-address-no-zone {
              pattern '[Ff]{2}[0-9A-Fa-f][03-9a-fA-F].+';
            }
            description
              "Specify the address of a multicast group. In batch configuration mode, this parameter specifies the start multicast group address. In the case of an IPv6 address, the value is in hexadecimal notation and in the format of FFxA:xxxx:xxxx::xxxx, among which x ranges from 0 to F and A can be 0, or in the range of 3 to F.";
          }
          leaf is-source-address {
            type boolean;
            description
              "Enable/disable a device to configure an address for the multicast source.";
          }
          leaf source-address {
            type inet:ipv6-address-no-zone;
            must "../source-address='::' or ../is-source-address='true'" {
              tailf:xpath-root 3;
            }
            must "../source-address!='::' or ../is-source-address='false'" {
              tailf:xpath-root 3;
            }
            description
              "Specify the address of a multicast source.";
          }
          leaf is-mask-length {
            type boolean;
            description
              "Enable/disable a device to specify the length for the step mask of a multicast group address in batch configuration mode.";
          }
          leaf mask-length {
            type uint32 {
              range "0..128";
            }
            must "../mask-length=0 or ../is-mask-length='true'" {
              tailf:xpath-root 3;
            }
            description
              "Specify the mask length of a multicast group address. In the case of an IPv6 address, the mask length is 16/32/64/128.";
          }
          leaf total-number {
            when "../is-mask-length='true'" {
              tailf:xpath-root 3;
            }
            type uint32 {
              range "2..512";
            }
            mandatory true;
            description
              "Specify the number of multicast group addresses in batch configuration mode.";
          }
        }
      }
      container dot1q-static-groups {
        description
          "List of static multicast groups on dot1q-termination interfaces.";
        list dot1q-static-group {
          must '../../../ni:name=/ifm:ifm/ifm:interfaces/ifm:interface[ifm:name=current()/interface]/ifm:vrf-name' {
            tailf:xpath-root 3;
          }
          must '/ifm:ifm/ifm:interfaces/ifm:interface[ifm:name=current()/interface]/ethernet:ethernet/ethernet:l3-sub-interface/ethernet:dot1q-termination' {
            tailf:xpath-root 3;
          }
          must 'begin-vid<=end-vid' {
            tailf:xpath-root 3;
          }
          key "interface group-address is-source-address source-address is-mask-length mask-length begin-vid end-vid";
          description
            "Configure a static multicast group on a dot1q-termination interface.";
          leaf interface {
            type leafref {
              path "/ncs:devices/ncs:device/ncs:config/ifm:ifm/ifm:interfaces/ifm:interface/ifm:name" {
                tailf:xpath-root 3;
              }
            }
            description
              "Specify the name of an interface.";
          }
          leaf group-address {
            type inet:ipv6-address-no-zone {
              pattern '[Ff]{2}[0-9A-Fa-f][03-9a-fA-F].+';
            }
            description
              "Specify the address of a multicast group. In batch configuration mode, this parameter specifies the start multicast group address. In the case of an IPv6 address, the value is in hexadecimal notation and in the format of FFxA:xxxx:xxxx::xxxx, among which x ranges from 0 to F and A can be 0, or in the range of 3 to F.";
          }
          leaf is-source-address {
            type boolean;
            description
              "Enable/disable a device to configure an address for the multicast source.";
          }
          leaf source-address {
            type inet:ipv6-address-no-zone;
            must "../source-address='::' or ../is-source-address='true'" {
              tailf:xpath-root 3;
            }
            must "../source-address!='::' or ../is-source-address='false'" {
              tailf:xpath-root 3;
            }
            description
              "Specify the address of a multicast source.";
          }
          leaf is-mask-length {
            type boolean;
            description
              "Enable/disable a device to specify the length for the step mask of a multicast group address in batch configuration mode.";
          }
          leaf mask-length {
            type uint32 {
              range "0..128";
            }
            must "(../is-mask-length='true' and ../mask-length>=9) or (../is-mask-length='false' and ../mask-length=0)" {
              tailf:xpath-root 3;
            }
            description
              "Specify the step mask length of a multicast group address. An IPv4 address uses a mask with a length from 4 to 32 bits. An IPv6 address uses a mask with a length of 16, 32, 64, or 128 bits.";
          }
          leaf begin-vid {
            type uint32 {
              range "1..4094";
            }
            description
              "Specify the start DOT1Q tag.";
          }
          leaf end-vid {
            type uint32 {
              range "1..4094";
            }
            description
              "Specify the end DOT1Q tag.";
          }
          leaf group-number {
            when "../is-mask-length='true'" {
              tailf:xpath-root 3;
            }
            type uint32 {
              range "2..512";
            }
            mandatory true;
            description
              "Specify the number of multicast group addresses configured in a batch.";
          }
        }
      }
      container qinq-static-groups {
        description
          "List of static multicast groups configuration on qinq-termination interfaces.";
        list qinq-static-group {
          must '../../../ni:name=/ifm:ifm/ifm:interfaces/ifm:interface[ifm:name=current()/interface]/ifm:vrf-name' {
            tailf:xpath-root 3;
          }
          must '/ifm:ifm/ifm:interfaces/ifm:interface[ifm:name=current()/interface]/ethernet:ethernet/ethernet:l3-sub-interface/ethernet:qinq-termination' {
            tailf:xpath-root 3;
          }
          must 'ce-begin-vid<=ce-end-vid' {
            tailf:xpath-root 3;
          }
          key "interface group-address is-source-address source-address is-mask-length mask-length pe-vid ce-begin-vid ce-end-vid";
          description
            "Configure a static multicast group.";
          leaf interface {
            type leafref {
              path "/ncs:devices/ncs:device/ncs:config/ifm:ifm/ifm:interfaces/ifm:interface/ifm:name" {
                tailf:xpath-root 3;
              }
            }
            description
              "Specify the name of an interface.";
          }
          leaf group-address {
            type inet:ipv6-address-no-zone {
              pattern '[Ff]{2}[0-9A-Fa-f][03-9a-fA-F].+';
            }
            description
              "Specify the address of a multicast group. In batch configuration mode, this parameter specifies the start multicast group address. In the case of an IPv6 address, the value is in hexadecimal notation and in the format of FFxA:xxxx:xxxx::xxxx, among which x ranges from 0 to F and A can be 0, or in the range of 3 to F.";
          }
          leaf is-source-address {
            type boolean;
            description
              "Enable/disable a device to configure an address for the multicast source.";
          }
          leaf source-address {
            type inet:ipv6-address-no-zone;
            must "../source-address='::' or ../is-source-address='true'" {
              tailf:xpath-root 3;
            }
            must "../source-address!='::' or ../is-source-address='false'" {
              tailf:xpath-root 3;
            }
            description
              "Specify the address of a multicast source.";
          }
          leaf is-mask-length {
            type boolean;
            description
              "Enable/disable a device to specify the length for the step mask of a multicast group address in batch configuration mode.";
          }
          leaf mask-length {
            type uint32 {
              range "0..128";
            }
            must "(../is-mask-length='true' and ../mask-length>=9) or (../is-mask-length='false' and ../mask-length=0)" {
              tailf:xpath-root 3;
            }
            description
              "Specify the step mask length of a multicast group address. An IPv4 address uses a mask with a length from 4 to 32 bits. An IPv6 address uses a mask with a length of 16, 32, 64, or 128 bits.";
          }
          leaf pe-vid {
            type uint32 {
              range "1..4094";
            }
            description
              "QINQ PE ID in an outer VLAN tag.";
          }
          leaf ce-begin-vid {
            type uint32 {
              range "1..4094";
            }
            description
              "Specify the start QINQ CE ID.";
          }
          leaf ce-end-vid {
            type uint32 {
              range "1..4094";
            }
            description
              "Specify the end QINQ CE ID.";
          }
          leaf group-number {
            when "../is-mask-length='true'" {
              tailf:xpath-root 3;
            }
            type uint32 {
              range "2..512";
            }
            mandatory true;
            description
              "Specify the number of multicast group addresses configured in a batch.";
          }
        }
      }
      uses display-static-group;
      uses display-group;
    }
  }
}
