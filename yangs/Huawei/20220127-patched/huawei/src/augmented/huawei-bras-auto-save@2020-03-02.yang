module huawei-bras-auto-save {
  // Generated by yanger -t ncs
  tailf:mount-id "huawei-nc-1.0:huawei-nc-1.0";
  tailf:ncs-device-type "netconf";

  namespace "urn:huawei:yang:huawei-bras-auto-save";
  prefix bras-auto-save;

  import huawei-aaa {
    prefix aaa;
  }
  import huawei-bras-basic-access {
    prefix bras-basic-access;
  }
  import huawei-extension {
    prefix ext;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Bras auto save.";

  revision 2020-03-02 {
    description
      "Modify description.";
    reference "Huawei private.";
  }
  revision 2019-03-26 {
    description
      "Init revision.";
    reference "Huawei private.";
  }
  ext:task-name "bras-control";

  augment "/ncs:devices/ncs:device/ncs:config" {
    container bras-auto-save {
      tailf:ncs-device-type "netconf";
      tailf:display-when "not(../../ncs:module) or ../../ncs:module[ncs:name='huawei-bras-auto-save']";
      description
        "Bras auto save.";
      container auto-save-max-user {
        description
          "Configure auto save max user number.";
        leaf number {
          type uint32 {
            range "4000..1024000";
          }
          description
            "Specifies the maximum number of the DHCPv4 users whose information is automatically backed up.";
        }
      }
      container auto-recover {
        description
          "Configure automatic DHCPv4 user login.";
        leaf enable {
          type boolean;
          default "false";
          description
            "Enable/disable automatic DHCPv4 user login.";
        }
        leaf speed {
          type enumeration {
            enum "slow" {
              value 1;
              description
                "Indicates that the maximum rate at which DHCPv4 users automatically go online after the router recovers from a fault is 100/s.";
            }
            enum "normal" {
              value 2;
              description
                "Indicates that the maximum rate at which DHCPv4 users automatically go online after the router recovers from a fault is 300/s.";
            }
            enum "fast" {
              value 3;
              description
                "Indicates that the maximum rate at which DHCPv4 users automatically go online after the router recovers from a fault is 500/s.";
            }
          }
          default "normal";
          description
            "Configures the rate at which DHCPv4 users automatically go online after the router recovers from a fault.";
        }
        leaf no-send-packet {
          type boolean;
          default "false";
          description
            "Enable/disable no send packet to DHCP server.";
        }
      }
    }
  }
  augment "/ncs:devices/ncs:device/ncs:live-status" {
    container bras-auto-save {
      tailf:ncs-device-type "netconf";
      tailf:display-when "not(../../ncs:module) or ../../ncs:module[ncs:name='huawei-bras-auto-save'] or (../../ncs:live-status-protocol[not(ncs:capability)]) or (../../ncs:live-status-protocol/ncs:capability/ncs:module[.='huawei-bras-auto-save'])";
      description
        "Bras auto save.";
      container auto-save-max-user {
        description
          "Configure auto save max user number.";
        leaf number {
          type uint32 {
            range "4000..1024000";
          }
          description
            "Specifies the maximum number of the DHCPv4 users whose information is automatically backed up.";
        }
      }
      container auto-recover {
        description
          "Configure automatic DHCPv4 user login.";
        leaf enable {
          type boolean;
          // NCS drop default statement
          description
            "Enable/disable automatic DHCPv4 user login.";
        }
        leaf speed {
          type enumeration {
            enum "slow" {
              value 1;
              description
                "Indicates that the maximum rate at which DHCPv4 users automatically go online after the router recovers from a fault is 100/s.";
            }
            enum "normal" {
              value 2;
              description
                "Indicates that the maximum rate at which DHCPv4 users automatically go online after the router recovers from a fault is 300/s.";
            }
            enum "fast" {
              value 3;
              description
                "Indicates that the maximum rate at which DHCPv4 users automatically go online after the router recovers from a fault is 500/s.";
            }
          }
          // NCS drop default statement
          description
            "Configures the rate at which DHCPv4 users automatically go online after the router recovers from a fault.";
        }
        leaf no-send-packet {
          type boolean;
          // NCS drop default statement
          description
            "Enable/disable no send packet to DHCP server.";
        }
      }
    }
  }
  augment "/ncs:devices/ncs:template/ncs:ned-id/ncs:config" {
    container bras-auto-save {
      description
        "Bras auto save.";
      container auto-save-max-user {
        description
          "Configure auto save max user number.";
        leaf number {
          type string;
          description
            "Specifies the maximum number of the DHCPv4 users whose information is automatically backed up.";
        }
      }
      container auto-recover {
        description
          "Configure automatic DHCPv4 user login.";
        leaf enable {
          type string;
          // NCS drop default statement
          description
            "Enable/disable automatic DHCPv4 user login.";
        }
        leaf speed {
          type string;
          // NCS drop default statement
          description
            "Configures the rate at which DHCPv4 users automatically go online after the router recovers from a fault.";
        }
        leaf no-send-packet {
          type string;
          // NCS drop default statement
          description
            "Enable/disable no send packet to DHCP server.";
        }
      }
    }
  }
  augment "/ncs:devices/ncs:template/ncs:ned-id/ncs:config/aaa:aaa/aaa:domains/aaa:domain/bras-basic-access:bas" {
    description
      "Bras domain configuration.";
    container bras-auto-save {
      description
        "Configure a domain and enters the domain; alternatively, you can enter the existing domain. Exceptionally, the node in this module cannot be deleted or removed to delete its child nodes.";
      container dhcp-auto-save {
        description
          "Configure automatic backup of DHCPv4 user information in a domain.";
        leaf enable {
          type string;
          // NCS drop default statement
          description
            "Enable/disable automatic backup of DHCPv4 user information.";
        }
      }
    }
  }
  augment "/ncs:devices/ncs:device/ncs:live-status/aaa:aaa/aaa:domains/aaa:domain/bras-basic-access:bas" {
    description
      "Bras domain configuration.";
    container bras-auto-save {
      tailf:ncs-device-type "netconf";
      tailf:display-when "not(../../../../../../ncs:module) or ../../../../../../ncs:module[ncs:name='huawei-bras-auto-save'] or (../../../../../../ncs:live-status-protocol[not(ncs:capability)]) or (../../../../../../ncs:live-status-protocol/ncs:capability/ncs:module[.='huawei-bras-auto-save'])";
      description
        "Configure a domain and enters the domain; alternatively, you can enter the existing domain. Exceptionally, the node in this module cannot be deleted or removed to delete its child nodes.";
      container dhcp-auto-save {
        description
          "Configure automatic backup of DHCPv4 user information in a domain.";
        leaf enable {
          type boolean;
          // NCS drop default statement
          description
            "Enable/disable automatic backup of DHCPv4 user information.";
        }
      }
    }
  }
  augment "/ncs:devices/ncs:device/ncs:config/aaa:aaa/aaa:domains/aaa:domain/bras-basic-access:bas" {
    description
      "Bras domain configuration.";
    container bras-auto-save {
      tailf:ncs-device-type "netconf";
      tailf:display-when "not(../../../../../../ncs:module) or ../../../../../../ncs:module[ncs:name='huawei-bras-auto-save']";
      description
        "Configure a domain and enters the domain; alternatively, you can enter the existing domain. Exceptionally, the node in this module cannot be deleted or removed to delete its child nodes.";
      container dhcp-auto-save {
        description
          "Configure automatic backup of DHCPv4 user information in a domain.";
        leaf enable {
          type boolean;
          default "false";
          description
            "Enable/disable automatic backup of DHCPv4 user information.";
        }
      }
    }
  }
}
