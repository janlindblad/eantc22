module huawei-net-slice {
  // Generated by yanger -t ncs
  tailf:mount-id "huawei-nc-1.0:huawei-nc-1.0";
  tailf:ncs-device-type "netconf";

  namespace "urn:huawei:yang:huawei-net-slice";
  prefix net-slice;

  import huawei-ifm {
    prefix ifm;
  }
  import huawei-extension {
    prefix ext;
  }
  import huawei-ip {
    prefix ip;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "This YANG module defines the essential types for the management of Net-Slice for IGP.";

  revision 2021-02-03 {
    description
      "Initial revision.";
    reference "Huawei private.";
  }
  ext:task-name "netslicing";

  typedef ncs_template_net-af-type {
    type string;
    description
      "Net slice address family type.";
  }

  typedef ncs_template_slice-capability-type {
    type string;
    description
      "Net slice capability type.";
  }

  typedef ncs_template_slice-service-class {
    type string;
    description
      "Queue type.";
  }

  typedef ncs_rpc_notif_net-af-type {
    type enumeration {
      enum "afipv4" {
        value 1;
        description
          "IPv4 address family.";
      }
      enum "afipv6" {
        value 2;
        description
          "IPv6 address family.";
      }
    }
    description
      "Net slice address family type.";
  }

  typedef ncs_rpc_notif_slice-capability-type {
    type enumeration {
      enum "flexphy" {
        value 0;
        description
          "Flex phy port type.";
      }
      enum "flexe" {
        value 1;
        description
          "FlexE port type.";
      }
      enum "channelphy" {
        value 2;
        description
          "Channel phy port type.";
      }
    }
    description
      "Net slice capability type.";
  }

  typedef ncs_rpc_notif_slice-service-class {
    type enumeration {
      enum "be" {
        value 1;
        description
          "BE service-class.";
      }
      enum "af1" {
        value 2;
        description
          "AF1 service-class.";
      }
      enum "af2" {
        value 3;
        description
          "AF2 service-class.";
      }
      enum "af3" {
        value 4;
        description
          "AF3 service-class.";
      }
      enum "af4" {
        value 5;
        description
          "AF4 service-class.";
      }
      enum "ef" {
        value 6;
        description
          "EF service-class.";
      }
      enum "cs6" {
        value 7;
        description
          "CS6 service-class.";
      }
      enum "cs7" {
        value 8;
        description
          "CS7 service-class.";
      }
    }
    description
      "Queue type.";
  }

  typedef live_ncs_net-af-type {
    type enumeration {
      enum "afipv4" {
        value 1;
        description
          "IPv4 address family.";
      }
      enum "afipv6" {
        value 2;
        description
          "IPv6 address family.";
      }
    }
    description
      "Net slice address family type.";
  }

  typedef live_ncs_slice-capability-type {
    type enumeration {
      enum "flexphy" {
        value 0;
        description
          "Flex phy port type.";
      }
      enum "flexe" {
        value 1;
        description
          "FlexE port type.";
      }
      enum "channelphy" {
        value 2;
        description
          "Channel phy port type.";
      }
    }
    description
      "Net slice capability type.";
  }

  typedef live_ncs_slice-service-class {
    type enumeration {
      enum "be" {
        value 1;
        description
          "BE service-class.";
      }
      enum "af1" {
        value 2;
        description
          "AF1 service-class.";
      }
      enum "af2" {
        value 3;
        description
          "AF2 service-class.";
      }
      enum "af3" {
        value 4;
        description
          "AF3 service-class.";
      }
      enum "af4" {
        value 5;
        description
          "AF4 service-class.";
      }
      enum "ef" {
        value 6;
        description
          "EF service-class.";
      }
      enum "cs6" {
        value 7;
        description
          "CS6 service-class.";
      }
      enum "cs7" {
        value 8;
        description
          "CS7 service-class.";
      }
    }
    description
      "Queue type.";
  }

  typedef net-af-type {
    type enumeration {
      enum "afipv4" {
        value 1;
        description
          "IPv4 address family.";
      }
      enum "afipv6" {
        value 2;
        description
          "IPv6 address family.";
      }
    }
    description
      "Net slice address family type.";
  }

  typedef slice-capability-type {
    type enumeration {
      enum "flexphy" {
        value 0;
        description
          "Flex phy port type.";
      }
      enum "flexe" {
        value 1;
        description
          "FlexE port type.";
      }
      enum "channelphy" {
        value 2;
        description
          "Channel phy port type.";
      }
    }
    description
      "Net slice capability type.";
  }

  typedef slice-service-class {
    type enumeration {
      enum "be" {
        value 1;
        description
          "BE service-class.";
      }
      enum "af1" {
        value 2;
        description
          "AF1 service-class.";
      }
      enum "af2" {
        value 3;
        description
          "AF2 service-class.";
      }
      enum "af3" {
        value 4;
        description
          "AF3 service-class.";
      }
      enum "af4" {
        value 5;
        description
          "AF4 service-class.";
      }
      enum "ef" {
        value 6;
        description
          "EF service-class.";
      }
      enum "cs6" {
        value 7;
        description
          "CS6 service-class.";
      }
      enum "cs7" {
        value 8;
        description
          "CS7 service-class.";
      }
    }
    description
      "Queue type.";
  }

  augment "/ncs:devices/ncs:device/ncs:rpc" {
    container rpc-reset-flex-channel-statitic {
      tailf:ncs-device-type "netconf";
      tailf:display-when "not(../../ncs:module) or ../../ncs:module[ncs:name='huawei-net-slice']";
      tailf:action reset-flex-channel-statitic {
        tailf:actionpoint ncsproxy {
          tailf:internal;
        }
        description
          "Reset flex-channle statistic.";
        input {
          leaf slice-id {
            type uint32 {
              range "1 .. 4294967295";
            }
            description
              "Net-slice instance.";
          }
          leaf interface-name {
            type string;
            description
              "Interface name.";
          }
        }
      }
    }
  }
  augment "/ncs:devices/ncs:device-group/ncs:ned-id/ncs:rpc" {
    container rpc-reset-flex-channel-statitic {
      tailf:ncs-device-type "netconf";
      tailf:display-when "/ncs:devices/ncs:device[ncs:name=current()/../../../ncs:member]/ncs:module[ncs:name='huawei-net-slice']";
      tailf:action reset-flex-channel-statitic {
        tailf:actionpoint ncsproxy {
          tailf:internal;
        }
        description
          "Reset flex-channle statistic.";
        input {
          leaf slice-id {
            type uint32 {
              range "1 .. 4294967295";
            }
            description
              "Net-slice instance.";
          }
          leaf interface-name {
            type string;
            description
              "Interface name.";
          }
        }
      }
    }
  }
  augment "/ncs:devices/ncs:device/ncs:config" {
    container net-slice {
      tailf:ncs-device-type "netconf";
      tailf:display-when "not(../../ncs:module) or ../../ncs:module[ncs:name='huawei-net-slice']";
      description
        "Configure net slice parameters.";
      container instances {
        description
          "List of net slice instance information.";
        list instance {
          key "id";
          description
            "Configure net slice instance.";
          leaf id {
            type uint32 {
              range "0 .. 4294967295";
            }
            description
              "Configure net slice instance identifier.";
          }
          leaf description {
            type string {
              length "1..80";
            }
            description
              "Net slice instance description.";
          }
        }
      }
      container global {
        description
          "Configure net slice global information.";
        leaf protocol-id {
          type uint8 {
            range "0|160..252";
          }
          default "0";
          description
            "Configure net slice protocol number.";
        }
      }
    }
  }
  augment "/ncs:devices/ncs:device/ncs:live-status" {
    container net-slice {
      tailf:ncs-device-type "netconf";
      tailf:display-when "not(../../ncs:module) or ../../ncs:module[ncs:name='huawei-net-slice'] or (../../ncs:live-status-protocol[not(ncs:capability)]) or (../../ncs:live-status-protocol/ncs:capability/ncs:module[.='huawei-net-slice'])";
      description
        "Configure net slice parameters.";
      container instances {
        description
          "List of net slice instance information.";
        list instance {
          key "id";
          description
            "Configure net slice instance.";
          leaf id {
            type uint32 {
              range "0 .. 4294967295";
            }
            description
              "Configure net slice instance identifier.";
          }
          leaf description {
            type string {
              length "1..80";
            }
            description
              "Net slice instance description.";
          }
        }
      }
      container global {
        description
          "Configure net slice global information.";
        leaf protocol-id {
          type uint8 {
            range "0|160..252";
          }
          // NCS drop default statement
          description
            "Configure net slice protocol number.";
        }
      }
    }
  }
  augment "/ncs:devices/ncs:template/ncs:ned-id/ncs:config" {
    container net-slice {
      description
        "Configure net slice parameters.";
      container instances {
        description
          "List of net slice instance information.";
        list instance {
          // NCS patched for predictable order
          ordered-by user;
          key "id";
          description
            "Configure net slice instance.";
          leaf id {
            type string;
            description
              "Configure net slice instance identifier.";
          }
          leaf description {
            type string;
            description
              "Net slice instance description.";
          }
        }
      }
      container global {
        description
          "Configure net slice global information.";
        leaf protocol-id {
          type string;
          // NCS drop default statement
          description
            "Configure net slice protocol number.";
        }
      }
    }
  }
  augment "/ncs:devices/ncs:template/ncs:ned-id/ncs:config/ifm:ifm/ifm:interfaces/ifm:interface" {
    description
      "Net slice interface information.";
    // NCS drop config false container 'slice-capabilitys'
    container net-slice-binding {
      description
        "Configure parameters for a net slice basic interface.";
      leaf slice-id {
        type string;
        // NCS drop must statement
        description
          "Configure net slice basic instance identifier. When configuring a basic ID, ensure that a slice ID with the same value has been configured for the main interface or one of its sub-interfaces. If interface type is FLEXE, basic slice can't be enabled if the current interface has already enabled any of the following components:ISIS;ISIS IPv6;MPLS;pim sm;pim IPv6 sm;igmp;mld;dot1q/qinq termination;ip binding vpn;rip (IPv4, IPv6);ospf (IPv4, IPv6);ip address;ip address unnumbered interface;mac-address;IPv6 address;IPv6 address anycast;IPv6 address eui-64;IPv6 security rsakey-pair. Otherwise if the interface type is not FLEXE, basic slice can't be enabled only when the current interface has already enabled ip binding vpn.";
      }
    }
    container net-slices {
      description
        "List of net slice interfaces.";
      list net-slice {
        // NCS patched for predictable order
        ordered-by user;
        key "slice-id";
        description
          "Configure parameters for a net slice interface. The slice IDs on the same main interface must be different.";
        leaf slice-id {
          type string;
          // NCS drop must statement
          description
            "Configure net slice instance identifier.";
        }
        choice mode {
          description
            "Choose data plane mode or flex channel mode.";
          case data-plane-mode {
            description
              "Enable/disable data plane mode.";
            leaf data-plane {
              type string;
              // NCS drop must statement
              description
                "Enable/disable data plane mode.";
              ext:operation-exclude "update|delete";
            }
          }
          case flex-channel-mode {
            description
              "Configure net slice flex channel.";
            leaf flex-channel {
              type string;
              units "Mbit/s";
              // NCS drop must statement
              description
                "Configure net slice flex channel. Unit is Mbit/s.";
              ext:operation-exclude "delete";
            }
          }
        }
        // NCS drop config false container 'flex-channel-statistics'
      }
    }
  }
  augment "/ncs:devices/ncs:device/ncs:live-status/ifm:ifm/ifm:interfaces/ifm:interface" {
    description
      "Net slice interface information.";
    container slice-capabilitys {
      tailf:ncs-device-type "netconf";
      tailf:display-when "not(../../../../../ncs:module) or ../../../../../ncs:module[ncs:name='huawei-net-slice'] or (../../../../../ncs:live-status-protocol[not(ncs:capability)]) or (../../../../../ncs:live-status-protocol/ncs:capability/ncs:module[.='huawei-net-slice'])";
      description
        "List of Capabilitys for a interface.";
      list slice-capability {
        key "capability";
        description
          "Statistics of net slice capability for a interface.";
        leaf capability {
          type live_ncs_slice-capability-type;
          description
            "Slice capability type.";
        }
      }
    }
    container net-slice-binding {
      tailf:ncs-device-type "netconf";
      tailf:display-when "not(../../../../../ncs:module) or ../../../../../ncs:module[ncs:name='huawei-net-slice'] or (../../../../../ncs:live-status-protocol[not(ncs:capability)]) or (../../../../../ncs:live-status-protocol/ncs:capability/ncs:module[.='huawei-net-slice'])";
      description
        "Configure parameters for a net slice basic interface.";
      leaf slice-id {
        type leafref {
          path "/ncs:devices/ncs:device/ncs:live-status/net-slice:net-slice/net-slice:instances/net-slice:instance/net-slice:id" {
            tailf:xpath-root 3;
          }
        }
        // NCS drop must statement
        description
          "Configure net slice basic instance identifier. When configuring a basic ID, ensure that a slice ID with the same value has been configured for the main interface or one of its sub-interfaces. If interface type is FLEXE, basic slice can't be enabled if the current interface has already enabled any of the following components:ISIS;ISIS IPv6;MPLS;pim sm;pim IPv6 sm;igmp;mld;dot1q/qinq termination;ip binding vpn;rip (IPv4, IPv6);ospf (IPv4, IPv6);ip address;ip address unnumbered interface;mac-address;IPv6 address;IPv6 address anycast;IPv6 address eui-64;IPv6 security rsakey-pair. Otherwise if the interface type is not FLEXE, basic slice can't be enabled only when the current interface has already enabled ip binding vpn.";
      }
    }
    container net-slices {
      tailf:ncs-device-type "netconf";
      tailf:display-when "not(../../../../../ncs:module) or ../../../../../ncs:module[ncs:name='huawei-net-slice'] or (../../../../../ncs:live-status-protocol[not(ncs:capability)]) or (../../../../../ncs:live-status-protocol/ncs:capability/ncs:module[.='huawei-net-slice'])";
      description
        "List of net slice interfaces.";
      list net-slice {
        key "slice-id";
        description
          "Configure parameters for a net slice interface. The slice IDs on the same main interface must be different.";
        leaf slice-id {
          type leafref {
            path "/ncs:devices/ncs:device/ncs:live-status/net-slice:net-slice/net-slice:instances/net-slice:instance/net-slice:id" {
              tailf:xpath-root 3;
            }
          }
          // NCS drop must statement
          description
            "Configure net slice instance identifier.";
        }
        choice mode {
          description
            "Choose data plane mode or flex channel mode.";
          case data-plane-mode {
            description
              "Enable/disable data plane mode.";
            leaf data-plane {
              type boolean;
              // NCS drop must statement
              description
                "Enable/disable data plane mode.";
              ext:operation-exclude "update|delete";
            }
          }
          case flex-channel-mode {
            description
              "Configure net slice flex channel.";
            leaf flex-channel {
              type uint32 {
                range "1 .. 4294967295";
              }
              units "Mbit/s";
              // NCS drop must statement
              description
                "Configure net slice flex channel. Unit is Mbit/s.";
              ext:operation-exclude "delete";
            }
          }
        }
        container flex-channel-statistics {
          description
            "Statistics of flex-channel.";
          leaf service-class {
            type live_ncs_slice-service-class;
            description
              "Class of service.";
          }
          leaf passed-packets {
            type uint64;
            units "packet";
            description
              "Passed packets.";
          }
          leaf passed-bytes {
            type uint64;
            units "Byte";
            description
              "Passed bytes.";
          }
          leaf dropped-packets {
            type uint64;
            units "packet";
            description
              "Dropped packets.";
          }
          leaf dropped-bytes {
            type uint64;
            units "Byte";
            description
              "Dropped bytes.";
          }
          leaf passed-pps {
            type uint64;
            units "pps";
            description
              "Passed pps.";
          }
          leaf passed-bps {
            type uint64;
            units "bit/s";
            description
              "Passed bps.";
          }
          leaf dropped-pps {
            type uint64;
            units "pps";
            description
              "Dropped pps.";
          }
          leaf dropped-bps {
            type uint64;
            units "bit/s";
            description
              "Dropped bps.";
          }
        }
      }
    }
  }
  augment "/ncs:devices/ncs:device/ncs:config/ifm:ifm/ifm:interfaces/ifm:interface" {
    description
      "Net slice interface information.";
    // NCS drop config false container 'slice-capabilitys'
    container net-slice-binding {
      tailf:ncs-device-type "netconf";
      tailf:display-when "not(../../../../../ncs:module) or ../../../../../ncs:module[ncs:name='huawei-net-slice']";
      description
        "Configure parameters for a net slice basic interface.";
      leaf slice-id {
        type leafref {
          path "/ncs:devices/ncs:device/ncs:config/net-slice:net-slice/net-slice:instances/net-slice:instance/net-slice:id" {
            tailf:xpath-root 3;
          }
        }
        must "not (../../net-slice:net-slices/net-slice:net-slice/net-slice:data-plane or ../../net-slice:net-slices/net-slice:net-slice/net-slice:flex-channel) and ../../ip:ipv6 and ((../../ifm:type = 'FlexE' and ../../ip:ipv6/ip:addresses/ip:address/ip:ip) or not (../../ifm:type = 'FlexE'))" {
          tailf:xpath-root 3;
        }
        description
          "Configure net slice basic instance identifier. When configuring a basic ID, ensure that a slice ID with the same value has been configured for the main interface or one of its sub-interfaces. If interface type is FLEXE, basic slice can't be enabled if the current interface has already enabled any of the following components:ISIS;ISIS IPv6;MPLS;pim sm;pim IPv6 sm;igmp;mld;dot1q/qinq termination;ip binding vpn;rip (IPv4, IPv6);ospf (IPv4, IPv6);ip address;ip address unnumbered interface;mac-address;IPv6 address;IPv6 address anycast;IPv6 address eui-64;IPv6 security rsakey-pair. Otherwise if the interface type is not FLEXE, basic slice can't be enabled only when the current interface has already enabled ip binding vpn.";
      }
    }
    container net-slices {
      tailf:ncs-device-type "netconf";
      tailf:display-when "not(../../../../../ncs:module) or ../../../../../ncs:module[ncs:name='huawei-net-slice']";
      description
        "List of net slice interfaces.";
      list net-slice {
        key "slice-id";
        description
          "Configure parameters for a net slice interface. The slice IDs on the same main interface must be different.";
        leaf slice-id {
          type leafref {
            path "/ncs:devices/ncs:device/ncs:config/net-slice:net-slice/net-slice:instances/net-slice:instance/net-slice:id" {
              tailf:xpath-root 3;
            }
          }
          must '(../../../net-slice:net-slice-binding/net-slice:slice-id and (count(../../net-slice:net-slice/net-slice:data-plane) + count(../../net-slice:net-slice/net-slice:flex-channel)) <= 1) or not (../../../net-slice:net-slice-binding/net-slice:slice-id)' {
            tailf:xpath-root 3;
          }
          description
            "Configure net slice instance identifier.";
        }
        choice mode {
          description
            "Choose data plane mode or flex channel mode.";
          case data-plane-mode {
            description
              "Enable/disable data plane mode.";
            leaf data-plane {
              type boolean;
              must "../../../ip:ipv6 and ((../../../ifm:type = 'FlexE' and (../../../ip:ipv6/ip:addresses/ip:address/ip:ip or ../../../net-slice:net-slice-binding)) or not (../../../ifm:type = 'FlexE'))" {
                tailf:xpath-root 3;
              }
              description
                "Enable/disable data plane mode.";
              ext:operation-exclude "update|delete";
            }
          }
          case flex-channel-mode {
            description
              "Configure net slice flex channel.";
            leaf flex-channel {
              type uint32 {
                range "1 .. 4294967295";
              }
              units "Mbit/s";
              must "../../../ip:ipv6 and ((../../../ifm:type = 'FlexE' and (../../../ip:ipv6/ip:addresses/ip:address/ip:ip or ../../../net-slice:net-slice-binding)) or not (../../../ifm:type = 'FlexE'))" {
                tailf:xpath-root 3;
              }
              description
                "Configure net slice flex channel. Unit is Mbit/s.";
              ext:operation-exclude "delete";
            }
          }
        }
        // NCS drop config false container 'flex-channel-statistics'
      }
    }
  }
}
