module huawei-oam-cfm-evpn-deviations-NE8000 {
  // Generated by yanger -t ncs
  tailf:mount-id "huawei-nc-1.0:huawei-nc-1.0";
  tailf:ncs-device-type "netconf";

  yang-version 1;
  namespace "urn:huawei:yang:huawei-oam-cfm-evpn-deviations-NE8000";
  prefix oam-cfm-evpn-devs-NE8000;

  import huawei-oammgr {
    prefix oammgr;
  }
  import huawei-oam-cfm-evpn {
    prefix oam-cfm-evpn;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Configure the operation, administration and maintenance (OAM) association function.";

  revision 2020-09-18 {
    description
      "Initial revision.";
    reference "Huawei private.";
  }

  typedef ncs_template_cfm-bind-evpn-type-deviations {
    type string;
    description
      "Binding type.";
  }

  typedef ncs_rpc_notif_cfm-bind-evpn-type-deviations {
    type enumeration {
      enum "EVPN-CFM" {
        value 2;
        description
          "Type that EVPN transfers fault information to CFM.";
      }
    }
    description
      "Binding type.";
  }

  typedef live_ncs_cfm-bind-evpn-type-deviations {
    type enumeration {
      enum "EVPN-CFM" {
        value 2;
        description
          "Type that EVPN transfers fault information to CFM.";
      }
    }
    description
      "Binding type.";
  }

  typedef cfm-bind-evpn-type-deviations {
    type enumeration {
      enum "EVPN-CFM" {
        value 2;
        description
          "Type that EVPN transfers fault information to CFM.";
      }
    }
    description
      "Binding type.";
  }

  deviation "/ncs:devices/ncs:template/ncs:ned-id/ncs:config/oammgr:oammgr/oam-cfm-evpn:cfm-bind-evpns/oam-cfm-evpn:cfm-bind-evpn/oam-cfm-evpn:bind-type" {
    deviate replace {
      type oam-cfm-evpn-devs-NE8000:ncs_template_cfm-bind-evpn-type-deviations;
    }
  }
  deviation "/ncs:devices/ncs:device/ncs:live-status/oammgr:oammgr/oam-cfm-evpn:cfm-bind-evpns/oam-cfm-evpn:cfm-bind-evpn/oam-cfm-evpn:bind-type" {
    deviate replace {
      type oam-cfm-evpn-devs-NE8000:live_ncs_cfm-bind-evpn-type-deviations;
    }
  }
  deviation "/ncs:devices/ncs:device/ncs:config/oammgr:oammgr/oam-cfm-evpn:cfm-bind-evpns/oam-cfm-evpn:cfm-bind-evpn/oam-cfm-evpn:bind-type" {
    deviate replace {
      type oam-cfm-evpn-devs-NE8000:cfm-bind-evpn-type-deviations;
    }
  }
}
