module huawei-qos-notification-deviations-NE8000 {
  // Generated by yanger -t ncs
  tailf:mount-id "huawei-nc-1.0:huawei-nc-1.0";
  tailf:ncs-device-type "netconf";

  namespace "urn:huawei:yang:huawei-qos-notification-deviations-NE8000";
  prefix qos-notification-devs-NE8000;

  import huawei-qos-notification {
    prefix qos-notification;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "This module defines deviation statements for huawei-qos-notification module.";

  revision 2019-11-06 {
    description
      "Initial revision.";
    reference "Huawei private.";
  }

  deviation "/ncs:devices/ncs:device/ncs:notifications/ncs:received-notifications/ncs:notification/ncs:data/qos-notification:hqos-user-queue-apply-pir-from-pool-fail-alarm" {
    deviate not-supported;
  }
  deviation "/ncs:devices/ncs:device/ncs:netconf-notifications/ncs:received-notifications/ncs:notification/ncs:data/qos-notification:hqos-user-queue-apply-pir-from-pool-fail-alarm" {
    deviate not-supported;
  }
  deviation "/ncs:devices/ncs:device/ncs:notifications/ncs:received-notifications/ncs:notification/ncs:data/qos-notification:hqos-user-queue-apply-pir-from-pool-success-alarm" {
    deviate not-supported;
  }
  deviation "/ncs:devices/ncs:device/ncs:netconf-notifications/ncs:received-notifications/ncs:notification/ncs:data/qos-notification:hqos-user-queue-apply-pir-from-pool-success-alarm" {
    deviate not-supported;
  }
  deviation "/ncs:devices/ncs:device/ncs:notifications/ncs:received-notifications/ncs:notification/ncs:data/qos-notification:xqos-4queue-resource-over-alarm" {
    deviate not-supported;
  }
  deviation "/ncs:devices/ncs:device/ncs:netconf-notifications/ncs:received-notifications/ncs:notification/ncs:data/qos-notification:xqos-4queue-resource-over-alarm" {
    deviate not-supported;
  }
  deviation "/ncs:devices/ncs:device/ncs:notifications/ncs:received-notifications/ncs:notification/ncs:data/qos-notification:xqos-4queue-resource-over-alarm-resume" {
    deviate not-supported;
  }
  deviation "/ncs:devices/ncs:device/ncs:netconf-notifications/ncs:received-notifications/ncs:notification/ncs:data/qos-notification:xqos-4queue-resource-over-alarm-resume" {
    deviate not-supported;
  }
  deviation "/ncs:devices/ncs:device/ncs:notifications/ncs:received-notifications/ncs:notification/ncs:data/qos-notification:xqos-4queue-resource-pre-alarm" {
    deviate not-supported;
  }
  deviation "/ncs:devices/ncs:device/ncs:netconf-notifications/ncs:received-notifications/ncs:notification/ncs:data/qos-notification:xqos-4queue-resource-pre-alarm" {
    deviate not-supported;
  }
  deviation "/ncs:devices/ncs:device/ncs:notifications/ncs:received-notifications/ncs:notification/ncs:data/qos-notification:xqos-4queue-resource-pre-alarm-resume" {
    deviate not-supported;
  }
  deviation "/ncs:devices/ncs:device/ncs:netconf-notifications/ncs:received-notifications/ncs:notification/ncs:data/qos-notification:xqos-4queue-resource-pre-alarm-resume" {
    deviate not-supported;
  }
  deviation "/ncs:devices/ncs:device/ncs:notifications/ncs:received-notifications/ncs:notification/ncs:data/qos-notification:xqos-8queue-resource-over-alarm" {
    deviate not-supported;
  }
  deviation "/ncs:devices/ncs:device/ncs:netconf-notifications/ncs:received-notifications/ncs:notification/ncs:data/qos-notification:xqos-8queue-resource-over-alarm" {
    deviate not-supported;
  }
  deviation "/ncs:devices/ncs:device/ncs:notifications/ncs:received-notifications/ncs:notification/ncs:data/qos-notification:xqos-8queue-resource-over-alarm-resume" {
    deviate not-supported;
  }
  deviation "/ncs:devices/ncs:device/ncs:netconf-notifications/ncs:received-notifications/ncs:notification/ncs:data/qos-notification:xqos-8queue-resource-over-alarm-resume" {
    deviate not-supported;
  }
  deviation "/ncs:devices/ncs:device/ncs:notifications/ncs:received-notifications/ncs:notification/ncs:data/qos-notification:xqos-8queue-resource-pre-alarm" {
    deviate not-supported;
  }
  deviation "/ncs:devices/ncs:device/ncs:netconf-notifications/ncs:received-notifications/ncs:notification/ncs:data/qos-notification:xqos-8queue-resource-pre-alarm" {
    deviate not-supported;
  }
  deviation "/ncs:devices/ncs:device/ncs:notifications/ncs:received-notifications/ncs:notification/ncs:data/qos-notification:xqos-8queue-resource-pre-alarm-resume" {
    deviate not-supported;
  }
  deviation "/ncs:devices/ncs:device/ncs:netconf-notifications/ncs:received-notifications/ncs:notification/ncs:data/qos-notification:xqos-8queue-resource-pre-alarm-resume" {
    deviate not-supported;
  }
  deviation "/ncs:devices/ncs:device/ncs:notifications/ncs:received-notifications/ncs:notification/ncs:data/qos-notification:xqos-hard-pipe-ac-band-over-alarm" {
    deviate not-supported;
  }
  deviation "/ncs:devices/ncs:device/ncs:netconf-notifications/ncs:received-notifications/ncs:notification/ncs:data/qos-notification:xqos-hard-pipe-ac-band-over-alarm" {
    deviate not-supported;
  }
  deviation "/ncs:devices/ncs:device/ncs:notifications/ncs:received-notifications/ncs:notification/ncs:data/qos-notification:xqos-hard-pipe-ac-band-over-alarm-resume" {
    deviate not-supported;
  }
  deviation "/ncs:devices/ncs:device/ncs:netconf-notifications/ncs:received-notifications/ncs:notification/ncs:data/qos-notification:xqos-hard-pipe-ac-band-over-alarm-resume" {
    deviate not-supported;
  }
  deviation "/ncs:devices/ncs:device/ncs:notifications/ncs:received-notifications/ncs:notification/ncs:data/qos-notification:xqos-hard-pipe-alarm" {
    deviate not-supported;
  }
  deviation "/ncs:devices/ncs:device/ncs:netconf-notifications/ncs:received-notifications/ncs:notification/ncs:data/qos-notification:xqos-hard-pipe-alarm" {
    deviate not-supported;
  }
  deviation "/ncs:devices/ncs:device/ncs:notifications/ncs:received-notifications/ncs:notification/ncs:data/qos-notification:xqos-hard-pipe-alarm-resume" {
    deviate not-supported;
  }
  deviation "/ncs:devices/ncs:device/ncs:netconf-notifications/ncs:received-notifications/ncs:notification/ncs:data/qos-notification:xqos-hard-pipe-alarm-resume" {
    deviate not-supported;
  }
  deviation "/ncs:devices/ncs:device/ncs:notifications/ncs:received-notifications/ncs:notification/ncs:data/qos-notification:xqos-hard-pipe-apply-fail-alarm" {
    deviate not-supported;
  }
  deviation "/ncs:devices/ncs:device/ncs:netconf-notifications/ncs:received-notifications/ncs:notification/ncs:data/qos-notification:xqos-hard-pipe-apply-fail-alarm" {
    deviate not-supported;
  }
  deviation "/ncs:devices/ncs:device/ncs:notifications/ncs:received-notifications/ncs:notification/ncs:data/qos-notification:xqos-hard-pipe-apply-fail-alarm-resume" {
    deviate not-supported;
  }
  deviation "/ncs:devices/ncs:device/ncs:netconf-notifications/ncs:received-notifications/ncs:notification/ncs:data/qos-notification:xqos-hard-pipe-apply-fail-alarm-resume" {
    deviate not-supported;
  }
  deviation "/ncs:devices/ncs:device/ncs:notifications/ncs:received-notifications/ncs:notification/ncs:data/qos-notification:xqos-hard-pipe-apply-user-queue-fail-alarm" {
    deviate not-supported;
  }
  deviation "/ncs:devices/ncs:device/ncs:netconf-notifications/ncs:received-notifications/ncs:notification/ncs:data/qos-notification:xqos-hard-pipe-apply-user-queue-fail-alarm" {
    deviate not-supported;
  }
  deviation "/ncs:devices/ncs:device/ncs:notifications/ncs:received-notifications/ncs:notification/ncs:data/qos-notification:xqos-hard-pipe-apply-user-queue-fail-alarm-resume" {
    deviate not-supported;
  }
  deviation "/ncs:devices/ncs:device/ncs:netconf-notifications/ncs:received-notifications/ncs:notification/ncs:data/qos-notification:xqos-hard-pipe-apply-user-queue-fail-alarm-resume" {
    deviate not-supported;
  }
  deviation "/ncs:devices/ncs:device/ncs:notifications/ncs:received-notifications/ncs:notification/ncs:data/qos-notification:xqos-hard-pipe-bandwidth-alarm" {
    deviate not-supported;
  }
  deviation "/ncs:devices/ncs:device/ncs:netconf-notifications/ncs:received-notifications/ncs:notification/ncs:data/qos-notification:xqos-hard-pipe-bandwidth-alarm" {
    deviate not-supported;
  }
  deviation "/ncs:devices/ncs:device/ncs:notifications/ncs:received-notifications/ncs:notification/ncs:data/qos-notification:xqos-hard-pipe-bandwidth-alarm-resume" {
    deviate not-supported;
  }
  deviation "/ncs:devices/ncs:device/ncs:netconf-notifications/ncs:received-notifications/ncs:notification/ncs:data/qos-notification:xqos-hard-pipe-bandwidth-alarm-resume" {
    deviate not-supported;
  }
  deviation "/ncs:devices/ncs:device/ncs:notifications/ncs:received-notifications/ncs:notification/ncs:data/qos-notification:xqos-soft-pipe-alarm" {
    deviate not-supported;
  }
  deviation "/ncs:devices/ncs:device/ncs:netconf-notifications/ncs:received-notifications/ncs:notification/ncs:data/qos-notification:xqos-soft-pipe-alarm" {
    deviate not-supported;
  }
  deviation "/ncs:devices/ncs:device/ncs:notifications/ncs:received-notifications/ncs:notification/ncs:data/qos-notification:xqos-soft-pipe-alarm-resume" {
    deviate not-supported;
  }
  deviation "/ncs:devices/ncs:device/ncs:netconf-notifications/ncs:received-notifications/ncs:notification/ncs:data/qos-notification:xqos-soft-pipe-alarm-resume" {
    deviate not-supported;
  }
  deviation "/ncs:devices/ncs:device/ncs:notifications/ncs:received-notifications/ncs:notification/ncs:data/qos-notification:xqos-tm-performance-alarm" {
    deviate not-supported;
  }
  deviation "/ncs:devices/ncs:device/ncs:netconf-notifications/ncs:received-notifications/ncs:notification/ncs:data/qos-notification:xqos-tm-performance-alarm" {
    deviate not-supported;
  }
  deviation "/ncs:devices/ncs:device/ncs:notifications/ncs:received-notifications/ncs:notification/ncs:data/qos-notification:xqos-tm-performance-alarm-resume" {
    deviate not-supported;
  }
  deviation "/ncs:devices/ncs:device/ncs:netconf-notifications/ncs:received-notifications/ncs:notification/ncs:data/qos-notification:xqos-tm-performance-alarm-resume" {
    deviate not-supported;
  }
}
