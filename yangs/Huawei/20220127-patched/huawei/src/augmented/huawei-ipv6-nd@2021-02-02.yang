module huawei-ipv6-nd {
  // Generated by yanger -t ncs
  tailf:mount-id "huawei-nc-1.0:huawei-nc-1.0";
  tailf:ncs-device-type "netconf";

  yang-version 1;
  namespace "urn:huawei:yang:huawei-ipv6-nd";
  prefix ipv6-nd;

  import huawei-ifm {
    prefix ifm;
  }
  import huawei-pub-type {
    prefix pub-type;
  }
  import ietf-inet-types {
    prefix inet;
  }
  import huawei-extension {
    prefix ext;
  }
  import huawei-ip {
    prefix ip;
  }
  import huawei-network-instance {
    prefix ni;
  }
  import huawei-ethernet {
    prefix ethernet;
  }
  import huawei-bd {
    prefix bd;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "ND management.";

  revision 2021-02-02 {
    description
      "Containers dns-server-addresses and dns-search-suffixs are added.";
    reference "Huawei private.";
  }
  revision 2020-10-15 {
    description
      "ND rate limit and drop statistics are added;
       add some leaf nodes for the if-property and the proxys container;
       add some containers for the static-neighbor and ra-property container;
       add strict-prefix-learn container.";
    reference "Huawei private.";
  }
  revision 2020-03-26 {
    description
      "Leaf ns-send-rate-limit is added.";
    reference "Huawei private.";
  }
  revision 2020-02-29 {
    description
      "Default value of stale-time is deleted.";
    reference "Huawei private.";
  }
  revision 2020-02-26 {
    description
      "Default value.";
    reference "Huawei private.";
  }
  revision 2019-12-30 {
    description
      "Init revision.";
    reference "Huawei private.";
  }
  ext:task-name "nd";

  typedef ncs_template_nd-flag {
    type string;
    description
      "Description of nd-flag.";
  }

  typedef ncs_template_nd-switch-state {
    type string;
    description
      "The state of the switch.";
  }

  typedef ncs_template_nd-ngb-state {
    type string;
    description
      "The neighbor unreachability detection state.";
    reference "RFC 4861: Neighbor Discovery for IP version 6 (IPv6) Section 7.3.2";
  }

  typedef ncs_template_nd-route-preference {
    type string;
    description
      "The RA router preference level.";
  }

  typedef ncs_template_nd-nb-type {
    type string;
    description
      "The origin of neighbor entry.";
  }

  typedef ncs_template_nd-pkt-type {
    type string;
    description
      "The ND packet type value.";
  }

  typedef ncs_template_nd-pkt-evt-type {
    type string;
    description
      "The ND packet type or event value.";
  }

  typedef ncs_template_nd-tgt-pkt-type {
    type string;
    description
      "The type value of ND packet that supports the target address.";
  }

  typedef ncs_rpc_notif_nd-flag {
    type enumeration {
      enum "false" {
        value 0;
        description
          "NO.";
      }
      enum "true" {
        value 1;
        description
          "YES.";
      }
    }
    description
      "Description of nd-flag.";
  }

  typedef ncs_rpc_notif_nd-switch-state {
    type enumeration {
      enum "off" {
        value 0;
        description
          "Off.";
      }
      enum "on" {
        value 1;
        description
          "On.";
      }
    }
    description
      "The state of the switch.";
  }

  typedef ncs_rpc_notif_nd-ngb-state {
    type enumeration {
      enum "incomplete" {
        value 0;
        description
          "Address resolution is being performed on the entry.";
      }
      enum "reachable" {
        value 1;
        description
          "The neighbor is known to have been reachable recently.";
      }
      enum "stale" {
        value 2;
        description
          "The neighbor is no longer known to be reachable, but until traffic is sent to the neighbor no attempt should be made to verify its reachability.";
      }
      enum "delay" {
        value 3;
        description
          "The neighbor is no longer known to be reachable, and traffic has recently been sent to the neighbor. Rather than probe the neighbor immediately, however,
            delay sending probes for a short while in order to give upper-layer protocols a chance to provide reachability confirmation.";
      }
      enum "probe" {
        value 4;
        description
          "The neighbor is no longer known to be reachable, and unicast neighbor solicitation probes are being sent to verify reachability.";
      }
    }
    description
      "The neighbor unreachability detection state.";
    reference "RFC 4861: Neighbor Discovery for IP version 6 (IPv6) Section 7.3.2";
  }

  typedef ncs_rpc_notif_nd-route-preference {
    type enumeration {
      enum "medium" {
        value 0;
        description
          "Preference medium.";
      }
      enum "high" {
        value 1;
        description
          "Preference high.";
      }
      enum "low" {
        value 3;
        description
          "Preference low.";
      }
    }
    description
      "The RA router preference level.";
  }

  typedef ncs_rpc_notif_nd-nb-type {
    type enumeration {
      enum "remote" {
        value 0;
        description
          "Remote pushed.";
      }
      enum "static" {
        value 1;
        description
          "Statically configured.";
      }
      enum "dynamic" {
        value 2;
        description
          "Dynamically resolved.";
      }
    }
    description
      "The origin of neighbor entry.";
  }

  typedef ncs_rpc_notif_nd-pkt-type {
    type enumeration {
      enum "RS" {
        value 0;
        description
          "Router solicitation packet.";
      }
      enum "RA" {
        value 1;
        description
          "Router advertisement packet.";
      }
      enum "NS" {
        value 2;
        description
          "Neighbor solicitation packet.";
      }
      enum "NA" {
        value 3;
        description
          "Neighbor advertisement packet.";
      }
    }
    description
      "The ND packet type value.";
  }

  typedef ncs_rpc_notif_nd-pkt-evt-type {
    type enumeration {
      enum "RS" {
        value 0;
        description
          "Router solicitation packet.";
      }
      enum "RA" {
        value 1;
        description
          "Router advertisement packet.";
      }
      enum "NS" {
        value 2;
        description
          "Neighbor solicitation packet.";
      }
      enum "NA" {
        value 3;
        description
          "Neighbor advertisement packet.";
      }
      enum "NDMISS" {
        value 4;
        description
          "ND miss.";
      }
    }
    description
      "The ND packet type or event value.";
  }

  typedef ncs_rpc_notif_nd-tgt-pkt-type {
    type enumeration {
      enum "NS" {
        value 2;
        description
          "Neighbor solicitation packet.";
      }
      enum "NA" {
        value 3;
        description
          "Neighbor advertisement packet.";
      }
    }
    description
      "The type value of ND packet that supports the target address.";
  }

  typedef live_ncs_nd-flag {
    type enumeration {
      enum "false" {
        value 0;
        description
          "NO.";
      }
      enum "true" {
        value 1;
        description
          "YES.";
      }
    }
    description
      "Description of nd-flag.";
  }

  typedef live_ncs_nd-switch-state {
    type enumeration {
      enum "off" {
        value 0;
        description
          "Off.";
      }
      enum "on" {
        value 1;
        description
          "On.";
      }
    }
    description
      "The state of the switch.";
  }

  typedef live_ncs_nd-ngb-state {
    type enumeration {
      enum "incomplete" {
        value 0;
        description
          "Address resolution is being performed on the entry.";
      }
      enum "reachable" {
        value 1;
        description
          "The neighbor is known to have been reachable recently.";
      }
      enum "stale" {
        value 2;
        description
          "The neighbor is no longer known to be reachable, but until traffic is sent to the neighbor no attempt should be made to verify its reachability.";
      }
      enum "delay" {
        value 3;
        description
          "The neighbor is no longer known to be reachable, and traffic has recently been sent to the neighbor. Rather than probe the neighbor immediately, however,
            delay sending probes for a short while in order to give upper-layer protocols a chance to provide reachability confirmation.";
      }
      enum "probe" {
        value 4;
        description
          "The neighbor is no longer known to be reachable, and unicast neighbor solicitation probes are being sent to verify reachability.";
      }
    }
    description
      "The neighbor unreachability detection state.";
    reference "RFC 4861: Neighbor Discovery for IP version 6 (IPv6) Section 7.3.2";
  }

  typedef live_ncs_nd-route-preference {
    type enumeration {
      enum "medium" {
        value 0;
        description
          "Preference medium.";
      }
      enum "high" {
        value 1;
        description
          "Preference high.";
      }
      enum "low" {
        value 3;
        description
          "Preference low.";
      }
    }
    description
      "The RA router preference level.";
  }

  typedef live_ncs_nd-nb-type {
    type enumeration {
      enum "remote" {
        value 0;
        description
          "Remote pushed.";
      }
      enum "static" {
        value 1;
        description
          "Statically configured.";
      }
      enum "dynamic" {
        value 2;
        description
          "Dynamically resolved.";
      }
    }
    description
      "The origin of neighbor entry.";
  }

  typedef live_ncs_nd-pkt-type {
    type enumeration {
      enum "RS" {
        value 0;
        description
          "Router solicitation packet.";
      }
      enum "RA" {
        value 1;
        description
          "Router advertisement packet.";
      }
      enum "NS" {
        value 2;
        description
          "Neighbor solicitation packet.";
      }
      enum "NA" {
        value 3;
        description
          "Neighbor advertisement packet.";
      }
    }
    description
      "The ND packet type value.";
  }

  typedef live_ncs_nd-pkt-evt-type {
    type enumeration {
      enum "RS" {
        value 0;
        description
          "Router solicitation packet.";
      }
      enum "RA" {
        value 1;
        description
          "Router advertisement packet.";
      }
      enum "NS" {
        value 2;
        description
          "Neighbor solicitation packet.";
      }
      enum "NA" {
        value 3;
        description
          "Neighbor advertisement packet.";
      }
      enum "NDMISS" {
        value 4;
        description
          "ND miss.";
      }
    }
    description
      "The ND packet type or event value.";
  }

  typedef live_ncs_nd-tgt-pkt-type {
    type enumeration {
      enum "NS" {
        value 2;
        description
          "Neighbor solicitation packet.";
      }
      enum "NA" {
        value 3;
        description
          "Neighbor advertisement packet.";
      }
    }
    description
      "The type value of ND packet that supports the target address.";
  }

  typedef nd-flag {
    type enumeration {
      enum "false" {
        value 0;
        description
          "NO.";
      }
      enum "true" {
        value 1;
        description
          "YES.";
      }
    }
    description
      "Description of nd-flag.";
  }

  typedef nd-switch-state {
    type enumeration {
      enum "off" {
        value 0;
        description
          "Off.";
      }
      enum "on" {
        value 1;
        description
          "On.";
      }
    }
    description
      "The state of the switch.";
  }

  typedef nd-ngb-state {
    type enumeration {
      enum "incomplete" {
        value 0;
        description
          "Address resolution is being performed on the entry.";
      }
      enum "reachable" {
        value 1;
        description
          "The neighbor is known to have been reachable recently.";
      }
      enum "stale" {
        value 2;
        description
          "The neighbor is no longer known to be reachable, but until traffic is sent to the neighbor no attempt should be made to verify its reachability.";
      }
      enum "delay" {
        value 3;
        description
          "The neighbor is no longer known to be reachable, and traffic has recently been sent to the neighbor. Rather than probe the neighbor immediately, however,
            delay sending probes for a short while in order to give upper-layer protocols a chance to provide reachability confirmation.";
      }
      enum "probe" {
        value 4;
        description
          "The neighbor is no longer known to be reachable, and unicast neighbor solicitation probes are being sent to verify reachability.";
      }
    }
    description
      "The neighbor unreachability detection state.";
    reference "RFC 4861: Neighbor Discovery for IP version 6 (IPv6) Section 7.3.2";
  }

  typedef nd-route-preference {
    type enumeration {
      enum "medium" {
        value 0;
        description
          "Preference medium.";
      }
      enum "high" {
        value 1;
        description
          "Preference high.";
      }
      enum "low" {
        value 3;
        description
          "Preference low.";
      }
    }
    description
      "The RA router preference level.";
  }

  typedef nd-nb-type {
    type enumeration {
      enum "remote" {
        value 0;
        description
          "Remote pushed.";
      }
      enum "static" {
        value 1;
        description
          "Statically configured.";
      }
      enum "dynamic" {
        value 2;
        description
          "Dynamically resolved.";
      }
    }
    description
      "The origin of neighbor entry.";
  }

  typedef nd-pkt-type {
    type enumeration {
      enum "RS" {
        value 0;
        description
          "Router solicitation packet.";
      }
      enum "RA" {
        value 1;
        description
          "Router advertisement packet.";
      }
      enum "NS" {
        value 2;
        description
          "Neighbor solicitation packet.";
      }
      enum "NA" {
        value 3;
        description
          "Neighbor advertisement packet.";
      }
    }
    description
      "The ND packet type value.";
  }

  typedef nd-pkt-evt-type {
    type enumeration {
      enum "RS" {
        value 0;
        description
          "Router solicitation packet.";
      }
      enum "RA" {
        value 1;
        description
          "Router advertisement packet.";
      }
      enum "NS" {
        value 2;
        description
          "Neighbor solicitation packet.";
      }
      enum "NA" {
        value 3;
        description
          "Neighbor advertisement packet.";
      }
      enum "NDMISS" {
        value 4;
        description
          "ND miss.";
      }
    }
    description
      "The ND packet type or event value.";
  }

  typedef nd-tgt-pkt-type {
    type enumeration {
      enum "NS" {
        value 2;
        description
          "Neighbor solicitation packet.";
      }
      enum "NA" {
        value 3;
        description
          "Neighbor advertisement packet.";
      }
    }
    description
      "The type value of ND packet that supports the target address.";
  }

  grouping ncs_template_nd-ip-rate-limits-type {
    description
      "Rate limits for receiving ND packets or ND miss based on specified source IP address.";
    container ip-rate-limits {
      description
        "List of rate limits for receiving ND packets or ND miss based on specified source IP address.";
      list ip-rate-limit {
        // NCS patched for predictable order
        ordered-by user;
        key "packet-type ipv6-addr";
        description
          "Configure the rate limit for receiving ND packets or ND miss based on specified source IP address.";
        leaf packet-type {
          type ncs_template_nd-pkt-evt-type;
          description
            "ND packet type or ND miss.";
        }
        leaf ipv6-addr {
          type string;
          description
            "Source IPv6 address, the address cannot be a multicast address, that is, cannot start with FFXX or ffXX, X represents hexadecimal character. When the type is NDMISS, the source address cannot be the unspecified address.";
        }
        leaf value {
          type string;
          units "pps";
          // NCS drop mandatory statement
          description
            "Rate limit of receiving ND packet or ND miss.";
        }
      }
    }
  }

  grouping ncs_rpc_notif_nd-ip-rate-limits-type {
    description
      "Rate limits for receiving ND packets or ND miss based on specified source IP address.";
    container ip-rate-limits {
      description
        "List of rate limits for receiving ND packets or ND miss based on specified source IP address.";
      list ip-rate-limit {
        key "packet-type ipv6-addr";
        description
          "Configure the rate limit for receiving ND packets or ND miss based on specified source IP address.";
        leaf packet-type {
          type ncs_rpc_notif_nd-pkt-evt-type;
          description
            "ND packet type or ND miss.";
        }
        leaf ipv6-addr {
          type inet:ipv6-address-no-zone;
          description
            "Source IPv6 address, the address cannot be a multicast address, that is, cannot start with FFXX or ffXX, X represents hexadecimal character. When the type is NDMISS, the source address cannot be the unspecified address.";
        }
        leaf value {
          type uint16 {
            range "0..5000";
          }
          units "pps";
          mandatory true;
          description
            "Rate limit of receiving ND packet or ND miss.";
        }
      }
    }
  }

  grouping live_ncs_nd-ip-rate-limits-type {
    description
      "Rate limits for receiving ND packets or ND miss based on specified source IP address.";
    container ip-rate-limits {
      description
        "List of rate limits for receiving ND packets or ND miss based on specified source IP address.";
      list ip-rate-limit {
        key "packet-type ipv6-addr";
        description
          "Configure the rate limit for receiving ND packets or ND miss based on specified source IP address.";
        leaf packet-type {
          type live_ncs_nd-pkt-evt-type;
          description
            "ND packet type or ND miss.";
        }
        leaf ipv6-addr {
          type inet:ipv6-address-no-zone;
          description
            "Source IPv6 address, the address cannot be a multicast address, that is, cannot start with FFXX or ffXX, X represents hexadecimal character. When the type is NDMISS, the source address cannot be the unspecified address.";
        }
        leaf value {
          type uint16 {
            range "0..5000";
          }
          units "pps";
          // NCS drop mandatory statement
          description
            "Rate limit of receiving ND packet or ND miss.";
        }
      }
    }
  }

  grouping nd-ip-rate-limits-type {
    description
      "Rate limits for receiving ND packets or ND miss based on specified source IP address.";
    container ip-rate-limits {
      description
        "List of rate limits for receiving ND packets or ND miss based on specified source IP address.";
      list ip-rate-limit {
        key "packet-type ipv6-addr";
        description
          "Configure the rate limit for receiving ND packets or ND miss based on specified source IP address.";
        leaf packet-type {
          type nd-pkt-evt-type;
          description
            "ND packet type or ND miss.";
        }
        leaf ipv6-addr {
          type inet:ipv6-address-no-zone;
          description
            "Source IPv6 address, the address cannot be a multicast address, that is, cannot start with FFXX or ffXX, X represents hexadecimal character. When the type is NDMISS, the source address cannot be the unspecified address.";
        }
        leaf value {
          type uint16 {
            range "0..5000";
          }
          units "pps";
          mandatory true;
          description
            "Rate limit of receiving ND packet or ND miss.";
        }
      }
    }
  }

  augment "/ncs:devices/ncs:device/ncs:rpc" {
    container rpc-nd-pkt-clear-all {
      tailf:ncs-device-type "netconf";
      tailf:display-when "not(../../ncs:module) or ../../ncs:module[ncs:name='huawei-ipv6-nd']";
      tailf:action nd-pkt-clear-all {
        tailf:actionpoint ncsproxy {
          tailf:internal;
        }
        description
          "To clear all ND statistics.";
        ext:node-ref "/ipv6-nd/nd-pkt-stats";
      }
    }
  }
  augment "/ncs:devices/ncs:device-group/ncs:ned-id/ncs:rpc" {
    container rpc-nd-pkt-clear-all {
      tailf:ncs-device-type "netconf";
      tailf:display-when "/ncs:devices/ncs:device[ncs:name=current()/../../../ncs:member]/ncs:module[ncs:name='huawei-ipv6-nd']";
      tailf:action nd-pkt-clear-all {
        tailf:actionpoint ncsproxy {
          tailf:internal;
        }
        description
          "To clear all ND statistics.";
        ext:node-ref "/ipv6-nd/nd-pkt-stats";
      }
    }
  }
  augment "/ncs:devices/ncs:device/ncs:config" {
    container ipv6-nd {
      tailf:ncs-device-type "netconf";
      tailf:display-when "not(../../ncs:module) or ../../ncs:module[ncs:name='huawei-ipv6-nd']";
      description
        "ND management.";
      container global {
        description
          "Configure global configuration of ND.";
        leaf ns-send-rate-limit {
          type uint16 {
            range "1..1000";
          }
          units "pps";
          default "550";
          description
            "Rate limit of sending NS packet.";
        }
        leaf na-send-rate-limit {
          type uint16 {
            range "1..10240";
          }
          units "pps";
          default "5000";
          description
            "Rate limit of sending NA packet.";
        }
        leaf rs-send-rate-limit {
          type uint16 {
            range "1..1000";
          }
          units "pps";
          default "550";
          description
            "Rate limit of sending RS packet.";
        }
        leaf ra-send-rate-limit {
          type uint16 {
            range "1..1000";
          }
          units "pps";
          default "550";
          description
            "Rate limit of sending RA packet.";
        }
        leaf dad-detect {
          type nd-flag;
          default "true";
          description
            "The switch of DAD enhanced detection.";
        }
        leaf mac-check-flag {
          type nd-flag;
          default "false";
          description
            "Enable IPv6 ND MAC check.";
        }
        leaf auto-detect-flag {
          type nd-switch-state;
          default "on";
          description
            "To enable the automatic detection of ND entries.";
        }
        leaf prefix-strict-flag {
          type nd-switch-state;
          default "on";
          description
            "ND prefix learning strict.";
        }
        leaf pre-detect-flag {
          type nd-switch-state;
          default "off";
          description
            "To determine whether to enable pre-detection.";
        }
        leaf hop-limit {
          type uint8 {
            range "1..255";
          }
          default "64";
          description
            "IPv6 packet hoplimit.";
        }
        leaf stale-time {
          type uint32 {
            range "60..172800";
          }
          units "s";
          default "1200";
          description
            "Aging time of the global stale state.";
        }
        leaf rsa-calculate-rate-limit {
          type uint32 {
            range "0..100";
            ext:value-meaning {
              ext:item "0" {
                ext:meaning "disabling the function of rsa calculation limit";
              }
            }
          }
          default "0";
          description
            "Rate limit for RSA option calculation.";
        }
        leaf log-trap-time {
          type uint32 {
            range "60..3600";
          }
          units "s";
          default "600";
          description
            "The interval for sending speed-limit logs and alarms.";
        }
        leaf rs-receive-rate-limit {
          type uint16 {
            range "1..5000";
          }
          units "pps";
          ext:dynamic-default;
          description
            "Rate limit of receiving RS packet.";
        }
        leaf ra-receive-rate-limit {
          type uint16 {
            range "1..5000";
          }
          units "pps";
          ext:dynamic-default;
          description
            "Rate limit of receiving RA packet.";
        }
        leaf ns-receive-rate-limit {
          type uint16 {
            range "1..5000";
          }
          units "pps";
          ext:dynamic-default;
          description
            "Rate limit of receiving NS packet.";
        }
        leaf na-receive-rate-limit {
          type uint16 {
            range "1..5000";
          }
          units "pps";
          ext:dynamic-default;
          description
            "Rate limit of receiving NA packet.";
        }
        leaf miss-receive-rate-limit {
          type uint16 {
            range "1..5000";
          }
          units "pps";
          ext:dynamic-default;
          description
            "Rate limit of receiving ND miss.";
        }
        leaf dad-detect-rate-limit {
          type uint16 {
            range "1..100";
          }
          units "pps";
          default "50";
          description
            "Rate limit of sending DAD detect packet.";
        }
        leaf dad-detect-attempts {
          type uint16 {
            range "1..5";
          }
          default "3";
          description
            "Number of attempts to resolve address conflicts.";
        }
      }
      container m-lag-global {
        description
          "Configure M-LAG global configuration of ND.";
        leaf ipv6-neighbor-backup-rate {
          type uint32 {
            range "1..2000";
          }
          description
            "Specifies the number of IPv6 neighbor entries synchronized per second through M-LAG.";
          ext:dynamic-default;
        }
      }
      // NCS drop config false container 'ipv6-neighbors'
      // NCS drop config false container 'nd-pkt-stats'
      container anti-attack {
        description
          "Configure ND anti-attack for global.";
        container source-mac-receive {
          description
            "Configure the ND anti-attack based on packet source MAC address.";
          container every-mac-rate-limits {
            description
              "List of rate limits for receiving ND packets based on every source MAC address.";
            list every-mac-rate-limit {
              key "packet-type";
              description
                "Configure the rate limit for receiving ND packets based on every source MAC address.";
              leaf packet-type {
                type nd-pkt-type;
                description
                  "ND packet type.";
              }
              leaf value {
                type uint16 {
                  range "0..5000";
                }
                units "pps";
                mandatory true;
                description
                  "Rate limit of receiving ND packet.";
              }
            }
          }
          container mac-rate-limits {
            description
              "List of rate limits for receiving ND packets based on specified source MAC address.";
            list mac-rate-limit {
              key "packet-type mac-addr";
              description
                "Configure the rate limit for receiving ND packets based on specified source MAC address.";
              leaf packet-type {
                type nd-pkt-type;
                description
                  "ND packet type.";
              }
              leaf mac-addr {
                type pub-type:mac-address {
                  pattern '[0-9a-fA-F][0|2|4|6|8|aA|cC|eE][0-9a-fA-F]{2}(-[0-9a-fA-F]{4}){2}';
                }
                description
                  "Source MAC address.";
              }
              leaf value {
                type uint16 {
                  range "0..5000";
                }
                units "pps";
                mandatory true;
                description
                  "Rate limit of receiving ND packet.";
              }
            }
          }
        }
        container source-ip-receive {
          description
            "Configure the ND anti-attack based on packet or miss source IP address.";
          container every-ip-rate-limits {
            description
              "List of rate limits for receiving ND packets or ND miss based on every source IP address.";
            list every-ip-rate-limit {
              key "packet-type";
              description
                "Configure the rate limit for receiving ND packets or ND miss based on every source IP address.";
              leaf packet-type {
                type nd-pkt-evt-type;
                description
                  "ND packet type or ND miss.";
              }
              leaf value {
                type uint16 {
                  range "0..5000";
                }
                units "pps";
                mandatory true;
                description
                  "Rate limit of receiving ND packet or ND miss.";
              }
            }
          }
          uses nd-ip-rate-limits-type;
        }
        container destination-ip-receive {
          description
            "Configure the ND anti-attack based on packet destination IP address.";
          container every-ip-rate-limits {
            description
              "List of rate limits for receiving ND packets based on every destination IP address.";
            list every-ip-rate-limit {
              key "packet-type";
              description
                "Configure the rate limit for receiving ND packets based on every destination IP address.";
              leaf packet-type {
                type nd-pkt-type;
                description
                  "ND packet type.";
              }
              leaf value {
                type uint16 {
                  range "0..5000";
                }
                units "pps";
                mandatory true;
                description
                  "Rate limit of receiving ND packet.";
              }
            }
          }
          container ip-rate-limits {
            description
              "List of rate limits for receiving ND packets based on specified destination IP address.";
            list ip-rate-limit {
              key "packet-type ipv6-addr";
              description
                "Configure the rate limit for receiving ND packets based on specified destination IP address.";
              leaf packet-type {
                type nd-pkt-type;
                description
                  "ND packet type.";
              }
              leaf ipv6-addr {
                type inet:ipv6-address-no-zone;
                description
                  "Destination IPv6 address, the address cannot be the unspecified address.";
              }
              leaf value {
                type uint16 {
                  range "0..5000";
                }
                units "pps";
                mandatory true;
                description
                  "Rate limit of receiving ND packet.";
              }
            }
          }
        }
        container target-ip-receive {
          description
            "Configure the ND anti-attack based on packet target IP address.";
          container every-ip-rate-limits {
            description
              "List of rate limits for receiving ND packets based on every target IP address.";
            list every-ip-rate-limit {
              key "packet-type";
              description
                "Configure the rate limit for receiving ND packets based on every target IP address.";
              leaf packet-type {
                type nd-tgt-pkt-type;
                description
                  "ND packet type.";
              }
              leaf value {
                type uint16 {
                  range "0..5000";
                }
                units "pps";
                mandatory true;
                description
                  "Rate limit of receiving ND packet.";
              }
            }
          }
          container ip-rate-limits {
            description
              "List of rate limits for receiving ND packets based on specified target IP address.";
            list ip-rate-limit {
              key "packet-type ipv6-addr";
              description
                "Configure the rate limit for receiving ND packets based on specified target IP address.";
              leaf packet-type {
                type nd-tgt-pkt-type;
                description
                  "ND packet type.";
              }
              leaf ipv6-addr {
                type inet:ipv6-address-no-zone;
                description
                  "Target IPv6 address, the address cannot be the unspecified address or a multicast address.";
              }
              leaf value {
                type uint16 {
                  range "0..5000";
                }
                units "pps";
                mandatory true;
                description
                  "Rate limit of receiving ND packet.";
              }
            }
          }
        }
      }
      container send-rate-limit {
        description
          "Configure ND send rate limit for global.";
        container multicast-rate-limits {
          description
            "List of ND multicast packet sending rate limits.";
          list multicast-rate-limit {
            key "packet-type";
            description
              "Configure the rate limit of sending ND multicast packet.";
            leaf packet-type {
              type nd-pkt-type;
              description
                "ND packet type.";
            }
            leaf value {
              type uint16 {
                range "1..10240";
              }
              units "pps";
              must "((../packet-type = 'NA') and (../value <= 10240)) or (not(../packet-type = 'NA') and (../value <= 1000))" {
                tailf:xpath-root 3;
              }
              mandatory true;
              description
                "Rate limit of sending ND multicast packet, when the packet type is NS, RS or RA, the maximum value is 1000.";
            }
          }
        }
      }
    }
  }
  augment "/ncs:devices/ncs:device/ncs:live-status" {
    container ipv6-nd {
      tailf:ncs-device-type "netconf";
      tailf:display-when "not(../../ncs:module) or ../../ncs:module[ncs:name='huawei-ipv6-nd'] or (../../ncs:live-status-protocol[not(ncs:capability)]) or (../../ncs:live-status-protocol/ncs:capability/ncs:module[.='huawei-ipv6-nd'])";
      description
        "ND management.";
      container global {
        description
          "Configure global configuration of ND.";
        leaf ns-send-rate-limit {
          type uint16 {
            range "1..1000";
          }
          units "pps";
          // NCS drop default statement
          description
            "Rate limit of sending NS packet.";
        }
        leaf na-send-rate-limit {
          type uint16 {
            range "1..10240";
          }
          units "pps";
          // NCS drop default statement
          description
            "Rate limit of sending NA packet.";
        }
        leaf rs-send-rate-limit {
          type uint16 {
            range "1..1000";
          }
          units "pps";
          // NCS drop default statement
          description
            "Rate limit of sending RS packet.";
        }
        leaf ra-send-rate-limit {
          type uint16 {
            range "1..1000";
          }
          units "pps";
          // NCS drop default statement
          description
            "Rate limit of sending RA packet.";
        }
        leaf dad-detect {
          type live_ncs_nd-flag;
          // NCS drop default statement
          description
            "The switch of DAD enhanced detection.";
        }
        leaf mac-check-flag {
          type live_ncs_nd-flag;
          // NCS drop default statement
          description
            "Enable IPv6 ND MAC check.";
        }
        leaf auto-detect-flag {
          type live_ncs_nd-switch-state;
          // NCS drop default statement
          description
            "To enable the automatic detection of ND entries.";
        }
        leaf prefix-strict-flag {
          type live_ncs_nd-switch-state;
          // NCS drop default statement
          description
            "ND prefix learning strict.";
        }
        leaf pre-detect-flag {
          type live_ncs_nd-switch-state;
          // NCS drop default statement
          description
            "To determine whether to enable pre-detection.";
        }
        leaf hop-limit {
          type uint8 {
            range "1..255";
          }
          // NCS drop default statement
          description
            "IPv6 packet hoplimit.";
        }
        leaf stale-time {
          type uint32 {
            range "60..172800";
          }
          units "s";
          // NCS drop default statement
          description
            "Aging time of the global stale state.";
        }
        leaf rsa-calculate-rate-limit {
          type uint32 {
            range "0..100";
            ext:value-meaning {
              ext:item "0" {
                ext:meaning "disabling the function of rsa calculation limit";
              }
            }
          }
          // NCS drop default statement
          description
            "Rate limit for RSA option calculation.";
        }
        leaf log-trap-time {
          type uint32 {
            range "60..3600";
          }
          units "s";
          // NCS drop default statement
          description
            "The interval for sending speed-limit logs and alarms.";
        }
        leaf rs-receive-rate-limit {
          type uint16 {
            range "1..5000";
          }
          units "pps";
          ext:dynamic-default;
          description
            "Rate limit of receiving RS packet.";
        }
        leaf ra-receive-rate-limit {
          type uint16 {
            range "1..5000";
          }
          units "pps";
          ext:dynamic-default;
          description
            "Rate limit of receiving RA packet.";
        }
        leaf ns-receive-rate-limit {
          type uint16 {
            range "1..5000";
          }
          units "pps";
          ext:dynamic-default;
          description
            "Rate limit of receiving NS packet.";
        }
        leaf na-receive-rate-limit {
          type uint16 {
            range "1..5000";
          }
          units "pps";
          ext:dynamic-default;
          description
            "Rate limit of receiving NA packet.";
        }
        leaf miss-receive-rate-limit {
          type uint16 {
            range "1..5000";
          }
          units "pps";
          ext:dynamic-default;
          description
            "Rate limit of receiving ND miss.";
        }
        leaf dad-detect-rate-limit {
          type uint16 {
            range "1..100";
          }
          units "pps";
          // NCS drop default statement
          description
            "Rate limit of sending DAD detect packet.";
        }
        leaf dad-detect-attempts {
          type uint16 {
            range "1..5";
          }
          // NCS drop default statement
          description
            "Number of attempts to resolve address conflicts.";
        }
      }
      container m-lag-global {
        description
          "Configure M-LAG global configuration of ND.";
        leaf ipv6-neighbor-backup-rate {
          type uint32 {
            range "1..2000";
          }
          description
            "Specifies the number of IPv6 neighbor entries synchronized per second through M-LAG.";
          ext:dynamic-default;
        }
      }
      container ipv6-neighbors {
        description
          "List of information about neighbor entry query.";
        list ipv6-neighbor {
          key "if-name ipv6-addr";
          description
            "Statistics of query neighbor entries which can be static, or dynamic.";
          leaf if-name {
            type leafref {
              path "/ncs:devices/ncs:device/ncs:live-status/ifm:ifm/ifm:interfaces/ifm:interface/ifm:name" {
                tailf:xpath-root 3;
              }
            }
            description
              "Interface name.";
          }
          leaf ipv6-addr {
            type inet:ipv6-address-no-zone;
            description
              "IPv6 address of a neighbor entry.";
          }
          leaf slot-id {
            type string {
              length "1..24";
            }
            description
              "Slot ID.";
            ext:support-filter "true";
          }
          leaf mac-addr {
            type pub-type:live_ncs_mac-address;
            description
              "MAC address.";
          }
          leaf vpn-name {
            type leafref {
              path "/ncs:devices/ncs:device/ncs:live-status/ni:network-instance/ni:instances/ni:instance/ni:name" {
                tailf:xpath-root 3;
              }
            }
            description
              "VPN name.";
            ext:support-filter "true";
          }
          leaf vlan-id {
            type uint32 {
              range "1..4094";
            }
            description
              "VLAN ID.";
            ext:support-filter "true";
          }
          leaf state {
            type live_ncs_nd-ngb-state;
            description
              "Status of a neighbor entry.";
          }
          leaf static-flag {
            type live_ncs_nd-nb-type;
            description
              "Type of a neighbor entry. The available options are static, dynamic or remote.";
          }
          leaf age {
            type uint32 {
              range "0..4294967293";
            }
            units "min";
            description
              "Time when a neighbor entry is established.";
          }
          leaf is-router {
            type live_ncs_nd-flag;
            description
              "Is a router.";
          }
          leaf cevid {
            type uint32 {
              range "1..4094";
            }
            description
              "Inner VLAN tag. If this parameter is not set, the value of the VLAN ID is considered to be 0. If this parameter is set, it indicates that the ND entry is in the associated VLAN.";
          }
          leaf strict-flag {
            type boolean;
            description
              "Enable/disable strict security mode.";
          }
          leaf nickname {
            type uint32 {
              range "1..65535";
            }
            description
              "Nickname which uniquely identifies an RB on a TRILL network.";
          }
          leaf bd-id {
            type uint32 {
              range "1..16777215";
            }
            description
              "Bridge-domain ID.";
          }
          leaf vni {
            type uint32 {
              range "1..16777215";
            }
            description
              "Vxlan VNI.";
          }
          leaf source-addr {
            type inet:ip-address-no-zone;
            description
              "Tunnel SourceIPAddr.";
          }
          leaf peer-addr {
            type inet:ip-address-no-zone;
            description
              "Tunnel PeerIPAddr.";
          }
        }
      }
      container nd-pkt-stats {
        description
          "Statistics of ND packets.";
        container ns-stats {
          description
            "Statistics of NS packets.";
          container ns-global {
            description
              "Statistics of global NS packets.";
            leaf send-total {
              type uint32;
              units "packet";
              description
                "Number of sent NS packets.";
            }
            leaf send-dip-ucast {
              type uint32;
              units "packet";
              description
                "Number of sent NS packets with the destination address as a unicast address.";
            }
            leaf send-dip-mcast {
              type uint32;
              units "packet";
              description
                "Number of sent NS packets with the destination address as a multicast address.";
            }
            leaf send-target-linklocal {
              type uint32;
              units "packet";
              description
                "Number of sent NS packets with the target address as a link-local address.";
            }
            leaf send-target-global {
              type uint32;
              units "packet";
              description
                "Number of sent NS packets with the target address as a global address.";
            }
            leaf recv-total {
              type uint32;
              units "packet";
              description
                "Number of received NS packets.";
            }
            leaf recv-valid-total {
              type uint32;
              units "packet";
              description
                "Number of received valid NS packets.";
            }
            leaf recv-dip-ucast {
              type uint32;
              units "packet";
              description
                "Number of received NS packets with the destination address as a unicast address.";
            }
            leaf recv-dip-mcast {
              type uint32;
              units "packet";
              description
                "Number of NS packets with the destination address as a multicast address.";
            }
            leaf recv-target-linklocal {
              type uint32;
              units "packet";
              description
                "Number of NS packets with the target address as a link-local address.";
            }
            leaf recv-target-global {
              type uint32;
              units "packet";
              description
                "Number of NS packets with the target address as a global address.";
            }
            leaf drop-total {
              type uint32;
              units "packet";
              description
                "Number of discarded NS packets.";
            }
            leaf drop-checksum-err {
              type uint32;
              units "packet";
              description
                "Number of NS packets discarded due to checksum errors.";
            }
            leaf drop-bad-len {
              type uint32;
              units "packet";
              description
                "Number of NS packets discarded due to bad packet length.";
            }
            leaf drop-bad-code {
              type uint32;
              units "packet";
              description
                "Number of NS packets discarded due to bad code.";
            }
            leaf drop-bad-hoplimit {
              type uint32;
              units "packet";
              description
                "Number of NS packets discarded due to bad hoplimit.";
            }
            leaf drop-bad-src-mac {
              type uint32;
              units "packet";
              description
                "Number of NS packets discarded due to bad source MAC addresses.";
            }
            leaf drop-bad-dst-mac {
              type uint32;
              units "packet";
              description
                "Number of NS packets discarded due to bad destination MAC addresses.";
            }
            leaf drop-bad-tgt-mac {
              type uint32;
              units "packet";
              description
                "Number of NS packets discarded due to bad target MAC addresses.";
            }
            leaf drop-bad-src-ip {
              type uint32;
              units "packet";
              description
                "Number of NS packets discarded due to bad source IP addresses.";
            }
            leaf drop-bad-dst-ip {
              type uint32;
              units "packet";
              description
                "Number of NS packets discarded due to bad destination IP addresses.";
            }
            leaf drop-bad-tgt-ip {
              type uint32;
              units "packet";
              description
                "Number of NS packets discarded due to bad target IP addresses.";
            }
            leaf drop-bad-option {
              type uint32;
              units "packet";
              description
                "Number of NS packets discarded due to bad options.";
            }
            leaf drop-local-addr {
              type uint32;
              units "packet";
              description
                "Number of NS packets discarded because the source address is the local address.";
            }
            leaf drop-mac-check {
              type uint32;
              units "packet";
              description
                "Number of NS packets discarded due to source MAC address consistency check errors.";
            }
            leaf drop-rate-limit {
              type uint32;
              units "packet";
              description
                "Number of NS packets discarded due to global rate limit.";
            }
            leaf drop-src-mac-attack {
              type uint32;
              units "packet";
              description
                "Number of NS packets discarded due to source MAC address attacks.";
            }
            leaf drop-src-mac-rate-limit {
              type uint32;
              units "packet";
              description
                "Number of NS packets discarded due to source MAC rate limit.";
            }
            leaf drop-src-ip-rate-limit {
              type uint32;
              units "packet";
              description
                "Number of NS packets discarded due to source IP rate limit.";
            }
            leaf drop-if-src-ip-rate-limit {
              type uint32;
              units "packet";
              description
                "Number of NS packets discarded due to interface source IP rate limit.";
            }
            leaf drop-if-rate-limit {
              type uint32;
              units "packet";
              description
                "Number of NS packets discarded due to interface rate limit.";
            }
            leaf drop-lr-rate-limit {
              type uint32;
              units "packet";
              description
                "Number of NS packets discarded due to LR rate limit.";
            }
            leaf send-sip-unspecified {
              type uint32;
              units "packet";
              description
                "Number of sent NS packets with the source address as an unspecified address.";
            }
            leaf recv-sip-unspecified {
              type uint32;
              units "packet";
              description
                "Number of received NS packets with the source address as an unspecified address.";
            }
            leaf drop-dst-ip-rate-limit {
              type uint32;
              units "packet";
              description
                "Number of NS packets discarded due to destination IP rate limit.";
            }
            leaf drop-tgt-ip-rate-limit {
              type uint32;
              units "packet";
              description
                "Number of NS packets discarded due to target IP rate limit.";
            }
          }
          container ns-slots {
            description
              "List of NS packets in these slots.";
            list ns-slot {
              key "slot-id";
              description
                "Statistics of NS packets in the slot.";
              leaf slot-id {
                type string {
                  length "1..24";
                }
                description
                  "Slot ID, which refers to the position of logical MPU board and physical LPU boards.";
              }
              leaf send-total {
                type uint32;
                units "packet";
                description
                  "Number of sent NS packets.";
              }
              leaf send-dip-ucast {
                type uint32;
                units "packet";
                description
                  "Number of sent NS packets with the destination address as a unicast address.";
              }
              leaf send-dip-mcast {
                type uint32;
                units "packet";
                description
                  "Number of sent NS packets with the destination address as a multicast address.";
              }
              leaf send-target-linklocal {
                type uint32;
                units "packet";
                description
                  "Number of sent NS packets with the target address as a link-local address.";
              }
              leaf send-target-global {
                type uint32;
                units "packet";
                description
                  "Number of sent NS packets with the target address as a global address.";
              }
              leaf recv-total {
                type uint32;
                units "packet";
                description
                  "Number of received NS packets.";
              }
              leaf recv-valid-total {
                type uint32;
                units "packet";
                description
                  "Number of received valid NS packets.";
              }
              leaf recv-dip-ucast {
                type uint32;
                units "packet";
                description
                  "Number of received NS packets with the destination address as a unicast address.";
              }
              leaf recv-dip-mcast {
                type uint32;
                units "packet";
                description
                  "Number of NS packets with the destination address as a multicast address.";
              }
              leaf recv-target-linklocal {
                type uint32;
                units "packet";
                description
                  "Number of NS packets with the destination address as a link-local address.";
              }
              leaf recv-target-global {
                type uint32;
                units "packet";
                description
                  "Number of NS packets with the destination address as a global address.";
              }
              leaf drop-total {
                type uint32;
                units "packet";
                description
                  "Number of discarded NS packets.";
              }
              leaf drop-checksum-err {
                type uint32;
                units "packet";
                description
                  "Number of NS packets discarded due to checksum errors.";
              }
              leaf drop-bad-len {
                type uint32;
                units "packet";
                description
                  "Number of NS packets discarded due to bad packet length.";
              }
              leaf drop-bad-code {
                type uint32;
                units "packet";
                description
                  "Number of NS packets discarded due to bad code.";
              }
              leaf drop-bad-hoplimit {
                type uint32;
                units "packet";
                description
                  "Number of NS packets discarded due to bad hoplimit.";
              }
              leaf drop-bad-src-mac {
                type uint32;
                units "packet";
                description
                  "Number of NS packets discarded due to bad source MAC addresses.";
              }
              leaf drop-bad-dst-mac {
                type uint32;
                units "packet";
                description
                  "Number of NS packets discarded due to bad destination MAC addresses.";
              }
              leaf drop-bad-tgt-mac {
                type uint32;
                units "packet";
                description
                  "Number of NS packets discarded due to bad target MAC addresses.";
              }
              leaf drop-bad-src-ip {
                type uint32;
                units "packet";
                description
                  "Number of NS packets discarded due to bad source IP addresses.";
              }
              leaf drop-bad-dst-ip {
                type uint32;
                units "packet";
                description
                  "Number of NS packets discarded due to bad destination IP addresses.";
              }
              leaf drop-bad-tgt-ip {
                type uint32;
                units "packet";
                description
                  "Number of NS packets discarded due to bad target IP addresses.";
              }
              leaf drop-bad-option {
                type uint32;
                units "packet";
                description
                  "Number of NS packets discarded due to bad options.";
              }
              leaf drop-local-addr {
                type uint32;
                units "packet";
                description
                  "Number of NS packets discarded because the source address is the local address.";
              }
              leaf drop-mac-check {
                type uint32;
                units "packet";
                description
                  "Number of NS packets discarded due to source MAC address consistency check errors.";
              }
              leaf drop-rate-limit {
                type uint32;
                units "packet";
                description
                  "Number of NS packets discarded due to global rate limit.";
              }
              leaf drop-src-mac-attack {
                type uint32;
                units "packet";
                description
                  "Number of NS packets discarded due to source MAC address attacks.";
              }
              leaf drop-src-mac-rate-limit {
                type uint32;
                units "packet";
                description
                  "Number of NS packets discarded due to source MAC rate limit.";
              }
              leaf drop-src-ip-rate-limit {
                type uint32;
                units "packet";
                description
                  "Number of NS packets discarded due to source IP rate limit.";
              }
              leaf drop-if-src-ip-rate-limit {
                type uint32;
                units "packet";
                description
                  "Number of NS packets discarded due to interface source IP rate limit.";
              }
              leaf drop-if-rate-limit {
                type uint32;
                units "packet";
                description
                  "Number of NS packets discarded due to interface rate limit.";
              }
              leaf drop-lr-rate-limit {
                type uint32;
                units "packet";
                description
                  "Number of NS packets discarded due to LR rate limit.";
              }
              leaf send-sip-unspecified {
                type uint32;
                units "packet";
                description
                  "Number of sent NS packets with the source address as an unspecified address.";
              }
              leaf recv-sip-unspecified {
                type uint32;
                units "packet";
                description
                  "Number of received NS packets with the source address as an unspecified address.";
              }
              leaf drop-dst-ip-rate-limit {
                type uint32;
                units "packet";
                description
                  "Number of NS packets discarded due to destination IP rate limit.";
              }
              leaf drop-tgt-ip-rate-limit {
                type uint32;
                units "packet";
                description
                  "Number of NS packets discarded due to target IP rate limit.";
              }
            }
          }
          container ns-ifs {
            description
              "List of NS packets in these interfaces.";
            list ns-if {
              key "if-name";
              description
                "Statistics of NS packets in the interface.";
              leaf if-name {
                type leafref {
                  path "/ncs:devices/ncs:device/ncs:live-status/ifm:ifm/ifm:interfaces/ifm:interface/ifm:name" {
                    tailf:xpath-root 3;
                  }
                }
                description
                  "Interface name.";
              }
              leaf send-total {
                type uint32;
                units "packet";
                description
                  "Number of sent NS packets.";
              }
              leaf send-dip-ucast {
                type uint32;
                units "packet";
                description
                  "Number of sent NS packets with the destination address as a unicast address.";
              }
              leaf send-dip-mcast {
                type uint32;
                units "packet";
                description
                  "Number of sent NS packets with the destination address as a multicast address.";
              }
              leaf send-target-linklocal {
                type uint32;
                units "packet";
                description
                  "Number of sent NS packets with the target address as a link-local address.";
              }
              leaf send-target-global {
                type uint32;
                units "packet";
                description
                  "Number of sent NS packets with the target address as a global address.";
              }
              leaf recv-total {
                type uint32;
                units "packet";
                description
                  "Number of received NS packets.";
              }
              leaf recv-valid-total {
                type uint32;
                units "packet";
                description
                  "Number of received valid NS packets.";
              }
              leaf recv-dip-ucast {
                type uint32;
                units "packet";
                description
                  "Number of received NS packets with the destination address as a unicast address.";
              }
              leaf recv-dip-mcast {
                type uint32;
                units "packet";
                description
                  "Number of NS packets with the destination address as a multicast address.";
              }
              leaf recv-target-linklocal {
                type uint32;
                units "packet";
                description
                  "Number of NS packets with the destination address as a link-local address.";
              }
              leaf recv-target-global {
                type uint32;
                units "packet";
                description
                  "Number of NS packets with the destination address as a global address.";
              }
              leaf drop-total {
                type uint32;
                units "packet";
                description
                  "Number of discarded NS packets.";
              }
              leaf drop-checksum-err {
                type uint32;
                units "packet";
                description
                  "Number of NS packets discarded due to checksum errors.";
              }
              leaf drop-bad-len {
                type uint32;
                units "packet";
                description
                  "Number of NS packets discarded due to bad packet length.";
              }
              leaf drop-bad-code {
                type uint32;
                units "packet";
                description
                  "Number of NS packets discarded due to bad code.";
              }
              leaf drop-bad-hoplimit {
                type uint32;
                units "packet";
                description
                  "Number of NS packets discarded due to bad hoplimit.";
              }
              leaf drop-bad-src-mac {
                type uint32;
                units "packet";
                description
                  "Number of NS packets discarded due to bad source MAC addresses.";
              }
              leaf drop-bad-dst-mac {
                type uint32;
                units "packet";
                description
                  "Number of NS packets discarded due to bad destination MAC addresses.";
              }
              leaf drop-bad-tgt-mac {
                type uint32;
                units "packet";
                description
                  "Number of NS packets discarded due to bad target MAC addresses.";
              }
              leaf drop-bad-src-ip {
                type uint32;
                units "packet";
                description
                  "Number of NS packets discarded due to bad source IP addresses.";
              }
              leaf drop-bad-dst-ip {
                type uint32;
                units "packet";
                description
                  "Number of NS packets discarded due to bad destination IP addresses.";
              }
              leaf drop-bad-tgt-ip {
                type uint32;
                units "packet";
                description
                  "Number of NS packets discarded due to bad target IP addresses.";
              }
              leaf drop-bad-option {
                type uint32;
                units "packet";
                description
                  "Number of NS packets discarded due to bad options.";
              }
              leaf drop-local-addr {
                type uint32;
                units "packet";
                description
                  "Number of NS packets discarded because the source address is the local address.";
              }
              leaf drop-mac-check {
                type uint32;
                units "packet";
                description
                  "Number of NS packets discarded due to source MAC address consistency check errors.";
              }
              leaf drop-rate-limit {
                type uint32;
                units "packet";
                description
                  "Number of NS packets discarded due to global rate limit.";
              }
              leaf drop-src-mac-attack {
                type uint32;
                units "packet";
                description
                  "Number of NS packets discarded due to source MAC address attacks.";
              }
              leaf drop-src-mac-rate-limit {
                type uint32;
                units "packet";
                description
                  "Number of NS packets discarded due to source MAC rate limit.";
              }
              leaf drop-src-ip-rate-limit {
                type uint32;
                units "packet";
                description
                  "Number of NS packets discarded due to source IP rate limit.";
              }
              leaf drop-if-src-ip-rate-limit {
                type uint32;
                units "packet";
                description
                  "Number of NS packets discarded due to interface source IP rate limit.";
              }
              leaf drop-if-rate-limit {
                type uint32;
                units "packet";
                description
                  "Number of NS packets discarded due to interface rate limit.";
              }
              leaf drop-lr-rate-limit {
                type uint32;
                units "packet";
                description
                  "Number of NS packets discarded due to LR rate limit.";
              }
              leaf send-sip-unspecified {
                type uint32;
                units "packet";
                description
                  "Number of sent NS packets with the source address as an unspecified address.";
              }
              leaf recv-sip-unspecified {
                type uint32;
                units "packet";
                description
                  "Number of received NS packets with the source address as an unspecified address.";
              }
              leaf drop-dst-ip-rate-limit {
                type uint32;
                units "packet";
                description
                  "Number of NS packets discarded due to destination IP rate limit.";
              }
              leaf drop-tgt-ip-rate-limit {
                type uint32;
                units "packet";
                description
                  "Number of NS packets discarded due to target IP rate limit.";
              }
            }
          }
        }
        container na-stats {
          description
            "Statistics of NA packets.";
          container na-global {
            description
              "Statistics of global NA packets.";
            leaf send-total {
              type uint32;
              units "packet";
              description
                "Number of sent NA packets.";
            }
            leaf send-dip-ucast {
              type uint32;
              units "packet";
              description
                "Number of sent NA packets with the destination address as a unicast address.";
            }
            leaf send-dip-mcast {
              type uint32;
              units "packet";
              description
                "Number of sent NA packets with the destination address as a multicast address.";
            }
            leaf send-target-linklocal {
              type uint32;
              units "packet";
              description
                "Number of sent NA packets with the target address as a link-local address.";
            }
            leaf send-target-global {
              type uint32;
              units "packet";
              description
                "Number of sent NA packets with the target address as a global address.";
            }
            leaf recv-total {
              type uint32;
              units "packet";
              description
                "Number of received NA packets.";
            }
            leaf recv-valid-total {
              type uint32;
              units "packet";
              description
                "Number of received valid NA packets.";
            }
            leaf recv-dip-ucast {
              type uint32;
              units "packet";
              description
                "Number of received NA packets with the destination address as a unicast address.";
            }
            leaf recv-dip-mcast {
              type uint32;
              units "packet";
              description
                "Number of NA packets with the destination address as a multicast address.";
            }
            leaf recv-target-linklocal {
              type uint32;
              units "packet";
              description
                "Number of NA packets with the destination address as a link-local address.";
            }
            leaf recv-target-global {
              type uint32;
              units "packet";
              description
                "Number of NA packets with the destination address as a global address.";
            }
            leaf drop-total {
              type uint32;
              units "packet";
              description
                "Number of discarded NA packets.";
            }
            leaf drop-checksum-err {
              type uint32;
              units "packet";
              description
                "Number of NA packets discarded due to checksum errors.";
            }
            leaf drop-bad-len {
              type uint32;
              units "packet";
              description
                "Number of NA packets discarded due to bad packet length.";
            }
            leaf drop-bad-code {
              type uint32;
              units "packet";
              description
                "Number of NA packets discarded due to bad code.";
            }
            leaf drop-bad-hoplimit {
              type uint32;
              units "packet";
              description
                "Number of NA packets discarded due to bad hoplimit.";
            }
            leaf drop-bad-src-mac {
              type uint32;
              units "packet";
              description
                "Number of NA packets discarded due to bad source MAC addresses.";
            }
            leaf drop-bad-dst-mac {
              type uint32;
              units "packet";
              description
                "Number of NA packets discarded due to bad destination MAC addresses.";
            }
            leaf drop-bad-tgt-mac {
              type uint32;
              units "packet";
              description
                "Number of NA packets discarded due to bad target MAC addresses.";
            }
            leaf drop-bad-src-ip {
              type uint32;
              units "packet";
              description
                "Number of NA packets discarded due to bad source IP addresses.";
            }
            leaf drop-bad-dst-ip {
              type uint32;
              units "packet";
              description
                "Number of NA packets discarded due to bad destination IP addresses.";
            }
            leaf drop-bad-tgt-ip {
              type uint32;
              units "packet";
              description
                "Number of NA packets discarded due to bad target IP addresses.";
            }
            leaf drop-bad-option {
              type uint32;
              units "packet";
              description
                "Number of NA packets discarded due to bad options.";
            }
            leaf drop-local-addr {
              type uint32;
              units "packet";
              description
                "Number of NA packets discarded because the source address is the local address.";
            }
            leaf drop-mac-check {
              type uint32;
              units "packet";
              description
                "Number of NA packets discarded due to source MAC address consistency check errors.";
            }
            leaf drop-rate-limit {
              type uint32;
              units "packet";
              description
                "Number of NA packets discarded due to global rate limit.";
            }
            leaf drop-src-mac-attack {
              type uint32;
              units "packet";
              description
                "Number of NA packets discarded due to source MAC address attacks.";
            }
            leaf drop-src-mac-rate-limit {
              type uint32;
              units "packet";
              description
                "Number of NA packets discarded due to source MAC rate limit.";
            }
            leaf drop-src-ip-rate-limit {
              type uint32;
              units "packet";
              description
                "Number of NA packets discarded due to source IP rate limit.";
            }
            leaf drop-if-src-ip-rate-limit {
              type uint32;
              units "packet";
              description
                "Number of NA packets discarded due to interface source IP rate limit.";
            }
            leaf drop-if-rate-limit {
              type uint32;
              units "packet";
              description
                "Number of NA packets discarded due to interface rate limit.";
            }
            leaf drop-lr-rate-limit {
              type uint32;
              units "packet";
              description
                "Number of NA packets discarded due to LR rate limit.";
            }
            leaf drop-dst-ip-rate-limit {
              type uint32;
              units "packet";
              description
                "Number of NA packets discarded due to destination IP rate limit.";
            }
            leaf drop-tgt-ip-rate-limit {
              type uint32;
              units "packet";
              description
                "Number of NA packets discarded due to target IP rate limit.";
            }
          }
          container na-slots {
            description
              "List of NA packets in these slots.";
            list na-slot {
              key "slot-id";
              description
                "Statistics of NA packets in the slot.";
              leaf slot-id {
                type string {
                  length "1..24";
                }
                description
                  "Slot ID, which refers to the position of logical MPU board and physical LPU boards.";
              }
              leaf send-total {
                type uint32;
                units "packet";
                description
                  "Number of send NA packets.";
              }
              leaf send-dip-ucast {
                type uint32;
                units "packet";
                description
                  "Number of send NA packets with the destination address as a unicast address.";
              }
              leaf send-dip-mcast {
                type uint32;
                units "packet";
                description
                  "Number of send NA packets with the destination address as a multicast address.";
              }
              leaf send-target-linklocal {
                type uint32;
                units "packet";
                description
                  "Number of send NA packets with the target address as a link-local address.";
              }
              leaf send-target-global {
                type uint32;
                units "packet";
                description
                  "Number of send NA packets with the target address as a global address.";
              }
              leaf recv-total {
                type uint32;
                units "packet";
                description
                  "Number of received NA packets.";
              }
              leaf recv-valid-total {
                type uint32;
                units "packet";
                description
                  "Number of received valid NA packets.";
              }
              leaf recv-dip-ucast {
                type uint32;
                units "packet";
                description
                  "Number of received NA packets with the destination address as a unicast address.";
              }
              leaf recv-dip-mcast {
                type uint32;
                units "packet";
                description
                  "Number of NA packets with the destination address as a multicast address.";
              }
              leaf recv-target-linklocal {
                type uint32;
                units "packet";
                description
                  "Number of NA packets with the destination address as a link-local address.";
              }
              leaf recv-target-global {
                type uint32;
                units "packet";
                description
                  "Number of NA packets with the destination address as a global address.";
              }
              leaf drop-total {
                type uint32;
                units "packet";
                description
                  "Number of discarded NA packets.";
              }
              leaf drop-checksum-err {
                type uint32;
                units "packet";
                description
                  "Number of NA packets discarded due to checksum errors.";
              }
              leaf drop-bad-len {
                type uint32;
                units "packet";
                description
                  "Number of NA packets discarded due to bad packet length.";
              }
              leaf drop-bad-code {
                type uint32;
                units "packet";
                description
                  "Number of NA packets discarded due to bad code.";
              }
              leaf drop-bad-hoplimit {
                type uint32;
                units "packet";
                description
                  "Number of NA packets discarded due to bad hoplimit.";
              }
              leaf drop-bad-src-mac {
                type uint32;
                units "packet";
                description
                  "Number of NA packets discarded due to bad source MAC addresses.";
              }
              leaf drop-bad-dst-mac {
                type uint32;
                units "packet";
                description
                  "Number of NA packets discarded due to bad destination MAC addresses.";
              }
              leaf drop-bad-tgt-mac {
                type uint32;
                units "packet";
                description
                  "Number of NA packets discarded due to bad target MAC addresses.";
              }
              leaf drop-bad-src-ip {
                type uint32;
                units "packet";
                description
                  "Number of NA packets discarded due to bad source IP addresses.";
              }
              leaf drop-bad-dst-ip {
                type uint32;
                units "packet";
                description
                  "Number of NA packets discarded due to bad destination IP addresses.";
              }
              leaf drop-bad-tgt-ip {
                type uint32;
                units "packet";
                description
                  "Number of NA packets discarded due to bad target IP addresses.";
              }
              leaf drop-bad-option {
                type uint32;
                units "packet";
                description
                  "Number of NA packets discarded due to bad options.";
              }
              leaf drop-local-addr {
                type uint32;
                units "packet";
                description
                  "Number of NA packets discarded because the source address is the local address.";
              }
              leaf drop-mac-check {
                type uint32;
                units "packet";
                description
                  "Number of NA packets discarded due to source MAC address consistency check errors.";
              }
              leaf drop-rate-limit {
                type uint32;
                units "packet";
                description
                  "Number of NA packets discarded due to global rate limit.";
              }
              leaf drop-src-mac-attack {
                type uint32;
                units "packet";
                description
                  "Number of NA packets discarded due to source MAC address attacks.";
              }
              leaf drop-src-mac-rate-limit {
                type uint32;
                units "packet";
                description
                  "Number of NA packets discarded due to source MAC rate limit.";
              }
              leaf drop-src-ip-rate-limit {
                type uint32;
                units "packet";
                description
                  "Number of NA packets discarded due to source IP rate limit.";
              }
              leaf drop-if-src-ip-rate-limit {
                type uint32;
                units "packet";
                description
                  "Number of NA packets discarded due to interface source IP rate limit.";
              }
              leaf drop-if-rate-limit {
                type uint32;
                units "packet";
                description
                  "Number of NA packets discarded due to interface rate limit.";
              }
              leaf drop-lr-rate-limit {
                type uint32;
                units "packet";
                description
                  "Number of NA packets discarded due to LR rate limit.";
              }
              leaf drop-dst-ip-rate-limit {
                type uint32;
                units "packet";
                description
                  "Number of NA packets discarded due to destination IP rate limit.";
              }
              leaf drop-tgt-ip-rate-limit {
                type uint32;
                units "packet";
                description
                  "Number of NA packets discarded due to target IP rate limit.";
              }
            }
          }
          container na-ifs {
            description
              "List of NA packets in these interfaces.";
            list na-if {
              key "if-name";
              description
                "Statistics of NA packets in the interface.";
              leaf if-name {
                type leafref {
                  path "/ncs:devices/ncs:device/ncs:live-status/ifm:ifm/ifm:interfaces/ifm:interface/ifm:name" {
                    tailf:xpath-root 3;
                  }
                }
                description
                  "Interface name.";
              }
              leaf send-total {
                type uint32;
                units "packet";
                description
                  "Number of send NA packets.";
              }
              leaf send-dip-ucast {
                type uint32;
                units "packet";
                description
                  "Number of send NA packets with the destination address as a unicast address.";
              }
              leaf send-dip-mcast {
                type uint32;
                units "packet";
                description
                  "Number of send NA packets with the destination address as a multicast address.";
              }
              leaf send-target-linklocal {
                type uint32;
                units "packet";
                description
                  "Number of send NA packets with the target address as a link-local address.";
              }
              leaf send-target-global {
                type uint32;
                units "packet";
                description
                  "Number of send NA packets with the target address as a global address.";
              }
              leaf recv-total {
                type uint32;
                units "packet";
                description
                  "Number of received NA packets.";
              }
              leaf recv-valid-total {
                type uint32;
                units "packet";
                description
                  "Number of received valid NA packets.";
              }
              leaf recv-dip-ucast {
                type uint32;
                units "packet";
                description
                  "Number of received NA packets with the destination address as a unicast address.";
              }
              leaf recv-dip-mcast {
                type uint32;
                units "packet";
                description
                  "Number of NA packets with the destination address as a multicast address.";
              }
              leaf recv-target-linklocal {
                type uint32;
                units "packet";
                description
                  "Number of NA packets with the destination address as a link-local address.";
              }
              leaf recv-target-global {
                type uint32;
                units "packet";
                description
                  "Number of NA packets with the destination address as a global address.";
              }
              leaf drop-total {
                type uint32;
                units "packet";
                description
                  "Number of discarded NA packets.";
              }
              leaf drop-checksum-err {
                type uint32;
                units "packet";
                description
                  "Number of NA packets discarded due to checksum errors.";
              }
              leaf drop-bad-len {
                type uint32;
                units "packet";
                description
                  "Number of NA packets discarded due to bad packet length.";
              }
              leaf drop-bad-code {
                type uint32;
                units "packet";
                description
                  "Number of NA packets discarded due to bad code.";
              }
              leaf drop-bad-hoplimit {
                type uint32;
                units "packet";
                description
                  "Number of NA packets discarded due to bad hoplimit.";
              }
              leaf drop-bad-src-mac {
                type uint32;
                units "packet";
                description
                  "Number of NA packets discarded due to bad source MAC addresses.";
              }
              leaf drop-bad-dst-mac {
                type uint32;
                units "packet";
                description
                  "Number of NA packets discarded due to bad destination MAC addresses.";
              }
              leaf drop-bad-tgt-mac {
                type uint32;
                units "packet";
                description
                  "Number of NA packets discarded due to bad target MAC addresses.";
              }
              leaf drop-bad-src-ip {
                type uint32;
                units "packet";
                description
                  "Number of NA packets discarded due to bad source IP addresses.";
              }
              leaf drop-bad-dst-ip {
                type uint32;
                units "packet";
                description
                  "Number of NA packets discarded due to bad destination IP addresses.";
              }
              leaf drop-bad-tgt-ip {
                type uint32;
                units "packet";
                description
                  "Number of NA packets discarded due to bad target IP addresses.";
              }
              leaf drop-bad-option {
                type uint32;
                units "packet";
                description
                  "Number of NA packets discarded due to bad options.";
              }
              leaf drop-local-addr {
                type uint32;
                units "packet";
                description
                  "Number of NA packets discarded because the source address is the local address.";
              }
              leaf drop-mac-check {
                type uint32;
                units "packet";
                description
                  "Number of NA packets discarded due to source MAC address consistency check errors.";
              }
              leaf drop-rate-limit {
                type uint32;
                units "packet";
                description
                  "Number of NA packets discarded due to global rate limit.";
              }
              leaf drop-src-mac-attack {
                type uint32;
                units "packet";
                description
                  "Number of NA packets discarded due to source MAC address attacks.";
              }
              leaf drop-src-mac-rate-limit {
                type uint32;
                units "packet";
                description
                  "Number of NA packets discarded due to source MAC rate limit.";
              }
              leaf drop-src-ip-rate-limit {
                type uint32;
                units "packet";
                description
                  "Number of NA packets discarded due to source IP rate limit.";
              }
              leaf drop-if-src-ip-rate-limit {
                type uint32;
                units "packet";
                description
                  "Number of NA packets discarded due to interface source IP rate limit.";
              }
              leaf drop-if-rate-limit {
                type uint32;
                units "packet";
                description
                  "Number of NA packets discarded due to interface rate limit.";
              }
              leaf drop-lr-rate-limit {
                type uint32;
                units "packet";
                description
                  "Number of NA packets discarded due to LR rate limit.";
              }
              leaf drop-dst-ip-rate-limit {
                type uint32;
                units "packet";
                description
                  "Number of NA packets discarded due to destination IP rate limit.";
              }
              leaf drop-tgt-ip-rate-limit {
                type uint32;
                units "packet";
                description
                  "Number of NA packets discarded due to target IP rate limit.";
              }
            }
          }
        }
        container rs-stats {
          description
            "Statistics of RS packets.";
          container rs-global {
            description
              "Statistics of global RS packets.";
            leaf send-total {
              type uint32;
              units "packet";
              description
                "Number of send RS packets.";
            }
            leaf send-dip-mcast {
              type uint32;
              units "packet";
              description
                "Number of send RS packets with the destination address as a multicast address.";
            }
            leaf recv-total {
              type uint32;
              units "packet";
              description
                "Number of received RS packets.";
            }
            leaf recv-valid-total {
              type uint32;
              units "packet";
              description
                "Number of received valid RS packets.";
            }
            leaf recv-dip-ucast {
              type uint32;
              units "packet";
              description
                "Number of received RS packets with the destination address as a unicast address.";
            }
            leaf recv-dip-mcast {
              type uint32;
              units "packet";
              description
                "Number of RS packets with the destination address as a multicast address.";
            }
            leaf drop-total {
              type uint32;
              units "packet";
              description
                "Number of discarded RS packets.";
            }
            leaf drop-checksum-err {
              type uint32;
              units "packet";
              description
                "Number of RS packets discarded due to checksum errors.";
            }
            leaf drop-bad-len {
              type uint32;
              units "packet";
              description
                "Number of RS packets discarded due to bad packet length.";
            }
            leaf drop-bad-code {
              type uint32;
              units "packet";
              description
                "Number of RS packets discarded due to bad code.";
            }
            leaf drop-bad-hoplimit {
              type uint32;
              units "packet";
              description
                "Number of RS packets discarded due to bad hoplimit.";
            }
            leaf drop-bad-src-mac {
              type uint32;
              units "packet";
              description
                "Number of RS packets discarded due to bad source MAC addresses.";
            }
            leaf drop-bad-dst-mac {
              type uint32;
              units "packet";
              description
                "Number of RS packets discarded due to bad destination MAC addresses.";
            }
            leaf drop-bad-tgt-mac {
              type uint32;
              units "packet";
              description
                "Number of RS packets discarded due to bad target MAC addresses.";
            }
            leaf drop-bad-src-ip {
              type uint32;
              units "packet";
              description
                "Number of RS packets discarded due to bad source IP addresses.";
            }
            leaf drop-bad-dst-ip {
              type uint32;
              units "packet";
              description
                "Number of RS packets discarded due to bad destination IP addresses.";
            }
            leaf drop-bad-option {
              type uint32;
              units "packet";
              description
                "Number of RS packets discarded due to bad options.";
            }
            leaf drop-local-addr {
              type uint32;
              units "packet";
              description
                "Number of RS packets discarded because the source address is the local address.";
            }
            leaf drop-mac-check {
              type uint32;
              units "packet";
              description
                "Number of RS packets discarded due to source MAC address consistency check errors.";
            }
            leaf drop-rate-limit {
              type uint32;
              units "packet";
              description
                "Number of RS packets discarded due to global rate limit.";
            }
            leaf drop-src-mac-attack {
              type uint32;
              units "packet";
              description
                "Number of RS packets discarded due to source MAC address attacks.";
            }
            leaf drop-src-mac-rate-limit {
              type uint32;
              units "packet";
              description
                "Number of RS packets discarded due to source MAC rate limit.";
            }
            leaf drop-src-ip-rate-limit {
              type uint32;
              units "packet";
              description
                "Number of RS packets discarded due to source IP rate limit.";
            }
            leaf drop-if-src-ip-rate-limit {
              type uint32;
              units "packet";
              description
                "Number of RS packets discarded due to interface source IP rate limit.";
            }
            leaf drop-if-rate-limit {
              type uint32;
              units "packet";
              description
                "Number of RS packets discarded due to interface rate limit.";
            }
            leaf drop-lr-rate-limit {
              type uint32;
              units "packet";
              description
                "Number of RS packets discarded due to LR rate limit.";
            }
            leaf drop-dst-ip-rate-limit {
              type uint32;
              units "packet";
              description
                "Number of RS packets discarded due to destination IP rate limit.";
            }
          }
          container rs-slots {
            description
              "List of RS packets in these slots.";
            list rs-slot {
              key "slot-id";
              description
                "Statistics of RS packets in the slot.";
              leaf slot-id {
                type string {
                  length "1..24";
                }
                description
                  "Slot ID, which refers to the position of logical MPU board and physical LPU boards.";
              }
              leaf send-total {
                type uint32;
                units "packet";
                description
                  "Number of send RS packets.";
              }
              leaf send-dip-mcast {
                type uint32;
                units "packet";
                description
                  "Number of send RS packets with the destination address as a multicast address.";
              }
              leaf recv-total {
                type uint32;
                units "packet";
                description
                  "Number of received RS packets.";
              }
              leaf recv-valid-total {
                type uint32;
                units "packet";
                description
                  "Number of received valid RS packets.";
              }
              leaf recv-dip-ucast {
                type uint32;
                units "packet";
                description
                  "Number of received RS packets with the destination address as a unicast address.";
              }
              leaf recv-dip-mcast {
                type uint32;
                units "packet";
                description
                  "Number of RS packets with the destination address as a multicast address.";
              }
              leaf drop-total {
                type uint32;
                units "packet";
                description
                  "Number of discarded RS packets.";
              }
              leaf drop-checksum-err {
                type uint32;
                units "packet";
                description
                  "Number of RS packets discarded due to checksum errors.";
              }
              leaf drop-bad-len {
                type uint32;
                units "packet";
                description
                  "Number of RS packets discarded due to bad packet length.";
              }
              leaf drop-bad-code {
                type uint32;
                units "packet";
                description
                  "Number of RS packets discarded due to bad code.";
              }
              leaf drop-bad-hoplimit {
                type uint32;
                units "packet";
                description
                  "Number of RS packets discarded due to bad hoplimit.";
              }
              leaf drop-bad-src-mac {
                type uint32;
                units "packet";
                description
                  "Number of RS packets discarded due to bad source MAC addresses.";
              }
              leaf drop-bad-dst-mac {
                type uint32;
                units "packet";
                description
                  "Number of RS packets discarded due to bad destination MAC addresses.";
              }
              leaf drop-bad-tgt-mac {
                type uint32;
                units "packet";
                description
                  "Number of RS packets discarded due to bad target MAC addresses.";
              }
              leaf drop-bad-src-ip {
                type uint32;
                units "packet";
                description
                  "Number of RS packets discarded due to bad source IP addresses.";
              }
              leaf drop-bad-dst-ip {
                type uint32;
                units "packet";
                description
                  "Number of RS packets discarded due to bad destination IP addresses.";
              }
              leaf drop-bad-option {
                type uint32;
                units "packet";
                description
                  "Number of RS packets discarded due to bad options.";
              }
              leaf drop-local-addr {
                type uint32;
                units "packet";
                description
                  "Number of RS packets discarded because the source address is the local address.";
              }
              leaf drop-mac-check {
                type uint32;
                units "packet";
                description
                  "Number of RS packets discarded due to source MAC address consistency check errors.";
              }
              leaf drop-rate-limit {
                type uint32;
                units "packet";
                description
                  "Number of RS packets discarded due to global rate limit.";
              }
              leaf drop-src-mac-attack {
                type uint32;
                units "packet";
                description
                  "Number of RS packets discarded due to source MAC address attacks.";
              }
              leaf drop-src-mac-rate-limit {
                type uint32;
                units "packet";
                description
                  "Number of RS packets discarded due to source MAC rate limit.";
              }
              leaf drop-src-ip-rate-limit {
                type uint32;
                units "packet";
                description
                  "Number of RS packets discarded due to source IP rate limit.";
              }
              leaf drop-if-src-ip-rate-limit {
                type uint32;
                units "packet";
                description
                  "Number of RS packets discarded due to interface source IP rate limit.";
              }
              leaf drop-if-rate-limit {
                type uint32;
                units "packet";
                description
                  "Number of RS packets discarded due to interface rate limit.";
              }
              leaf drop-lr-rate-limit {
                type uint32;
                units "packet";
                description
                  "Number of RS packets discarded due to LR rate limit.";
              }
              leaf drop-dst-ip-rate-limit {
                type uint32;
                units "packet";
                description
                  "Number of RS packets discarded due to destination IP rate limit.";
              }
            }
          }
          container rs-ifs {
            description
              "List of RS packets in these interfaces.";
            list rs-if {
              key "if-name";
              description
                "Statistics of RS packets in the interface.";
              leaf if-name {
                type leafref {
                  path "/ncs:devices/ncs:device/ncs:live-status/ifm:ifm/ifm:interfaces/ifm:interface/ifm:name" {
                    tailf:xpath-root 3;
                  }
                }
                description
                  "Interface name.";
              }
              leaf send-total {
                type uint32;
                units "packet";
                description
                  "Number of send RS packets.";
              }
              leaf send-dip-mcast {
                type uint32;
                units "packet";
                description
                  "Number of send RS packets with the destination address as a multicast address.";
              }
              leaf recv-total {
                type uint32;
                units "packet";
                description
                  "Number of received RS packets.";
              }
              leaf recv-valid-total {
                type uint32;
                units "packet";
                description
                  "Number of received valid RS packets.";
              }
              leaf recv-dip-ucast {
                type uint32;
                units "packet";
                description
                  "Number of received RS packets with the destination address as a unicast address.";
              }
              leaf recv-dip-mcast {
                type uint32;
                units "packet";
                description
                  "Number of RS packets with the destination address as a multicast address.";
              }
              leaf drop-total {
                type uint32;
                units "packet";
                description
                  "Number of discarded RS packets.";
              }
              leaf drop-checksum-err {
                type uint32;
                units "packet";
                description
                  "Number of RS packets discarded due to checksum errors.";
              }
              leaf drop-bad-len {
                type uint32;
                units "packet";
                description
                  "Number of RS packets discarded due to bad packet length.";
              }
              leaf drop-bad-code {
                type uint32;
                units "packet";
                description
                  "Number of RS packets discarded due to bad code.";
              }
              leaf drop-bad-hoplimit {
                type uint32;
                units "packet";
                description
                  "Number of RS packets discarded due to bad hoplimit.";
              }
              leaf drop-bad-src-mac {
                type uint32;
                units "packet";
                description
                  "Number of RS packets discarded due to bad source MAC addresses.";
              }
              leaf drop-bad-dst-mac {
                type uint32;
                units "packet";
                description
                  "Number of RS packets discarded due to bad destination MAC addresses.";
              }
              leaf drop-bad-tgt-mac {
                type uint32;
                units "packet";
                description
                  "Number of RS packets discarded due to bad target MAC addresses.";
              }
              leaf drop-bad-src-ip {
                type uint32;
                units "packet";
                description
                  "Number of RS packets discarded due to bad source IP addresses.";
              }
              leaf drop-bad-dst-ip {
                type uint32;
                units "packet";
                description
                  "Number of RS packets discarded due to bad destination IP addresses.";
              }
              leaf drop-bad-option {
                type uint32;
                units "packet";
                description
                  "Number of RS packets discarded due to bad options.";
              }
              leaf drop-local-addr {
                type uint32;
                units "packet";
                description
                  "Number of RS packets discarded because the source address is the local address.";
              }
              leaf drop-mac-check {
                type uint32;
                units "packet";
                description
                  "Number of RS packets discarded due to source MAC address consistency check errors.";
              }
              leaf drop-rate-limit {
                type uint32;
                units "packet";
                description
                  "Number of RS packets discarded due to global rate limit.";
              }
              leaf drop-src-mac-attack {
                type uint32;
                units "packet";
                description
                  "Number of RS packets discarded due to source MAC address attacks.";
              }
              leaf drop-src-mac-rate-limit {
                type uint32;
                units "packet";
                description
                  "Number of RS packets discarded due to source MAC rate limit.";
              }
              leaf drop-src-ip-rate-limit {
                type uint32;
                units "packet";
                description
                  "Number of RS packets discarded due to source IP rate limit.";
              }
              leaf drop-if-src-ip-rate-limit {
                type uint32;
                units "packet";
                description
                  "Number of RS packets discarded due to interface source IP rate limit.";
              }
              leaf drop-if-rate-limit {
                type uint32;
                units "packet";
                description
                  "Number of RS packets discarded due to interface rate limit.";
              }
              leaf drop-lr-rate-limit {
                type uint32;
                units "packet";
                description
                  "Number of RS packets discarded due to LR rate limit.";
              }
              leaf drop-dst-ip-rate-limit {
                type uint32;
                units "packet";
                description
                  "Number of RS packets discarded due to destination IP rate limit.";
              }
            }
          }
        }
        container ra-stats {
          description
            "Statistics of RA packets.";
          container ra-global {
            description
              "Statistics of global RA packets.";
            leaf send-total {
              type uint32;
              units "packet";
              description
                "Number of send RA packets.";
            }
            leaf send-dip-ucast {
              type uint32;
              units "packet";
              description
                "Number of send RA packets with the destination address as a unicast address.";
            }
            leaf send-dip-mcast {
              type uint32;
              units "packet";
              description
                "Number of send RA packets with the destination address as a multicast address.";
            }
            leaf recv-total {
              type uint32;
              units "packet";
              description
                "Number of received RA packets.";
            }
            leaf recv-valid-total {
              type uint32;
              units "packet";
              description
                "Number of received valid RA packets.";
            }
            leaf recv-dip-ucast {
              type uint32;
              units "packet";
              description
                "Number of received RA packets with the destination address as a unicast address.";
            }
            leaf recv-dip-mcast {
              type uint32;
              units "packet";
              description
                "Number of RA packets with the destination address as a multicast address.";
            }
            leaf drop-total {
              type uint32;
              units "packet";
              description
                "Number of discarded RA packets.";
            }
            leaf drop-checksum-err {
              type uint32;
              units "packet";
              description
                "Number of RA packets discarded due to checksum errors.";
            }
            leaf drop-bad-len {
              type uint32;
              units "packet";
              description
                "Number of RA packets discarded due to bad packet length.";
            }
            leaf drop-bad-code {
              type uint32;
              units "packet";
              description
                "Number of RA packets discarded due to bad code.";
            }
            leaf drop-bad-hoplimit {
              type uint32;
              units "packet";
              description
                "Number of RA packets discarded due to bad hoplimit.";
            }
            leaf drop-bad-src-mac {
              type uint32;
              units "packet";
              description
                "Number of RA packets discarded due to bad source MAC addresses.";
            }
            leaf drop-bad-dst-mac {
              type uint32;
              units "packet";
              description
                "Number of RA packets discarded due to bad destination MAC addresses.";
            }
            leaf drop-bad-tgt-mac {
              type uint32;
              units "packet";
              description
                "Number of RA packets discarded due to bad target MAC addresses.";
            }
            leaf drop-bad-src-ip {
              type uint32;
              units "packet";
              description
                "Number of RA packets discarded due to bad source IP addresses.";
            }
            leaf drop-bad-dst-ip {
              type uint32;
              units "packet";
              description
                "Number of RA packets discarded due to bad destination IP addresses.";
            }
            leaf drop-bad-option {
              type uint32;
              units "packet";
              description
                "Number of RA packets discarded due to bad options.";
            }
            leaf drop-local-addr {
              type uint32;
              units "packet";
              description
                "Number of RA packets discarded because the source address is the local address.";
            }
            leaf drop-mac-check {
              type uint32;
              units "packet";
              description
                "Number of RA packets discarded due to source MAC address consistency check errors.";
            }
            leaf drop-rate-limit {
              type uint32;
              units "packet";
              description
                "Number of RA packets discarded due to global rate limit.";
            }
            leaf drop-src-mac-attack {
              type uint32;
              units "packet";
              description
                "Number of RA packets discarded due to source MAC address attacks.";
            }
            leaf drop-src-mac-rate-limit {
              type uint32;
              units "packet";
              description
                "Number of RA packets discarded due to source MAC rate limit.";
            }
            leaf drop-src-ip-rate-limit {
              type uint32;
              units "packet";
              description
                "Number of RA packets discarded due to source IP rate limit.";
            }
            leaf drop-if-src-ip-rate-limit {
              type uint32;
              units "packet";
              description
                "Number of RA packets discarded due to interface source IP rate limit.";
            }
            leaf drop-if-rate-limit {
              type uint32;
              units "packet";
              description
                "Number of RA packets discarded due to interface rate limit.";
            }
            leaf drop-lr-rate-limit {
              type uint32;
              units "packet";
              description
                "Number of RA packets discarded due to LR rate limit.";
            }
            leaf drop-dst-ip-rate-limit {
              type uint32;
              units "packet";
              description
                "Number of RA packets discarded due to destination IP rate limit.";
            }
          }
          container ra-slots {
            description
              "List of RA packets in these slots.";
            list ra-slot {
              key "slot-id";
              description
                "Statistics of RA packets in the slot.";
              leaf slot-id {
                type string {
                  length "1..24";
                }
                description
                  "Slot ID, which refers to the position of logical MPU board and physical LPU boards.";
              }
              leaf send-total {
                type uint32;
                units "packet";
                description
                  "Number of send RA packets.";
              }
              leaf send-dip-ucast {
                type uint32;
                units "packet";
                description
                  "Number of send RA packets with the destination address as a unicast address.";
              }
              leaf send-dip-mcast {
                type uint32;
                units "packet";
                description
                  "Number of send RA packets with the destination address as a multicast address.";
              }
              leaf recv-total {
                type uint32;
                units "packet";
                description
                  "Number of received RA packets.";
              }
              leaf recv-valid-total {
                type uint32;
                units "packet";
                description
                  "Number of received valid RA packets.";
              }
              leaf recv-dip-ucast {
                type uint32;
                units "packet";
                description
                  "Number of received RA packets with the destination address as a unicast address.";
              }
              leaf recv-dip-mcast {
                type uint32;
                units "packet";
                description
                  "Number of RA packets with the destination address as a multicast address.";
              }
              leaf drop-total {
                type uint32;
                units "packet";
                description
                  "Number of discarded RA packets.";
              }
              leaf drop-checksum-err {
                type uint32;
                units "packet";
                description
                  "Number of RA packets discarded due to checksum errors.";
              }
              leaf drop-bad-len {
                type uint32;
                units "packet";
                description
                  "Number of RA packets discarded due to bad packet length.";
              }
              leaf drop-bad-code {
                type uint32;
                units "packet";
                description
                  "Number of RA packets discarded due to bad code.";
              }
              leaf drop-bad-hoplimit {
                type uint32;
                units "packet";
                description
                  "Number of RA packets discarded due to bad hoplimit.";
              }
              leaf drop-bad-src-mac {
                type uint32;
                units "packet";
                description
                  "Number of RA packets discarded due to bad source MAC addresses.";
              }
              leaf drop-bad-dst-mac {
                type uint32;
                units "packet";
                description
                  "Number of RA packets discarded due to bad destination MAC addresses.";
              }
              leaf drop-bad-tgt-mac {
                type uint32;
                units "packet";
                description
                  "Number of RA packets discarded due to bad target MAC addresses.";
              }
              leaf drop-bad-src-ip {
                type uint32;
                units "packet";
                description
                  "Number of RA packets discarded due to bad source IP addresses.";
              }
              leaf drop-bad-dst-ip {
                type uint32;
                units "packet";
                description
                  "Number of RA packets discarded due to bad destination IP addresses.";
              }
              leaf drop-bad-option {
                type uint32;
                units "packet";
                description
                  "Number of RA packets discarded due to bad options.";
              }
              leaf drop-local-addr {
                type uint32;
                units "packet";
                description
                  "Number of RA packets discarded because the source address is the local address.";
              }
              leaf drop-mac-check {
                type uint32;
                units "packet";
                description
                  "Number of RA packets discarded due to source MAC address consistency check errors.";
              }
              leaf drop-rate-limit {
                type uint32;
                units "packet";
                description
                  "Number of RA packets discarded due to global rate limit.";
              }
              leaf drop-src-mac-attack {
                type uint32;
                units "packet";
                description
                  "Number of RA packets discarded due to source MAC address attacks.";
              }
              leaf drop-src-mac-rate-limit {
                type uint32;
                units "packet";
                description
                  "Number of RA packets discarded due to source MAC rate limit.";
              }
              leaf drop-src-ip-rate-limit {
                type uint32;
                units "packet";
                description
                  "Number of RA packets discarded due to source IP rate limit.";
              }
              leaf drop-if-src-ip-rate-limit {
                type uint32;
                units "packet";
                description
                  "Number of RA packets discarded due to interface source IP rate limit.";
              }
              leaf drop-if-rate-limit {
                type uint32;
                units "packet";
                description
                  "Number of RA packets discarded due to interface rate limit.";
              }
              leaf drop-lr-rate-limit {
                type uint32;
                units "packet";
                description
                  "Number of RA packets discarded due to LR rate limit.";
              }
              leaf drop-dst-ip-rate-limit {
                type uint32;
                units "packet";
                description
                  "Number of RA packets discarded due to destination IP rate limit.";
              }
            }
          }
          container ra-ifs {
            description
              "List of RA packets in these interfaces.";
            list ra-if {
              key "if-name";
              description
                "Statistics of RA packets in the interface.";
              leaf if-name {
                type leafref {
                  path "/ncs:devices/ncs:device/ncs:live-status/ifm:ifm/ifm:interfaces/ifm:interface/ifm:name" {
                    tailf:xpath-root 3;
                  }
                }
                description
                  "Interface name.";
              }
              leaf send-total {
                type uint32;
                units "packet";
                description
                  "Number of send RA packets.";
              }
              leaf send-dip-ucast {
                type uint32;
                units "packet";
                description
                  "Number of send RA packets with the destination address as a unicast address.";
              }
              leaf send-dip-mcast {
                type uint32;
                units "packet";
                description
                  "Number of send RA packets with the destination address as a multicast address.";
              }
              leaf recv-total {
                type uint32;
                units "packet";
                description
                  "Number of received RA packets.";
              }
              leaf recv-valid-total {
                type uint32;
                units "packet";
                description
                  "Number of received valid RA packets.";
              }
              leaf recv-dip-ucast {
                type uint32;
                units "packet";
                description
                  "Number of received RA packets with the destination address as a unicast address.";
              }
              leaf recv-dip-mcast {
                type uint32;
                units "packet";
                description
                  "Number of RA packets with the destination address as a multicast address.";
              }
              leaf drop-total {
                type uint32;
                units "packet";
                description
                  "Number of discarded RA packets.";
              }
              leaf drop-checksum-err {
                type uint32;
                units "packet";
                description
                  "Number of RA packets discarded due to checksum errors.";
              }
              leaf drop-bad-len {
                type uint32;
                units "packet";
                description
                  "Number of RA packets discarded due to bad packet length.";
              }
              leaf drop-bad-code {
                type uint32;
                units "packet";
                description
                  "Number of RA packets discarded due to bad code.";
              }
              leaf drop-bad-hoplimit {
                type uint32;
                units "packet";
                description
                  "Number of RA packets discarded due to bad hoplimit.";
              }
              leaf drop-bad-src-mac {
                type uint32;
                units "packet";
                description
                  "Number of RA packets discarded due to bad source MAC addresses.";
              }
              leaf drop-bad-dst-mac {
                type uint32;
                units "packet";
                description
                  "Number of RA packets discarded due to bad destination MAC addresses.";
              }
              leaf drop-bad-tgt-mac {
                type uint32;
                units "packet";
                description
                  "Number of RA packets discarded due to bad target MAC addresses.";
              }
              leaf drop-bad-src-ip {
                type uint32;
                units "packet";
                description
                  "Number of RA packets discarded due to bad source IP addresses.";
              }
              leaf drop-bad-dst-ip {
                type uint32;
                units "packet";
                description
                  "Number of RA packets discarded due to bad destination IP addresses.";
              }
              leaf drop-bad-option {
                type uint32;
                units "packet";
                description
                  "Number of RA packets discarded due to bad options.";
              }
              leaf drop-local-addr {
                type uint32;
                units "packet";
                description
                  "Number of RA packets discarded because the source address is the local address.";
              }
              leaf drop-mac-check {
                type uint32;
                units "packet";
                description
                  "Number of RA packets discarded due to source MAC address consistency check errors.";
              }
              leaf drop-rate-limit {
                type uint32;
                units "packet";
                description
                  "Number of RA packets discarded due to global rate limit.";
              }
              leaf drop-src-mac-attack {
                type uint32;
                units "packet";
                description
                  "Number of RA packets discarded due to source MAC address attacks.";
              }
              leaf drop-src-mac-rate-limit {
                type uint32;
                units "packet";
                description
                  "Number of RA packets discarded due to source MAC rate limit.";
              }
              leaf drop-src-ip-rate-limit {
                type uint32;
                units "packet";
                description
                  "Number of RA packets discarded due to source IP rate limit.";
              }
              leaf drop-if-src-ip-rate-limit {
                type uint32;
                units "packet";
                description
                  "Number of RA packets discarded due to interface source IP rate limit.";
              }
              leaf drop-if-rate-limit {
                type uint32;
                units "packet";
                description
                  "Number of RA packets discarded due to interface rate limit.";
              }
              leaf drop-lr-rate-limit {
                type uint32;
                units "packet";
                description
                  "Number of RA packets discarded due to LR rate limit.";
              }
              leaf drop-dst-ip-rate-limit {
                type uint32;
                units "packet";
                description
                  "Number of RA packets discarded due to destination IP rate limit.";
              }
            }
          }
        }
        container ndmiss-stats {
          description
            "Statistics of ND miss packets.";
          container ndmiss-global {
            description
              "Statistics of global ND miss packets.";
            leaf recv-total {
              type uint32;
              units "packet";
              description
                "Number of received ND miss packets.";
            }
            leaf recv-valid-total {
              type uint32;
              units "packet";
              description
                "Number of received valid ND miss packets.";
            }
            leaf drop-total {
              type uint32;
              units "packet";
              description
                "Number of discarded ND miss packets.";
            }
            leaf drop-rate-limit {
              type uint32;
              units "packet";
              description
                "Number of ND miss packets discarded due to global rate limit.";
            }
            leaf drop-if-rate-limit {
              type uint32;
              units "packet";
              description
                "Number of ND miss discarded due to interface rate limit.";
            }
            leaf drop-lr-rate-limit {
              type uint32;
              units "packet";
              description
                "Number of ND miss discarded due to LR rate limit.";
            }
            leaf drop-src-ip-rate-limit {
              type uint32;
              units "packet";
              description
                "Number of ND miss discarded due to source IP rate limit.";
            }
            leaf drop-if-src-ip-rate-limit {
              type uint32;
              units "packet";
              description
                "Number of ND miss discarded due to interface source IP rate limit.";
            }
          }
          container ndmiss-slots {
            description
              "List of ND miss packets in these slots.";
            list ndmiss-slot {
              key "slot-id";
              description
                "Statistics of ND miss packets in the slot.";
              leaf slot-id {
                type string {
                  length "1..24";
                }
                description
                  "Slot ID, which refers to the position of logical MPU board and physical LPU boards.";
              }
              leaf recv-total {
                type uint32;
                units "packet";
                description
                  "Number of received ND miss packets.";
              }
              leaf recv-valid-total {
                type uint32;
                units "packet";
                description
                  "Number of received valid ND miss packets.";
              }
              leaf drop-total {
                type uint32;
                units "packet";
                description
                  "Number of discarded ND miss packets.";
              }
              leaf drop-rate-limit {
                type uint32;
                units "packet";
                description
                  "Number of ND miss packets discarded due to global rate limit.";
              }
              leaf drop-if-rate-limit {
                type uint32;
                units "packet";
                description
                  "Number of ND miss discarded due to interface rate limit.";
              }
              leaf drop-lr-rate-limit {
                type uint32;
                units "packet";
                description
                  "Number of ND miss discarded due to LR rate limit.";
              }
              leaf drop-src-ip-rate-limit {
                type uint32;
                units "packet";
                description
                  "Number of ND miss discarded due to source IP rate limit.";
              }
              leaf drop-if-src-ip-rate-limit {
                type uint32;
                units "packet";
                description
                  "Number of ND miss discarded due to interface source IP rate limit.";
              }
            }
          }
          container ndmiss-ifs {
            description
              "List of ND miss packets in these interfaces.";
            list ndmiss-if {
              key "if-name";
              description
                "Statistics of ND miss packets in the interface.";
              leaf if-name {
                type leafref {
                  path "/ncs:devices/ncs:device/ncs:live-status/ifm:ifm/ifm:interfaces/ifm:interface/ifm:name" {
                    tailf:xpath-root 3;
                  }
                }
                description
                  "Interface name.";
              }
              leaf recv-total {
                type uint32;
                units "packet";
                description
                  "Number of received ND miss packets.";
              }
              leaf recv-valid-total {
                type uint32;
                units "packet";
                description
                  "Number of received valid ND miss packets.";
              }
              leaf drop-total {
                type uint32;
                units "packet";
                description
                  "Number of discarded ND miss packets.";
              }
              leaf drop-rate-limit {
                type uint32;
                units "packet";
                description
                  "Number of ND miss packets discarded due to global rate limit.";
              }
              leaf drop-if-rate-limit {
                type uint32;
                units "packet";
                description
                  "Number of ND miss discarded due to interface rate limit.";
              }
              leaf drop-lr-rate-limit {
                type uint32;
                units "packet";
                description
                  "Number of ND miss discarded due to LR rate limit.";
              }
              leaf drop-src-ip-rate-limit {
                type uint32;
                units "packet";
                description
                  "Number of ND miss discarded due to source IP rate limit.";
              }
              leaf drop-if-src-ip-rate-limit {
                type uint32;
                units "packet";
                description
                  "Number of ND miss discarded due to interface source IP rate limit.";
              }
            }
          }
        }
      }
      container anti-attack {
        description
          "Configure ND anti-attack for global.";
        container source-mac-receive {
          description
            "Configure the ND anti-attack based on packet source MAC address.";
          container every-mac-rate-limits {
            description
              "List of rate limits for receiving ND packets based on every source MAC address.";
            list every-mac-rate-limit {
              key "packet-type";
              description
                "Configure the rate limit for receiving ND packets based on every source MAC address.";
              leaf packet-type {
                type live_ncs_nd-pkt-type;
                description
                  "ND packet type.";
              }
              leaf value {
                type uint16 {
                  range "0..5000";
                }
                units "pps";
                // NCS drop mandatory statement
                description
                  "Rate limit of receiving ND packet.";
              }
            }
          }
          container mac-rate-limits {
            description
              "List of rate limits for receiving ND packets based on specified source MAC address.";
            list mac-rate-limit {
              key "packet-type mac-addr";
              description
                "Configure the rate limit for receiving ND packets based on specified source MAC address.";
              leaf packet-type {
                type live_ncs_nd-pkt-type;
                description
                  "ND packet type.";
              }
              leaf mac-addr {
                type pub-type:live_ncs_mac-address;
                description
                  "Source MAC address.";
              }
              leaf value {
                type uint16 {
                  range "0..5000";
                }
                units "pps";
                // NCS drop mandatory statement
                description
                  "Rate limit of receiving ND packet.";
              }
            }
          }
        }
        container source-ip-receive {
          description
            "Configure the ND anti-attack based on packet or miss source IP address.";
          container every-ip-rate-limits {
            description
              "List of rate limits for receiving ND packets or ND miss based on every source IP address.";
            list every-ip-rate-limit {
              key "packet-type";
              description
                "Configure the rate limit for receiving ND packets or ND miss based on every source IP address.";
              leaf packet-type {
                type live_ncs_nd-pkt-evt-type;
                description
                  "ND packet type or ND miss.";
              }
              leaf value {
                type uint16 {
                  range "0..5000";
                }
                units "pps";
                // NCS drop mandatory statement
                description
                  "Rate limit of receiving ND packet or ND miss.";
              }
            }
          }
          uses live_ncs_nd-ip-rate-limits-type;
        }
        container destination-ip-receive {
          description
            "Configure the ND anti-attack based on packet destination IP address.";
          container every-ip-rate-limits {
            description
              "List of rate limits for receiving ND packets based on every destination IP address.";
            list every-ip-rate-limit {
              key "packet-type";
              description
                "Configure the rate limit for receiving ND packets based on every destination IP address.";
              leaf packet-type {
                type live_ncs_nd-pkt-type;
                description
                  "ND packet type.";
              }
              leaf value {
                type uint16 {
                  range "0..5000";
                }
                units "pps";
                // NCS drop mandatory statement
                description
                  "Rate limit of receiving ND packet.";
              }
            }
          }
          container ip-rate-limits {
            description
              "List of rate limits for receiving ND packets based on specified destination IP address.";
            list ip-rate-limit {
              key "packet-type ipv6-addr";
              description
                "Configure the rate limit for receiving ND packets based on specified destination IP address.";
              leaf packet-type {
                type live_ncs_nd-pkt-type;
                description
                  "ND packet type.";
              }
              leaf ipv6-addr {
                type inet:ipv6-address-no-zone;
                description
                  "Destination IPv6 address, the address cannot be the unspecified address.";
              }
              leaf value {
                type uint16 {
                  range "0..5000";
                }
                units "pps";
                // NCS drop mandatory statement
                description
                  "Rate limit of receiving ND packet.";
              }
            }
          }
        }
        container target-ip-receive {
          description
            "Configure the ND anti-attack based on packet target IP address.";
          container every-ip-rate-limits {
            description
              "List of rate limits for receiving ND packets based on every target IP address.";
            list every-ip-rate-limit {
              key "packet-type";
              description
                "Configure the rate limit for receiving ND packets based on every target IP address.";
              leaf packet-type {
                type live_ncs_nd-tgt-pkt-type;
                description
                  "ND packet type.";
              }
              leaf value {
                type uint16 {
                  range "0..5000";
                }
                units "pps";
                // NCS drop mandatory statement
                description
                  "Rate limit of receiving ND packet.";
              }
            }
          }
          container ip-rate-limits {
            description
              "List of rate limits for receiving ND packets based on specified target IP address.";
            list ip-rate-limit {
              key "packet-type ipv6-addr";
              description
                "Configure the rate limit for receiving ND packets based on specified target IP address.";
              leaf packet-type {
                type live_ncs_nd-tgt-pkt-type;
                description
                  "ND packet type.";
              }
              leaf ipv6-addr {
                type inet:ipv6-address-no-zone;
                description
                  "Target IPv6 address, the address cannot be the unspecified address or a multicast address.";
              }
              leaf value {
                type uint16 {
                  range "0..5000";
                }
                units "pps";
                // NCS drop mandatory statement
                description
                  "Rate limit of receiving ND packet.";
              }
            }
          }
        }
      }
      container send-rate-limit {
        description
          "Configure ND send rate limit for global.";
        container multicast-rate-limits {
          description
            "List of ND multicast packet sending rate limits.";
          list multicast-rate-limit {
            key "packet-type";
            description
              "Configure the rate limit of sending ND multicast packet.";
            leaf packet-type {
              type live_ncs_nd-pkt-type;
              description
                "ND packet type.";
            }
            leaf value {
              type uint16 {
                range "1..10240";
              }
              units "pps";
              // NCS drop must statement
              // NCS drop mandatory statement
              description
                "Rate limit of sending ND multicast packet, when the packet type is NS, RS or RA, the maximum value is 1000.";
            }
          }
        }
      }
    }
  }
  augment "/ncs:devices/ncs:template/ncs:ned-id/ncs:config" {
    container ipv6-nd {
      description
        "ND management.";
      container global {
        description
          "Configure global configuration of ND.";
        leaf ns-send-rate-limit {
          type string;
          units "pps";
          // NCS drop default statement
          description
            "Rate limit of sending NS packet.";
        }
        leaf na-send-rate-limit {
          type string;
          units "pps";
          // NCS drop default statement
          description
            "Rate limit of sending NA packet.";
        }
        leaf rs-send-rate-limit {
          type string;
          units "pps";
          // NCS drop default statement
          description
            "Rate limit of sending RS packet.";
        }
        leaf ra-send-rate-limit {
          type string;
          units "pps";
          // NCS drop default statement
          description
            "Rate limit of sending RA packet.";
        }
        leaf dad-detect {
          type ncs_template_nd-flag;
          // NCS drop default statement
          description
            "The switch of DAD enhanced detection.";
        }
        leaf mac-check-flag {
          type ncs_template_nd-flag;
          // NCS drop default statement
          description
            "Enable IPv6 ND MAC check.";
        }
        leaf auto-detect-flag {
          type ncs_template_nd-switch-state;
          // NCS drop default statement
          description
            "To enable the automatic detection of ND entries.";
        }
        leaf prefix-strict-flag {
          type ncs_template_nd-switch-state;
          // NCS drop default statement
          description
            "ND prefix learning strict.";
        }
        leaf pre-detect-flag {
          type ncs_template_nd-switch-state;
          // NCS drop default statement
          description
            "To determine whether to enable pre-detection.";
        }
        leaf hop-limit {
          type string;
          // NCS drop default statement
          description
            "IPv6 packet hoplimit.";
        }
        leaf stale-time {
          type string;
          units "s";
          // NCS drop default statement
          description
            "Aging time of the global stale state.";
        }
        leaf rsa-calculate-rate-limit {
          type string;
          // NCS drop default statement
          description
            "Rate limit for RSA option calculation.";
        }
        leaf log-trap-time {
          type string;
          units "s";
          // NCS drop default statement
          description
            "The interval for sending speed-limit logs and alarms.";
        }
        leaf rs-receive-rate-limit {
          type string;
          units "pps";
          ext:dynamic-default;
          description
            "Rate limit of receiving RS packet.";
        }
        leaf ra-receive-rate-limit {
          type string;
          units "pps";
          ext:dynamic-default;
          description
            "Rate limit of receiving RA packet.";
        }
        leaf ns-receive-rate-limit {
          type string;
          units "pps";
          ext:dynamic-default;
          description
            "Rate limit of receiving NS packet.";
        }
        leaf na-receive-rate-limit {
          type string;
          units "pps";
          ext:dynamic-default;
          description
            "Rate limit of receiving NA packet.";
        }
        leaf miss-receive-rate-limit {
          type string;
          units "pps";
          ext:dynamic-default;
          description
            "Rate limit of receiving ND miss.";
        }
        leaf dad-detect-rate-limit {
          type string;
          units "pps";
          // NCS drop default statement
          description
            "Rate limit of sending DAD detect packet.";
        }
        leaf dad-detect-attempts {
          type string;
          // NCS drop default statement
          description
            "Number of attempts to resolve address conflicts.";
        }
      }
      container m-lag-global {
        description
          "Configure M-LAG global configuration of ND.";
        leaf ipv6-neighbor-backup-rate {
          type string;
          description
            "Specifies the number of IPv6 neighbor entries synchronized per second through M-LAG.";
          ext:dynamic-default;
        }
      }
      // NCS drop config false container 'ipv6-neighbors'
      // NCS drop config false container 'nd-pkt-stats'
      container anti-attack {
        description
          "Configure ND anti-attack for global.";
        container source-mac-receive {
          description
            "Configure the ND anti-attack based on packet source MAC address.";
          container every-mac-rate-limits {
            description
              "List of rate limits for receiving ND packets based on every source MAC address.";
            list every-mac-rate-limit {
              // NCS patched for predictable order
              ordered-by user;
              key "packet-type";
              description
                "Configure the rate limit for receiving ND packets based on every source MAC address.";
              leaf packet-type {
                type ncs_template_nd-pkt-type;
                description
                  "ND packet type.";
              }
              leaf value {
                type string;
                units "pps";
                // NCS drop mandatory statement
                description
                  "Rate limit of receiving ND packet.";
              }
            }
          }
          container mac-rate-limits {
            description
              "List of rate limits for receiving ND packets based on specified source MAC address.";
            list mac-rate-limit {
              // NCS patched for predictable order
              ordered-by user;
              key "packet-type mac-addr";
              description
                "Configure the rate limit for receiving ND packets based on specified source MAC address.";
              leaf packet-type {
                type ncs_template_nd-pkt-type;
                description
                  "ND packet type.";
              }
              leaf mac-addr {
                type pub-type:ncs_template_mac-address;
                description
                  "Source MAC address.";
              }
              leaf value {
                type string;
                units "pps";
                // NCS drop mandatory statement
                description
                  "Rate limit of receiving ND packet.";
              }
            }
          }
        }
        container source-ip-receive {
          description
            "Configure the ND anti-attack based on packet or miss source IP address.";
          container every-ip-rate-limits {
            description
              "List of rate limits for receiving ND packets or ND miss based on every source IP address.";
            list every-ip-rate-limit {
              // NCS patched for predictable order
              ordered-by user;
              key "packet-type";
              description
                "Configure the rate limit for receiving ND packets or ND miss based on every source IP address.";
              leaf packet-type {
                type ncs_template_nd-pkt-evt-type;
                description
                  "ND packet type or ND miss.";
              }
              leaf value {
                type string;
                units "pps";
                // NCS drop mandatory statement
                description
                  "Rate limit of receiving ND packet or ND miss.";
              }
            }
          }
          uses ncs_template_nd-ip-rate-limits-type;
        }
        container destination-ip-receive {
          description
            "Configure the ND anti-attack based on packet destination IP address.";
          container every-ip-rate-limits {
            description
              "List of rate limits for receiving ND packets based on every destination IP address.";
            list every-ip-rate-limit {
              // NCS patched for predictable order
              ordered-by user;
              key "packet-type";
              description
                "Configure the rate limit for receiving ND packets based on every destination IP address.";
              leaf packet-type {
                type ncs_template_nd-pkt-type;
                description
                  "ND packet type.";
              }
              leaf value {
                type string;
                units "pps";
                // NCS drop mandatory statement
                description
                  "Rate limit of receiving ND packet.";
              }
            }
          }
          container ip-rate-limits {
            description
              "List of rate limits for receiving ND packets based on specified destination IP address.";
            list ip-rate-limit {
              // NCS patched for predictable order
              ordered-by user;
              key "packet-type ipv6-addr";
              description
                "Configure the rate limit for receiving ND packets based on specified destination IP address.";
              leaf packet-type {
                type ncs_template_nd-pkt-type;
                description
                  "ND packet type.";
              }
              leaf ipv6-addr {
                type string;
                description
                  "Destination IPv6 address, the address cannot be the unspecified address.";
              }
              leaf value {
                type string;
                units "pps";
                // NCS drop mandatory statement
                description
                  "Rate limit of receiving ND packet.";
              }
            }
          }
        }
        container target-ip-receive {
          description
            "Configure the ND anti-attack based on packet target IP address.";
          container every-ip-rate-limits {
            description
              "List of rate limits for receiving ND packets based on every target IP address.";
            list every-ip-rate-limit {
              // NCS patched for predictable order
              ordered-by user;
              key "packet-type";
              description
                "Configure the rate limit for receiving ND packets based on every target IP address.";
              leaf packet-type {
                type ncs_template_nd-tgt-pkt-type;
                description
                  "ND packet type.";
              }
              leaf value {
                type string;
                units "pps";
                // NCS drop mandatory statement
                description
                  "Rate limit of receiving ND packet.";
              }
            }
          }
          container ip-rate-limits {
            description
              "List of rate limits for receiving ND packets based on specified target IP address.";
            list ip-rate-limit {
              // NCS patched for predictable order
              ordered-by user;
              key "packet-type ipv6-addr";
              description
                "Configure the rate limit for receiving ND packets based on specified target IP address.";
              leaf packet-type {
                type ncs_template_nd-tgt-pkt-type;
                description
                  "ND packet type.";
              }
              leaf ipv6-addr {
                type string;
                description
                  "Target IPv6 address, the address cannot be the unspecified address or a multicast address.";
              }
              leaf value {
                type string;
                units "pps";
                // NCS drop mandatory statement
                description
                  "Rate limit of receiving ND packet.";
              }
            }
          }
        }
      }
      container send-rate-limit {
        description
          "Configure ND send rate limit for global.";
        container multicast-rate-limits {
          description
            "List of ND multicast packet sending rate limits.";
          list multicast-rate-limit {
            // NCS patched for predictable order
            ordered-by user;
            key "packet-type";
            description
              "Configure the rate limit of sending ND multicast packet.";
            leaf packet-type {
              type ncs_template_nd-pkt-type;
              description
                "ND packet type.";
            }
            leaf value {
              type string;
              units "pps";
              // NCS drop must statement
              // NCS drop mandatory statement
              description
                "Rate limit of sending ND multicast packet, when the packet type is NS, RS or RA, the maximum value is 1000.";
            }
          }
        }
      }
    }
  }
  augment "/ncs:devices/ncs:template/ncs:ned-id/ncs:config/bd:bd/bd:instances/bd:instance" {
    description
      "List of Bridge-Domain Neighbor Multicast-Suppress Information.";
    container nd-bd-property {
      description
        "Configure Bridge-Domain neighbor multicast-suppress information.";
      leaf unicast-forward {
        type string;
        // NCS drop default statement
        description
          "Enable/disable Bridge-Domain unicast forward.";
      }
    }
  }
  augment "/ncs:devices/ncs:device/ncs:live-status/bd:bd/bd:instances/bd:instance" {
    description
      "List of Bridge-Domain Neighbor Multicast-Suppress Information.";
    container nd-bd-property {
      tailf:ncs-device-type "netconf";
      tailf:display-when "not(../../../../../ncs:module) or ../../../../../ncs:module[ncs:name='huawei-ipv6-nd'] or (../../../../../ncs:live-status-protocol[not(ncs:capability)]) or (../../../../../ncs:live-status-protocol/ncs:capability/ncs:module[.='huawei-ipv6-nd'])";
      description
        "Configure Bridge-Domain neighbor multicast-suppress information.";
      leaf unicast-forward {
        type boolean;
        // NCS drop default statement
        description
          "Enable/disable Bridge-Domain unicast forward.";
      }
    }
  }
  augment "/ncs:devices/ncs:device/ncs:config/bd:bd/bd:instances/bd:instance" {
    description
      "List of Bridge-Domain Neighbor Multicast-Suppress Information.";
    container nd-bd-property {
      tailf:ncs-device-type "netconf";
      tailf:display-when "not(../../../../../ncs:module) or ../../../../../ncs:module[ncs:name='huawei-ipv6-nd']";
      description
        "Configure Bridge-Domain neighbor multicast-suppress information.";
      leaf unicast-forward {
        type boolean;
        default "false";
        description
          "Enable/disable Bridge-Domain unicast forward.";
      }
    }
  }
  augment "/ncs:devices/ncs:template/ncs:ned-id/ncs:config/ifm:ifm/ifm:interfaces/ifm:interface/ip:ipv6" {
    // NCS drop when statement
    description
      "All configurations of the ND under the interface.";
    container nd-collection {
      description
        "Configure ND interface configurations.";
      container if-property {
        description
          "Configure ND interface configurations.";
        leaf retrans-timer {
          // NCS drop when statement
          type string;
          units "ms";
          // NCS drop default statement
          description
            "To set the retransmission timer of a router.";
        }
        leaf nud-reach-time {
          // NCS drop when statement
          type string;
          units "ms";
          // NCS drop default statement
          description
            "To set the reachable time of a neighbor.";
        }
        leaf attempts-value {
          // NCS drop when statement
          type string;
          // NCS drop default statement
          description
            "To set the number of sent NS messages during DAD.";
        }
        leaf ns-mcast-flag {
          // NCS drop when statement
          type ncs_template_nd-switch-state;
          // NCS drop default statement
          description
            "Flag of enabling multicast.";
        }
        leaf max-dyn-nb-num {
          // NCS drop when statement
          type string;
          // NCS drop default statement
          description
            "The maximum of limitation of dynamic neighbor.";
        }
        leaf dad-timeout {
          // NCS drop when statement
          type string;
          units "s";
          // NCS drop default statement
          description
            "Timeout of DAD.";
        }
        leaf nud-attempts {
          // NCS drop when statement
          type string;
          // NCS drop default statement
          description
            "ND entries NUD attempts.";
        }
        leaf na-glean {
          // NCS drop when statement
          type ncs_template_nd-switch-state;
          // NCS drop default statement
          description
            "Flag of generating NB when receiving NA packet.";
        }
        leaf ma-flag {
          // NCS drop when statement
          type ncs_template_nd-switch-state;
          // NCS drop default statement
          description
            "Flag of obtaining the routable address through state-based automatic configuration.";
        }
        leaf o-flag {
          // NCS drop when statement
          type ncs_template_nd-switch-state;
          // NCS drop default statement
          description
            "Flag of setting state-based automatic configuration.";
        }
        leaf ra-halt-flag {
          // NCS drop when statement
          type ncs_template_nd-switch-state;
          // NCS drop default statement
          description
            "To suppress the advertisement of RA packets.";
        }
        leaf max-interval {
          // NCS drop when statement
          type string;
          units "s";
          // NCS drop default statement
          description
            "The Maximum interval between periodic RA packets sent on this interface.";
        }
        leaf ra-lifetime {
          // NCS drop when statement
          type string;
          units "s";
          // NCS drop must statement
          description
            "TTL of RA packets. If the value is 0, it implies that this node is not a router. And the value from 1 to 3 is invalid.";
        }
        leaf ra-preference {
          // NCS drop when statement
          type ncs_template_nd-route-preference;
          // NCS drop default statement
          description
            "RA router preference.";
        }
        leaf ra-prefix-flag {
          // NCS drop when statement
          type ncs_template_nd-switch-state;
          // NCS drop default statement
          description
            "Flag of RA packet carry prefix information.";
        }
        leaf ra-mtu-flag {
          // NCS drop when statement
          type ncs_template_nd-switch-state;
          // NCS drop default statement
          description
            "Flag of RA packet carry MTU option.";
        }
        leaf strict-flag {
          // NCS drop when statement
          type string;
          // NCS drop default statement
          description
            "Enable/disable strict security mode.";
        }
        leaf ts-fuzz-factor {
          // NCS drop when statement
          type string;
          units "s";
          // NCS drop default statement
          description
            "Fuzz factor for timestamp option.";
        }
        leaf ts-clock-drift {
          // NCS drop when statement
          type string;
          // NCS drop default statement
          description
            "Drift for timestamp option.";
        }
        leaf ts-delta {
          // NCS drop when statement
          type string;
          units "s";
          // NCS drop default statement
          description
            "Delta for timestamp option.";
        }
        leaf rsa-min-key-len {
          // NCS drop when statement
          type string;
          units "bit";
          // NCS drop must statement
          // NCS drop default statement
          description
            "The minimum length of acceptable RSA key pair.";
        }
        leaf rsa-max-key-len {
          // NCS drop when statement
          type string;
          units "bit";
          // NCS drop default statement
          description
            "The maximum length of acceptable RSA key pair.";
        }
        leaf stale-time {
          // NCS drop when statement
          type string;
          units "s";
          description
            "Aging time of the stale state.";
        }
        leaf collect-host-flag {
          // NCS drop when statement
          type ncs_template_nd-switch-state;
          // NCS drop default statement
          description
            "Flag of collecting host Information.";
        }
        leaf generate-rd-enable {
          // NCS drop when statement
          type ncs_template_nd-switch-state;
          // NCS drop default statement
          description
            "Flag of generating redirect ND table.";
        }
        leaf nud-interval {
          // NCS drop when statement
          type string;
          units "ms";
          // NCS drop default statement
          description
            "ND entries NUD interval.";
        }
        leaf hop-limit {
          type string;
          description
            "IPv6 packet hop limit.";
        }
        leaf link-down-trigger-del-flag {
          // NCS drop when statement
          type ncs_template_nd-switch-state;
          // NCS drop default statement
          description
            "Flag of link down trigger fast deletion of ND entries.";
        }
      }
      container proxys {
        // NCS drop when statement
        description
          "Configure list of ND proxy.";
        leaf route-proxy {
          // NCS drop when statement
          type ncs_template_nd-switch-state;
          // NCS drop default statement
          description
            "Router proxy.";
        }
        leaf inner-vlan-proxy {
          // NCS drop when statement
          type ncs_template_nd-switch-state;
          // NCS drop default statement
          description
            "InnerVLAN proxy.";
        }
        leaf inter-vlan-proxy {
          // NCS drop when statement
          type ncs_template_nd-switch-state;
          // NCS drop default statement
          description
            "InterVLAN proxy.";
        }
        leaf anyway-proxy {
          type ncs_template_nd-switch-state;
          // NCS drop default statement
          description
            "Anyway proxy.";
        }
        leaf local-proxy {
          // NCS drop when statement
          type ncs_template_nd-switch-state;
          // NCS drop default statement
          description
            "Local proxy.";
        }
      }
      container anti-attack {
        // NCS drop when statement
        description
          "Configure ND anti-attack for interface.";
        container receive-rate-limits {
          description
            "List of rate limits for receiving ND packets.";
          list receive-rate-limit {
            // NCS patched for predictable order
            ordered-by user;
            key "type";
            description
              "Configure the rate limit for receiving ND packet or ND miss.";
            leaf type {
              type ncs_template_nd-pkt-evt-type;
              description
                "ND packet type or ND miss.";
            }
            leaf value {
              type string;
              units "pps";
              // NCS drop mandatory statement
              description
                "Rate limit of receiving ND packet or ND miss.";
            }
          }
        }
        container source-ip-receive {
          description
            "Configure the ND anti-attack based on packet or miss source IP address.";
          uses ncs_template_nd-ip-rate-limits-type;
        }
      }
      container static-neighbor {
        description
          "Configure static neighbor entry.";
        container common-ifs {
          // NCS drop when statement
          description
            "List of static neighbor entry on common interface.";
          list common-if {
            // NCS patched for predictable order
            ordered-by user;
            key "ipv6-addr";
            description
              "Configure static neighbor entry on common interface.";
            leaf ipv6-addr {
              type string;
              description
                "IPv6 address of a static neighbor entry.";
            }
            leaf mac-addr {
              type pub-type:ncs_template_mac-address;
              // NCS drop mandatory statement
              description
                "MAC address.";
            }
          }
        }
        container dot1q-termination-ifs {
          // NCS drop when statement
          description
            "List of static neighbor entry on dot1q termination interface.";
          list dot1q-termination-if {
            // NCS patched for predictable order
            ordered-by user;
            key "ipv6-addr";
            description
              "Configure static neighbor entry on dot1q termination interface.";
            leaf ipv6-addr {
              type string;
              description
                "IPv6 address of a static neighbor entry.";
            }
            leaf mac-addr {
              type pub-type:ncs_template_mac-address;
              // NCS drop mandatory statement
              description
                "MAC address.";
            }
            leaf pe-vlan {
              type string;
              // NCS drop mandatory statement
              description
                "Outer VLAN tag.";
            }
          }
        }
        container qinq-termination-ifs {
          // NCS drop when statement
          description
            "List of static neighbor entry on qinq termination interface.";
          list qinq-termination-if {
            // NCS patched for predictable order
            ordered-by user;
            key "ipv6-addr";
            description
              "Configure static neighbor entry on qinq termination interface.";
            leaf ipv6-addr {
              type string;
              description
                "IPv6 address of a static neighbor entry.";
            }
            leaf mac-addr {
              type pub-type:ncs_template_mac-address;
              // NCS drop mandatory statement
              description
                "MAC address.";
            }
            leaf pe-vlan {
              type string;
              // NCS drop mandatory statement
              description
                "Outer VLAN tag.";
            }
            leaf ce-vlan {
              type string;
              // NCS drop mandatory statement
              description
                "Inner VLAN tag.";
            }
          }
        }
        container vlan-ifs {
          // NCS drop when statement
          description
            "List of static neighbor entry on VLAN interface.";
          list vlan-if {
            // NCS patched for predictable order
            ordered-by user;
            key "ipv6-addr";
            description
              "Configure static neighbor entry on VLAN interface.";
            leaf ipv6-addr {
              type string;
              description
                "IPv6 address of a static neighbor entry.";
            }
            leaf mac-addr {
              type pub-type:ncs_template_mac-address;
              // NCS drop mandatory statement
              description
                "MAC address.";
            }
            leaf vlan-id {
              type string;
              description
                "VLAN ID.";
              ext:support-filter "true";
            }
            leaf port-name {
              type string;
              // NCS drop mandatory statement
              description
                "Port name.";
            }
          }
        }
      }
      container send-rate-limit {
        // NCS drop when statement
        description
          "Configure ND send rate limit for interface.";
        container packet-rate-limits {
          description
            "List of ND packet sending rate limits.";
          list packet-rate-limit {
            // NCS patched for predictable order
            ordered-by user;
            key "packet-type";
            description
              "Configure the rate limit of sending ND packet.";
            leaf packet-type {
              type ncs_template_nd-pkt-type;
              // NCS drop must statement
              description
                "ND packet type.";
            }
            leaf value {
              type string;
              units "pps";
              // NCS drop must statement
              // NCS drop mandatory statement
              description
                "Rate limit of sending ND packet, when the packet type is NS, RS or RA, the maximum value is 1000.";
            }
          }
        }
        container multicast-rate-limits {
          description
            "List of ND multicast packet sending rate limits.";
          list multicast-rate-limit {
            // NCS patched for predictable order
            ordered-by user;
            key "packet-type";
            description
              "Configure the rate limit of sending ND multicast packet.";
            leaf packet-type {
              type ncs_template_nd-pkt-type;
              // NCS drop must statement
              description
                "ND packet type.";
            }
            leaf value {
              type string;
              units "pps";
              // NCS drop must statement
              // NCS drop mandatory statement
              description
                "Rate limit of sending ND multicast packet, when the packet type is NS, RS or RA, the maximum value is 1000.";
            }
          }
        }
      }
      container ra-property {
        // NCS drop when statement
        description
          "Configure ND RA configurations under the interface.";
        container ra-control {
          description
            "Configure ND RA configurations.";
          leaf unicast-send {
            type ncs_template_nd-switch-state;
            // NCS drop default statement
            description
              "Flag of Sending RA unicast packet when receive a RS packet.";
          }
        }
        container ra-routes {
          description
            "List of RA route information option.";
          list ra-route {
            // NCS patched for predictable order
            ordered-by user;
            key "prefix-addr prefix-len";
            description
              "Configure RA route information option.";
            leaf prefix-addr {
              type string;
              description
                "The IPv6 prefix address of RA route information.";
            }
            leaf prefix-len {
              type string;
              description
                "The prefix length of RA route information.";
            }
            leaf lifetime {
              type string;
              units "s";
              // NCS drop mandatory statement
              description
                "The lifetime of RA route information.";
            }
            leaf preference {
              type ncs_template_nd-route-preference;
              // NCS drop default statement
              description
                "The preference of RA route information.";
            }
          }
        }
        container dns-server-addresses {
          description
            "List of DNS server address.";
          list dns-server-address {
            // NCS patched for predictable order
            ordered-by user;
            key "ipv6-address";
            description
              "Configure the DNS server address.";
            leaf ipv6-address {
              type string;
              description
                "Address of IPv6 recursive DNS server. The address cannot be a multicast address or an unspecified address.";
            }
            leaf lifetime {
              type string;
              units "s";
              description
                "The maximum time over which this RDNSS address may be used for name resolution.";
            }
          }
        }
        container dns-search-suffixes {
          description
            "List of DNS search list.";
          list dns-search-suffix {
            // NCS patched for predictable order
            ordered-by user;
            key "suffix-name";
            description
              "Configure DNS suffix name.";
            leaf suffix-name {
              type string;
              ext:case-sensitivity "lower-or-upper";
              description
                "Domain name of DNS search list.";
            }
            leaf lifetime {
              type string;
              units "s";
              description
                "The maximum time over which this DNSSL domain name may be used for name resolution.";
            }
          }
        }
      }
      container strict-prefix-learn {
        // NCS drop when statement
        description
          "Configure strict prefix learning of interface.";
        leaf switch {
          type ncs_template_nd-switch-state;
          description
            "ND prefix learning strict.";
        }
      }
    }
  }
  augment "/ncs:devices/ncs:device/ncs:live-status/ifm:ifm/ifm:interfaces/ifm:interface/ip:ipv6" {
    // NCS drop when statement
    description
      "All configurations of the ND under the interface.";
    container nd-collection {
      tailf:ncs-device-type "netconf";
      tailf:display-when "not(../../../../../../ncs:module) or ../../../../../../ncs:module[ncs:name='huawei-ipv6-nd'] or (../../../../../../ncs:live-status-protocol[not(ncs:capability)]) or (../../../../../../ncs:live-status-protocol/ncs:capability/ncs:module[.='huawei-ipv6-nd'])";
      description
        "Configure ND interface configurations.";
      container if-property {
        description
          "Configure ND interface configurations.";
        leaf retrans-timer {
          // NCS drop when statement
          type uint32 {
            range "1000..4294967295";
          }
          units "ms";
          // NCS drop default statement
          description
            "To set the retransmission timer of a router.";
        }
        leaf nud-reach-time {
          // NCS drop when statement
          type uint32 {
            range "1..3600000";
          }
          units "ms";
          // NCS drop default statement
          description
            "To set the reachable time of a neighbor.";
        }
        leaf attempts-value {
          // NCS drop when statement
          type uint32 {
            range "0..600";
          }
          // NCS drop default statement
          description
            "To set the number of sent NS messages during DAD.";
        }
        leaf ns-mcast-flag {
          // NCS drop when statement
          type live_ncs_nd-switch-state;
          // NCS drop default statement
          description
            "Flag of enabling multicast.";
        }
        leaf max-dyn-nb-num {
          // NCS drop when statement
          type uint64 {
            range "0..65536";
          }
          // NCS drop default statement
          description
            "The maximum of limitation of dynamic neighbor.";
        }
        leaf dad-timeout {
          // NCS drop when statement
          type uint32 {
            range "1..60";
          }
          units "s";
          // NCS drop default statement
          description
            "Timeout of DAD.";
        }
        leaf nud-attempts {
          // NCS drop when statement
          type uint8 {
            range "1..10";
          }
          // NCS drop default statement
          description
            "ND entries NUD attempts.";
        }
        leaf na-glean {
          // NCS drop when statement
          type live_ncs_nd-switch-state;
          // NCS drop default statement
          description
            "Flag of generating NB when receiving NA packet.";
        }
        leaf ma-flag {
          // NCS drop when statement
          type live_ncs_nd-switch-state;
          // NCS drop default statement
          description
            "Flag of obtaining the routable address through state-based automatic configuration.";
        }
        leaf o-flag {
          // NCS drop when statement
          type live_ncs_nd-switch-state;
          // NCS drop default statement
          description
            "Flag of setting state-based automatic configuration.";
        }
        leaf ra-halt-flag {
          // NCS drop when statement
          type live_ncs_nd-switch-state;
          // NCS drop default statement
          description
            "To suppress the advertisement of RA packets.";
        }
        leaf max-interval {
          // NCS drop when statement
          type uint32 {
            range "4..1800";
          }
          units "s";
          // NCS drop default statement
          description
            "The Maximum interval between periodic RA packets sent on this interface.";
        }
        leaf ra-lifetime {
          // NCS drop when statement
          type uint32 {
            range "0|4..9000";
          }
          units "s";
          // NCS drop must statement
          description
            "TTL of RA packets. If the value is 0, it implies that this node is not a router. And the value from 1 to 3 is invalid.";
        }
        leaf ra-preference {
          // NCS drop when statement
          type live_ncs_nd-route-preference;
          // NCS drop default statement
          description
            "RA router preference.";
        }
        leaf ra-prefix-flag {
          // NCS drop when statement
          type live_ncs_nd-switch-state;
          // NCS drop default statement
          description
            "Flag of RA packet carry prefix information.";
        }
        leaf ra-mtu-flag {
          // NCS drop when statement
          type live_ncs_nd-switch-state;
          // NCS drop default statement
          description
            "Flag of RA packet carry MTU option.";
        }
        leaf strict-flag {
          // NCS drop when statement
          type boolean;
          // NCS drop default statement
          description
            "Enable/disable strict security mode.";
        }
        leaf ts-fuzz-factor {
          // NCS drop when statement
          type uint16 {
            range "0..1000";
          }
          units "s";
          // NCS drop default statement
          description
            "Fuzz factor for timestamp option.";
        }
        leaf ts-clock-drift {
          // NCS drop when statement
          type uint8 {
            range "0..100";
          }
          // NCS drop default statement
          description
            "Drift for timestamp option.";
        }
        leaf ts-delta {
          // NCS drop when statement
          type uint16 {
            range "0..1000";
          }
          units "s";
          // NCS drop default statement
          description
            "Delta for timestamp option.";
        }
        leaf rsa-min-key-len {
          // NCS drop when statement
          type uint16 {
            range "384..3072";
          }
          units "bit";
          // NCS drop must statement
          // NCS drop default statement
          description
            "The minimum length of acceptable RSA key pair.";
        }
        leaf rsa-max-key-len {
          // NCS drop when statement
          type uint16 {
            range "384..3072";
          }
          units "bit";
          // NCS drop default statement
          description
            "The maximum length of acceptable RSA key pair.";
        }
        leaf stale-time {
          // NCS drop when statement
          type uint32 {
            range "60..172800";
          }
          units "s";
          description
            "Aging time of the stale state.";
        }
        leaf collect-host-flag {
          // NCS drop when statement
          type live_ncs_nd-switch-state;
          // NCS drop default statement
          description
            "Flag of collecting host Information.";
        }
        leaf generate-rd-enable {
          // NCS drop when statement
          type live_ncs_nd-switch-state;
          // NCS drop default statement
          description
            "Flag of generating redirect ND table.";
        }
        leaf nud-interval {
          // NCS drop when statement
          type uint32 {
            range "1000..4294967295";
          }
          units "ms";
          // NCS drop default statement
          description
            "ND entries NUD interval.";
        }
        leaf hop-limit {
          type uint8 {
            range "0..255";
          }
          description
            "IPv6 packet hop limit.";
        }
        leaf link-down-trigger-del-flag {
          // NCS drop when statement
          type live_ncs_nd-switch-state;
          // NCS drop default statement
          description
            "Flag of link down trigger fast deletion of ND entries.";
        }
      }
      container proxys {
        // NCS drop when statement
        description
          "Configure list of ND proxy.";
        leaf route-proxy {
          // NCS drop when statement
          type live_ncs_nd-switch-state;
          // NCS drop default statement
          description
            "Router proxy.";
        }
        leaf inner-vlan-proxy {
          // NCS drop when statement
          type live_ncs_nd-switch-state;
          // NCS drop default statement
          description
            "InnerVLAN proxy.";
        }
        leaf inter-vlan-proxy {
          // NCS drop when statement
          type live_ncs_nd-switch-state;
          // NCS drop default statement
          description
            "InterVLAN proxy.";
        }
        leaf anyway-proxy {
          type live_ncs_nd-switch-state;
          // NCS drop default statement
          description
            "Anyway proxy.";
        }
        leaf local-proxy {
          // NCS drop when statement
          type live_ncs_nd-switch-state;
          // NCS drop default statement
          description
            "Local proxy.";
        }
      }
      container anti-attack {
        // NCS drop when statement
        description
          "Configure ND anti-attack for interface.";
        container receive-rate-limits {
          description
            "List of rate limits for receiving ND packets.";
          list receive-rate-limit {
            key "type";
            description
              "Configure the rate limit for receiving ND packet or ND miss.";
            leaf type {
              type live_ncs_nd-pkt-evt-type;
              description
                "ND packet type or ND miss.";
            }
            leaf value {
              type uint16 {
                range "0..5000";
              }
              units "pps";
              // NCS drop mandatory statement
              description
                "Rate limit of receiving ND packet or ND miss.";
            }
          }
        }
        container source-ip-receive {
          description
            "Configure the ND anti-attack based on packet or miss source IP address.";
          uses live_ncs_nd-ip-rate-limits-type;
        }
      }
      container static-neighbor {
        description
          "Configure static neighbor entry.";
        container common-ifs {
          // NCS drop when statement
          description
            "List of static neighbor entry on common interface.";
          list common-if {
            key "ipv6-addr";
            description
              "Configure static neighbor entry on common interface.";
            leaf ipv6-addr {
              type inet:ipv6-address-no-zone;
              description
                "IPv6 address of a static neighbor entry.";
            }
            leaf mac-addr {
              type pub-type:live_ncs_mac-address;
              // NCS drop mandatory statement
              description
                "MAC address.";
            }
          }
        }
        container dot1q-termination-ifs {
          // NCS drop when statement
          description
            "List of static neighbor entry on dot1q termination interface.";
          list dot1q-termination-if {
            key "ipv6-addr";
            description
              "Configure static neighbor entry on dot1q termination interface.";
            leaf ipv6-addr {
              type inet:ipv6-address-no-zone;
              description
                "IPv6 address of a static neighbor entry.";
            }
            leaf mac-addr {
              type pub-type:live_ncs_mac-address;
              // NCS drop mandatory statement
              description
                "MAC address.";
            }
            leaf pe-vlan {
              type uint16 {
                range "1..4094";
              }
              // NCS drop mandatory statement
              description
                "Outer VLAN tag.";
            }
          }
        }
        container qinq-termination-ifs {
          // NCS drop when statement
          description
            "List of static neighbor entry on qinq termination interface.";
          list qinq-termination-if {
            key "ipv6-addr";
            description
              "Configure static neighbor entry on qinq termination interface.";
            leaf ipv6-addr {
              type inet:ipv6-address-no-zone;
              description
                "IPv6 address of a static neighbor entry.";
            }
            leaf mac-addr {
              type pub-type:live_ncs_mac-address;
              // NCS drop mandatory statement
              description
                "MAC address.";
            }
            leaf pe-vlan {
              type uint16 {
                range "1..4094";
              }
              // NCS drop mandatory statement
              description
                "Outer VLAN tag.";
            }
            leaf ce-vlan {
              type uint16 {
                range "1..4094";
              }
              // NCS drop mandatory statement
              description
                "Inner VLAN tag.";
            }
          }
        }
        container vlan-ifs {
          // NCS drop when statement
          description
            "List of static neighbor entry on VLAN interface.";
          list vlan-if {
            key "ipv6-addr";
            description
              "Configure static neighbor entry on VLAN interface.";
            leaf ipv6-addr {
              type inet:ipv6-address-no-zone;
              description
                "IPv6 address of a static neighbor entry.";
            }
            leaf mac-addr {
              type pub-type:live_ncs_mac-address;
              // NCS drop mandatory statement
              description
                "MAC address.";
            }
            leaf vlan-id {
              type uint16 {
                range "1..4094";
              }
              description
                "VLAN ID.";
              ext:support-filter "true";
            }
            leaf port-name {
              type leafref {
                path "/ncs:devices/ncs:device/ncs:live-status/ifm:ifm/ifm:interfaces/ifm:interface/ifm:name" {
                  tailf:xpath-root 3;
                }
              }
              // NCS drop mandatory statement
              description
                "Port name.";
            }
          }
        }
      }
      container send-rate-limit {
        // NCS drop when statement
        description
          "Configure ND send rate limit for interface.";
        container packet-rate-limits {
          description
            "List of ND packet sending rate limits.";
          list packet-rate-limit {
            key "packet-type";
            description
              "Configure the rate limit of sending ND packet.";
            leaf packet-type {
              type live_ncs_nd-pkt-type;
              // NCS drop must statement
              description
                "ND packet type.";
            }
            leaf value {
              type uint16 {
                range "1..10240";
              }
              units "pps";
              // NCS drop must statement
              // NCS drop mandatory statement
              description
                "Rate limit of sending ND packet, when the packet type is NS, RS or RA, the maximum value is 1000.";
            }
          }
        }
        container multicast-rate-limits {
          description
            "List of ND multicast packet sending rate limits.";
          list multicast-rate-limit {
            key "packet-type";
            description
              "Configure the rate limit of sending ND multicast packet.";
            leaf packet-type {
              type live_ncs_nd-pkt-type;
              // NCS drop must statement
              description
                "ND packet type.";
            }
            leaf value {
              type uint16 {
                range "1..10240";
              }
              units "pps";
              // NCS drop must statement
              // NCS drop mandatory statement
              description
                "Rate limit of sending ND multicast packet, when the packet type is NS, RS or RA, the maximum value is 1000.";
            }
          }
        }
      }
      container ra-property {
        // NCS drop when statement
        description
          "Configure ND RA configurations under the interface.";
        container ra-control {
          description
            "Configure ND RA configurations.";
          leaf unicast-send {
            type live_ncs_nd-switch-state;
            // NCS drop default statement
            description
              "Flag of Sending RA unicast packet when receive a RS packet.";
          }
        }
        container ra-routes {
          description
            "List of RA route information option.";
          list ra-route {
            key "prefix-addr prefix-len";
            description
              "Configure RA route information option.";
            leaf prefix-addr {
              type inet:ipv6-address-no-zone;
              description
                "The IPv6 prefix address of RA route information.";
            }
            leaf prefix-len {
              type uint32 {
                range "0..128";
              }
              description
                "The prefix length of RA route information.";
            }
            leaf lifetime {
              type uint32;
              units "s";
              // NCS drop mandatory statement
              description
                "The lifetime of RA route information.";
            }
            leaf preference {
              type live_ncs_nd-route-preference;
              // NCS drop default statement
              description
                "The preference of RA route information.";
            }
          }
        }
        container dns-server-addresses {
          description
            "List of DNS server address.";
          list dns-server-address {
            key "ipv6-address";
            description
              "Configure the DNS server address.";
            leaf ipv6-address {
              type inet:ipv6-address-no-zone;
              description
                "Address of IPv6 recursive DNS server. The address cannot be a multicast address or an unspecified address.";
            }
            leaf lifetime {
              type uint32 {
                range "1..max";
              }
              units "s";
              description
                "The maximum time over which this RDNSS address may be used for name resolution.";
            }
          }
        }
        container dns-search-suffixes {
          description
            "List of DNS search list.";
          list dns-search-suffix {
            key "suffix-name";
            description
              "Configure DNS suffix name.";
            leaf suffix-name {
              type string {
                length "1..63";
              }
              ext:case-sensitivity "lower-or-upper";
              description
                "Domain name of DNS search list.";
            }
            leaf lifetime {
              type uint32 {
                range "1..max";
              }
              units "s";
              description
                "The maximum time over which this DNSSL domain name may be used for name resolution.";
            }
          }
        }
      }
      container strict-prefix-learn {
        // NCS drop when statement
        description
          "Configure strict prefix learning of interface.";
        leaf switch {
          type live_ncs_nd-switch-state;
          description
            "ND prefix learning strict.";
        }
      }
    }
  }
  augment "/ncs:devices/ncs:device/ncs:config/ifm:ifm/ifm:interfaces/ifm:interface/ip:ipv6" {
    when "../ifm:type!='Tunnel' and ../ifm:type!='LoopBack' and ../ifm:type!='ServiceIf' and ../ifm:type!='Virtual-if'" {
      tailf:xpath-root 3;
    }
    description
      "All configurations of the ND under the interface.";
    container nd-collection {
      tailf:ncs-device-type "netconf";
      tailf:display-when "not(../../../../../../ncs:module) or ../../../../../../ncs:module[ncs:name='huawei-ipv6-nd']";
      description
        "Configure ND interface configurations.";
      container if-property {
        description
          "Configure ND interface configurations.";
        leaf retrans-timer {
          when "../../../../ifm:type!='Serial'" {
            tailf:xpath-root 3;
          }
          type uint32 {
            range "1000..4294967295";
          }
          units "ms";
          default "1000";
          description
            "To set the retransmission timer of a router.";
        }
        leaf nud-reach-time {
          when "../../../../ifm:type!='Ip-Trunk' and ../../../../ifm:type!='Pos' and ../../../../ifm:type!='Mp-group' and ../../../../ifm:type!='Serial'" {
            tailf:xpath-root 3;
          }
          type uint32 {
            range "1..3600000";
          }
          units "ms";
          default "1200000";
          description
            "To set the reachable time of a neighbor.";
        }
        leaf attempts-value {
          when "../../../../ifm:type!='Serial'" {
            tailf:xpath-root 3;
          }
          type uint32 {
            range "0..600";
          }
          default "1";
          description
            "To set the number of sent NS messages during DAD.";
        }
        leaf ns-mcast-flag {
          when '../../../../ethernet:ethernet/ethernet:l3-sub-interface/ethernet:dot1q-termination or ../../../../ethernet:ethernet/ethernet:l3-sub-interface/ethernet:qinq-termination' {
            tailf:xpath-root 3;
          }
          type nd-switch-state;
          default "off";
          description
            "Flag of enabling multicast.";
        }
        leaf max-dyn-nb-num {
          when "../../../../ifm:type!='Ip-Trunk' and ../../../../ifm:type!='Pos' and ../../../../ifm:type!='Mp-group' and ../../../../ifm:type!='Serial'" {
            tailf:xpath-root 3;
          }
          type uint64 {
            range "0..65536";
          }
          default "0";
          description
            "The maximum of limitation of dynamic neighbor.";
        }
        leaf dad-timeout {
          when '../../../../ethernet:ethernet/ethernet:l3-sub-interface/ethernet:dot1q-termination or ../../../../ethernet:ethernet/ethernet:l3-sub-interface/ethernet:qinq-termination' {
            tailf:xpath-root 3;
          }
          type uint32 {
            range "1..60";
          }
          units "s";
          default "1";
          description
            "Timeout of DAD.";
        }
        leaf nud-attempts {
          when "../../../../ifm:type!='Ip-Trunk' and ../../../../ifm:type!='Pos' and ../../../../ifm:type!='Mp-group' and ../../../../ifm:type!='Serial'" {
            tailf:xpath-root 3;
          }
          type uint8 {
            range "1..10";
          }
          default "3";
          description
            "ND entries NUD attempts.";
        }
        leaf na-glean {
          when "../../../../ifm:type!='Ip-Trunk' and ../../../../ifm:type!='Pos' and ../../../../ifm:type!='Mp-group' and ../../../../ifm:type!='Serial'" {
            tailf:xpath-root 3;
          }
          type nd-switch-state;
          default "off";
          description
            "Flag of generating NB when receiving NA packet.";
        }
        leaf ma-flag {
          when "../../../../ifm:type!='MEth' and ../../../../ifm:type!='Serial'" {
            tailf:xpath-root 3;
          }
          type nd-switch-state;
          default "off";
          description
            "Flag of obtaining the routable address through state-based automatic configuration.";
        }
        leaf o-flag {
          when "../../../../ifm:type!='MEth' and ../../../../ifm:type!='Serial'" {
            tailf:xpath-root 3;
          }
          type nd-switch-state;
          default "off";
          description
            "Flag of setting state-based automatic configuration.";
        }
        leaf ra-halt-flag {
          when "../../../../ifm:type!='MEth'" {
            tailf:xpath-root 3;
          }
          type nd-switch-state;
          default "on";
          description
            "To suppress the advertisement of RA packets.";
        }
        leaf max-interval {
          when "../../../../ifm:type!='MEth'" {
            tailf:xpath-root 3;
          }
          type uint32 {
            range "4..1800";
          }
          units "s";
          default "600";
          description
            "The Maximum interval between periodic RA packets sent on this interface.";
        }
        leaf ra-lifetime {
          when "../../../../ifm:type!='MEth'" {
            tailf:xpath-root 3;
          }
          type uint32 {
            range "0|4..9000";
          }
          units "s";
          must '../ra-lifetime = 0 or (../ra-lifetime != 0 and ../ra-lifetime >= ../max-interval)' {
            tailf:xpath-root 3;
          }
          description
            "TTL of RA packets. If the value is 0, it implies that this node is not a router. And the value from 1 to 3 is invalid.";
        }
        leaf ra-preference {
          when "../../../../ifm:type!='MEth'" {
            tailf:xpath-root 3;
          }
          type nd-route-preference;
          default "medium";
          description
            "RA router preference.";
        }
        leaf ra-prefix-flag {
          when "../../../../ifm:type!='MEth'" {
            tailf:xpath-root 3;
          }
          type nd-switch-state;
          default "on";
          description
            "Flag of RA packet carry prefix information.";
        }
        leaf ra-mtu-flag {
          when "../../../../ifm:type!='MEth'" {
            tailf:xpath-root 3;
          }
          type nd-switch-state;
          default "on";
          description
            "Flag of RA packet carry MTU option.";
        }
        leaf strict-flag {
          when "../../../../ifm:type!='Mp-group' and ../../../../ifm:type!='Serial'" {
            tailf:xpath-root 3;
          }
          type boolean;
          default "false";
          description
            "Enable/disable strict security mode.";
        }
        leaf ts-fuzz-factor {
          when "../../../../ifm:type!='Serial'" {
            tailf:xpath-root 3;
          }
          type uint16 {
            range "0..1000";
          }
          units "s";
          default "1";
          description
            "Fuzz factor for timestamp option.";
        }
        leaf ts-clock-drift {
          when "../../../../ifm:type!='Serial'" {
            tailf:xpath-root 3;
          }
          type uint8 {
            range "0..100";
          }
          default "1";
          description
            "Drift for timestamp option.";
        }
        leaf ts-delta {
          when "../../../../ifm:type!='Serial'" {
            tailf:xpath-root 3;
          }
          type uint16 {
            range "0..1000";
          }
          units "s";
          default "300";
          description
            "Delta for timestamp option.";
        }
        leaf rsa-min-key-len {
          when "../../../../ifm:type!='Serial'" {
            tailf:xpath-root 3;
          }
          type uint16 {
            range "384..3072";
          }
          units "bit";
          must '(../rsa-min-key-len<=../rsa-max-key-len)' {
            tailf:xpath-root 3;
          }
          default "512";
          description
            "The minimum length of acceptable RSA key pair.";
        }
        leaf rsa-max-key-len {
          when "../../../../ifm:type!='Serial'" {
            tailf:xpath-root 3;
          }
          type uint16 {
            range "384..3072";
          }
          units "bit";
          default "2048";
          description
            "The maximum length of acceptable RSA key pair.";
        }
        leaf stale-time {
          when "../../../../ifm:type!='Ip-Trunk' and ../../../../ifm:type!='Pos' and ../../../../ifm:type!='Mp-group' and ../../../../ifm:type!='Serial'" {
            tailf:xpath-root 3;
          }
          type uint32 {
            range "60..172800";
          }
          units "s";
          description
            "Aging time of the stale state.";
        }
        leaf collect-host-flag {
          when "../../../../ifm:type='Vbdif'" {
            tailf:xpath-root 3;
          }
          type nd-switch-state;
          default "off";
          description
            "Flag of collecting host Information.";
        }
        leaf generate-rd-enable {
          when "../../../../ifm:type='Vbdif'" {
            tailf:xpath-root 3;
          }
          type nd-switch-state;
          default "off";
          description
            "Flag of generating redirect ND table.";
        }
        leaf nud-interval {
          when "../../../../ifm:type!='Ip-Trunk' and ../../../../ifm:type!='Pos' and ../../../../ifm:type!='Mp-group' and ../../../../ifm:type!='Serial'" {
            tailf:xpath-root 3;
          }
          type uint32 {
            range "1000..4294967295";
          }
          units "ms";
          default "5000";
          description
            "ND entries NUD interval.";
        }
        leaf hop-limit {
          type uint8 {
            range "0..255";
          }
          description
            "IPv6 packet hop limit.";
        }
        leaf link-down-trigger-del-flag {
          when "../../../../ifm:type='Vlanif'" {
            tailf:xpath-root 3;
          }
          type nd-switch-state;
          default "off";
          description
            "Flag of link down trigger fast deletion of ND entries.";
        }
      }
      container proxys {
        when "../../../ifm:type!='MEth' and ../../../ifm:type!='Ip-Trunk' and ../../../ifm:type!='Serial' and ../../../ifm:type!='Pos' and ../../../ifm:type!='Mp-group'" {
          tailf:xpath-root 3;
        }
        description
          "Configure list of ND proxy.";
        leaf route-proxy {
          when "../../../../ifm:type!='PW-VE'" {
            tailf:xpath-root 3;
          }
          type nd-switch-state;
          default "off";
          description
            "Router proxy.";
        }
        leaf inner-vlan-proxy {
          when "(../../../../ifm:class='sub-interface' and ../../../../ifm:type!='PW-VE') or ../../../../ifm:type='Vlanif'" {
            tailf:xpath-root 3;
          }
          type nd-switch-state;
          default "off";
          description
            "InnerVLAN proxy.";
        }
        leaf inter-vlan-proxy {
          when "(../../../../ifm:class='sub-interface' and ../../../../ifm:type!='PW-VE') or ../../../../ifm:type='Vlanif'" {
            tailf:xpath-root 3;
          }
          type nd-switch-state;
          default "off";
          description
            "InterVLAN proxy.";
        }
        leaf anyway-proxy {
          type nd-switch-state;
          default "off";
          description
            "Anyway proxy.";
        }
        leaf local-proxy {
          when "../../../../ifm:type='Vbdif'" {
            tailf:xpath-root 3;
          }
          type nd-switch-state;
          default "off";
          description
            "Local proxy.";
        }
      }
      container anti-attack {
        when "../../../ifm:type!='Serial'" {
          tailf:xpath-root 3;
        }
        description
          "Configure ND anti-attack for interface.";
        container receive-rate-limits {
          description
            "List of rate limits for receiving ND packets.";
          list receive-rate-limit {
            key "type";
            description
              "Configure the rate limit for receiving ND packet or ND miss.";
            leaf type {
              type nd-pkt-evt-type;
              description
                "ND packet type or ND miss.";
            }
            leaf value {
              type uint16 {
                range "0..5000";
              }
              units "pps";
              mandatory true;
              description
                "Rate limit of receiving ND packet or ND miss.";
            }
          }
        }
        container source-ip-receive {
          description
            "Configure the ND anti-attack based on packet or miss source IP address.";
          uses nd-ip-rate-limits-type;
        }
      }
      container static-neighbor {
        description
          "Configure static neighbor entry.";
        container common-ifs {
          when "../../../../ifm:type!='Vlanif' and ../../../../ifm:type!='Vbdif'" {
            tailf:xpath-root 3;
          }
          description
            "List of static neighbor entry on common interface.";
          list common-if {
            key "ipv6-addr";
            description
              "Configure static neighbor entry on common interface.";
            leaf ipv6-addr {
              type inet:ipv6-address-no-zone;
              description
                "IPv6 address of a static neighbor entry.";
            }
            leaf mac-addr {
              type pub-type:mac-address;
              mandatory true;
              description
                "MAC address.";
            }
          }
        }
        container dot1q-termination-ifs {
          when '../../../../ethernet:ethernet/ethernet:l3-sub-interface/ethernet:dot1q-termination' {
            tailf:xpath-root 3;
          }
          description
            "List of static neighbor entry on dot1q termination interface.";
          list dot1q-termination-if {
            key "ipv6-addr";
            description
              "Configure static neighbor entry on dot1q termination interface.";
            leaf ipv6-addr {
              type inet:ipv6-address-no-zone;
              description
                "IPv6 address of a static neighbor entry.";
            }
            leaf mac-addr {
              type pub-type:mac-address {
                pattern '[0-9a-fA-F][0|2|4|6|8|aA|cC|eE][0-9a-fA-F]{2}(-[0-9a-fA-F]{4}){2}';
              }
              mandatory true;
              description
                "MAC address.";
            }
            leaf pe-vlan {
              type uint16 {
                range "1..4094";
              }
              mandatory true;
              description
                "Outer VLAN tag.";
            }
          }
        }
        container qinq-termination-ifs {
          when '../../../../ethernet:ethernet/ethernet:l3-sub-interface/ethernet:qinq-termination' {
            tailf:xpath-root 3;
          }
          description
            "List of static neighbor entry on qinq termination interface.";
          list qinq-termination-if {
            key "ipv6-addr";
            description
              "Configure static neighbor entry on qinq termination interface.";
            leaf ipv6-addr {
              type inet:ipv6-address-no-zone;
              description
                "IPv6 address of a static neighbor entry.";
            }
            leaf mac-addr {
              type pub-type:mac-address {
                pattern '[0-9a-fA-F][0|2|4|6|8|aA|cC|eE][0-9a-fA-F]{2}(-[0-9a-fA-F]{4}){2}';
              }
              mandatory true;
              description
                "MAC address.";
            }
            leaf pe-vlan {
              type uint16 {
                range "1..4094";
              }
              mandatory true;
              description
                "Outer VLAN tag.";
            }
            leaf ce-vlan {
              type uint16 {
                range "1..4094";
              }
              mandatory true;
              description
                "Inner VLAN tag.";
            }
          }
        }
        container vlan-ifs {
          when "../../../../ifm:type='Vlanif'" {
            tailf:xpath-root 3;
          }
          description
            "List of static neighbor entry on VLAN interface.";
          list vlan-if {
            key "ipv6-addr";
            description
              "Configure static neighbor entry on VLAN interface.";
            leaf ipv6-addr {
              type inet:ipv6-address-no-zone;
              description
                "IPv6 address of a static neighbor entry.";
            }
            leaf mac-addr {
              type pub-type:mac-address {
                pattern '[0-9a-fA-F][0|2|4|6|8|aA|cC|eE][0-9a-fA-F]{2}(-[0-9a-fA-F]{4}){2}';
              }
              mandatory true;
              description
                "MAC address.";
            }
            leaf vlan-id {
              type uint16 {
                range "1..4094";
              }
              description
                "VLAN ID.";
              ext:support-filter "true";
            }
            leaf port-name {
              type leafref {
                path "/ncs:devices/ncs:device/ncs:config/ifm:ifm/ifm:interfaces/ifm:interface/ifm:name" {
                  tailf:xpath-root 3;
                }
              }
              mandatory true;
              description
                "Port name.";
            }
          }
        }
      }
      container send-rate-limit {
        when "../../../ifm:type!='Serial'" {
          tailf:xpath-root 3;
        }
        description
          "Configure ND send rate limit for interface.";
        container packet-rate-limits {
          description
            "List of ND packet sending rate limits.";
          list packet-rate-limit {
            key "packet-type";
            description
              "Configure the rate limit of sending ND packet.";
            leaf packet-type {
              type nd-pkt-type;
              must "not((../packet-type = 'RA') and (../../../../../../ifm:type='MEth'))" {
                tailf:xpath-root 3;
              }
              description
                "ND packet type.";
            }
            leaf value {
              type uint16 {
                range "1..10240";
              }
              units "pps";
              must "((../packet-type = 'NA') and (../value <= 10240)) or (not(../packet-type = 'NA') and (../value <= 1000))" {
                tailf:xpath-root 3;
              }
              mandatory true;
              description
                "Rate limit of sending ND packet, when the packet type is NS, RS or RA, the maximum value is 1000.";
            }
          }
        }
        container multicast-rate-limits {
          description
            "List of ND multicast packet sending rate limits.";
          list multicast-rate-limit {
            key "packet-type";
            description
              "Configure the rate limit of sending ND multicast packet.";
            leaf packet-type {
              type nd-pkt-type;
              must "not((../packet-type = 'RA') and (../../../../../../ifm:type='MEth'))" {
                tailf:xpath-root 3;
              }
              description
                "ND packet type.";
            }
            leaf value {
              type uint16 {
                range "1..10240";
              }
              units "pps";
              must "((../packet-type = 'NA') and (../value <= 10240)) or (not(../packet-type = 'NA') and (../value <= 1000))" {
                tailf:xpath-root 3;
              }
              mandatory true;
              description
                "Rate limit of sending ND multicast packet, when the packet type is NS, RS or RA, the maximum value is 1000.";
            }
          }
        }
      }
      container ra-property {
        when "../../../ifm:type!='MEth'" {
          tailf:xpath-root 3;
        }
        description
          "Configure ND RA configurations under the interface.";
        container ra-control {
          description
            "Configure ND RA configurations.";
          leaf unicast-send {
            type nd-switch-state;
            default "off";
            description
              "Flag of Sending RA unicast packet when receive a RS packet.";
          }
        }
        container ra-routes {
          description
            "List of RA route information option.";
          list ra-route {
            key "prefix-addr prefix-len";
            description
              "Configure RA route information option.";
            leaf prefix-addr {
              type inet:ipv6-address-no-zone;
              description
                "The IPv6 prefix address of RA route information.";
            }
            leaf prefix-len {
              type uint32 {
                range "0..128";
              }
              description
                "The prefix length of RA route information.";
            }
            leaf lifetime {
              type uint32;
              units "s";
              mandatory true;
              description
                "The lifetime of RA route information.";
            }
            leaf preference {
              type nd-route-preference;
              default "medium";
              description
                "The preference of RA route information.";
            }
          }
        }
        container dns-server-addresses {
          description
            "List of DNS server address.";
          list dns-server-address {
            key "ipv6-address";
            description
              "Configure the DNS server address.";
            leaf ipv6-address {
              type inet:ipv6-address-no-zone;
              description
                "Address of IPv6 recursive DNS server. The address cannot be a multicast address or an unspecified address.";
            }
            leaf lifetime {
              type uint32 {
                range "1..max";
              }
              units "s";
              description
                "The maximum time over which this RDNSS address may be used for name resolution.";
            }
          }
        }
        container dns-search-suffixes {
          description
            "List of DNS search list.";
          list dns-search-suffix {
            key "suffix-name";
            description
              "Configure DNS suffix name.";
            leaf suffix-name {
              type string {
                length "1..63";
              }
              ext:case-sensitivity "lower-or-upper";
              description
                "Domain name of DNS search list.";
            }
            leaf lifetime {
              type uint32 {
                range "1..max";
              }
              units "s";
              description
                "The maximum time over which this DNSSL domain name may be used for name resolution.";
            }
          }
        }
      }
      container strict-prefix-learn {
        when "../../../ifm:type!='Vlanif' and ../../../ifm:type!='Vbdif' and ../../../ifm:type!='Global-VE'" {
          tailf:xpath-root 3;
        }
        description
          "Configure strict prefix learning of interface.";
        leaf switch {
          type nd-switch-state;
          description
            "ND prefix learning strict.";
        }
      }
    }
  }
  augment "/ncs:devices/ncs:template/ncs:ned-id/ncs:config/ifm:ifm/ifm:interfaces/ifm:interface" {
    description
      "List of ND configurations under ifm interface.";
    container nd-dyn-nb-limit {
      description
        "Configure the maximum of limitation of dynamic neighbor.";
      container vlan-limits {
        description
          "List of the maximum of limitation of dynamic neighbor based on VLAN.";
        list vlan-limit {
          // NCS patched for predictable order
          ordered-by user;
          key "vlan-id";
          description
            "Configure the maximum of limitation of dynamic neighbor based on VLAN.";
          leaf vlan-id {
            type string;
            description
              "VLAN ID.";
          }
          leaf max-dyn-nb-num {
            type string;
            // NCS drop mandatory statement
            description
              "The maximum of limitation of dynamic neighbor.";
          }
        }
      }
    }
  }
  augment "/ncs:devices/ncs:device/ncs:live-status/ifm:ifm/ifm:interfaces/ifm:interface" {
    description
      "List of ND configurations under ifm interface.";
    container nd-dyn-nb-limit {
      tailf:ncs-device-type "netconf";
      tailf:display-when "not(../../../../../ncs:module) or ../../../../../ncs:module[ncs:name='huawei-ipv6-nd'] or (../../../../../ncs:live-status-protocol[not(ncs:capability)]) or (../../../../../ncs:live-status-protocol/ncs:capability/ncs:module[.='huawei-ipv6-nd'])";
      description
        "Configure the maximum of limitation of dynamic neighbor.";
      container vlan-limits {
        description
          "List of the maximum of limitation of dynamic neighbor based on VLAN.";
        list vlan-limit {
          key "vlan-id";
          description
            "Configure the maximum of limitation of dynamic neighbor based on VLAN.";
          leaf vlan-id {
            type uint16 {
              range "1..4094";
            }
            description
              "VLAN ID.";
          }
          leaf max-dyn-nb-num {
            type uint32 {
              range "0..65536";
            }
            // NCS drop mandatory statement
            description
              "The maximum of limitation of dynamic neighbor.";
          }
        }
      }
    }
  }
  augment "/ncs:devices/ncs:device/ncs:config/ifm:ifm/ifm:interfaces/ifm:interface" {
    description
      "List of ND configurations under ifm interface.";
    container nd-dyn-nb-limit {
      tailf:ncs-device-type "netconf";
      tailf:display-when "not(../../../../../ncs:module) or ../../../../../ncs:module[ncs:name='huawei-ipv6-nd']";
      description
        "Configure the maximum of limitation of dynamic neighbor.";
      container vlan-limits {
        description
          "List of the maximum of limitation of dynamic neighbor based on VLAN.";
        list vlan-limit {
          key "vlan-id";
          description
            "Configure the maximum of limitation of dynamic neighbor based on VLAN.";
          leaf vlan-id {
            type uint16 {
              range "1..4094";
            }
            description
              "VLAN ID.";
          }
          leaf max-dyn-nb-num {
            type uint32 {
              range "0..65536";
            }
            mandatory true;
            description
              "The maximum of limitation of dynamic neighbor.";
          }
        }
      }
    }
  }
}
