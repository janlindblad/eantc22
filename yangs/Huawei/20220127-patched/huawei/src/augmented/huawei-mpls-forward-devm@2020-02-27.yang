module huawei-mpls-forward-devm {
  // Generated by yanger -t ncs
  tailf:mount-id "huawei-nc-1.0:huawei-nc-1.0";
  tailf:ncs-device-type "netconf";

  yang-version 1;
  namespace "urn:huawei:yang:huawei-mpls-forward-devm";
  prefix mpls-forward-devm;

  import huawei-devm {
    prefix devm;
  }
  import huawei-loadbalance {
    prefix loadbalance;
  }
  import huawei-extension {
    prefix ext;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "MPLS forward for DEVM.";

  revision 2020-02-27 {
    description
      "The type of some nodes is fixed.";
    reference "Huawei private.";
  }
  revision 2019-03-27 {
    description
      "Init revision.";
    reference "Huawei private.";
  }
  ext:task-name "forwarding";

  typedef ncs_template_hash-cfg-flag {
    type string;
    description
      "Hash configuration flag.";
  }

  typedef ncs_template_enable-flag {
    type string;
    description
      "Enable flag type.";
  }

  typedef ncs_template_check-mode {
    type string;
    description
      "Check mode.";
  }

  typedef ncs_template_hash-type {
    type string;
    description
      "Hash type.";
  }

  typedef ncs_rpc_notif_hash-cfg-flag {
    type enumeration {
      enum "payload-header" {
        value 64;
        description
          "Hashed based on payload-header.";
      }
      enum "label" {
        value 192;
        description
          "Hashed based on label.";
      }
      enum "ip" {
        value 160;
        description
          "Hashed based on label or payload-header.";
      }
      enum "ip-tos" {
        value 193;
        description
          "Hashed based on label or TOS.";
      }
      enum "mac" {
        value 196;
        description
          "Hashed based on label or MAC.";
      }
    }
    description
      "Hash configuration flag.";
  }

  typedef ncs_rpc_notif_enable-flag {
    type enumeration {
      enum "enable" {
        value 1;
        description
          "The CFG is enabled.";
      }
      enum "disable" {
        value 0;
        description
          "The CFG is disabled.";
      }
    }
    description
      "Enable flag type.";
  }

  typedef ncs_rpc_notif_check-mode {
    type enumeration {
      enum "ip" {
        value 291;
        description
          "The check mode is IP.";
      }
      enum "label-contained-length" {
        value 292;
        description
          "The check mode is label-contained-length.";
      }
    }
    description
      "Check mode.";
  }

  typedef ncs_rpc_notif_hash-type {
    type enumeration {
      enum "flow" {
        value 194;
        description
          "Load balance based on flow.";
      }
      enum "packet" {
        value 195;
        description
          "Load balance based on packet.";
      }
    }
    description
      "Hash type.";
  }

  typedef live_ncs_hash-cfg-flag {
    type enumeration {
      enum "payload-header" {
        value 64;
        description
          "Hashed based on payload-header.";
      }
      enum "label" {
        value 192;
        description
          "Hashed based on label.";
      }
      enum "ip" {
        value 160;
        description
          "Hashed based on label or payload-header.";
      }
      enum "ip-tos" {
        value 193;
        description
          "Hashed based on label or TOS.";
      }
      enum "mac" {
        value 196;
        description
          "Hashed based on label or MAC.";
      }
    }
    description
      "Hash configuration flag.";
  }

  typedef live_ncs_enable-flag {
    type enumeration {
      enum "enable" {
        value 1;
        description
          "The CFG is enabled.";
      }
      enum "disable" {
        value 0;
        description
          "The CFG is disabled.";
      }
    }
    description
      "Enable flag type.";
  }

  typedef live_ncs_check-mode {
    type enumeration {
      enum "ip" {
        value 291;
        description
          "The check mode is IP.";
      }
      enum "label-contained-length" {
        value 292;
        description
          "The check mode is label-contained-length.";
      }
    }
    description
      "Check mode.";
  }

  typedef live_ncs_hash-type {
    type enumeration {
      enum "flow" {
        value 194;
        description
          "Load balance based on flow.";
      }
      enum "packet" {
        value 195;
        description
          "Load balance based on packet.";
      }
    }
    description
      "Hash type.";
  }

  typedef hash-cfg-flag {
    type enumeration {
      enum "payload-header" {
        value 64;
        description
          "Hashed based on payload-header.";
      }
      enum "label" {
        value 192;
        description
          "Hashed based on label.";
      }
      enum "ip" {
        value 160;
        description
          "Hashed based on label or payload-header.";
      }
      enum "ip-tos" {
        value 193;
        description
          "Hashed based on label or TOS.";
      }
      enum "mac" {
        value 196;
        description
          "Hashed based on label or MAC.";
      }
    }
    description
      "Hash configuration flag.";
  }

  typedef enable-flag {
    type enumeration {
      enum "enable" {
        value 1;
        description
          "The CFG is enabled.";
      }
      enum "disable" {
        value 0;
        description
          "The CFG is disabled.";
      }
    }
    description
      "Enable flag type.";
  }

  typedef check-mode {
    type enumeration {
      enum "ip" {
        value 291;
        description
          "The check mode is IP.";
      }
      enum "label-contained-length" {
        value 292;
        description
          "The check mode is label-contained-length.";
      }
    }
    description
      "Check mode.";
  }

  typedef hash-type {
    type enumeration {
      enum "flow" {
        value 194;
        description
          "Load balance based on flow.";
      }
      enum "packet" {
        value 195;
        description
          "Load balance based on packet.";
      }
    }
    description
      "Hash type.";
  }

  augment "/ncs:devices/ncs:template/ncs:ned-id/ncs:config/devm:devm/devm:lpu-boards/devm:lpu-board" {
    description
      "MPLS forward configuration to the DEVM module.";
    container mpls-forward {
      description
        "Configure MPLS forward.";
      container mpls-hash-mode {
        description
          "Configure MPLS hash mode.";
        leaf hashcfg {
          type ncs_template_hash-cfg-flag;
          // NCS drop default statement
          description
            "MPLS hash mode value.";
        }
      }
      container mplsfrags {
        description
          "Configure dynamic load balance.";
        leaf mplsfrag-enable {
          type ncs_template_enable-flag;
          // NCS drop default statement
          description
            "MPLS fragment enable value.";
        }
      }
      container mpls-load-ctrwords {
        description
          "Configure MPLS load balance control word disable.";
        leaf mplsload-ctrword-disable {
          type ncs_template_enable-flag;
          // NCS drop default statement
          description
            "MPLS load balance control word disable value.";
        }
      }
    }
  }
  augment "/ncs:devices/ncs:device/ncs:live-status/devm:devm/devm:lpu-boards/devm:lpu-board" {
    description
      "MPLS forward configuration to the DEVM module.";
    container mpls-forward {
      tailf:ncs-device-type "netconf";
      tailf:display-when "not(../../../../../ncs:module) or ../../../../../ncs:module[ncs:name='huawei-mpls-forward-devm'] or (../../../../../ncs:live-status-protocol[not(ncs:capability)]) or (../../../../../ncs:live-status-protocol/ncs:capability/ncs:module[.='huawei-mpls-forward-devm'])";
      description
        "Configure MPLS forward.";
      container mpls-hash-mode {
        description
          "Configure MPLS hash mode.";
        leaf hashcfg {
          type live_ncs_hash-cfg-flag;
          // NCS drop default statement
          description
            "MPLS hash mode value.";
        }
      }
      container mplsfrags {
        description
          "Configure dynamic load balance.";
        leaf mplsfrag-enable {
          type live_ncs_enable-flag;
          // NCS drop default statement
          description
            "MPLS fragment enable value.";
        }
      }
      container mpls-load-ctrwords {
        description
          "Configure MPLS load balance control word disable.";
        leaf mplsload-ctrword-disable {
          type live_ncs_enable-flag;
          // NCS drop default statement
          description
            "MPLS load balance control word disable value.";
        }
      }
    }
  }
  augment "/ncs:devices/ncs:device/ncs:config/devm:devm/devm:lpu-boards/devm:lpu-board" {
    description
      "MPLS forward configuration to the DEVM module.";
    container mpls-forward {
      tailf:ncs-device-type "netconf";
      tailf:display-when "not(../../../../../ncs:module) or ../../../../../ncs:module[ncs:name='huawei-mpls-forward-devm']";
      description
        "Configure MPLS forward.";
      container mpls-hash-mode {
        description
          "Configure MPLS hash mode.";
        leaf hashcfg {
          type hash-cfg-flag;
          default "ip";
          description
            "MPLS hash mode value.";
        }
      }
      container mplsfrags {
        description
          "Configure dynamic load balance.";
        leaf mplsfrag-enable {
          type enable-flag;
          default "disable";
          description
            "MPLS fragment enable value.";
        }
      }
      container mpls-load-ctrwords {
        description
          "Configure MPLS load balance control word disable.";
        leaf mplsload-ctrword-disable {
          type enable-flag;
          default "disable";
          description
            "MPLS load balance control word disable value.";
        }
      }
    }
  }
  augment "/ncs:devices/ncs:template/ncs:ned-id/ncs:config/devm:devm/devm:mpu-boards/devm:mpu-board" {
    description
      "MPLS forward configuration to the DEVM module.";
    container mpls-forward {
      description
        "Configure MPLS forward.";
      container mpls-hash-mode {
        description
          "Configure MPLS hash mode.";
        leaf hashcfg {
          type ncs_template_hash-cfg-flag;
          // NCS drop default statement
          description
            "MPLS hash mode value.";
        }
      }
      container mplsfrags {
        description
          "Configure dynamic load balance configuration.";
        leaf mplsfrag-enable {
          type ncs_template_enable-flag;
          // NCS drop default statement
          description
            "MPLS fragment enable value.";
        }
      }
      container mpls-load-ctrwords {
        description
          "Configure MPLS load balance control word disable.";
        leaf mplsload-ctrword-disable {
          type ncs_template_enable-flag;
          // NCS drop default statement
          description
            "MPLS load balance control word disable value.";
        }
      }
    }
  }
  augment "/ncs:devices/ncs:device/ncs:live-status/devm:devm/devm:mpu-boards/devm:mpu-board" {
    description
      "MPLS forward configuration to the DEVM module.";
    container mpls-forward {
      tailf:ncs-device-type "netconf";
      tailf:display-when "not(../../../../../ncs:module) or ../../../../../ncs:module[ncs:name='huawei-mpls-forward-devm'] or (../../../../../ncs:live-status-protocol[not(ncs:capability)]) or (../../../../../ncs:live-status-protocol/ncs:capability/ncs:module[.='huawei-mpls-forward-devm'])";
      description
        "Configure MPLS forward.";
      container mpls-hash-mode {
        description
          "Configure MPLS hash mode.";
        leaf hashcfg {
          type live_ncs_hash-cfg-flag;
          // NCS drop default statement
          description
            "MPLS hash mode value.";
        }
      }
      container mplsfrags {
        description
          "Configure dynamic load balance configuration.";
        leaf mplsfrag-enable {
          type live_ncs_enable-flag;
          // NCS drop default statement
          description
            "MPLS fragment enable value.";
        }
      }
      container mpls-load-ctrwords {
        description
          "Configure MPLS load balance control word disable.";
        leaf mplsload-ctrword-disable {
          type live_ncs_enable-flag;
          // NCS drop default statement
          description
            "MPLS load balance control word disable value.";
        }
      }
    }
  }
  augment "/ncs:devices/ncs:device/ncs:config/devm:devm/devm:mpu-boards/devm:mpu-board" {
    description
      "MPLS forward configuration to the DEVM module.";
    container mpls-forward {
      tailf:ncs-device-type "netconf";
      tailf:display-when "not(../../../../../ncs:module) or ../../../../../ncs:module[ncs:name='huawei-mpls-forward-devm']";
      description
        "Configure MPLS forward.";
      container mpls-hash-mode {
        description
          "Configure MPLS hash mode.";
        leaf hashcfg {
          type hash-cfg-flag;
          default "ip";
          description
            "MPLS hash mode value.";
        }
      }
      container mplsfrags {
        description
          "Configure dynamic load balance configuration.";
        leaf mplsfrag-enable {
          type enable-flag;
          default "disable";
          description
            "MPLS fragment enable value.";
        }
      }
      container mpls-load-ctrwords {
        description
          "Configure MPLS load balance control word disable.";
        leaf mplsload-ctrword-disable {
          type enable-flag;
          default "disable";
          description
            "MPLS load balance control word disable value.";
        }
      }
    }
  }
  augment "/ncs:devices/ncs:template/ncs:ned-id/ncs:config/loadbalance:loadbalance" {
    description
      "MPLS forward configuration to the load balance module.";
    container mpls-hashpacket {
      description
        "Configure load balance based on packet.";
      list hashpacket {
        // NCS patched for predictable order
        ordered-by user;
        key "slotid";
        description
          "Configure load balance based on packet.";
        ext:generated-by "system" {
          description
            "The all instances are generated automatically.";
        }
        ext:operation-exclude "create" {
          description
            "The all instances cannot be created.";
        }
        leaf slotid {
          type string;
          description
            "Slot ID.";
        }
        leaf hash-type {
          type ncs_template_hash-type;
          // NCS drop default statement
          description
            "Load balance mode.";
          ext:support-filter "true";
        }
      }
    }
    container mpls-intfmtu {
      description
        "Configure interface MTU check mode.";
      list intfmtu {
        // NCS patched for predictable order
        ordered-by user;
        key "slotid";
        description
          "Configure interface MTU check mode.";
        ext:generated-by "system" {
          description
            "The all instances are generated automatically.";
        }
        ext:operation-exclude "create" {
          description
            "The all instances cannot be created.";
        }
        leaf slotid {
          type string;
          description
            "Slot ID.";
        }
        leaf chkmode {
          type ncs_template_check-mode;
          // NCS drop mandatory statement
          description
            "Check mode configuration.";
          ext:support-filter "true";
        }
      }
    }
  }
  augment "/ncs:devices/ncs:device/ncs:live-status/loadbalance:loadbalance" {
    description
      "MPLS forward configuration to the load balance module.";
    container mpls-hashpacket {
      tailf:ncs-device-type "netconf";
      tailf:display-when "not(../../../ncs:module) or ../../../ncs:module[ncs:name='huawei-mpls-forward-devm'] or (../../../ncs:live-status-protocol[not(ncs:capability)]) or (../../../ncs:live-status-protocol/ncs:capability/ncs:module[.='huawei-mpls-forward-devm'])";
      description
        "Configure load balance based on packet.";
      list hashpacket {
        key "slotid";
        description
          "Configure load balance based on packet.";
        ext:generated-by "system" {
          description
            "The all instances are generated automatically.";
        }
        ext:operation-exclude "create" {
          description
            "The all instances cannot be created.";
        }
        leaf slotid {
          type string {
            length "1..32";
          }
          description
            "Slot ID.";
        }
        leaf hash-type {
          type live_ncs_hash-type;
          // NCS drop default statement
          description
            "Load balance mode.";
          ext:support-filter "true";
        }
      }
    }
    container mpls-intfmtu {
      tailf:ncs-device-type "netconf";
      tailf:display-when "not(../../../ncs:module) or ../../../ncs:module[ncs:name='huawei-mpls-forward-devm'] or (../../../ncs:live-status-protocol[not(ncs:capability)]) or (../../../ncs:live-status-protocol/ncs:capability/ncs:module[.='huawei-mpls-forward-devm'])";
      description
        "Configure interface MTU check mode.";
      list intfmtu {
        key "slotid";
        description
          "Configure interface MTU check mode.";
        ext:generated-by "system" {
          description
            "The all instances are generated automatically.";
        }
        ext:operation-exclude "create" {
          description
            "The all instances cannot be created.";
        }
        leaf slotid {
          type string {
            length "1..32";
          }
          description
            "Slot ID.";
        }
        leaf chkmode {
          type live_ncs_check-mode;
          // NCS drop mandatory statement
          description
            "Check mode configuration.";
          ext:support-filter "true";
        }
      }
    }
  }
  augment "/ncs:devices/ncs:device/ncs:config/loadbalance:loadbalance" {
    description
      "MPLS forward configuration to the load balance module.";
    container mpls-hashpacket {
      tailf:ncs-device-type "netconf";
      tailf:display-when "not(../../../ncs:module) or ../../../ncs:module[ncs:name='huawei-mpls-forward-devm']";
      description
        "Configure load balance based on packet.";
      list hashpacket {
        key "slotid";
        description
          "Configure load balance based on packet.";
        ext:generated-by "system" {
          description
            "The all instances are generated automatically.";
        }
        ext:operation-exclude "create" {
          description
            "The all instances cannot be created.";
        }
        leaf slotid {
          type string {
            length "1..32";
          }
          description
            "Slot ID.";
        }
        leaf hash-type {
          type hash-type;
          default "flow";
          description
            "Load balance mode.";
          ext:support-filter "true";
        }
      }
    }
    container mpls-intfmtu {
      tailf:ncs-device-type "netconf";
      tailf:display-when "not(../../../ncs:module) or ../../../ncs:module[ncs:name='huawei-mpls-forward-devm']";
      description
        "Configure interface MTU check mode.";
      list intfmtu {
        key "slotid";
        description
          "Configure interface MTU check mode.";
        ext:generated-by "system" {
          description
            "The all instances are generated automatically.";
        }
        ext:operation-exclude "create" {
          description
            "The all instances cannot be created.";
        }
        leaf slotid {
          type string {
            length "1..32";
          }
          description
            "Slot ID.";
        }
        leaf chkmode {
          type check-mode;
          mandatory true;
          description
            "Check mode configuration.";
          ext:support-filter "true";
        }
      }
    }
  }
}
