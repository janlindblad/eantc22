module huawei-netconf-sync-notif {
  // Generated by yanger -t ncs
  tailf:mount-id "huawei-nc-1.0:huawei-nc-1.0";
  tailf:ncs-device-type "netconf";

  yang-version 1;
  namespace "urn:huawei:yang:huawei-netconf-sync-notif";
  prefix netconf-sync-notif;

  import huawei-extension {
    prefix ext;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "The NETCONF sync notification nodes are defined in this file.";
  reference "Huawei private";

  revision 2021-03-05 {
    description
      "Initial revision.";
    reference "Huawei private";
  }
  ext:task-name "netconf";

  augment "/ncs:devices/ncs:device/ncs:notifications/ncs:received-notifications/ncs:notification/ncs:data" {
    container netconf-mda-resource-change {
      presence "";
      config false;
      description
        "Generated when any kind of MDA resource file changed. Then the
         MDA resource package files will be regenerated.";
      leaf resource-type {
        type bits {
          bit yang;
          bit yang-patch;
          bit yang-zh-cn;
          bit yang-zh-cn-patch;
          bit alarm;
          bit alarm-patch;
          bit panel;
          bit panel-patch;
        }
        // NCS drop mandatory statement
        description
          "The type of MDA resource files that changed.";
      }
    }
  }
  augment "/ncs:devices/ncs:device/ncs:netconf-notifications/ncs:received-notifications/ncs:notification/ncs:data" {
    container netconf-mda-resource-change {
      presence "";
      config false;
      description
        "Generated when any kind of MDA resource file changed. Then the
         MDA resource package files will be regenerated.";
      leaf resource-type {
        type bits {
          bit yang;
          bit yang-patch;
          bit yang-zh-cn;
          bit yang-zh-cn-patch;
          bit alarm;
          bit alarm-patch;
          bit panel;
          bit panel-patch;
        }
        // NCS drop mandatory statement
        description
          "The type of MDA resource files that changed.";
      }
    }
  }
}
