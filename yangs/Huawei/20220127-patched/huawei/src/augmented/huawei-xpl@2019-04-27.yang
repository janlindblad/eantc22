module huawei-xpl {
  // Generated by yanger -t ncs
  tailf:mount-id "huawei-nc-1.0:huawei-nc-1.0";
  tailf:ncs-device-type "netconf";

  yang-version 1;
  namespace "urn:huawei:yang:huawei-xpl";
  prefix xpl;

  import huawei-ifm {
    prefix ifm;
  }
  import huawei-extension {
    prefix ext;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Extended router policy language.";

  revision 2019-04-27 {
    description
      "Initial revision.";
    reference "Huawei private.";
  }
  ext:task-name "route-base";

  typedef ncs_template_xpl-filter-name {
    type string;
    description
      "XPL route-filter's name.";
  }

  typedef ncs_template_filter-parameter-type {
    type string;
    description
      "XPL route-filter's parameter name.";
  }

  typedef ncs_rpc_notif_xpl-filter-name {
    type string {
      length "1..200";
      pattern '\s*(([0-9a-zA-Z][0-9a-zA-Z\-_\.]{0,200})|([0-9a-zA-Z][0-9a-zA-Z\-_\.]{0,200}[\(](($)?[0-9a-zA-Z][0-9a-zA-Z\-_\.]{0,200})(([,]($)?[0-9a-zA-Z][0-9a-zA-Z\-_\.]{0,200}){0,7})[\)]))\s*';
    }
    description
      "XPL route-filter's name.";
  }

  typedef ncs_rpc_notif_filter-parameter-type {
    type string {
      length "3..1609";
      pattern '(\([^\)]+\))';
    }
    description
      "XPL route-filter's parameter name.";
  }

  typedef live_ncs_xpl-filter-name {
    type string {
      length "1..200";
      pattern '\s*(([0-9a-zA-Z][0-9a-zA-Z\-_\.]{0,200})|([0-9a-zA-Z][0-9a-zA-Z\-_\.]{0,200}[\(](($)?[0-9a-zA-Z][0-9a-zA-Z\-_\.]{0,200})(([,]($)?[0-9a-zA-Z][0-9a-zA-Z\-_\.]{0,200}){0,7})[\)]))\s*';
    }
    description
      "XPL route-filter's name.";
  }

  typedef live_ncs_filter-parameter-type {
    type string {
      length "3..1609";
      pattern '(\([^\)]+\))';
    }
    description
      "XPL route-filter's parameter name.";
  }

  typedef xpl-filter-name {
    type string {
      length "1..200";
      pattern '\s*(([0-9a-zA-Z][0-9a-zA-Z\-_\.]{0,200})|([0-9a-zA-Z][0-9a-zA-Z\-_\.]{0,200}[\(](($)?[0-9a-zA-Z][0-9a-zA-Z\-_\.]{0,200})(([,]($)?[0-9a-zA-Z][0-9a-zA-Z\-_\.]{0,200}){0,7})[\)]))\s*';
    }
    description
      "XPL route-filter's name.";
  }

  typedef filter-parameter-type {
    type string {
      length "3..1609";
      pattern '(\([^\)]+\))';
    }
    description
      "XPL route-filter's parameter name.";
  }

  augment "/ncs:devices/ncs:device/ncs:config" {
    container xpl {
      tailf:ncs-device-type "netconf";
      tailf:display-when "not(../../ncs:module) or ../../ncs:module[ncs:name='huawei-xpl']";
      description
        "Extended router policy language.";
      container global {
        description
          "Configure global variable.";
        leaf content {
          type string {
            length "1..16380";
          }
          description
            "Global variable config.";
        }
      }
      container route-flow-group-lists {
        description
          "List of route flow group.";
        list route-flow-group-list {
          key "name";
          max-elements 65535;
          description
            "Configure of route flow group. A route flow group is used to create a QPPB attribute configuration group to assign a value to the QoS attribute of routes.";
          leaf name {
            type string {
              length "1..200";
              pattern '\s*([0-9a-zA-Z][0-9a-zA-Z\-_\.]{0,200})\s*';
            }
            description
              "Name.";
          }
          leaf content {
            type string {
              length "1..16380";
            }
            mandatory true;
            description
              "List config.";
          }
        }
      }
      container as-path-lists {
        description
          "List of AS_PATH.";
        list as-path-list {
          key "name";
          max-elements 65535;
          description
            "Configure a list of AS_PATH. A group of AS_Path data and can be used by a route-filter to filter BGP routes.";
          leaf name {
            type string {
              length "1..200";
              pattern '\s*([0-9a-zA-Z][0-9a-zA-Z\-_\.]{0,200})\s*';
            }
            description
              "Name.";
          }
          leaf content {
            type string {
              length "1..16380";
            }
            mandatory true;
            description
              "List config.";
          }
        }
      }
      container community-lists {
        description
          "List of community attributes.";
        list community-list {
          key "name";
          max-elements 65535;
          description
            "Configure a list of community attributes.";
          leaf name {
            type string {
              length "1..200";
              pattern '\s*([0-9a-zA-Z][0-9a-zA-Z\-_\.]{0,200})\s*';
            }
            description
              "Name.";
          }
          leaf content {
            type string {
              length "1..16380";
            }
            mandatory true;
            description
              "List config.";
          }
        }
      }
      container ext-community-rt-lists {
        description
          "List of Extcommunity RT Attributes.";
        list ext-community-rt-list {
          key "name";
          max-elements 65535;
          description
            "Configure a list of extcommunity RT attributes.";
          leaf name {
            type string {
              length "1..200";
              pattern '\s*([0-9a-zA-Z][0-9a-zA-Z\-_\.]{0,200})\s*';
            }
            description
              "Name.";
          }
          leaf content {
            type string {
              length "1..16380";
            }
            mandatory true;
            description
              "List config.";
          }
        }
      }
      container ext-community-soo-lists {
        description
          "List of Extcommunity SoO Attributes.";
        list ext-community-soo-list {
          key "name";
          max-elements 65535;
          description
            "Configure a list of extcommunity SoO attributes configuration.";
          leaf name {
            type string {
              length "1..200";
              pattern '\s*([0-9a-zA-Z][0-9a-zA-Z\-_\.]{0,200})\s*';
            }
            description
              "Name.";
          }
          leaf content {
            type string {
              length "1..16380";
            }
            mandatory true;
            description
              "List config.";
          }
        }
      }
      container ipv4-prefix-lists {
        description
          "List of Prefix.";
        list ipv4-prefix-list {
          key "name";
          max-elements 65535;
          description
            "Configure a list of IPv4 prefix.";
          leaf name {
            type string {
              length "1..200";
              pattern '\s*([0-9a-zA-Z][0-9a-zA-Z\-_\.]{0,200})\s*';
            }
            description
              "Name.";
          }
          leaf content {
            type string {
              length "1..16380";
            }
            mandatory true;
            description
              "List config.";
          }
        }
      }
      container ipv6-prefix-lists {
        description
          "List of IPv6 Prefix.";
        list ipv6-prefix-list {
          key "name";
          max-elements 65535;
          description
            "Configure a list of IPv6 prefix.";
          leaf name {
            type string {
              length "1..200";
              pattern '\s*([0-9a-zA-Z][0-9a-zA-Z\-_\.]{0,200})\s*';
            }
            description
              "Name.";
          }
          leaf content {
            type string {
              length "1..16380";
            }
            mandatory true;
            description
              "List config.";
          }
        }
      }
      container rd-lists {
        description
          "List of RD.";
        list rd-list {
          key "name";
          max-elements 65535;
          description
            "Configure a list of RD.";
          leaf name {
            type string {
              length "1..200";
              pattern '\s*([0-9a-zA-Z][0-9a-zA-Z\-_\.]{0,200})\s*';
            }
            description
              "Name.";
          }
          leaf content {
            type string {
              length "1..16380";
            }
            mandatory true;
            description
              "List config.";
          }
        }
      }
      container large-community-lists {
        description
          "List of large community sets.";
        list large-community-list {
          key "name";
          max-elements 65535;
          description
            "Configure a list of large community.";
          leaf name {
            type string {
              length "1..200";
              pattern '\s*([0-9a-zA-Z][0-9a-zA-Z\-_\.]{0,200})\s*';
            }
            description
              "Name.";
          }
          leaf content {
            type string {
              length "1..16380";
            }
            mandatory true;
            description
              "List config.";
          }
        }
      }
      container interface-lists {
        description
          "List of interface.";
        list interface-list {
          key "name";
          max-elements 1000;
          description
            "Configure a list of interface.";
          leaf name {
            type string {
              length "1..200";
              pattern '\s*([0-9a-zA-Z][0-9a-zA-Z\-_\.]{0,200})\s*';
            }
            description
              "Interface list name.";
          }
          container interface-sets {
            description
              "List of interface set. An interface set can be applied to route-filters to filter routes based on outbound interfaces.";
            list interface-set {
              key "interface-name";
              max-elements 256;
              description
                "Specify interface configuration, based on which routes are filtered.";
              leaf interface-name {
                type leafref {
                  path "/ncs:devices/ncs:device/ncs:config/ifm:ifm/ifm:interfaces/ifm:interface/ifm:name" {
                    tailf:xpath-root 3;
                  }
                }
                description
                  "Interface set name.";
              }
            }
          }
        }
      }
      container route-filters {
        description
          "List of extended policies.";
        list route-filter {
          key "name";
          max-elements 15000;
          description
            "Configure a list of extended policy. A route-filter can use its condition clauses to filter routes and use its action clauses to set or modify route attributes of the routes that match the condition clauses.";
          leaf name {
            type xpl-filter-name;
            description
              "Policy name in the format of a string.";
          }
          leaf content {
            type string {
              length "1..16380";
            }
            mandatory true;
            description
              "Policy config.";
          }
        }
      }
    }
  }
  augment "/ncs:devices/ncs:device/ncs:live-status" {
    container xpl {
      tailf:ncs-device-type "netconf";
      tailf:display-when "not(../../ncs:module) or ../../ncs:module[ncs:name='huawei-xpl'] or (../../ncs:live-status-protocol[not(ncs:capability)]) or (../../ncs:live-status-protocol/ncs:capability/ncs:module[.='huawei-xpl'])";
      description
        "Extended router policy language.";
      container global {
        description
          "Configure global variable.";
        leaf content {
          type string {
            length "1..16380";
          }
          description
            "Global variable config.";
        }
      }
      container route-flow-group-lists {
        description
          "List of route flow group.";
        list route-flow-group-list {
          key "name";
          // NCS drop max-elements statement
          description
            "Configure of route flow group. A route flow group is used to create a QPPB attribute configuration group to assign a value to the QoS attribute of routes.";
          leaf name {
            type string {
              length "1..200";
              pattern '\s*([0-9a-zA-Z][0-9a-zA-Z\-_\.]{0,200})\s*';
            }
            description
              "Name.";
          }
          leaf content {
            type string {
              length "1..16380";
            }
            // NCS drop mandatory statement
            description
              "List config.";
          }
        }
      }
      container as-path-lists {
        description
          "List of AS_PATH.";
        list as-path-list {
          key "name";
          // NCS drop max-elements statement
          description
            "Configure a list of AS_PATH. A group of AS_Path data and can be used by a route-filter to filter BGP routes.";
          leaf name {
            type string {
              length "1..200";
              pattern '\s*([0-9a-zA-Z][0-9a-zA-Z\-_\.]{0,200})\s*';
            }
            description
              "Name.";
          }
          leaf content {
            type string {
              length "1..16380";
            }
            // NCS drop mandatory statement
            description
              "List config.";
          }
        }
      }
      container community-lists {
        description
          "List of community attributes.";
        list community-list {
          key "name";
          // NCS drop max-elements statement
          description
            "Configure a list of community attributes.";
          leaf name {
            type string {
              length "1..200";
              pattern '\s*([0-9a-zA-Z][0-9a-zA-Z\-_\.]{0,200})\s*';
            }
            description
              "Name.";
          }
          leaf content {
            type string {
              length "1..16380";
            }
            // NCS drop mandatory statement
            description
              "List config.";
          }
        }
      }
      container ext-community-rt-lists {
        description
          "List of Extcommunity RT Attributes.";
        list ext-community-rt-list {
          key "name";
          // NCS drop max-elements statement
          description
            "Configure a list of extcommunity RT attributes.";
          leaf name {
            type string {
              length "1..200";
              pattern '\s*([0-9a-zA-Z][0-9a-zA-Z\-_\.]{0,200})\s*';
            }
            description
              "Name.";
          }
          leaf content {
            type string {
              length "1..16380";
            }
            // NCS drop mandatory statement
            description
              "List config.";
          }
        }
      }
      container ext-community-soo-lists {
        description
          "List of Extcommunity SoO Attributes.";
        list ext-community-soo-list {
          key "name";
          // NCS drop max-elements statement
          description
            "Configure a list of extcommunity SoO attributes configuration.";
          leaf name {
            type string {
              length "1..200";
              pattern '\s*([0-9a-zA-Z][0-9a-zA-Z\-_\.]{0,200})\s*';
            }
            description
              "Name.";
          }
          leaf content {
            type string {
              length "1..16380";
            }
            // NCS drop mandatory statement
            description
              "List config.";
          }
        }
      }
      container ipv4-prefix-lists {
        description
          "List of Prefix.";
        list ipv4-prefix-list {
          key "name";
          // NCS drop max-elements statement
          description
            "Configure a list of IPv4 prefix.";
          leaf name {
            type string {
              length "1..200";
              pattern '\s*([0-9a-zA-Z][0-9a-zA-Z\-_\.]{0,200})\s*';
            }
            description
              "Name.";
          }
          leaf content {
            type string {
              length "1..16380";
            }
            // NCS drop mandatory statement
            description
              "List config.";
          }
        }
      }
      container ipv6-prefix-lists {
        description
          "List of IPv6 Prefix.";
        list ipv6-prefix-list {
          key "name";
          // NCS drop max-elements statement
          description
            "Configure a list of IPv6 prefix.";
          leaf name {
            type string {
              length "1..200";
              pattern '\s*([0-9a-zA-Z][0-9a-zA-Z\-_\.]{0,200})\s*';
            }
            description
              "Name.";
          }
          leaf content {
            type string {
              length "1..16380";
            }
            // NCS drop mandatory statement
            description
              "List config.";
          }
        }
      }
      container rd-lists {
        description
          "List of RD.";
        list rd-list {
          key "name";
          // NCS drop max-elements statement
          description
            "Configure a list of RD.";
          leaf name {
            type string {
              length "1..200";
              pattern '\s*([0-9a-zA-Z][0-9a-zA-Z\-_\.]{0,200})\s*';
            }
            description
              "Name.";
          }
          leaf content {
            type string {
              length "1..16380";
            }
            // NCS drop mandatory statement
            description
              "List config.";
          }
        }
      }
      container large-community-lists {
        description
          "List of large community sets.";
        list large-community-list {
          key "name";
          // NCS drop max-elements statement
          description
            "Configure a list of large community.";
          leaf name {
            type string {
              length "1..200";
              pattern '\s*([0-9a-zA-Z][0-9a-zA-Z\-_\.]{0,200})\s*';
            }
            description
              "Name.";
          }
          leaf content {
            type string {
              length "1..16380";
            }
            // NCS drop mandatory statement
            description
              "List config.";
          }
        }
      }
      container interface-lists {
        description
          "List of interface.";
        list interface-list {
          key "name";
          // NCS drop max-elements statement
          description
            "Configure a list of interface.";
          leaf name {
            type string {
              length "1..200";
              pattern '\s*([0-9a-zA-Z][0-9a-zA-Z\-_\.]{0,200})\s*';
            }
            description
              "Interface list name.";
          }
          container interface-sets {
            description
              "List of interface set. An interface set can be applied to route-filters to filter routes based on outbound interfaces.";
            list interface-set {
              key "interface-name";
              // NCS drop max-elements statement
              description
                "Specify interface configuration, based on which routes are filtered.";
              leaf interface-name {
                type leafref {
                  path "/ncs:devices/ncs:device/ncs:live-status/ifm:ifm/ifm:interfaces/ifm:interface/ifm:name" {
                    tailf:xpath-root 3;
                  }
                }
                description
                  "Interface set name.";
              }
            }
          }
        }
      }
      container route-filters {
        description
          "List of extended policies.";
        list route-filter {
          key "name";
          // NCS drop max-elements statement
          description
            "Configure a list of extended policy. A route-filter can use its condition clauses to filter routes and use its action clauses to set or modify route attributes of the routes that match the condition clauses.";
          leaf name {
            type live_ncs_xpl-filter-name;
            description
              "Policy name in the format of a string.";
          }
          leaf content {
            type string {
              length "1..16380";
            }
            // NCS drop mandatory statement
            description
              "Policy config.";
          }
        }
      }
    }
  }
  augment "/ncs:devices/ncs:template/ncs:ned-id/ncs:config" {
    container xpl {
      description
        "Extended router policy language.";
      container global {
        description
          "Configure global variable.";
        leaf content {
          type string;
          description
            "Global variable config.";
        }
      }
      container route-flow-group-lists {
        description
          "List of route flow group.";
        list route-flow-group-list {
          // NCS patched for predictable order
          ordered-by user;
          key "name";
          // NCS drop max-elements statement
          description
            "Configure of route flow group. A route flow group is used to create a QPPB attribute configuration group to assign a value to the QoS attribute of routes.";
          leaf name {
            type string;
            description
              "Name.";
          }
          leaf content {
            type string;
            // NCS drop mandatory statement
            description
              "List config.";
          }
        }
      }
      container as-path-lists {
        description
          "List of AS_PATH.";
        list as-path-list {
          // NCS patched for predictable order
          ordered-by user;
          key "name";
          // NCS drop max-elements statement
          description
            "Configure a list of AS_PATH. A group of AS_Path data and can be used by a route-filter to filter BGP routes.";
          leaf name {
            type string;
            description
              "Name.";
          }
          leaf content {
            type string;
            // NCS drop mandatory statement
            description
              "List config.";
          }
        }
      }
      container community-lists {
        description
          "List of community attributes.";
        list community-list {
          // NCS patched for predictable order
          ordered-by user;
          key "name";
          // NCS drop max-elements statement
          description
            "Configure a list of community attributes.";
          leaf name {
            type string;
            description
              "Name.";
          }
          leaf content {
            type string;
            // NCS drop mandatory statement
            description
              "List config.";
          }
        }
      }
      container ext-community-rt-lists {
        description
          "List of Extcommunity RT Attributes.";
        list ext-community-rt-list {
          // NCS patched for predictable order
          ordered-by user;
          key "name";
          // NCS drop max-elements statement
          description
            "Configure a list of extcommunity RT attributes.";
          leaf name {
            type string;
            description
              "Name.";
          }
          leaf content {
            type string;
            // NCS drop mandatory statement
            description
              "List config.";
          }
        }
      }
      container ext-community-soo-lists {
        description
          "List of Extcommunity SoO Attributes.";
        list ext-community-soo-list {
          // NCS patched for predictable order
          ordered-by user;
          key "name";
          // NCS drop max-elements statement
          description
            "Configure a list of extcommunity SoO attributes configuration.";
          leaf name {
            type string;
            description
              "Name.";
          }
          leaf content {
            type string;
            // NCS drop mandatory statement
            description
              "List config.";
          }
        }
      }
      container ipv4-prefix-lists {
        description
          "List of Prefix.";
        list ipv4-prefix-list {
          // NCS patched for predictable order
          ordered-by user;
          key "name";
          // NCS drop max-elements statement
          description
            "Configure a list of IPv4 prefix.";
          leaf name {
            type string;
            description
              "Name.";
          }
          leaf content {
            type string;
            // NCS drop mandatory statement
            description
              "List config.";
          }
        }
      }
      container ipv6-prefix-lists {
        description
          "List of IPv6 Prefix.";
        list ipv6-prefix-list {
          // NCS patched for predictable order
          ordered-by user;
          key "name";
          // NCS drop max-elements statement
          description
            "Configure a list of IPv6 prefix.";
          leaf name {
            type string;
            description
              "Name.";
          }
          leaf content {
            type string;
            // NCS drop mandatory statement
            description
              "List config.";
          }
        }
      }
      container rd-lists {
        description
          "List of RD.";
        list rd-list {
          // NCS patched for predictable order
          ordered-by user;
          key "name";
          // NCS drop max-elements statement
          description
            "Configure a list of RD.";
          leaf name {
            type string;
            description
              "Name.";
          }
          leaf content {
            type string;
            // NCS drop mandatory statement
            description
              "List config.";
          }
        }
      }
      container large-community-lists {
        description
          "List of large community sets.";
        list large-community-list {
          // NCS patched for predictable order
          ordered-by user;
          key "name";
          // NCS drop max-elements statement
          description
            "Configure a list of large community.";
          leaf name {
            type string;
            description
              "Name.";
          }
          leaf content {
            type string;
            // NCS drop mandatory statement
            description
              "List config.";
          }
        }
      }
      container interface-lists {
        description
          "List of interface.";
        list interface-list {
          // NCS patched for predictable order
          ordered-by user;
          key "name";
          // NCS drop max-elements statement
          description
            "Configure a list of interface.";
          leaf name {
            type string;
            description
              "Interface list name.";
          }
          container interface-sets {
            description
              "List of interface set. An interface set can be applied to route-filters to filter routes based on outbound interfaces.";
            list interface-set {
              // NCS patched for predictable order
              ordered-by user;
              key "interface-name";
              // NCS drop max-elements statement
              description
                "Specify interface configuration, based on which routes are filtered.";
              leaf interface-name {
                type string;
                description
                  "Interface set name.";
              }
            }
          }
        }
      }
      container route-filters {
        description
          "List of extended policies.";
        list route-filter {
          // NCS patched for predictable order
          ordered-by user;
          key "name";
          // NCS drop max-elements statement
          description
            "Configure a list of extended policy. A route-filter can use its condition clauses to filter routes and use its action clauses to set or modify route attributes of the routes that match the condition clauses.";
          leaf name {
            type ncs_template_xpl-filter-name;
            description
              "Policy name in the format of a string.";
          }
          leaf content {
            type string;
            // NCS drop mandatory statement
            description
              "Policy config.";
          }
        }
      }
    }
  }
}
