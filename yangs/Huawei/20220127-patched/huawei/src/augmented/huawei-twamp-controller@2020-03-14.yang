module huawei-twamp-controller {
  // Generated by yanger -t ncs
  tailf:mount-id "huawei-nc-1.0:huawei-nc-1.0";
  tailf:ncs-device-type "netconf";

  namespace "urn:huawei:yang:huawei-twamp-controller";
  prefix twamp-controller;

  import huawei-extension {
    prefix ext;
  }
  import ietf-inet-types {
    prefix inet;
  }
  import ietf-yang-types {
    prefix yang;
  }
  import huawei-network-instance {
    prefix ni;
  }
  import huawei-l3vpn {
    prefix l3vpn;
  }
  import huawei-ifm {
    prefix ifm;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "TWAMP Controller.";

  revision 2020-03-14 {
    description
      "Modify description.";
    reference "Huawei private.";
  }
  revision 2019-12-27 {
    description
      "Solve some errors.";
    reference "Huawei private.";
  }
  revision 2019-05-05 {
    description
      "Initial revision.";
    reference "Huawei private.";
  }
  ext:task-name "twampclient";

  typedef ncs_template_period-type {
    type string;
    description
      "The period of sending packets.";
  }

  typedef ncs_template_test-state {
    type string;
    description
      "Test session state.";
  }

  typedef ncs_template_session-start-type {
    type string;
    description
      "Session start type.";
  }

  typedef ncs_template_ctrl-auth-mode {
    type string;
    description
      "Controller authentication mode.";
  }

  typedef ncs_template_padding-info {
    type string;
    description
      "Padding information.";
  }

  typedef ncs_template_inactive-reason {
    type string;
    description
      "The inactive reason.";
  }

  typedef ncs_rpc_notif_period-type {
    type enumeration {
      enum "10ms" {
        value 1;
        description
          "The period of sending packets is 10ms.";
      }
      enum "100ms" {
        value 2;
        description
          "The period of sending packets is 100ms.";
      }
      enum "1000ms" {
        value 3;
        description
          "The period of sending packets is 1000ms.";
      }
      enum "30000ms" {
        value 4;
        description
          "The period of sending packets is 30000ms.";
      }
    }
    description
      "The period of sending packets.";
  }

  typedef ncs_rpc_notif_test-state {
    type enumeration {
      enum "initial" {
        value 0;
        description
          "Test session state is initial.";
      }
      enum "active" {
        value 2;
        description
          "Test session state is active.";
      }
      enum "inactive" {
        value 1;
        description
          "Test session state is inactive.";
      }
      enum "unknown" {
        value 3;
        description
          "Test session state is unknown.";
      }
      enum "inconsistent" {
        value 4;
        description
          "Test session state is inconsistent.";
      }
    }
    description
      "Test session state.";
  }

  typedef ncs_rpc_notif_session-start-type {
    type enumeration {
      enum "continual" {
        value 1;
        description
          "Session start type is continual.";
      }
      enum "on-demand" {
        value 2;
        description
          "Session start type is on-demand.";
      }
      enum "unknown" {
        value 0;
        description
          "Session start type is unknown.";
      }
      enum "regular" {
        value 3;
        description
          "Session start type is regular.";
      }
    }
    description
      "Session start type.";
  }

  typedef ncs_rpc_notif_ctrl-auth-mode {
    type enumeration {
      enum "unauthenticated" {
        value 0;
        description
          "Controller authentication mode is unauthenticated.";
      }
      enum "authenticated" {
        value 1;
        description
          "Controller authentication mode is authenticated.";
      }
      enum "encrypted" {
        value 2;
        description
          "Controller authentication mode is encrypted.";
      }
      enum "unknown" {
        value 3;
        description
          "Controller authentication mode is unknown.";
      }
    }
    description
      "Controller authentication mode.";
  }

  typedef ncs_rpc_notif_padding-info {
    type enumeration {
      enum "00" {
        value 0;
        description
          "Padding information is 00.";
      }
      enum "aa" {
        value 170;
        description
          "Padding information is aa.";
      }
      enum "55" {
        value 85;
        description
          "Padding information is 55.";
      }
      enum "ff" {
        value 255;
        description
          "Padding information is ff.";
      }
    }
    description
      "Padding information.";
  }

  typedef ncs_rpc_notif_inactive-reason {
    type enumeration {
      enum "not-startup" {
        value 1;
        description
          "The inactive reason is not startup.";
      }
      enum "absence-resource" {
        value 2;
        description
          "The inactive reason is absence of resource.";
      }
      enum "board-fault" {
        value 3;
        description
          "The inactive reason is board fault.";
      }
    }
    description
      "The inactive reason.";
  }

  typedef live_ncs_period-type {
    type enumeration {
      enum "10ms" {
        value 1;
        description
          "The period of sending packets is 10ms.";
      }
      enum "100ms" {
        value 2;
        description
          "The period of sending packets is 100ms.";
      }
      enum "1000ms" {
        value 3;
        description
          "The period of sending packets is 1000ms.";
      }
      enum "30000ms" {
        value 4;
        description
          "The period of sending packets is 30000ms.";
      }
    }
    description
      "The period of sending packets.";
  }

  typedef live_ncs_test-state {
    type enumeration {
      enum "initial" {
        value 0;
        description
          "Test session state is initial.";
      }
      enum "active" {
        value 2;
        description
          "Test session state is active.";
      }
      enum "inactive" {
        value 1;
        description
          "Test session state is inactive.";
      }
      enum "unknown" {
        value 3;
        description
          "Test session state is unknown.";
      }
      enum "inconsistent" {
        value 4;
        description
          "Test session state is inconsistent.";
      }
    }
    description
      "Test session state.";
  }

  typedef live_ncs_session-start-type {
    type enumeration {
      enum "continual" {
        value 1;
        description
          "Session start type is continual.";
      }
      enum "on-demand" {
        value 2;
        description
          "Session start type is on-demand.";
      }
      enum "unknown" {
        value 0;
        description
          "Session start type is unknown.";
      }
      enum "regular" {
        value 3;
        description
          "Session start type is regular.";
      }
    }
    description
      "Session start type.";
  }

  typedef live_ncs_ctrl-auth-mode {
    type enumeration {
      enum "unauthenticated" {
        value 0;
        description
          "Controller authentication mode is unauthenticated.";
      }
      enum "authenticated" {
        value 1;
        description
          "Controller authentication mode is authenticated.";
      }
      enum "encrypted" {
        value 2;
        description
          "Controller authentication mode is encrypted.";
      }
      enum "unknown" {
        value 3;
        description
          "Controller authentication mode is unknown.";
      }
    }
    description
      "Controller authentication mode.";
  }

  typedef live_ncs_padding-info {
    type enumeration {
      enum "00" {
        value 0;
        description
          "Padding information is 00.";
      }
      enum "aa" {
        value 170;
        description
          "Padding information is aa.";
      }
      enum "55" {
        value 85;
        description
          "Padding information is 55.";
      }
      enum "ff" {
        value 255;
        description
          "Padding information is ff.";
      }
    }
    description
      "Padding information.";
  }

  typedef live_ncs_inactive-reason {
    type enumeration {
      enum "not-startup" {
        value 1;
        description
          "The inactive reason is not startup.";
      }
      enum "absence-resource" {
        value 2;
        description
          "The inactive reason is absence of resource.";
      }
      enum "board-fault" {
        value 3;
        description
          "The inactive reason is board fault.";
      }
    }
    description
      "The inactive reason.";
  }

  typedef period-type {
    type enumeration {
      enum "10ms" {
        value 1;
        description
          "The period of sending packets is 10ms.";
      }
      enum "100ms" {
        value 2;
        description
          "The period of sending packets is 100ms.";
      }
      enum "1000ms" {
        value 3;
        description
          "The period of sending packets is 1000ms.";
      }
      enum "30000ms" {
        value 4;
        description
          "The period of sending packets is 30000ms.";
      }
    }
    description
      "The period of sending packets.";
  }

  typedef test-state {
    type enumeration {
      enum "initial" {
        value 0;
        description
          "Test session state is initial.";
      }
      enum "active" {
        value 2;
        description
          "Test session state is active.";
      }
      enum "inactive" {
        value 1;
        description
          "Test session state is inactive.";
      }
      enum "unknown" {
        value 3;
        description
          "Test session state is unknown.";
      }
      enum "inconsistent" {
        value 4;
        description
          "Test session state is inconsistent.";
      }
    }
    description
      "Test session state.";
  }

  typedef session-start-type {
    type enumeration {
      enum "continual" {
        value 1;
        description
          "Session start type is continual.";
      }
      enum "on-demand" {
        value 2;
        description
          "Session start type is on-demand.";
      }
      enum "unknown" {
        value 0;
        description
          "Session start type is unknown.";
      }
      enum "regular" {
        value 3;
        description
          "Session start type is regular.";
      }
    }
    description
      "Session start type.";
  }

  typedef ctrl-auth-mode {
    type enumeration {
      enum "unauthenticated" {
        value 0;
        description
          "Controller authentication mode is unauthenticated.";
      }
      enum "authenticated" {
        value 1;
        description
          "Controller authentication mode is authenticated.";
      }
      enum "encrypted" {
        value 2;
        description
          "Controller authentication mode is encrypted.";
      }
      enum "unknown" {
        value 3;
        description
          "Controller authentication mode is unknown.";
      }
    }
    description
      "Controller authentication mode.";
  }

  typedef padding-info {
    type enumeration {
      enum "00" {
        value 0;
        description
          "Padding information is 00.";
      }
      enum "aa" {
        value 170;
        description
          "Padding information is aa.";
      }
      enum "55" {
        value 85;
        description
          "Padding information is 55.";
      }
      enum "ff" {
        value 255;
        description
          "Padding information is ff.";
      }
    }
    description
      "Padding information.";
  }

  typedef inactive-reason {
    type enumeration {
      enum "not-startup" {
        value 1;
        description
          "The inactive reason is not startup.";
      }
      enum "absence-resource" {
        value 2;
        description
          "The inactive reason is absence of resource.";
      }
      enum "board-fault" {
        value 3;
        description
          "The inactive reason is board fault.";
      }
    }
    description
      "The inactive reason.";
  }

  augment "/ncs:devices/ncs:device/ncs:rpc" {
    container rpc-reset-statistics {
      tailf:ncs-device-type "netconf";
      tailf:display-when "not(../../ncs:module) or ../../ncs:module[ncs:name='huawei-twamp-controller']";
      tailf:action reset-statistics {
        tailf:actionpoint ncsproxy {
          tailf:internal;
        }
        description
          "Reset the twamp-light statistics.";
        input {
          leaf id {
            type string;
            description
              "The session ID of test session.";
          }
        }
      }
    }
  }
  augment "/ncs:devices/ncs:device-group/ncs:ned-id/ncs:rpc" {
    container rpc-reset-statistics {
      tailf:ncs-device-type "netconf";
      tailf:display-when "/ncs:devices/ncs:device[ncs:name=current()/../../../ncs:member]/ncs:module[ncs:name='huawei-twamp-controller']";
      tailf:action reset-statistics {
        tailf:actionpoint ncsproxy {
          tailf:internal;
        }
        description
          "Reset the twamp-light statistics.";
        input {
          leaf id {
            type string;
            description
              "The session ID of test session.";
          }
        }
      }
    }
  }
  augment "/ncs:devices/ncs:device/ncs:rpc" {
    container rpc-stop-on-demand-test {
      tailf:ncs-device-type "netconf";
      tailf:display-when "not(../../ncs:module) or ../../ncs:module[ncs:name='huawei-twamp-controller']";
      tailf:action stop-on-demand-test {
        tailf:actionpoint ncsproxy {
          tailf:internal;
        }
        description
          "Stop twamp-light on demand test.";
        input {
          leaf id {
            type string;
            description
              "The session ID of on demand test session.";
          }
        }
      }
    }
  }
  augment "/ncs:devices/ncs:device-group/ncs:ned-id/ncs:rpc" {
    container rpc-stop-on-demand-test {
      tailf:ncs-device-type "netconf";
      tailf:display-when "/ncs:devices/ncs:device[ncs:name=current()/../../../ncs:member]/ncs:module[ncs:name='huawei-twamp-controller']";
      tailf:action stop-on-demand-test {
        tailf:actionpoint ncsproxy {
          tailf:internal;
        }
        description
          "Stop twamp-light on demand test.";
        input {
          leaf id {
            type string;
            description
              "The session ID of on demand test session.";
          }
        }
      }
    }
  }
  augment "/ncs:devices/ncs:device/ncs:rpc" {
    container rpc-start-on-demand-test {
      tailf:ncs-device-type "netconf";
      tailf:display-when "not(../../ncs:module) or ../../ncs:module[ncs:name='huawei-twamp-controller']";
      tailf:action start-on-demand-test {
        tailf:actionpoint ncsproxy {
          tailf:internal;
        }
        description
          "Start twamp-light on demand test.";
        input {
          leaf id {
            type string;
            mandatory true;
            description
              "The session ID of on demand test session.";
          }
          choice packet-sent-type {
            mandatory true;
            description
              "Configure the type how the packet is sent in on demand test session.";
            case duration-type {
              description
                "The packet is sent in dedicated duration.";
              leaf duration-time {
                type uint32 {
                  range "60..300";
                }
                units "s";
                description
                  "The duation time of on demand test session.";
              }
            }
            case count-type {
              description
                "The packet is sent by total count.";
              leaf packet-count {
                type uint32 {
                  range "100..3000";
                }
                description
                  "The packet count of on demand test session.";
              }
            }
          }
          leaf period {
            type ncs_rpc_notif_period-type;
            units "ms";
            default "100ms";
            description
              "The period of on demand test session.";
          }
          leaf timeout {
            type uint16 {
              range "1..10";
            }
            units "s";
            default "5";
            description
              "The timeout of on demand test session.";
          }
        }
      }
    }
  }
  augment "/ncs:devices/ncs:device-group/ncs:ned-id/ncs:rpc" {
    container rpc-start-on-demand-test {
      tailf:ncs-device-type "netconf";
      tailf:display-when "/ncs:devices/ncs:device[ncs:name=current()/../../../ncs:member]/ncs:module[ncs:name='huawei-twamp-controller']";
      tailf:action start-on-demand-test {
        tailf:actionpoint ncsproxy {
          tailf:internal;
        }
        description
          "Start twamp-light on demand test.";
        input {
          leaf id {
            type string;
            mandatory true;
            description
              "The session ID of on demand test session.";
          }
          choice packet-sent-type {
            mandatory true;
            description
              "Configure the type how the packet is sent in on demand test session.";
            case duration-type {
              description
                "The packet is sent in dedicated duration.";
              leaf duration-time {
                type uint32 {
                  range "60..300";
                }
                units "s";
                description
                  "The duation time of on demand test session.";
              }
            }
            case count-type {
              description
                "The packet is sent by total count.";
              leaf packet-count {
                type uint32 {
                  range "100..3000";
                }
                description
                  "The packet count of on demand test session.";
              }
            }
          }
          leaf period {
            type ncs_rpc_notif_period-type;
            units "ms";
            default "100ms";
            description
              "The period of on demand test session.";
          }
          leaf timeout {
            type uint16 {
              range "1..10";
            }
            units "s";
            default "5";
            description
              "The timeout of on demand test session.";
          }
        }
      }
    }
  }
  augment "/ncs:devices/ncs:device/ncs:config" {
    container twamp-controller {
      tailf:ncs-device-type "netconf";
      tailf:display-when "not(../../ncs:module) or ../../ncs:module[ncs:name='huawei-twamp-controller']";
      description
        "TWAMP Controller.";
      container client {
        presence "Enable client of TWAMP.";
        description
          "Configure the client of TWAMP light.";
        container sessions {
          description
            "List of configuration session.";
          list session {
            key "id";
            unique "send-ip-addr ref-ip-addr send-port ref-port vrf-name";
            description
              "Configure the object of session.";
            leaf id {
              type uint32 {
                range "1..65535";
              }
              description
                "The session ID of configuration session.";
            }
            leaf send-ip-addr {
              type inet:ip-address-no-zone;
              must '((../send-ip-addr) != (../ref-ip-addr))' {
                tailf:xpath-root 3;
              }
              mandatory true;
              description
                "The sender IP address of configuration session.";
            }
            leaf ref-ip-addr {
              type inet:ip-address-no-zone;
              must '((../send-ip-addr) != (../ref-ip-addr))' {
                tailf:xpath-root 3;
              }
              mandatory true;
              description
                "The reflector IP address of configuration session.";
            }
            leaf send-port {
              type uint16 {
                range "862..863|1025..65535";
              }
              mandatory true;
              description
                "The sender port of configuration session.";
            }
            leaf ref-port {
              type uint16 {
                range "862..863|1025..65535";
              }
              mandatory true;
              description
                "The reflector port of configuration session.";
            }
            leaf vrf-name {
              type leafref {
                path "/ncs:devices/ncs:device/ncs:config/ni:network-instance/ni:instances/ni:instance/ni:name" {
                  tailf:xpath-root 3;
                }
              }
              must "(contains(../send-ip-addr,':') and /ni:network-instance/ni:instances/ni:instance[ni:name = current()]/l3vpn:afs/l3vpn:af[l3vpn:type='ipv6-unicast']) or (not(contains(../send-ip-addr,':'))and /ni:network-instance/ni:instances/ni:instance[ni:name = current()]/l3vpn:afs/l3vpn:af[l3vpn:type='ipv4-unicast'])" {
                tailf:xpath-root 3;
              }
              description
                "The VRF name of configuration session.";
            }
            leaf dscp-value {
              type uint32 {
                range "0..63";
              }
              default "0";
              description
                "The DSCP value of configuration session.";
            }
            leaf padding-length {
              type uint32 {
                range "32..1454";
              }
              must "(contains(../send-ip-addr,':') and ((../link-bundle-if and ../padding-length>=38 and ../padding-length<=1428) or (not(../link-bundle-if) and ../padding-length<=1434))) or (not(contains(../send-ip-addr,':')) and ((../link-bundle-if and ../padding-length>=38 and ../padding-length<=1448) or not(../link-bundle-if)))" {
                tailf:xpath-root 3;
              }
              default "128";
              description
                "The padding length of configuration session. The value range is 32-1454 and 32-1434 in V4 and V6, respectively.";
            }
            leaf padding-type {
              type padding-info;
              default "00";
              description
                "Padding type.";
            }
            leaf binded-interface {
              type leafref {
                path "/ncs:devices/ncs:device/ncs:config/ifm:ifm/ifm:interfaces/ifm:interface/ifm:name" {
                  tailf:xpath-root 3;
                }
              }
              description
                "The interface name which the test-session is binded to.";
            }
            leaf description {
              type string {
                length "3..32";
              }
              description
                "Session description.";
            }
            leaf link-bundle-if {
              type leafref {
                path "/ncs:devices/ncs:device/ncs:config/ifm:ifm/ifm:interfaces/ifm:interface/ifm:name" {
                  tailf:xpath-root 3;
                }
              }
              must "/ifm:ifm/ifm:interfaces/ifm:interface[ifm:name = current()]/ifm:type='Eth-Trunk'" {
                tailf:xpath-root 3;
              }
              must 'not(../binded-interface)' {
                tailf:xpath-root 3;
              }
              description
                "Link-bundle interface that the session binds.";
            }
            container twoway-loss-threshold {
              description
                "Configure the twoway loss threshold of session.";
              leaf up-limit {
                type string {
                  length "1..7";
                  pattern '[0-1]{0,1}[0-9]{0,1}[0-9]{0,1}(\.[0-9]{1,4})?';
                }
                units "%";
                default "0.1";
                description
                  "Twoway loss threshold upper limit.";
              }
              leaf low-limit {
                type string {
                  length "1..7";
                  pattern '[0-1]{0,1}[0-9]{0,1}[0-9]{0,1}(\.[0-9]{1,4})?';
                }
                units "%";
                default "0.05";
                description
                  "Twoway loss threshold lower limit.";
              }
            }
            container twoway-delay-threshold {
              description
                "Configure the twoway delay threshold of session.";
              leaf up-limit {
                type uint32 {
                  range "2..1000";
                }
                units "ms";
                must '../low-limit < ../up-limit' {
                  tailf:xpath-root 3;
                }
                default "100";
                description
                  "Twoway delay threshold upper limit.";
              }
              leaf low-limit {
                type uint32 {
                  range "1..999";
                }
                units "ms";
                must '../low-limit < ../up-limit' {
                  tailf:xpath-root 3;
                }
                default "80";
                description
                  "Twoway delay threshold lower limit.";
              }
            }
            container twoway-jitter-threshold {
              description
                "Configure the twoway jitter threshold of session.";
              leaf up-limit {
                type uint32 {
                  range "2..1000";
                }
                units "ms";
                must '../low-limit < ../up-limit' {
                  tailf:xpath-root 3;
                }
                default "10";
                description
                  "Twoway jitter threshold upper limit.";
              }
              leaf low-limit {
                type uint32 {
                  range "1..999";
                }
                units "ms";
                must '../low-limit < ../up-limit' {
                  tailf:xpath-root 3;
                }
                default "8";
                description
                  "Twoway jitter threshold lower limit.";
              }
            }
            // NCS drop config false container 'session-detail'
            // NCS drop config false container 'twoway-delay-result'
            // NCS drop config false container 'twoway-delay-result-link-bundle-ifs'
            // NCS drop config false container 'twoway-loss-result'
            // NCS drop config false container 'twoway-loss-result-link-bundle-ifs'
          }
        }
      }
      container sender {
        presence "Enable sender of TWAMP";
        description
          "Configure the sender of TWAMP light.";
        container sessions {
          description
            "List of sender session.";
          list session {
            key "id";
            description
              "Configure the object of sender session.";
            leaf id {
              type leafref {
                path "/ncs:devices/ncs:device/ncs:config/twamp-controller:twamp-controller/twamp-controller:client/twamp-controller:sessions/twamp-controller:session/twamp-controller:id" {
                  tailf:xpath-root 3;
                }
              }
              description
                "Configure the session ID of sender session.";
            }
            leaf period {
              type period-type;
              units "ms";
              default "100ms";
              description
                "The period of sender session.";
            }
            leaf timeout {
              type uint16 {
                range "1..10";
              }
              units "s";
              default "5";
              description
                "The timeout of sender session.";
            }
          }
        }
        container regular-sessions {
          description
            "List of sender regular session.";
          list regular-session {
            key "id";
            description
              "Configure the object of sender regular session.";
            leaf id {
              type leafref {
                path "/ncs:devices/ncs:device/ncs:config/twamp-controller:twamp-controller/twamp-controller:client/twamp-controller:sessions/twamp-controller:session/twamp-controller:id" {
                  tailf:xpath-root 3;
                }
              }
              description
                "The session ID of regular sender session.";
            }
            leaf regular-time {
              ext:operation-exclude "update|delete";
              type uint16 {
                range "10..60";
              }
              units "s";
              default "30";
              description
                "The regular time of sender regular session.";
            }
            leaf packet-count {
              ext:operation-exclude "update|delete";
              type uint32 {
                range "10..1000";
              }
              default "100";
              description
                "The packet count of sender regular session.";
            }
            leaf timeout {
              ext:operation-exclude "update|delete";
              type uint8 {
                range "1..10";
              }
              units "s";
              default "5";
              description
                "The timeout of sender regular session.";
            }
          }
        }
      }
    }
  }
  augment "/ncs:devices/ncs:device/ncs:live-status" {
    container twamp-controller {
      tailf:ncs-device-type "netconf";
      tailf:display-when "not(../../ncs:module) or ../../ncs:module[ncs:name='huawei-twamp-controller'] or (../../ncs:live-status-protocol[not(ncs:capability)]) or (../../ncs:live-status-protocol/ncs:capability/ncs:module[.='huawei-twamp-controller'])";
      description
        "TWAMP Controller.";
      container client {
        presence "Enable client of TWAMP.";
        description
          "Configure the client of TWAMP light.";
        container sessions {
          description
            "List of configuration session.";
          list session {
            key "id";
            unique "send-ip-addr ref-ip-addr send-port ref-port vrf-name";
            description
              "Configure the object of session.";
            leaf id {
              type uint32 {
                range "1..65535";
              }
              description
                "The session ID of configuration session.";
            }
            leaf send-ip-addr {
              type inet:ip-address-no-zone;
              // NCS drop must statement
              // NCS drop mandatory statement
              description
                "The sender IP address of configuration session.";
            }
            leaf ref-ip-addr {
              type inet:ip-address-no-zone;
              // NCS drop must statement
              // NCS drop mandatory statement
              description
                "The reflector IP address of configuration session.";
            }
            leaf send-port {
              type uint16 {
                range "862..863|1025..65535";
              }
              // NCS drop mandatory statement
              description
                "The sender port of configuration session.";
            }
            leaf ref-port {
              type uint16 {
                range "862..863|1025..65535";
              }
              // NCS drop mandatory statement
              description
                "The reflector port of configuration session.";
            }
            leaf vrf-name {
              type leafref {
                path "/ncs:devices/ncs:device/ncs:live-status/ni:network-instance/ni:instances/ni:instance/ni:name" {
                  tailf:xpath-root 3;
                }
              }
              // NCS drop must statement
              description
                "The VRF name of configuration session.";
            }
            leaf dscp-value {
              type uint32 {
                range "0..63";
              }
              // NCS drop default statement
              description
                "The DSCP value of configuration session.";
            }
            leaf padding-length {
              type uint32 {
                range "32..1454";
              }
              // NCS drop must statement
              // NCS drop default statement
              description
                "The padding length of configuration session. The value range is 32-1454 and 32-1434 in V4 and V6, respectively.";
            }
            leaf padding-type {
              type live_ncs_padding-info;
              // NCS drop default statement
              description
                "Padding type.";
            }
            leaf binded-interface {
              type leafref {
                path "/ncs:devices/ncs:device/ncs:live-status/ifm:ifm/ifm:interfaces/ifm:interface/ifm:name" {
                  tailf:xpath-root 3;
                }
              }
              description
                "The interface name which the test-session is binded to.";
            }
            leaf description {
              type string {
                length "3..32";
              }
              description
                "Session description.";
            }
            leaf link-bundle-if {
              type leafref {
                path "/ncs:devices/ncs:device/ncs:live-status/ifm:ifm/ifm:interfaces/ifm:interface/ifm:name" {
                  tailf:xpath-root 3;
                }
              }
              // NCS drop must statement
              // NCS drop must statement
              description
                "Link-bundle interface that the session binds.";
            }
            container twoway-loss-threshold {
              description
                "Configure the twoway loss threshold of session.";
              leaf up-limit {
                type string {
                  length "1..7";
                  pattern '[0-1]{0,1}[0-9]{0,1}[0-9]{0,1}(\.[0-9]{1,4})?';
                }
                units "%";
                // NCS drop default statement
                description
                  "Twoway loss threshold upper limit.";
              }
              leaf low-limit {
                type string {
                  length "1..7";
                  pattern '[0-1]{0,1}[0-9]{0,1}[0-9]{0,1}(\.[0-9]{1,4})?';
                }
                units "%";
                // NCS drop default statement
                description
                  "Twoway loss threshold lower limit.";
              }
            }
            container twoway-delay-threshold {
              description
                "Configure the twoway delay threshold of session.";
              leaf up-limit {
                type uint32 {
                  range "2..1000";
                }
                units "ms";
                // NCS drop must statement
                // NCS drop default statement
                description
                  "Twoway delay threshold upper limit.";
              }
              leaf low-limit {
                type uint32 {
                  range "1..999";
                }
                units "ms";
                // NCS drop must statement
                // NCS drop default statement
                description
                  "Twoway delay threshold lower limit.";
              }
            }
            container twoway-jitter-threshold {
              description
                "Configure the twoway jitter threshold of session.";
              leaf up-limit {
                type uint32 {
                  range "2..1000";
                }
                units "ms";
                // NCS drop must statement
                // NCS drop default statement
                description
                  "Twoway jitter threshold upper limit.";
              }
              leaf low-limit {
                type uint32 {
                  range "1..999";
                }
                units "ms";
                // NCS drop must statement
                // NCS drop default statement
                description
                  "Twoway jitter threshold lower limit.";
              }
            }
            container session-detail {
              description
                "Statistics of the running session information.";
              leaf state {
                type live_ncs_test-state;
                description
                  "The state of configuration session.";
              }
              leaf type {
                type live_ncs_session-start-type;
                description
                  "The type of configuration session.";
              }
              leaf auth-mode {
                type live_ncs_ctrl-auth-mode;
                description
                  "The authentication mode of configuration session.";
              }
              leaf last-start-time {
                type yang:date-and-time;
                description
                  "The last start time of configuration session.";
              }
              leaf last-stop-time {
                type yang:date-and-time;
                description
                  "The last stop time of configuration session.";
              }
              leaf duration-time {
                type uint32;
                units "s";
                description
                  "The duation time of configuration session.";
              }
              leaf packet-count {
                type uint32;
                description
                  "The packet count of configuration session.";
              }
              leaf period {
                type live_ncs_period-type;
                units "ms";
                description
                  "The period of configuration session.";
              }
              leaf timeout {
                type uint16 {
                  range "1..10";
                }
                units "s";
                description
                  "The timeout of configuration session.";
              }
              container member-interface-infos {
                description
                  "List of member interface information.";
                list member-interface-info {
                  key "member-if";
                  description
                    "Statistics of the member interface information.";
                  leaf member-if {
                    type leafref {
                      path "/ncs:devices/ncs:device/ncs:live-status/ifm:ifm/ifm:interfaces/ifm:interface/ifm:name" {
                        tailf:xpath-root 3;
                      }
                    }
                    description
                      "Member interface name.";
                  }
                  leaf state {
                    type live_ncs_test-state;
                    description
                      "The state of configuration session.";
                  }
                  leaf inactive-reason {
                    type live_ncs_inactive-reason;
                    description
                      "The inactive reason.";
                  }
                  leaf last-start-time {
                    type yang:date-and-time;
                    description
                      "The last start time of configuration session.";
                  }
                  leaf last-stop-time {
                    type yang:date-and-time;
                    description
                      "The last stop time of configuration session.";
                  }
                }
              }
            }
            container twoway-delay-result {
              description
                "Statistics of the result of two way delay.";
              leaf average-delay {
                type uint32;
                units "us";
                description
                  "The average delay.";
              }
              leaf maximum-delay {
                type uint32;
                units "us";
                description
                  "The maximum delay.";
              }
              leaf minimum-delay {
                type uint32;
                units "us";
                description
                  "The minimum delay.";
              }
              leaf average-jitter {
                type uint32;
                units "us";
                description
                  "The average jitter.";
              }
              leaf maximum-jitter {
                type uint32;
                units "us";
                description
                  "The maximum jitter.";
              }
              leaf minimum-jitter {
                type uint32;
                units "us";
                description
                  "The minimum jitter.";
              }
              leaf average-tx-jitter {
                type uint32;
                units "us";
                description
                  "The average TX jitter.";
              }
              leaf maximum-tx-jitter {
                type uint32;
                units "us";
                description
                  "The maximum TX jitter.";
              }
              leaf minimum-tx-jitter {
                type uint32;
                units "us";
                description
                  "The minimum TX jitter.";
              }
              leaf average-rx-jitter {
                type uint32;
                units "us";
                description
                  "The average RX jitter.";
              }
              leaf maximum-rx-jitter {
                type uint32;
                units "us";
                description
                  "The maximum RX jitter.";
              }
              leaf minimum-rx-jitter {
                type uint32;
                units "us";
                description
                  "The minimum RX jitter.";
              }
              container twoway-delay-datas {
                description
                  "List of two way delay data.";
                list twoway-delay-data {
                  key "index";
                  description
                    "Statistics of data of two-way delay measurement.";
                  leaf index {
                    type uint32;
                    description
                      "Data index of two-way delay measurement.";
                  }
                  leaf delay {
                    type uint32;
                    units "us";
                    description
                      "Two-way delay results.";
                  }
                  leaf jitter {
                    type uint32;
                    units "us";
                    description
                      "Two-way jitter results.";
                  }
                  leaf tx-jitter {
                    type uint32;
                    units "us";
                    description
                      "Two-way TX jitter results.";
                  }
                  leaf rx-jitter {
                    type uint32;
                    units "us";
                    description
                      "Two-way RX jitter results.";
                  }
                }
              }
            }
            container twoway-delay-result-link-bundle-ifs {
              description
                "List of the result of two way delay of link bundle session.";
              list twoway-delay-result-link-bundle-if {
                key "member-if";
                description
                  "Statistics of data of two-way loss measurement.";
                leaf member-if {
                  type leafref {
                    path "/ncs:devices/ncs:device/ncs:live-status/ifm:ifm/ifm:interfaces/ifm:interface/ifm:name" {
                      tailf:xpath-root 3;
                    }
                  }
                  description
                    "Member interface name.";
                }
                leaf average-delay {
                  type uint32;
                  units "us";
                  description
                    "The average delay.";
                }
                leaf maximum-delay {
                  type uint32;
                  units "us";
                  description
                    "The maximum delay.";
                }
                leaf minimum-delay {
                  type uint32;
                  units "us";
                  description
                    "The minimum delay.";
                }
                leaf average-jitter {
                  type uint32;
                  units "us";
                  description
                    "The average jitter.";
                }
                leaf maximum-jitter {
                  type uint32;
                  units "us";
                  description
                    "The maximum jitter.";
                }
                leaf minimum-jitter {
                  type uint32;
                  units "us";
                  description
                    "The minimum jitter.";
                }
                leaf average-tx-jitter {
                  type uint32;
                  units "us";
                  description
                    "The average TX jitter.";
                }
                leaf maximum-tx-jitter {
                  type uint32;
                  units "us";
                  description
                    "The maximum TX jitter.";
                }
                leaf minimum-tx-jitter {
                  type uint32;
                  units "us";
                  description
                    "The minimum TX jitter.";
                }
                leaf average-rx-jitter {
                  type uint32;
                  units "us";
                  description
                    "The average RX jitter.";
                }
                leaf maximum-rx-jitter {
                  type uint32;
                  units "us";
                  description
                    "The maximum RX jitter.";
                }
                leaf minimum-rx-jitter {
                  type uint32;
                  units "us";
                  description
                    "The minimum RX jitter.";
                }
                container twoway-delay-datas {
                  description
                    "List of two way delay data.";
                  list twoway-delay-data {
                    key "index";
                    description
                      "Statistics of data of two-way delay measurement.";
                    leaf index {
                      type uint32;
                      description
                        "Data index of two-way delay measurement.";
                    }
                    leaf delay {
                      type uint32;
                      units "us";
                      description
                        "Two-way delay results.";
                    }
                    leaf jitter {
                      type uint32;
                      units "us";
                      description
                        "Two-way jitter results.";
                    }
                    leaf tx-jitter {
                      type uint32;
                      units "us";
                      description
                        "Two-way TX jitter results.";
                    }
                    leaf rx-jitter {
                      type uint32;
                      units "us";
                      description
                        "Two-way RX jitter results.";
                    }
                  }
                }
              }
            }
            container twoway-loss-result {
              description
                "Statistics of the result of two way loss.";
              leaf average-loss {
                type uint32;
                description
                  "The average loss.";
              }
              leaf maximum-loss {
                type uint32;
                description
                  "The maximum loss.";
              }
              leaf minimum-loss {
                type uint32;
                description
                  "The minimum loss.";
              }
              leaf average-loss-ratio {
                type string {
                  length "1..9";
                }
                description
                  "The average loss ratio.";
              }
              leaf maximum-loss-ratio {
                type string {
                  length "1..9";
                }
                description
                  "The maximum loss ratio.";
              }
              leaf minimum-loss-ratio {
                type string {
                  length "1..9";
                }
                description
                  "The minimum loss ratio.";
              }
              leaf average-rx-error {
                type uint32;
                description
                  "The average RX error.";
              }
              leaf maximum-rx-error {
                type uint32;
                description
                  "The maximum RX error.";
              }
              leaf minium-rx-error {
                type uint32;
                description
                  "The minium RX error.";
              }
              leaf average-rx-error-ratio {
                type string {
                  length "1..9";
                }
                description
                  "The average RX error ratio.";
              }
              leaf maximum-rx-error-ratio {
                type string {
                  length "1..9";
                }
                description
                  "The maximum RX error ratio.";
              }
              leaf minimum-rx-error-ratio {
                type string {
                  length "1..9";
                }
                description
                  "The minimum RX error ratio.";
              }
              container twoway-loss-datas {
                description
                  "List of two way loss data.";
                list twoway-loss-data {
                  key "index";
                  description
                    "Statistics of data of two-way loss measurement.";
                  leaf index {
                    type uint32;
                    description
                      "Data index of two-way loss measurement.";
                  }
                  leaf loss {
                    type uint32;
                    description
                      "Two-way loss results.";
                  }
                  leaf loss-ratio {
                    type string {
                      length "1..9";
                    }
                    description
                      "Two-way lossRatio results.";
                  }
                  leaf error {
                    type uint32;
                    description
                      "Two-way error results.";
                  }
                  leaf error-ratio {
                    type string {
                      length "1..9";
                    }
                    description
                      "Two-way error ratio results.";
                  }
                }
              }
            }
            container twoway-loss-result-link-bundle-ifs {
              description
                "List of the result of two way loss of link bundle session.";
              list twoway-loss-result-link-bundle-if {
                key "member-if";
                description
                  "Statistics of data of two-way loss measurement.";
                leaf member-if {
                  type leafref {
                    path "/ncs:devices/ncs:device/ncs:live-status/ifm:ifm/ifm:interfaces/ifm:interface/ifm:name" {
                      tailf:xpath-root 3;
                    }
                  }
                  description
                    "Member interface name.";
                }
                leaf average-loss {
                  type uint32;
                  description
                    "The average loss.";
                }
                leaf maximum-loss {
                  type uint32;
                  description
                    "The maximum loss.";
                }
                leaf minimum-loss {
                  type uint32;
                  description
                    "The minimum loss.";
                }
                leaf average-loss-ratio {
                  type string {
                    length "1..9";
                  }
                  description
                    "The average loss ratio.";
                }
                leaf maximum-loss-ratio {
                  type string {
                    length "1..9";
                  }
                  description
                    "The maximum loss ratio.";
                }
                leaf minimum-loss-ratio {
                  type string {
                    length "1..9";
                  }
                  description
                    "The minimum loss ratio.";
                }
                leaf average-rx-error {
                  type uint32;
                  description
                    "The average RX error.";
                }
                leaf maximum-rx-error {
                  type uint32;
                  description
                    "The maximum RX error.";
                }
                leaf minium-rx-error {
                  type uint32;
                  description
                    "The minium RX error.";
                }
                leaf average-rx-error-ratio {
                  type string {
                    length "1..9";
                  }
                  description
                    "The average RX error ratio.";
                }
                leaf maximum-rx-error-ratio {
                  type string {
                    length "1..9";
                  }
                  description
                    "The maximum RX error ratio.";
                }
                leaf minimum-rx-error-ratio {
                  type string {
                    length "1..9";
                  }
                  description
                    "The minimum RX error ratio.";
                }
                container twoway-loss-datas {
                  description
                    "List of two way loss data.";
                  list twoway-loss-data {
                    key "index";
                    description
                      "Statistics of data of two-way loss measurement.";
                    leaf index {
                      type uint32;
                      description
                        "Data index of two-way loss measurement.";
                    }
                    leaf loss {
                      type uint32;
                      description
                        "Two-way loss results.";
                    }
                    leaf loss-ratio {
                      type string {
                        length "1..9";
                      }
                      description
                        "Two-way lossRatio results.";
                    }
                    leaf error {
                      type uint32;
                      description
                        "Two-way error results.";
                    }
                    leaf error-ratio {
                      type string {
                        length "1..9";
                      }
                      description
                        "Two-way error ratio results.";
                    }
                  }
                }
              }
            }
          }
        }
      }
      container sender {
        presence "Enable sender of TWAMP";
        description
          "Configure the sender of TWAMP light.";
        container sessions {
          description
            "List of sender session.";
          list session {
            key "id";
            description
              "Configure the object of sender session.";
            leaf id {
              type leafref {
                path "/ncs:devices/ncs:device/ncs:live-status/twamp-controller:twamp-controller/twamp-controller:client/twamp-controller:sessions/twamp-controller:session/twamp-controller:id" {
                  tailf:xpath-root 3;
                }
              }
              description
                "Configure the session ID of sender session.";
            }
            leaf period {
              type live_ncs_period-type;
              units "ms";
              // NCS drop default statement
              description
                "The period of sender session.";
            }
            leaf timeout {
              type uint16 {
                range "1..10";
              }
              units "s";
              // NCS drop default statement
              description
                "The timeout of sender session.";
            }
          }
        }
        container regular-sessions {
          description
            "List of sender regular session.";
          list regular-session {
            key "id";
            description
              "Configure the object of sender regular session.";
            leaf id {
              type leafref {
                path "/ncs:devices/ncs:device/ncs:live-status/twamp-controller:twamp-controller/twamp-controller:client/twamp-controller:sessions/twamp-controller:session/twamp-controller:id" {
                  tailf:xpath-root 3;
                }
              }
              description
                "The session ID of regular sender session.";
            }
            leaf regular-time {
              ext:operation-exclude "update|delete";
              type uint16 {
                range "10..60";
              }
              units "s";
              // NCS drop default statement
              description
                "The regular time of sender regular session.";
            }
            leaf packet-count {
              ext:operation-exclude "update|delete";
              type uint32 {
                range "10..1000";
              }
              // NCS drop default statement
              description
                "The packet count of sender regular session.";
            }
            leaf timeout {
              ext:operation-exclude "update|delete";
              type uint8 {
                range "1..10";
              }
              units "s";
              // NCS drop default statement
              description
                "The timeout of sender regular session.";
            }
          }
        }
      }
    }
  }
  augment "/ncs:devices/ncs:template/ncs:ned-id/ncs:config" {
    container twamp-controller {
      description
        "TWAMP Controller.";
      container client {
        presence "Enable client of TWAMP.";
        description
          "Configure the client of TWAMP light.";
        container sessions {
          description
            "List of configuration session.";
          list session {
            // NCS patched for predictable order
            ordered-by user;
            key "id";
            unique "send-ip-addr ref-ip-addr send-port ref-port vrf-name";
            description
              "Configure the object of session.";
            leaf id {
              type string;
              description
                "The session ID of configuration session.";
            }
            leaf send-ip-addr {
              type string;
              // NCS drop must statement
              // NCS drop mandatory statement
              description
                "The sender IP address of configuration session.";
            }
            leaf ref-ip-addr {
              type string;
              // NCS drop must statement
              // NCS drop mandatory statement
              description
                "The reflector IP address of configuration session.";
            }
            leaf send-port {
              type string;
              // NCS drop mandatory statement
              description
                "The sender port of configuration session.";
            }
            leaf ref-port {
              type string;
              // NCS drop mandatory statement
              description
                "The reflector port of configuration session.";
            }
            leaf vrf-name {
              type string;
              // NCS drop must statement
              description
                "The VRF name of configuration session.";
            }
            leaf dscp-value {
              type string;
              // NCS drop default statement
              description
                "The DSCP value of configuration session.";
            }
            leaf padding-length {
              type string;
              // NCS drop must statement
              // NCS drop default statement
              description
                "The padding length of configuration session. The value range is 32-1454 and 32-1434 in V4 and V6, respectively.";
            }
            leaf padding-type {
              type ncs_template_padding-info;
              // NCS drop default statement
              description
                "Padding type.";
            }
            leaf binded-interface {
              type string;
              description
                "The interface name which the test-session is binded to.";
            }
            leaf description {
              type string;
              description
                "Session description.";
            }
            leaf link-bundle-if {
              type string;
              // NCS drop must statement
              // NCS drop must statement
              description
                "Link-bundle interface that the session binds.";
            }
            container twoway-loss-threshold {
              description
                "Configure the twoway loss threshold of session.";
              leaf up-limit {
                type string;
                units "%";
                // NCS drop default statement
                description
                  "Twoway loss threshold upper limit.";
              }
              leaf low-limit {
                type string;
                units "%";
                // NCS drop default statement
                description
                  "Twoway loss threshold lower limit.";
              }
            }
            container twoway-delay-threshold {
              description
                "Configure the twoway delay threshold of session.";
              leaf up-limit {
                type string;
                units "ms";
                // NCS drop must statement
                // NCS drop default statement
                description
                  "Twoway delay threshold upper limit.";
              }
              leaf low-limit {
                type string;
                units "ms";
                // NCS drop must statement
                // NCS drop default statement
                description
                  "Twoway delay threshold lower limit.";
              }
            }
            container twoway-jitter-threshold {
              description
                "Configure the twoway jitter threshold of session.";
              leaf up-limit {
                type string;
                units "ms";
                // NCS drop must statement
                // NCS drop default statement
                description
                  "Twoway jitter threshold upper limit.";
              }
              leaf low-limit {
                type string;
                units "ms";
                // NCS drop must statement
                // NCS drop default statement
                description
                  "Twoway jitter threshold lower limit.";
              }
            }
            // NCS drop config false container 'session-detail'
            // NCS drop config false container 'twoway-delay-result'
            // NCS drop config false container 'twoway-delay-result-link-bundle-ifs'
            // NCS drop config false container 'twoway-loss-result'
            // NCS drop config false container 'twoway-loss-result-link-bundle-ifs'
          }
        }
      }
      container sender {
        presence "Enable sender of TWAMP";
        description
          "Configure the sender of TWAMP light.";
        container sessions {
          description
            "List of sender session.";
          list session {
            // NCS patched for predictable order
            ordered-by user;
            key "id";
            description
              "Configure the object of sender session.";
            leaf id {
              type string;
              description
                "Configure the session ID of sender session.";
            }
            leaf period {
              type ncs_template_period-type;
              units "ms";
              // NCS drop default statement
              description
                "The period of sender session.";
            }
            leaf timeout {
              type string;
              units "s";
              // NCS drop default statement
              description
                "The timeout of sender session.";
            }
          }
        }
        container regular-sessions {
          description
            "List of sender regular session.";
          list regular-session {
            // NCS patched for predictable order
            ordered-by user;
            key "id";
            description
              "Configure the object of sender regular session.";
            leaf id {
              type string;
              description
                "The session ID of regular sender session.";
            }
            leaf regular-time {
              ext:operation-exclude "update|delete";
              type string;
              units "s";
              // NCS drop default statement
              description
                "The regular time of sender regular session.";
            }
            leaf packet-count {
              ext:operation-exclude "update|delete";
              type string;
              // NCS drop default statement
              description
                "The packet count of sender regular session.";
            }
            leaf timeout {
              ext:operation-exclude "update|delete";
              type string;
              units "s";
              // NCS drop default statement
              description
                "The timeout of sender regular session.";
            }
          }
        }
      }
    }
  }
}
