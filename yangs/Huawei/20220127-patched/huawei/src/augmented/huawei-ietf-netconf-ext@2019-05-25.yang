module huawei-ietf-netconf-ext {
  // Generated by yanger -t ncs
  tailf:mount-id "huawei-nc-1.0:huawei-nc-1.0";
  tailf:ncs-device-type "netconf";

  namespace "urn:huawei:yang:huawei-ietf-netconf-ext";
  prefix nc-ext;

  import ietf-netconf {
    prefix nc;
  }
  import huawei-extension {
    prefix ext;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Extension of NETCONF protocol standard operations that were used privately for Huawei device.";

  revision 2019-05-25 {
    description
      "Initial revision.";
    reference "Huawei private.";
  }
  ext:task-name "netconf";

  typedef ncs_template_flow-id-type {
    type string;
    description
      "This type used for the attribute 'flow-id';
       The rpc-reply of the sync-full/edit-config operation will contain the 'flow-id' XML attribute.";
  }

  typedef ncs_rpc_notif_flow-id-type {
    type uint32;
    description
      "This type used for the attribute 'flow-id';
       The rpc-reply of the sync-full/edit-config operation will contain the 'flow-id' XML attribute.";
  }

  typedef live_ncs_flow-id-type {
    type uint32;
    description
      "This type used for the attribute 'flow-id';
       The rpc-reply of the sync-full/edit-config operation will contain the 'flow-id' XML attribute.";
  }

  typedef flow-id-type {
    type uint32;
    description
      "This type used for the attribute 'flow-id';
       The rpc-reply of the sync-full/edit-config operation will contain the 'flow-id' XML attribute.";
  }

  augment "/ncs:devices/ncs:device/ncs:notifications/ncs:received-notifications/ncs:notification/ncs:data" {
    container netconf-rpc-keepalive {
      presence "";
      config false;
      description
        "This notification will be generated every 20 seconds if the operation takes more time,
         Client must use filter to subscribe this notification for a specific session,
         and it can report error if this notification is not enabled without the filter.";
      leaf session-id {
        type uint32;
        description
          "Session in which client want to receive this notitification;
           Unique identifier for the session. This value is the NETCONF session identifier, as defined in [RFC4741].Refer to RFC 6022 section 2.1.4.";
      }
      leaf message-id {
        type string {
          length "0..4095";
        }
        description
          "Message id of the rpc operation that is taking long time to execute.";
      }
    }
  }
  augment "/ncs:devices/ncs:device/ncs:netconf-notifications/ncs:received-notifications/ncs:notification/ncs:data" {
    container netconf-rpc-keepalive {
      presence "";
      config false;
      description
        "This notification will be generated every 20 seconds if the operation takes more time,
         Client must use filter to subscribe this notification for a specific session,
         and it can report error if this notification is not enabled without the filter.";
      leaf session-id {
        type uint32;
        description
          "Session in which client want to receive this notitification;
           Unique identifier for the session. This value is the NETCONF session identifier, as defined in [RFC4741].Refer to RFC 6022 section 2.1.4.";
      }
      leaf message-id {
        type string {
          length "0..4095";
        }
        description
          "Message id of the rpc operation that is taking long time to execute.";
      }
    }
  }
  augment "/ncs:devices/ncs:device/ncs:rpc/nc:rpc-commit/nc:commit/nc:input" {
    description
      "Adds the <description> parameter to
       the input of the NETCONF <commit> operation.";
    leaf description {
      type string {
        length "1..60";
      }
      description
        "This is used for commit comments to identify specific commit operation.";
    }
  }
  augment "/ncs:devices/ncs:device/ncs:rpc/nc:rpc-delete-config/nc:delete-config/nc:input/nc:target/nc:config-target" {
    description
      "Adds the <candidate> target to
       the input of the NETCONF <delete-config> operation.";
    leaf candidate {
      type empty;
      description
        "The candidate configuration is the config target.";
    }
  }
}
