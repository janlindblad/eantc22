module huawei-mpls-forward-deviations-NE8000 {
  // Generated by yanger -t ncs
  tailf:mount-id "huawei-nc-1.0:huawei-nc-1.0";
  tailf:ncs-device-type "netconf";

  namespace "urn:huawei:yang:huawei-mpls-forward-deviations-NE8000";
  prefix mpls-forward-devs-NE8000;

  import huawei-mpls-forward {
    prefix mpls-forward;
  }
  import huawei-loadbalance {
    prefix loadbalance;
  }
  import huawei-mpls {
    prefix mpls;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "This module defines deviation statements for huawei-mpls-forward module.";

  revision 2019-11-06 {
    description
      "Initial revision.";
    reference "Huawei private.";
  }

  deviation "/ncs:devices/ncs:template/ncs:ned-id/ncs:config/loadbalance:loadbalance/mpls-forward:mpls-hashpacket" {
    deviate not-supported;
  }
  deviation "/ncs:devices/ncs:device/ncs:live-status/loadbalance:loadbalance/mpls-forward:mpls-hashpacket" {
    deviate not-supported;
  }
  deviation "/ncs:devices/ncs:device/ncs:config/loadbalance:loadbalance/mpls-forward:mpls-hashpacket" {
    deviate not-supported;
  }
  deviation "/ncs:devices/ncs:template/ncs:ned-id/ncs:config/loadbalance:loadbalance/mpls-forward:mpls-intfmtu" {
    deviate not-supported;
  }
  deviation "/ncs:devices/ncs:device/ncs:live-status/loadbalance:loadbalance/mpls-forward:mpls-intfmtu" {
    deviate not-supported;
  }
  deviation "/ncs:devices/ncs:device/ncs:config/loadbalance:loadbalance/mpls-forward:mpls-intfmtu" {
    deviate not-supported;
  }
  deviation "/ncs:devices/ncs:template/ncs:ned-id/ncs:config/mpls:mpls/mpls-forward:ldp-separate" {
    deviate not-supported;
  }
  deviation "/ncs:devices/ncs:device/ncs:live-status/mpls:mpls/mpls-forward:ldp-separate" {
    deviate not-supported;
  }
  deviation "/ncs:devices/ncs:device/ncs:config/mpls:mpls/mpls-forward:ldp-separate" {
    deviate not-supported;
  }
  deviation "/ncs:devices/ncs:device/ncs:live-status/mpls:mpls/mpls-forward:disp-convergence-mode" {
    deviate not-supported;
  }
  deviation "/ncs:devices/ncs:template/ncs:ned-id/ncs:config/mpls:mpls/mpls:common/mpls-forward:mpls-forward/mpls-forward:static-label-only" {
    deviate not-supported;
  }
  deviation "/ncs:devices/ncs:device/ncs:live-status/mpls:mpls/mpls:common/mpls-forward:mpls-forward/mpls-forward:static-label-only" {
    deviate not-supported;
  }
  deviation "/ncs:devices/ncs:device/ncs:config/mpls:mpls/mpls:common/mpls-forward:mpls-forward/mpls-forward:static-label-only" {
    deviate not-supported;
  }
}
