module huawei-dcn {
  // Generated by yanger -t ncs
  tailf:mount-id "huawei-nc-1.0:huawei-nc-1.0";
  tailf:ncs-device-type "netconf";

  yang-version 1;
  namespace "urn:huawei:yang:huawei-dcn";
  prefix dcn;

  import huawei-extension {
    prefix ext;
  }
  import huawei-pub-type {
    prefix pub-type;
  }
  import huawei-ifm {
    prefix ifm;
  }
  import huawei-network-instance {
    prefix ni;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Data communication network.";

  revision 2020-09-23 {
    description
      "Added the DCN and TC DCN functions for interfaces.";
    reference "Huawei private.";
  }
  revision 2020-07-16 {
    description
      "Init revision.";
    reference "Huawei private.";
  }
  ext:task-name "dcn";
  ext:refine-ext "/ni:network-instance/ni:instances/ni:instance" {
    ext:generated-by "system" {
      description
        "The instance is create by DCN.";
      when "/dcn:dcn/dcn:site/dcn:enable = 'true'" {
        tailf:xpath-root 3;
      }
      ext:filter "starts-with(ni:name, '__dcn_vpn__')";
    }
  }

  augment "/ncs:devices/ncs:device/ncs:config" {
    container dcn {
      tailf:ncs-device-type "netconf";
      tailf:display-when "not(../../ncs:module) or ../../ncs:module[ncs:name='huawei-dcn']";
      description
        "Data communication network.";
      container site {
        description
          "Configure data communication network.";
        leaf enable {
          type boolean;
          default "true";
          description
            "Enable/disable DCN.";
        }
        leaf ne-id {
          ext:dynamic-default;
          ext:operation-exclude "create|delete";
          type pub-type:hex-binary;
          description
            "Configure the NE identifier.
             Neid identify a network element (NE) uniquely.
             Neid=subnetid<<16+baseid, in which subnetid varies from 0x01 to 0xfe, and baseid varies from 0x0001 to 0xfffe.
             An error is reported if the NE ID conflicts with the NE ID in the core routing table.";
        }
      }
    }
  }
  augment "/ncs:devices/ncs:device/ncs:live-status" {
    container dcn {
      tailf:ncs-device-type "netconf";
      tailf:display-when "not(../../ncs:module) or ../../ncs:module[ncs:name='huawei-dcn'] or (../../ncs:live-status-protocol[not(ncs:capability)]) or (../../ncs:live-status-protocol/ncs:capability/ncs:module[.='huawei-dcn'])";
      description
        "Data communication network.";
      container site {
        description
          "Configure data communication network.";
        leaf enable {
          type boolean;
          // NCS drop default statement
          description
            "Enable/disable DCN.";
        }
        leaf ne-id {
          ext:dynamic-default;
          ext:operation-exclude "create|delete";
          type pub-type:live_ncs_hex-binary;
          description
            "Configure the NE identifier.
             Neid identify a network element (NE) uniquely.
             Neid=subnetid<<16+baseid, in which subnetid varies from 0x01 to 0xfe, and baseid varies from 0x0001 to 0xfffe.
             An error is reported if the NE ID conflicts with the NE ID in the core routing table.";
        }
      }
    }
  }
  augment "/ncs:devices/ncs:template/ncs:ned-id/ncs:config" {
    container dcn {
      description
        "Data communication network.";
      container site {
        description
          "Configure data communication network.";
        leaf enable {
          type string;
          // NCS drop default statement
          description
            "Enable/disable DCN.";
        }
        leaf ne-id {
          ext:dynamic-default;
          ext:operation-exclude "create|delete";
          type pub-type:ncs_template_hex-binary;
          description
            "Configure the NE identifier.
             Neid identify a network element (NE) uniquely.
             Neid=subnetid<<16+baseid, in which subnetid varies from 0x01 to 0xfe, and baseid varies from 0x0001 to 0xfffe.
             An error is reported if the NE ID conflicts with the NE ID in the core routing table.";
        }
      }
    }
  }
  augment "/ncs:devices/ncs:template/ncs:ned-id/ncs:config/ifm:ifm/ifm:interfaces/ifm:interface" {
    description
      "DCN interface configuration.";
    container dcn {
      // NCS drop when statement
      description
        "Configure DCN interface.";
      container dcnv4 {
        description
          "Configure DCN interface.";
        leaf default-port {
          type string;
          ext:operation-exclude "create|delete|update";
          description
            "Enable/disable auto enable DCN.";
        }
        leaf enable {
          type string;
          ext:dynamic-default {
            ext:default-value "true" {
              // NCS drop when statement
              description
                "DCN is enabled on a default DCN port when the global DCN is enabled.";
            }
          }
          description
            "Enable/disable DCN.";
        }
      }
      container tc-dcn {
        description
          "Configure TC DCN interface.";
        leaf default-port {
          type string;
          ext:operation-exclude "create|delete|update";
          description
            "Enable/disable auto enable TC DCN.";
        }
        leaf enable {
          type string;
          ext:dynamic-default {
            ext:default-value "true" {
              // NCS drop when statement
              description
                "TC DCN is enabled on a default TC DCN port when the global DCN is enabled.";
            }
          }
          description
            "Enable/disable TC DCN.";
        }
      }
    }
  }
  augment "/ncs:devices/ncs:device/ncs:live-status/ifm:ifm/ifm:interfaces/ifm:interface" {
    description
      "DCN interface configuration.";
    container dcn {
      tailf:ncs-device-type "netconf";
      tailf:display-when "not(../../../../../ncs:module) or ../../../../../ncs:module[ncs:name='huawei-dcn'] or (../../../../../ncs:live-status-protocol[not(ncs:capability)]) or (../../../../../ncs:live-status-protocol/ncs:capability/ncs:module[.='huawei-dcn'])";
      // NCS drop when statement
      description
        "Configure DCN interface.";
      container dcnv4 {
        description
          "Configure DCN interface.";
        leaf default-port {
          type boolean;
          ext:operation-exclude "create|delete|update";
          description
            "Enable/disable auto enable DCN.";
        }
        leaf enable {
          type boolean;
          ext:dynamic-default {
            ext:default-value "true" {
              // NCS drop when statement
              description
                "DCN is enabled on a default DCN port when the global DCN is enabled.";
            }
          }
          description
            "Enable/disable DCN.";
        }
      }
      container tc-dcn {
        description
          "Configure TC DCN interface.";
        leaf default-port {
          type boolean;
          ext:operation-exclude "create|delete|update";
          description
            "Enable/disable auto enable TC DCN.";
        }
        leaf enable {
          type boolean;
          ext:dynamic-default {
            ext:default-value "true" {
              // NCS drop when statement
              description
                "TC DCN is enabled on a default TC DCN port when the global DCN is enabled.";
            }
          }
          description
            "Enable/disable TC DCN.";
        }
      }
    }
  }
  augment "/ncs:devices/ncs:device/ncs:config/ifm:ifm/ifm:interfaces/ifm:interface" {
    description
      "DCN interface configuration.";
    container dcn {
      tailf:ncs-device-type "netconf";
      tailf:display-when "not(../../../../../ncs:module) or ../../../../../ncs:module[ncs:name='huawei-dcn']";
      when "/dcn:dcn/dcn:site/dcn:enable = 'true'" {
        tailf:xpath-root 3;
      }
      description
        "Configure DCN interface.";
      container dcnv4 {
        description
          "Configure DCN interface.";
        leaf default-port {
          type boolean;
          ext:operation-exclude "create|delete|update";
          description
            "Enable/disable auto enable DCN.";
        }
        leaf enable {
          type boolean;
          ext:dynamic-default {
            ext:default-value "true" {
              when "/dcn:dcn/dcn:site/dcn:enable = 'true' and ../default-port = 'true'" {
                tailf:xpath-root 3;
              }
              description
                "DCN is enabled on a default DCN port when the global DCN is enabled.";
            }
          }
          description
            "Enable/disable DCN.";
        }
      }
      container tc-dcn {
        description
          "Configure TC DCN interface.";
        leaf default-port {
          type boolean;
          ext:operation-exclude "create|delete|update";
          description
            "Enable/disable auto enable TC DCN.";
        }
        leaf enable {
          type boolean;
          ext:dynamic-default {
            ext:default-value "true" {
              when "/dcn:dcn/dcn:site/dcn:enable = 'true' and ../default-port = 'true'" {
                tailf:xpath-root 3;
              }
              description
                "TC DCN is enabled on a default TC DCN port when the global DCN is enabled.";
            }
          }
          description
            "Enable/disable TC DCN.";
        }
      }
    }
  }
}
