module huawei-codesign {
  // Generated by yanger -t ncs
  tailf:mount-id "huawei-nc-1.0:huawei-nc-1.0";
  tailf:ncs-device-type "netconf";

  namespace "urn:huawei:yang:huawei-codesign";
  prefix codesign;

  import ietf-yang-types {
    prefix yang;
  }
  import huawei-extension {
    prefix ext;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Indicate code signature management.";

  revision 2020-07-23 {
    description
      "Add key of list software-crl.";
    reference "Huawei private.";
  }
  revision 2020-06-29 {
    description
      "Modify node description.";
    reference "Huawei private.";
  }
  revision 2020-04-02 {
    description
      "Modify YANG check.";
    reference "Huawei private.";
  }
  revision 2019-03-01 {
    description
      "Initial revision.";
    reference "Huawei private.";
  }
  ext:task-name "patch";

  typedef ncs_template_crl-status {
    type string;
    status deprecated;
    description
      "CRL status value. The alternative enumeration node is valid-type.";
  }

  typedef ncs_template_valid-type {
    type string;
    description
      "CRL status value.";
  }

  typedef ncs_rpc_notif_crl-status {
    type enumeration {
      enum "0" {
        value 0;
        description
          "Invalid file.";
      }
      enum "1" {
        value 1;
        description
          "Valid file.";
      }
    }
    status deprecated;
    description
      "CRL status value. The alternative enumeration node is valid-type.";
  }

  typedef ncs_rpc_notif_valid-type {
    type enumeration {
      enum "invalid" {
        value 0;
        description
          "Invalid file.";
      }
      enum "valid" {
        value 1;
        description
          "Valid file.";
      }
    }
    description
      "CRL status value.";
  }

  typedef live_ncs_crl-status {
    type enumeration {
      enum "0" {
        value 0;
        description
          "Invalid file.";
      }
      enum "1" {
        value 1;
        description
          "Valid file.";
      }
    }
    status deprecated;
    description
      "CRL status value. The alternative enumeration node is valid-type.";
  }

  typedef live_ncs_valid-type {
    type enumeration {
      enum "invalid" {
        value 0;
        description
          "Invalid file.";
      }
      enum "valid" {
        value 1;
        description
          "Valid file.";
      }
    }
    description
      "CRL status value.";
  }

  typedef crl-status {
    type enumeration {
      enum "0" {
        value 0;
        description
          "Invalid file.";
      }
      enum "1" {
        value 1;
        description
          "Valid file.";
      }
    }
    status deprecated;
    description
      "CRL status value. The alternative enumeration node is valid-type.";
  }

  typedef valid-type {
    type enumeration {
      enum "invalid" {
        value 0;
        description
          "Invalid file.";
      }
      enum "valid" {
        value 1;
        description
          "Valid file.";
      }
    }
    description
      "CRL status value.";
  }

  augment "/ncs:devices/ncs:device/ncs:rpc" {
    container rpc-software-crl-load {
      tailf:ncs-device-type "netconf";
      tailf:display-when "not(../../ncs:module) or ../../ncs:module[ncs:name='huawei-codesign']";
      tailf:action software-crl-load {
        tailf:actionpoint ncsproxy {
          tailf:internal;
        }
        description
          "Load CRL file.";
        ext:node-ref "/codesign/crl-names/crl-name";
        input {
          leaf name {
            type string;
            mandatory true;
            description
              "CRL file name.";
          }
        }
      }
    }
  }
  augment "/ncs:devices/ncs:device-group/ncs:ned-id/ncs:rpc" {
    container rpc-software-crl-load {
      tailf:ncs-device-type "netconf";
      tailf:display-when "/ncs:devices/ncs:device[ncs:name=current()/../../../ncs:member]/ncs:module[ncs:name='huawei-codesign']";
      tailf:action software-crl-load {
        tailf:actionpoint ncsproxy {
          tailf:internal;
        }
        description
          "Load CRL file.";
        ext:node-ref "/codesign/crl-names/crl-name";
        input {
          leaf name {
            type string;
            mandatory true;
            description
              "CRL file name.";
          }
        }
      }
    }
  }
  augment "/ncs:devices/ncs:device/ncs:config" {
    // NCS drop config false container codesign
  }
  augment "/ncs:devices/ncs:device/ncs:live-status" {
    container codesign {
      tailf:ncs-device-type "netconf";
      tailf:display-when "not(../../ncs:module) or ../../ncs:module[ncs:name='huawei-codesign'] or (../../ncs:live-status-protocol[not(ncs:capability)]) or (../../ncs:live-status-protocol/ncs:capability/ncs:module[.='huawei-codesign'])";
      description
        "Indicate code signature management.";
      container software-crls {
        description
          "List of operational state of CRL information.";
        list software-crl {
          key "slot publisher";
          description
            "Operational state of CRL information.";
          leaf slot {
            type string {
              length "1..64";
            }
            description
              "Slot ID of a board.";
          }
          leaf publisher {
            type string {
              length "1..256";
            }
            description
              "CRL publisher.";
          }
          leaf date {
            type yang:date-and-time;
            description
              "CRL publish date.";
          }
          leaf valid {
            type live_ncs_crl-status;
            status deprecated;
            description
              "CRL status. The node valid is deprecated. You are advised to use the node valid-type.";
          }
          leaf valid-type {
            type live_ncs_valid-type;
            description
              "CRL status.";
          }
        }
      }
      container packages-verify-faileds {
        description
          "List of operational state of package digital signature verification failed.";
        list packages-verify-failed {
          key "slot";
          description
            "Operational state of package digital signature verification failed.";
          leaf slot {
            type string {
              length "1..64";
            }
            description
              "Slot ID of a board.";
          }
          leaf name {
            type string {
              length "4..127";
            }
            ext:support-filter "true";
            description
              "Package name that package digital signature verification failed to be verified.";
          }
        }
      }
      container crl-names {
        description
          "List of operational data of CRL file.";
        list crl-name {
          key "name";
          description
            "Operational data of CRL file.";
          leaf name {
            type string {
              length "5..63";
            }
            description
              "CRL file name.";
          }
        }
      }
    }
  }
  augment "/ncs:devices/ncs:template/ncs:ned-id/ncs:config" {
    // NCS drop config false container codesign
  }
}
