module huawei-ip-deviations-NE8000 {
  // Generated by yanger -t ncs
  tailf:mount-id "huawei-nc-1.0:huawei-nc-1.0";
  tailf:ncs-device-type "netconf";

  namespace "urn:huawei:yang:huawei-ip-deviations-NE8000";
  prefix ip-devs-NE8000;

  import huawei-ip {
    prefix ip;
  }
  import huawei-ifm {
    prefix ifm;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Common interface management, which includes the public configuration of interfaces.";

  revision 2019-04-15 {
    description
      "Init revision.";
    reference "Huawei private.";
  }

  deviation "/ncs:devices/ncs:device/ncs:live-status/ifm:ifm/ifm:interfaces/ifm:interface/ip:ipv4/ip:state/ip:gateways" {
    deviate not-supported;
  }
  deviation "/ncs:devices/ncs:template/ncs:ned-id/ncs:config/ifm:ifm/ifm:interfaces/ifm:interface/ip:ipv4/ip:address/ip:common-address/ip:addresses/ip:address/ip:type" {
    deviate add {
      // NCS drop must statement
    }
  }
  deviation "/ncs:devices/ncs:device/ncs:live-status/ifm:ifm/ifm:interfaces/ifm:interface/ip:ipv4/ip:address/ip:common-address/ip:addresses/ip:address/ip:type" {
    deviate add {
      // NCS drop must statement
    }
  }
  deviation "/ncs:devices/ncs:device/ncs:config/ifm:ifm/ifm:interfaces/ifm:interface/ip:ipv4/ip:address/ip:common-address/ip:addresses/ip:address/ip:type" {
    deviate add {
      must "(../ip:type='sub' and /ifm:ifm/ifm:global/ifm:ipv4-ignore-primary-sub='false') or ../ip:type='main'" {
        tailf:xpath-root 3;
      }
    }
  }
}
