module huawei-software-notification {
  // Generated by yanger -t ncs
  tailf:mount-id "huawei-nc-1.0:huawei-nc-1.0";
  tailf:ncs-device-type "netconf";

  yang-version 1;
  namespace "urn:huawei:yang:huawei-software-notification";
  prefix software-notification;

  import huawei-extension {
    prefix ext;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Notification of software.";

  revision 2020-01-13 {
    description
      "Yang white-box.";
    reference "Huawei private.";
  }
  revision 2019-10-16 {
    description
      "Initial revision.";
    reference "Huawei private.";
  }
  ext:task-name "rpm";

  augment "/ncs:devices/ncs:device/ncs:notifications/ncs:received-notifications/ncs:notification/ncs:data" {
    container package-verify-failed-resume {
      presence "";
      config false;
      description
        "Package digital signature verification succeeded to be verified.";
      leaf physical-name {
        type string {
          length "1..31";
        }
        description
          "Entity name.";
      }
      leaf package-name {
        type string {
          length "4..127";
        }
        description
          "Software package name.";
      }
      leaf fail-reason {
        type string {
          length "1..127";
        }
        description
          "Error reason.";
      }
    }
  }
  augment "/ncs:devices/ncs:device/ncs:notifications/ncs:received-notifications/ncs:notification/ncs:data" {
    container package-verify-failed {
      presence "";
      config false;
      description
        "Package digital signature verification failed to be verified.";
      leaf physical-name {
        type string {
          length "1..31";
        }
        description
          "Entity name.";
      }
      leaf package-name {
        type string {
          length "4..127";
        }
        description
          "Software package name.";
      }
      leaf fail-reason {
        type string {
          length "1..127";
        }
        description
          "Error reason.";
      }
    }
  }
  augment "/ncs:devices/ncs:device/ncs:netconf-notifications/ncs:received-notifications/ncs:notification/ncs:data" {
    container package-verify-failed-resume {
      presence "";
      config false;
      description
        "Package digital signature verification succeeded to be verified.";
      leaf physical-name {
        type string {
          length "1..31";
        }
        description
          "Entity name.";
      }
      leaf package-name {
        type string {
          length "4..127";
        }
        description
          "Software package name.";
      }
      leaf fail-reason {
        type string {
          length "1..127";
        }
        description
          "Error reason.";
      }
    }
  }
  augment "/ncs:devices/ncs:device/ncs:netconf-notifications/ncs:received-notifications/ncs:notification/ncs:data" {
    container package-verify-failed {
      presence "";
      config false;
      description
        "Package digital signature verification failed to be verified.";
      leaf physical-name {
        type string {
          length "1..31";
        }
        description
          "Entity name.";
      }
      leaf package-name {
        type string {
          length "4..127";
        }
        description
          "Software package name.";
      }
      leaf fail-reason {
        type string {
          length "1..127";
        }
        description
          "Error reason.";
      }
    }
  }
}
