module huawei-bras-multicast-fwd {
  // Generated by yanger -t ncs
  tailf:mount-id "huawei-nc-1.0:huawei-nc-1.0";
  tailf:ncs-device-type "netconf";

  yang-version 1;
  namespace "urn:huawei:yang:huawei-bras-multicast-fwd";
  prefix bras-multicast-fwd;

  import huawei-extension {
    prefix ext;
  }
  import huawei-bras-multicast {
    prefix bras-multicast;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Configure bras attribute.";

  revision 2020-11-19 {
    description
      "Add new nodes.";
    reference "Huawei private.";
  }
  revision 2019-11-19 {
    description
      "Init revision.";
    reference "Huawei private.";
  }
  ext:task-name "forwarding";

  typedef ncs_template_board-type {
    type string;
    description
      "Multicast RUI static board type.";
  }

  typedef ncs_rpc_notif_board-type {
    type enumeration {
      enum "board-type-total" {
        value 0;
        description
          "All board types.";
      }
      enum "board-type-mpu" {
        value 1;
        description
          "Board type of MPU.";
      }
      enum "board-type-lpu" {
        value 2;
        description
          "Board type of LPU.";
      }
    }
    description
      "Multicast RUI static board type.";
  }

  typedef live_ncs_board-type {
    type enumeration {
      enum "board-type-total" {
        value 0;
        description
          "All board types.";
      }
      enum "board-type-mpu" {
        value 1;
        description
          "Board type of MPU.";
      }
      enum "board-type-lpu" {
        value 2;
        description
          "Board type of LPU.";
      }
    }
    description
      "Multicast RUI static board type.";
  }

  typedef board-type {
    type enumeration {
      enum "board-type-total" {
        value 0;
        description
          "All board types.";
      }
      enum "board-type-mpu" {
        value 1;
        description
          "Board type of MPU.";
      }
      enum "board-type-lpu" {
        value 2;
        description
          "Board type of LPU.";
      }
    }
    description
      "Multicast RUI static board type.";
  }

  augment "/ncs:devices/ncs:device/ncs:rpc" {
    container rpc-reset-rbs-service-statistics {
      tailf:ncs-device-type "netconf";
      tailf:display-when "not(../../ncs:module) or ../../ncs:module[ncs:name='huawei-bras-multicast-fwd']";
      tailf:action reset-rbs-service-statistics {
        tailf:actionpoint ncsproxy {
          tailf:internal;
        }
        description
          "Delete the statistic of RBS services informations.";
      }
    }
  }
  augment "/ncs:devices/ncs:device-group/ncs:ned-id/ncs:rpc" {
    container rpc-reset-rbs-service-statistics {
      tailf:ncs-device-type "netconf";
      tailf:display-when "/ncs:devices/ncs:device[ncs:name=current()/../../../ncs:member]/ncs:module[ncs:name='huawei-bras-multicast-fwd']";
      tailf:action reset-rbs-service-statistics {
        tailf:actionpoint ncsproxy {
          tailf:internal;
        }
        description
          "Delete the statistic of RBS services informations.";
      }
    }
  }
  augment "/ncs:devices/ncs:device/ncs:config" {
    container bras-multicast-fwd {
      tailf:ncs-device-type "netconf";
      tailf:display-when "not(../../ncs:module) or ../../ncs:module[ncs:name='huawei-bras-multicast-fwd']";
      description
        "Table of BRAS multicast forward.";
      // NCS drop config false container 'rbs-service-statistics'
    }
  }
  augment "/ncs:devices/ncs:device/ncs:live-status" {
    container bras-multicast-fwd {
      tailf:ncs-device-type "netconf";
      tailf:display-when "not(../../ncs:module) or ../../ncs:module[ncs:name='huawei-bras-multicast-fwd'] or (../../ncs:live-status-protocol[not(ncs:capability)]) or (../../ncs:live-status-protocol/ncs:capability/ncs:module[.='huawei-bras-multicast-fwd'])";
      description
        "Table of BRAS multicast forward.";
      container rbs-service-statistics {
        description
          "List of IGMP packet statistics based on the RBS name.";
        list rbs-service-statistic {
          key "name";
          description
            "Statistics of IGMP packets based on the RBS name.";
          leaf name {
            type string {
              length "1..32";
            }
            description
              "RBS name.";
          }
          leaf send-total {
            type uint32;
            units "packet";
            description
              "Total of sent packets.";
          }
          leaf send-fail-total {
            type uint32;
            units "packet";
            description
              "Total of packets that fail to be sent.";
          }
          leaf send-success-total {
            type uint32;
            units "packet";
            description
              "Total of packets that are successfully sent.";
          }
          leaf receive-total {
            type uint32;
            units "packet";
            description
              "Total of received packets.";
          }
          leaf receive-fail-total {
            type uint32;
            units "packet";
            description
              "Total of packets that fail to be received.";
          }
          leaf receive-success-total {
            type uint32;
            units "packet";
            description
              "Total of packets that are successfully received.";
          }
          container board-statistics {
            description
              "List of IGMP packet statistics based on the board type.";
            list board-statistic {
              key "slot";
              description
                "Statistics of IGMP packets based on the board type.";
              leaf slot {
                type string {
                  length "1..16";
                }
                description
                  "Slot ID.";
              }
              leaf board-type {
                type live_ncs_board-type;
                description
                  "Board type.";
              }
              leaf send-packet {
                type uint32;
                units "packet";
                description
                  "Number of sent packets.";
              }
              leaf send-fail-packet {
                type uint32;
                units "packet";
                description
                  "Number of packets that failed to be sent.";
              }
              leaf send-success-packet {
                type uint32;
                units "packet";
                description
                  "Number of successfully sent packets.";
              }
              leaf receive-packet {
                type uint32;
                units "packet";
                description
                  "Number of received packets.";
              }
              leaf receive-fail-packet {
                type uint32;
                units "packet";
                description
                  "Number of packets that failed to be received.";
              }
              leaf receive-success-packet {
                type uint32;
                units "packet";
                description
                  "Number of successfully received packets.";
              }
            }
          }
        }
      }
    }
  }
  augment "/ncs:devices/ncs:template/ncs:ned-id/ncs:config" {
    container bras-multicast-fwd {
      description
        "Table of BRAS multicast forward.";
      // NCS drop config false container 'rbs-service-statistics'
    }
  }
  augment "/ncs:devices/ncs:template/ncs:ned-id/ncs:config/bras-multicast:bras-multicast" {
    description
      "Configure bras attribute.";
    container bandwidth-enable {
      presence "multicastbandwidth enable";
      description
        "Enable/disable multicast bandwidth.";
    }
  }
  augment "/ncs:devices/ncs:device/ncs:live-status/bras-multicast:bras-multicast" {
    description
      "Configure bras attribute.";
    container bandwidth-enable {
      tailf:ncs-device-type "netconf";
      tailf:display-when "not(../../../ncs:module) or ../../../ncs:module[ncs:name='huawei-bras-multicast-fwd'] or (../../../ncs:live-status-protocol[not(ncs:capability)]) or (../../../ncs:live-status-protocol/ncs:capability/ncs:module[.='huawei-bras-multicast-fwd'])";
      presence "multicastbandwidth enable";
      description
        "Enable/disable multicast bandwidth.";
    }
  }
  augment "/ncs:devices/ncs:device/ncs:config/bras-multicast:bras-multicast" {
    description
      "Configure bras attribute.";
    container bandwidth-enable {
      tailf:ncs-device-type "netconf";
      tailf:display-when "not(../../../ncs:module) or ../../../ncs:module[ncs:name='huawei-bras-multicast-fwd']";
      presence "multicastbandwidth enable";
      description
        "Enable/disable multicast bandwidth.";
    }
  }
}
