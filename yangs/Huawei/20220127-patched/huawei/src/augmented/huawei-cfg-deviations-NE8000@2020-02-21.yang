module huawei-cfg-deviations-NE8000 {
  // Generated by yanger -t ncs
  tailf:mount-id "huawei-nc-1.0:huawei-nc-1.0";
  tailf:ncs-device-type "netconf";

  namespace "urn:huawei:yang:huawei-cfg-deviations-NE8000";
  prefix cfg-devs-NE8000;

  import huawei-cfg {
    prefix cfg;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Configuration management module.";

  revision 2020-02-21 {
    description
      "Init revision.";
    reference "Huawei private.";
  }

  deviation "/ncs:devices/ncs:device/ncs:rpc/cfg:rpc-create-user-label-checkpoint/cfg:create-user-label-checkpoint" {
    deviate not-supported;
  }
  deviation "/ncs:devices/ncs:template/ncs:ned-id/ncs:config/cfg:cfg/cfg:configuration-backup-to-file" {
    deviate not-supported;
  }
  deviation "/ncs:devices/ncs:device/ncs:live-status/cfg:cfg/cfg:configuration-backup-to-file" {
    deviate not-supported;
  }
  deviation "/ncs:devices/ncs:device/ncs:config/cfg:cfg/cfg:configuration-backup-to-file" {
    deviate not-supported;
  }
  deviation "/ncs:devices/ncs:device/ncs:rpc/cfg:rpc-load-configuration-to-candidate/cfg:load-configuration-to-candidate" {
    deviate not-supported;
  }
  deviation "/ncs:devices/ncs:device/ncs:rpc/cfg:rpc-load-configuration-to-candidate-result/cfg:load-configuration-to-candidate-result" {
    deviate not-supported;
  }
}
