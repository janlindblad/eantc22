module huawei-rgm {
  // Generated by yanger -t ncs
  tailf:mount-id "huawei-nc-1.0:huawei-nc-1.0";
  tailf:ncs-device-type "netconf";

  namespace "urn:huawei:yang:huawei-rgm";
  prefix rgm;

  import huawei-ifm {
    prefix ifm;
  }
  import huawei-extension {
    prefix ext;
  }
  import huawei-ip {
    prefix ip;
  }
  import huawei-vrrp {
    prefix vrrp;
  }
  import huawei-route-monitor-group {
    prefix rmg;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "IPv4 Direct Route Association.";

  revision 2019-11-28 {
    description
      "Initial revision.";
    reference "Huawei private.";
  }
  ext:task-name "rgm";

  augment "/ncs:devices/ncs:template/ncs:ned-id/ncs:config/ifm:ifm/ifm:interfaces/ifm:interface/ip:ipv4" {
    description
      "Association between direct routes and a VRRP backup group.";
    container rgm {
      description
        "Configure IPv4 direct route track VRRP, PWs, virtual-access and so on under the ifm interface.";
      choice rgm-track {
        description
          "Association between direct routes and a VRRP backup group, PW status and delay for advertising direct routes.";
        case track-vrrp {
          description
            "Association between direct routes and a VRRP backup group.";
          container track-vrrp {
            description
              "Configure association between direct routes and a VRRP backup group.";
            leaf vrrp-id {
              type string;
              // NCS drop mandatory statement
              description
                "Virtual router identifier.";
            }
            leaf cost-change {
              type string;
              // NCS drop mandatory statement
              description
                "Value that is used as the cost of direct routes when the associated VRRP backup group status changes.";
            }
          }
        }
        case track-pw {
          description
            "Association between direct routes and PW status.";
          container track-pw {
            // NCS drop when statement
            description
              "Configure association between direct routes and PW status.";
            leaf cost-change {
              type string;
              description
                "Value that is used as the cost of direct routes when the associated PW status changes.";
            }
          }
        }
      }
      container track-rtmtg {
        presence "Track route-monitor-group.";
        description
          "Configure association between route-monitor-group routes and interface status.";
        leaf name {
          type string;
          // NCS drop mandatory statement
          description
            "The route-monitor-group was tracked under the interface.";
        }
        leaf down-weight {
          type string;
          description
            "Trigger down weight of a track interface.";
        }
      }
    }
  }
  augment "/ncs:devices/ncs:device/ncs:live-status/ifm:ifm/ifm:interfaces/ifm:interface/ip:ipv4" {
    description
      "Association between direct routes and a VRRP backup group.";
    container rgm {
      tailf:ncs-device-type "netconf";
      tailf:display-when "not(../../../../../../ncs:module) or ../../../../../../ncs:module[ncs:name='huawei-rgm'] or (../../../../../../ncs:live-status-protocol[not(ncs:capability)]) or (../../../../../../ncs:live-status-protocol/ncs:capability/ncs:module[.='huawei-rgm'])";
      description
        "Configure IPv4 direct route track VRRP, PWs, virtual-access and so on under the ifm interface.";
      choice rgm-track {
        description
          "Association between direct routes and a VRRP backup group, PW status and delay for advertising direct routes.";
        case track-vrrp {
          description
            "Association between direct routes and a VRRP backup group.";
          container track-vrrp {
            description
              "Configure association between direct routes and a VRRP backup group.";
            leaf vrrp-id {
              type leafref {
                path "/ncs:devices/ncs:device/ncs:live-status/ifm:ifm/ifm:interfaces/ifm:interface/ip:ipv4/vrrp:vrrp/vrrp:groups/vrrp:group/vrrp:id" {
                  tailf:xpath-root 3;
                }
              }
              // NCS drop mandatory statement
              description
                "Virtual router identifier.";
            }
            leaf cost-change {
              type uint32 {
                range "1..4294967295";
              }
              // NCS drop mandatory statement
              description
                "Value that is used as the cost of direct routes when the associated VRRP backup group status changes.";
            }
          }
        }
        case track-pw {
          description
            "Association between direct routes and PW status.";
          container track-pw {
            // NCS drop when statement
            description
              "Configure association between direct routes and PW status.";
            leaf cost-change {
              type uint32 {
                range "1..4294967295";
              }
              description
                "Value that is used as the cost of direct routes when the associated PW status changes.";
            }
          }
        }
      }
      container track-rtmtg {
        presence "Track route-monitor-group.";
        description
          "Configure association between route-monitor-group routes and interface status.";
        leaf name {
          type leafref {
            path "/ncs:devices/ncs:device/ncs:live-status/rmg:route-monitor-group/rmg:monitor-groups/rmg:monitor-group/rmg:group-name" {
              tailf:xpath-root 3;
            }
          }
          // NCS drop mandatory statement
          description
            "The route-monitor-group was tracked under the interface.";
        }
        leaf down-weight {
          type uint32 {
            range "1..1000";
          }
          description
            "Trigger down weight of a track interface.";
        }
      }
    }
  }
  augment "/ncs:devices/ncs:device/ncs:config/ifm:ifm/ifm:interfaces/ifm:interface/ip:ipv4" {
    description
      "Association between direct routes and a VRRP backup group.";
    container rgm {
      tailf:ncs-device-type "netconf";
      tailf:display-when "not(../../../../../../ncs:module) or ../../../../../../ncs:module[ncs:name='huawei-rgm']";
      description
        "Configure IPv4 direct route track VRRP, PWs, virtual-access and so on under the ifm interface.";
      choice rgm-track {
        description
          "Association between direct routes and a VRRP backup group, PW status and delay for advertising direct routes.";
        case track-vrrp {
          description
            "Association between direct routes and a VRRP backup group.";
          container track-vrrp {
            description
              "Configure association between direct routes and a VRRP backup group.";
            leaf vrrp-id {
              type leafref {
                path "/ncs:devices/ncs:device/ncs:config/ifm:ifm/ifm:interfaces/ifm:interface/ip:ipv4/vrrp:vrrp/vrrp:groups/vrrp:group/vrrp:id" {
                  tailf:xpath-root 3;
                }
              }
              mandatory true;
              description
                "Virtual router identifier.";
            }
            leaf cost-change {
              type uint32 {
                range "1..4294967295";
              }
              mandatory true;
              description
                "Value that is used as the cost of direct routes when the associated VRRP backup group status changes.";
            }
          }
        }
        case track-pw {
          description
            "Association between direct routes and PW status.";
          container track-pw {
            when "../../../ifm:type='Remote-Ap' or ../../../ifm:type='VBridge' or ../../../ifm:type='Virtual-Ethernet' or ../../../ifm:type='Global-VE'" {
              tailf:xpath-root 3;
            }
            description
              "Configure association between direct routes and PW status.";
            leaf cost-change {
              type uint32 {
                range "1..4294967295";
              }
              description
                "Value that is used as the cost of direct routes when the associated PW status changes.";
            }
          }
        }
      }
      container track-rtmtg {
        presence "Track route-monitor-group.";
        description
          "Configure association between route-monitor-group routes and interface status.";
        leaf name {
          type leafref {
            path "/ncs:devices/ncs:device/ncs:config/rmg:route-monitor-group/rmg:monitor-groups/rmg:monitor-group/rmg:group-name" {
              tailf:xpath-root 3;
            }
          }
          mandatory true;
          description
            "The route-monitor-group was tracked under the interface.";
        }
        leaf down-weight {
          type uint32 {
            range "1..1000";
          }
          description
            "Trigger down weight of a track interface.";
        }
      }
    }
  }
  augment "/ncs:devices/ncs:template/ncs:ned-id/ncs:config/ifm:ifm/ifm:interfaces/ifm:interface/ip:ipv6" {
    description
      "Association between IPv6 direct route and a VRRP backup group.";
    container rgm6 {
      description
        "Configure IPv6 direct route track VRRP6, PWs, virtual-access and so on under the ifm interface.";
      choice rgm6-track {
        description
          "Association between direct routes and a VRRP6 backup group, PW status and delay for advertising direct routes.";
        case advertise-delay {
          description
            "Delay for advertising direct routes.";
          container advertise-delay {
            // NCS drop when statement
            description
              "Configure delay for advertising IPv6 direct route.";
            leaf cost-change {
              type string;
              // NCS drop mandatory statement
              description
                "Value that is used as the cost of IPv6 direct route when the associated object status changes.";
            }
            leaf time-delay {
              type string;
              units "s";
              // NCS drop mandatory statement
              description
                "Delay for advertising IPv6 direct route.";
            }
          }
        }
      }
    }
  }
  augment "/ncs:devices/ncs:device/ncs:live-status/ifm:ifm/ifm:interfaces/ifm:interface/ip:ipv6" {
    description
      "Association between IPv6 direct route and a VRRP backup group.";
    container rgm6 {
      tailf:ncs-device-type "netconf";
      tailf:display-when "not(../../../../../../ncs:module) or ../../../../../../ncs:module[ncs:name='huawei-rgm'] or (../../../../../../ncs:live-status-protocol[not(ncs:capability)]) or (../../../../../../ncs:live-status-protocol/ncs:capability/ncs:module[.='huawei-rgm'])";
      description
        "Configure IPv6 direct route track VRRP6, PWs, virtual-access and so on under the ifm interface.";
      choice rgm6-track {
        description
          "Association between direct routes and a VRRP6 backup group, PW status and delay for advertising direct routes.";
        case advertise-delay {
          description
            "Delay for advertising direct routes.";
          container advertise-delay {
            // NCS drop when statement
            description
              "Configure delay for advertising IPv6 direct route.";
            leaf cost-change {
              type uint32 {
                range "1..4294967295";
              }
              // NCS drop mandatory statement
              description
                "Value that is used as the cost of IPv6 direct route when the associated object status changes.";
            }
            leaf time-delay {
              type uint32 {
                range "1..3600";
              }
              units "s";
              // NCS drop mandatory statement
              description
                "Delay for advertising IPv6 direct route.";
            }
          }
        }
      }
    }
  }
  augment "/ncs:devices/ncs:device/ncs:config/ifm:ifm/ifm:interfaces/ifm:interface/ip:ipv6" {
    description
      "Association between IPv6 direct route and a VRRP backup group.";
    container rgm6 {
      tailf:ncs-device-type "netconf";
      tailf:display-when "not(../../../../../../ncs:module) or ../../../../../../ncs:module[ncs:name='huawei-rgm']";
      description
        "Configure IPv6 direct route track VRRP6, PWs, virtual-access and so on under the ifm interface.";
      choice rgm6-track {
        description
          "Association between direct routes and a VRRP6 backup group, PW status and delay for advertising direct routes.";
        case advertise-delay {
          description
            "Delay for advertising direct routes.";
          container advertise-delay {
            when "../../../ifm:type='Remote-Ap' or ../../../ifm:type='VBridge' or ../../../ifm:type='Virtual-Ethernet' or ../../../ifm:type='Eth-Trunk'" {
              tailf:xpath-root 3;
            }
            description
              "Configure delay for advertising IPv6 direct route.";
            leaf cost-change {
              type uint32 {
                range "1..4294967295";
              }
              mandatory true;
              description
                "Value that is used as the cost of IPv6 direct route when the associated object status changes.";
            }
            leaf time-delay {
              type uint32 {
                range "1..3600";
              }
              units "s";
              mandatory true;
              description
                "Delay for advertising IPv6 direct route.";
            }
          }
        }
      }
    }
  }
}
