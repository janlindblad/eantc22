module huawei-driver-deviations-NE8000 {
  // Generated by yanger -t ncs
  tailf:mount-id "huawei-nc-1.0:huawei-nc-1.0";
  tailf:ncs-device-type "netconf";

  namespace "urn:huawei:yang:huawei-driver-deviations-NE8000";
  prefix driver-devs-NE8000;

  import huawei-driver {
    prefix driver;
  }
  import huawei-devm {
    prefix devm;
  }
  import huawei-license {
    prefix lcs;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "This module defines deviation statements for huawei-driver module.";

  revision 2019-11-06 {
    description
      "Initial revision.";
    reference "Huawei private.";
  }

  typedef ncs_template_fan-workmode-deviations {
    type string;
    description
      "Information of enum type fan-workmode.";
  }

  typedef ncs_template_pwr-supply-mode-type-deviations {
    type string;
    description
      "Information of enum type pwr-supply-mode-type.";
  }

  typedef ncs_rpc_notif_fan-workmode-deviations {
    type enumeration {
      enum "auto" {
        value 1;
        description
          "Automatic.";
      }
      enum "manual" {
        value 2;
        description
          "Percent.";
      }
      enum "full" {
        value 5;
        description
          "Full.";
      }
      enum "minimum-percent" {
        value 9;
        description
          "Minimum-percent.";
      }
    }
    description
      "Information of enum type fan-workmode.";
  }

  typedef ncs_rpc_notif_pwr-supply-mode-type-deviations {
    type enumeration {
      enum "standard" {
        value 1;
        description
          "Standard.";
      }
    }
    description
      "Information of enum type pwr-supply-mode-type.";
  }

  typedef live_ncs_fan-workmode-deviations {
    type enumeration {
      enum "auto" {
        value 1;
        description
          "Automatic.";
      }
      enum "manual" {
        value 2;
        description
          "Percent.";
      }
      enum "full" {
        value 5;
        description
          "Full.";
      }
      enum "minimum-percent" {
        value 9;
        description
          "Minimum-percent.";
      }
    }
    description
      "Information of enum type fan-workmode.";
  }

  typedef live_ncs_pwr-supply-mode-type-deviations {
    type enumeration {
      enum "standard" {
        value 1;
        description
          "Standard.";
      }
    }
    description
      "Information of enum type pwr-supply-mode-type.";
  }

  typedef fan-workmode-deviations {
    type enumeration {
      enum "auto" {
        value 1;
        description
          "Automatic.";
      }
      enum "manual" {
        value 2;
        description
          "Percent.";
      }
      enum "full" {
        value 5;
        description
          "Full.";
      }
      enum "minimum-percent" {
        value 9;
        description
          "Minimum-percent.";
      }
    }
    description
      "Information of enum type fan-workmode.";
  }

  typedef pwr-supply-mode-type-deviations {
    type enumeration {
      enum "standard" {
        value 1;
        description
          "Standard.";
      }
    }
    description
      "Information of enum type pwr-supply-mode-type.";
  }

  deviation "/ncs:devices/ncs:template/ncs:ned-id/ncs:config/driver:driver/driver:global-attribute/driver:optional-entity-fault-isolate" {
    deviate not-supported;
  }
  deviation "/ncs:devices/ncs:device/ncs:live-status/driver:driver/driver:global-attribute/driver:optional-entity-fault-isolate" {
    deviate not-supported;
  }
  deviation "/ncs:devices/ncs:device/ncs:config/driver:driver/driver:global-attribute/driver:optional-entity-fault-isolate" {
    deviate not-supported;
  }
  deviation "/ncs:devices/ncs:template/ncs:ned-id/ncs:config/driver:driver/driver:global-attribute/driver:pic-reload-cycle" {
    deviate not-supported;
  }
  deviation "/ncs:devices/ncs:device/ncs:live-status/driver:driver/driver:global-attribute/driver:pic-reload-cycle" {
    deviate not-supported;
  }
  deviation "/ncs:devices/ncs:device/ncs:config/driver:driver/driver:global-attribute/driver:pic-reload-cycle" {
    deviate not-supported;
  }
  deviation "/ncs:devices/ncs:template/ncs:ned-id/ncs:config/driver:driver/driver:global-attribute/driver:sampling-period" {
    deviate not-supported;
  }
  deviation "/ncs:devices/ncs:device/ncs:live-status/driver:driver/driver:global-attribute/driver:sampling-period" {
    deviate not-supported;
  }
  deviation "/ncs:devices/ncs:device/ncs:config/driver:driver/driver:global-attribute/driver:sampling-period" {
    deviate not-supported;
  }
  deviation "/ncs:devices/ncs:template/ncs:ned-id/ncs:config/driver:driver/driver:global-attribute/driver:system-mac-address" {
    deviate not-supported;
  }
  deviation "/ncs:devices/ncs:device/ncs:live-status/driver:driver/driver:global-attribute/driver:system-mac-address" {
    deviate not-supported;
  }
  deviation "/ncs:devices/ncs:device/ncs:config/driver:driver/driver:global-attribute/driver:system-mac-address" {
    deviate not-supported;
  }
  deviation "/ncs:devices/ncs:template/ncs:ned-id/ncs:config/driver:driver/driver:global-attribute/driver:system-mac-number" {
    deviate not-supported;
  }
  deviation "/ncs:devices/ncs:device/ncs:live-status/driver:driver/driver:global-attribute/driver:system-mac-number" {
    deviate not-supported;
  }
  deviation "/ncs:devices/ncs:device/ncs:config/driver:driver/driver:global-attribute/driver:system-mac-number" {
    deviate not-supported;
  }
  deviation "/ncs:devices/ncs:template/ncs:ned-id/ncs:config/driver:driver/driver:global-attribute/driver:system-trap" {
    deviate not-supported;
  }
  deviation "/ncs:devices/ncs:device/ncs:live-status/driver:driver/driver:global-attribute/driver:system-trap" {
    deviate not-supported;
  }
  deviation "/ncs:devices/ncs:device/ncs:config/driver:driver/driver:global-attribute/driver:system-trap" {
    deviate not-supported;
  }
  deviation "/ncs:devices/ncs:template/ncs:ned-id/ncs:config/driver:driver/driver:global-attribute/driver:temp-query-mode" {
    deviate not-supported;
  }
  deviation "/ncs:devices/ncs:device/ncs:live-status/driver:driver/driver:global-attribute/driver:temp-query-mode" {
    deviate not-supported;
  }
  deviation "/ncs:devices/ncs:device/ncs:config/driver:driver/driver:global-attribute/driver:temp-query-mode" {
    deviate not-supported;
  }
  deviation "/ncs:devices/ncs:template/ncs:ned-id/ncs:config/driver:driver/driver:global-attribute/driver:vlt-query-mode" {
    deviate not-supported;
  }
  deviation "/ncs:devices/ncs:device/ncs:live-status/driver:driver/driver:global-attribute/driver:vlt-query-mode" {
    deviate not-supported;
  }
  deviation "/ncs:devices/ncs:device/ncs:config/driver:driver/driver:global-attribute/driver:vlt-query-mode" {
    deviate not-supported;
  }
  deviation "/ncs:devices/ncs:device/ncs:live-status/driver:driver/driver:global-attribute/driver:cur-forward-mode" {
    deviate not-supported;
  }
  deviation "/ncs:devices/ncs:template/ncs:ned-id/ncs:config/driver:driver/driver:global-attribute/driver:next-forward-mode" {
    deviate not-supported;
  }
  deviation "/ncs:devices/ncs:device/ncs:live-status/driver:driver/driver:global-attribute/driver:next-forward-mode" {
    deviate not-supported;
  }
  deviation "/ncs:devices/ncs:device/ncs:config/driver:driver/driver:global-attribute/driver:next-forward-mode" {
    deviate not-supported;
  }
  deviation "/ncs:devices/ncs:device/ncs:live-status/driver:driver/driver:global-attribute/driver:cur-work-mode" {
    deviate not-supported;
  }
  deviation "/ncs:devices/ncs:device/ncs:live-status/driver:driver/driver:global-attribute/driver:next-work-mode" {
    deviate not-supported;
  }
  deviation "/ncs:devices/ncs:device/ncs:live-status/driver:driver/driver:global-attribute/driver:warm-backup-states" {
    deviate not-supported;
  }
  deviation "/ncs:devices/ncs:template/ncs:ned-id/ncs:config/driver:driver/driver:global-attribute/driver:warm-backup-mode" {
    deviate not-supported;
  }
  deviation "/ncs:devices/ncs:device/ncs:live-status/driver:driver/driver:global-attribute/driver:warm-backup-mode" {
    deviate not-supported;
  }
  deviation "/ncs:devices/ncs:device/ncs:config/driver:driver/driver:global-attribute/driver:warm-backup-mode" {
    deviate not-supported;
  }
  deviation "/ncs:devices/ncs:device/ncs:live-status/driver:driver/driver:global-attribute/driver:cur-device-work-mode" {
    deviate not-supported;
  }
  deviation "/ncs:devices/ncs:device/ncs:live-status/driver:driver/driver:global-attribute/driver:next-device-work-mode" {
    deviate not-supported;
  }
  deviation "/ncs:devices/ncs:device/ncs:live-status/driver:driver/driver:global-attribute/driver:cur-system-mode" {
    deviate not-supported;
  }
  deviation "/ncs:devices/ncs:device/ncs:live-status/driver:driver/driver:global-attribute/driver:next-system-mode" {
    deviate not-supported;
  }
  deviation "/ncs:devices/ncs:device/ncs:live-status/driver:driver/driver:global-attribute/driver:split-resume" {
    deviate not-supported;
  }
  deviation "/ncs:devices/ncs:device/ncs:live-status/driver:driver/driver:global-attribute/driver:switch-port-mode" {
    deviate not-supported;
  }
  deviation "/ncs:devices/ncs:device/ncs:live-status/driver:driver/driver:global-attribute/driver:usb-uart-status" {
    deviate not-supported;
  }
  deviation "/ncs:devices/ncs:device/ncs:live-status/driver:driver/driver:global-attribute/driver:cur-system-mac-address" {
    deviate not-supported;
  }
  deviation "/ncs:devices/ncs:device/ncs:live-status/driver:driver/driver:global-attribute/driver:dcn-management-plane-lock-status" {
    deviate not-supported;
  }
  deviation "/ncs:devices/ncs:device/ncs:live-status/driver:driver/driver:global-attribute/driver:cur-dcn-plane-mode" {
    deviate not-supported;
  }
  deviation "/ncs:devices/ncs:device/ncs:live-status/driver:driver/driver:global-attribute/driver:next-dcn-plane-mode" {
    deviate not-supported;
  }
  deviation "/ncs:devices/ncs:device/ncs:live-status/driver:driver/driver:io-inspect-states" {
    deviate not-supported;
  }
  deviation "/ncs:devices/ncs:template/ncs:ned-id/ncs:config/driver:driver/driver:io-inspect-attributes" {
    deviate not-supported;
  }
  deviation "/ncs:devices/ncs:device/ncs:live-status/driver:driver/driver:io-inspect-attributes" {
    deviate not-supported;
  }
  deviation "/ncs:devices/ncs:device/ncs:config/driver:driver/driver:io-inspect-attributes" {
    deviate not-supported;
  }
  deviation "/ncs:devices/ncs:device/ncs:live-status/driver:driver/driver:electric-current-infos" {
    deviate not-supported;
  }
  deviation "/ncs:devices/ncs:device/ncs:live-status/driver:driver/driver:board-powers" {
    deviate not-supported;
  }
  deviation "/ncs:devices/ncs:device/ncs:live-status/driver:driver/driver:multi-chassis-attributes" {
    deviate not-supported;
  }
  deviation "/ncs:devices/ncs:device/ncs:live-status/driver:driver/driver:chassis-run-modes" {
    deviate not-supported;
  }
  deviation "/ncs:devices/ncs:device/ncs:live-status/driver:driver/driver:system-sync-clocks" {
    deviate not-supported;
  }
  deviation "/ncs:devices/ncs:device/ncs:live-status/driver:driver/driver:rollback-attribute" {
    deviate not-supported;
  }
  deviation "/ncs:devices/ncs:device/ncs:live-status/driver:driver/driver:inner-links" {
    deviate not-supported;
  }
  deviation "/ncs:devices/ncs:device/ncs:rpc/driver:rpc-set-usb-uart-stat/driver:set-usb-uart-stat" {
    deviate not-supported;
  }
  deviation "/ncs:devices/ncs:device/ncs:rpc/driver:rpc-power-on-icu/driver:power-on-icu" {
    deviate not-supported;
  }
  deviation "/ncs:devices/ncs:device/ncs:rpc/driver:rpc-power-off-icu/driver:power-off-icu" {
    deviate not-supported;
  }
  deviation "/ncs:devices/ncs:device/ncs:rpc/driver:rpc-reset-icu-board/driver:reset-icu-board" {
    deviate not-supported;
  }
  deviation "/ncs:devices/ncs:device/ncs:rpc/driver:rpc-reset-cmu-board/driver:reset-cmu-board" {
    deviate not-supported;
  }
  deviation "/ncs:devices/ncs:device/ncs:rpc/driver:rpc-set-flash-lock/driver:set-flash-lock" {
    deviate not-supported;
  }
  deviation "/ncs:devices/ncs:device/ncs:rpc/driver:rpc-rollback/driver:rollback" {
    deviate not-supported;
  }
  deviation "/ncs:devices/ncs:device/ncs:rpc/driver:rpc-set-multi-chassis-id/driver:set-multi-chassis-id" {
    deviate not-supported;
  }
  deviation "/ncs:devices/ncs:device/ncs:rpc/driver:rpc-set-chassis-run-mode/driver:set-chassis-run-mode" {
    deviate not-supported;
  }
  deviation "/ncs:devices/ncs:device/ncs:rpc/driver:rpc-set-next-work-mode/driver:set-next-work-mode" {
    deviate not-supported;
  }
  deviation "/ncs:devices/ncs:device/ncs:rpc/driver:rpc-set-split-resume/driver:set-split-resume" {
    deviate not-supported;
  }
  deviation "/ncs:devices/ncs:device/ncs:rpc/driver:rpc-set-led-flash/driver:set-led-flash" {
    deviate not-supported;
  }
  deviation "/ncs:devices/ncs:device/ncs:rpc/driver:rpc-set-slot-led-flash/driver:set-slot-led-flash" {
    deviate not-supported;
  }
  deviation "/ncs:devices/ncs:device/ncs:rpc/driver:rpc-set-npu-led-flash/driver:set-npu-led-flash" {
    deviate not-supported;
  }
  deviation "/ncs:devices/ncs:device/ncs:rpc/driver:rpc-set-vsu-service-type/driver:set-vsu-service-type" {
    deviate not-supported;
  }
  deviation "/ncs:devices/ncs:device/ncs:rpc/driver:rpc-check-system-software/driver:check-system-software/driver:output/driver:match-result" {
    deviate not-supported;
  }
  deviation "/ncs:devices/ncs:device/ncs:rpc/driver:rpc-check-lcm-channel/driver:check-lcm-channel" {
    deviate not-supported;
  }
  deviation "/ncs:devices/ncs:device/ncs:rpc/driver:rpc-multi-level-alarm-boolean/driver:multi-level-alarm-boolean" {
    deviate not-supported;
  }
  deviation "/ncs:devices/ncs:device/ncs:rpc/driver:rpc-sysmac-load/driver:sysmac-load/driver:input/driver:slot-id" {
    deviate not-supported;
  }
  deviation "/ncs:devices/ncs:device/ncs:rpc/driver:rpc-set-next-system-mode/driver:set-next-system-mode" {
    deviate not-supported;
  }
  deviation "/ncs:devices/ncs:device/ncs:rpc/driver:rpc-set-dcn-management-plane-lock/driver:set-dcn-management-plane-lock" {
    deviate not-supported;
  }
  deviation "/ncs:devices/ncs:template/ncs:ned-id/ncs:config/devm:devm/devm:chassiss/devm:chassis/driver:dustproof-attribute" {
    deviate not-supported;
  }
  deviation "/ncs:devices/ncs:device/ncs:live-status/devm:devm/devm:chassiss/devm:chassis/driver:dustproof-attribute" {
    deviate not-supported;
  }
  deviation "/ncs:devices/ncs:device/ncs:config/devm:devm/devm:chassiss/devm:chassis/driver:dustproof-attribute" {
    deviate not-supported;
  }
  deviation "/ncs:devices/ncs:template/ncs:ned-id/ncs:config/devm:devm/driver:driver/driver:cmus" {
    deviate not-supported;
  }
  deviation "/ncs:devices/ncs:device/ncs:live-status/devm:devm/driver:driver/driver:cmus" {
    deviate not-supported;
  }
  deviation "/ncs:devices/ncs:device/ncs:config/devm:devm/driver:driver/driver:cmus" {
    deviate not-supported;
  }
  deviation "/ncs:devices/ncs:device/ncs:live-status/devm:devm/driver:driver/driver:ccus" {
    deviate not-supported;
  }
  deviation "/ncs:devices/ncs:device/ncs:live-status/devm:devm/driver:driver/driver:dacss" {
    deviate not-supported;
  }
  deviation "/ncs:devices/ncs:device/ncs:live-status/devm:devm/driver:driver/driver:icus" {
    deviate not-supported;
  }
  deviation "/ncs:devices/ncs:device/ncs:live-status/devm:devm/driver:driver/driver:pmus" {
    deviate not-supported;
  }
  deviation "/ncs:devices/ncs:device/ncs:live-status/devm:devm/driver:driver/driver:power-supplys/driver:power-supply/driver:power-environments/driver:power-environment/driver:out-voltage-value" {
    deviate not-supported;
  }
  deviation "/ncs:devices/ncs:device/ncs:live-status/devm:devm/driver:driver/driver:power-supplys/driver:power-supply/driver:power-environments/driver:power-environment/driver:out-electrical-value" {
    deviate not-supported;
  }
  deviation "/ncs:devices/ncs:device/ncs:live-status/devm:devm/driver:driver/driver:power-supplys/driver:power-supply/driver:power-environments/driver:power-environment/driver:out-power-value" {
    deviate not-supported;
  }
  deviation "/ncs:devices/ncs:device/ncs:live-status/devm:devm/driver:driver/driver:dmus" {
    deviate not-supported;
  }
  deviation "/ncs:devices/ncs:device/ncs:live-status/devm:devm/driver:driver/driver:pdus" {
    deviate not-supported;
  }
  deviation "/ncs:devices/ncs:device/ncs:live-status/devm:devm/driver:driver/driver:vsus" {
    deviate not-supported;
  }
  deviation "/ncs:devices/ncs:template/ncs:ned-id/ncs:config/driver:driver/driver:global-attribute/driver:least-sfu-number" {
    deviate replace {
      // NCS drop default statement
    }
  }
  deviation "/ncs:devices/ncs:device/ncs:live-status/driver:driver/driver:global-attribute/driver:least-sfu-number" {
    deviate replace {
      // NCS drop default statement
    }
  }
  deviation "/ncs:devices/ncs:device/ncs:config/driver:driver/driver:global-attribute/driver:least-sfu-number" {
    deviate replace {
      default "7";
    }
  }
  deviation "/ncs:devices/ncs:template/ncs:ned-id/ncs:config/driver:driver/driver:temperatures/driver:temperature" {
    deviate add {
      // NCS drop must statement
    }
  }
  deviation "/ncs:devices/ncs:device/ncs:live-status/driver:driver/driver:temperatures/driver:temperature" {
    deviate add {
      // NCS drop must statement
    }
  }
  deviation "/ncs:devices/ncs:device/ncs:config/driver:driver/driver:temperatures/driver:temperature" {
    deviate add {
      must '(minor and major and fatal) or (not(minor) and not(major) and not(fatal))' {
        tailf:xpath-root 3;
      }
    }
  }
  deviation "/ncs:devices/ncs:template/ncs:ned-id/ncs:config/driver:driver/driver:voltageinfos/driver:voltageinfo" {
    deviate add {
      // NCS drop must statement
    }
  }
  deviation "/ncs:devices/ncs:device/ncs:live-status/driver:driver/driver:voltageinfos/driver:voltageinfo" {
    deviate add {
      // NCS drop must statement
    }
  }
  deviation "/ncs:devices/ncs:device/ncs:config/driver:driver/driver:voltageinfos/driver:voltageinfo" {
    deviate add {
      must '(major-voltage-threshold-low and major-voltage-threshold-high and fatal-voltage-threshold-low and fatal-voltage-threshold-high) or (not(major-voltage-threshold-low) and not(major-voltage-threshold-high) and not(fatal-voltage-threshold-low) and not(fatal-voltage-threshold-high))' {
        tailf:xpath-root 3;
      }
    }
  }
  deviation "/ncs:devices/ncs:template/ncs:ned-id/ncs:config/devm:devm/devm:chassiss/devm:chassis/driver:fan-attribute/driver:workmode" {
    deviate replace {
      type driver-devs-NE8000:ncs_template_fan-workmode-deviations;
    }
  }
  deviation "/ncs:devices/ncs:device/ncs:live-status/devm:devm/devm:chassiss/devm:chassis/driver:fan-attribute/driver:workmode" {
    deviate replace {
      type driver-devs-NE8000:live_ncs_fan-workmode-deviations;
    }
  }
  deviation "/ncs:devices/ncs:device/ncs:config/devm:devm/devm:chassiss/devm:chassis/driver:fan-attribute/driver:workmode" {
    deviate replace {
      type driver-devs-NE8000:fan-workmode-deviations;
    }
  }
  deviation "/ncs:devices/ncs:template/ncs:ned-id/ncs:config/devm:devm/devm:chassiss/devm:chassis/driver:power-supply-attribute/driver:power-supply-mode" {
    deviate replace {
      type driver-devs-NE8000:ncs_template_pwr-supply-mode-type-deviations;
    }
    // NCS drop config false deviate replace
  }
  deviation "/ncs:devices/ncs:device/ncs:live-status/devm:devm/devm:chassiss/devm:chassis/driver:power-supply-attribute/driver:power-supply-mode" {
    deviate replace {
      type driver-devs-NE8000:live_ncs_pwr-supply-mode-type-deviations;
    }
    deviate replace;
  }
  deviation "/ncs:devices/ncs:device/ncs:config/devm:devm/devm:chassiss/devm:chassis/driver:power-supply-attribute/driver:power-supply-mode" {
    deviate replace {
      type driver-devs-NE8000:pwr-supply-mode-type-deviations;
    }
    // NCS drop config false deviate replace
  }
  deviation "/ncs:devices/ncs:template/ncs:ned-id/ncs:config/devm:devm/devm:chassiss/devm:chassis/driver:power-supply-attribute/driver:power-supply-input" {
    // NCS drop config false deviate replace
  }
  deviation "/ncs:devices/ncs:device/ncs:live-status/devm:devm/devm:chassiss/devm:chassis/driver:power-supply-attribute/driver:power-supply-input" {
    deviate replace;
  }
  deviation "/ncs:devices/ncs:device/ncs:config/devm:devm/devm:chassiss/devm:chassis/driver:power-supply-attribute/driver:power-supply-input" {
    // NCS drop config false deviate replace
  }
  deviation "/ncs:devices/ncs:template/ncs:ned-id/ncs:config/devm:devm/devm:chassiss/devm:chassis/driver:power-supply-attribute/driver:power-supply-temp" {
    // NCS drop config false deviate replace
  }
  deviation "/ncs:devices/ncs:device/ncs:live-status/devm:devm/devm:chassiss/devm:chassis/driver:power-supply-attribute/driver:power-supply-temp" {
    deviate replace;
  }
  deviation "/ncs:devices/ncs:device/ncs:config/devm:devm/devm:chassiss/devm:chassis/driver:power-supply-attribute/driver:power-supply-temp" {
    // NCS drop config false deviate replace
  }
  deviation "/ncs:devices/ncs:device/ncs:rpc/driver:rpc-check-hardware-version/driver:check-hardware-version/driver:input/driver:chassis-id" {
    deviate not-supported;
  }
  deviation "/ncs:devices/ncs:device/ncs:live-status/devm:devm/devm:chassiss/devm:chassis/driver:chassis-id" {
    deviate not-supported;
  }
  deviation "/ncs:devices/ncs:device/ncs:live-status/devm:devm/devm:chassiss/devm:chassis/driver:chassis-run-mode" {
    deviate not-supported;
  }
  deviation "/ncs:devices/ncs:device/ncs:rpc/driver:rpc-set-next-run-mode/driver:set-next-run-mode" {
    deviate not-supported;
  }
  deviation "/ncs:devices/ncs:device/ncs:rpc/driver:rpc-set-next-chassis-id/driver:set-next-chassis-id" {
    deviate not-supported;
  }
  deviation "/ncs:devices/ncs:template/ncs:ned-id/ncs:config/lcs:license/driver:lcs-boards" {
    deviate not-supported;
  }
  deviation "/ncs:devices/ncs:device/ncs:live-status/lcs:license/driver:lcs-boards" {
    deviate not-supported;
  }
  deviation "/ncs:devices/ncs:device/ncs:config/lcs:license/driver:lcs-boards" {
    deviate not-supported;
  }
  deviation "/ncs:devices/ncs:device/ncs:live-status/lcs:license/driver:lcs-usage-board-capacitys" {
    deviate not-supported;
  }
  deviation "/ncs:devices/ncs:device/ncs:rpc/driver:rpc-reset-chassis/driver:reset-chassis" {
    deviate not-supported;
  }
}
