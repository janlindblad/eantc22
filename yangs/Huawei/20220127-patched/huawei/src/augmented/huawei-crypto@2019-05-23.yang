module huawei-crypto {
  // Generated by yanger -t ncs
  tailf:mount-id "huawei-nc-1.0:huawei-nc-1.0";
  tailf:ncs-device-type "netconf";

  namespace "urn:huawei:yang:huawei-crypto";
  prefix crypto;

  import huawei-extension {
    prefix ext;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Crypto mode.";

  revision 2019-05-23 {
    description
      "Init revision.";
    reference "Huawei private.";
  }
  ext:task-name "system";

  typedef ncs_template_algorithm-type {
    type string;
    description
      "The encryption type of irreversible algorithm.";
  }

  typedef ncs_rpc_notif_algorithm-type {
    type enumeration {
      enum "default" {
        value 0;
        description
          "Default encryption type, more secure.";
      }
      enum "hmac-sha256" {
        value 1;
        description
          "Encryption type of hmac-sha256.";
      }
    }
    description
      "The encryption type of irreversible algorithm.";
  }

  typedef live_ncs_algorithm-type {
    type enumeration {
      enum "default" {
        value 0;
        description
          "Default encryption type, more secure.";
      }
      enum "hmac-sha256" {
        value 1;
        description
          "Encryption type of hmac-sha256.";
      }
    }
    description
      "The encryption type of irreversible algorithm.";
  }

  typedef algorithm-type {
    type enumeration {
      enum "default" {
        value 0;
        description
          "Default encryption type, more secure.";
      }
      enum "hmac-sha256" {
        value 1;
        description
          "Encryption type of hmac-sha256.";
      }
    }
    description
      "The encryption type of irreversible algorithm.";
  }

  augment "/ncs:devices/ncs:device/ncs:config" {
    container crypto {
      tailf:ncs-device-type "netconf";
      tailf:display-when "not(../../ncs:module) or ../../ncs:module[ncs:name='huawei-crypto']";
      description
        "Crypto mode.";
      container drbg {
        description
          "Configure DRBG.";
        leaf is-drbg-enabled {
          type boolean;
          default "true";
          description
            "Enable/disable DRBG.";
        }
      }
      container encryption-algorithm {
        description
          "Configure password encryption.";
        leaf type {
          type algorithm-type;
          default "default";
          description
            "Password encryption irreversible algorithm.";
        }
      }
    }
  }
  augment "/ncs:devices/ncs:device/ncs:live-status" {
    container crypto {
      tailf:ncs-device-type "netconf";
      tailf:display-when "not(../../ncs:module) or ../../ncs:module[ncs:name='huawei-crypto'] or (../../ncs:live-status-protocol[not(ncs:capability)]) or (../../ncs:live-status-protocol/ncs:capability/ncs:module[.='huawei-crypto'])";
      description
        "Crypto mode.";
      container drbg {
        description
          "Configure DRBG.";
        leaf is-drbg-enabled {
          type boolean;
          // NCS drop default statement
          description
            "Enable/disable DRBG.";
        }
      }
      container encryption-algorithm {
        description
          "Configure password encryption.";
        leaf type {
          type live_ncs_algorithm-type;
          // NCS drop default statement
          description
            "Password encryption irreversible algorithm.";
        }
      }
    }
  }
  augment "/ncs:devices/ncs:template/ncs:ned-id/ncs:config" {
    container crypto {
      description
        "Crypto mode.";
      container drbg {
        description
          "Configure DRBG.";
        leaf is-drbg-enabled {
          type string;
          // NCS drop default statement
          description
            "Enable/disable DRBG.";
        }
      }
      container encryption-algorithm {
        description
          "Configure password encryption.";
        leaf type {
          type ncs_template_algorithm-type;
          // NCS drop default statement
          description
            "Password encryption irreversible algorithm.";
        }
      }
    }
  }
}
