module huawei-said-frame-deviations-NE8000 {
  // Generated by yanger -t ncs
  tailf:mount-id "huawei-nc-1.0:huawei-nc-1.0";
  tailf:ncs-device-type "netconf";

  namespace "urn:huawei:yang:huawei-said-frame-deviations-NE8000";
  prefix sf-devs-NE8000;

  import huawei-said-frame {
    prefix sf;
  }
  import huawei-devm {
    prefix devm;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "This module defines deviation statements for huawei-said-frame module.";

  revision 2019-11-06 {
    description
      "Initial revision.";
    reference "Huawei private.";
  }

  deviation "/ncs:devices/ncs:device/ncs:live-status/sf:said-frame/sf:lpu-nodes/sf:lpu-node/sf:slot-id" {
    deviate replace {
      type leafref {
        path "/ncs:devices/ncs:device/ncs:live-status/devm:devm/devm:lpu-boards/devm:lpu-board/devm:position" {
          tailf:xpath-root 3;
        }
      }
    }
  }
  deviation "/ncs:devices/ncs:template/ncs:ned-id/ncs:config/sf:said-frame/sf:lpunodecfgs/sf:lpunodecfg/sf:slot-id" {
    deviate replace {
      type string;
    }
  }
  deviation "/ncs:devices/ncs:device/ncs:live-status/sf:said-frame/sf:lpunodecfgs/sf:lpunodecfg/sf:slot-id" {
    deviate replace {
      type leafref {
        path "/ncs:devices/ncs:device/ncs:live-status/devm:devm/devm:lpu-boards/devm:lpu-board/devm:position" {
          tailf:xpath-root 3;
        }
      }
    }
  }
  deviation "/ncs:devices/ncs:device/ncs:config/sf:said-frame/sf:lpunodecfgs/sf:lpunodecfg/sf:slot-id" {
    deviate replace {
      type leafref {
        path "/ncs:devices/ncs:device/ncs:config/devm:devm/devm:lpu-boards/devm:lpu-board/devm:position" {
          tailf:xpath-root 3;
        }
      }
    }
  }
}
