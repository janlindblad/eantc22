module huawei-loadbalance-deviations-NE8000 {
  // Generated by yanger -t ncs
  tailf:mount-id "huawei-nc-1.0:huawei-nc-1.0";
  tailf:ncs-device-type "netconf";

  namespace "urn:huawei:yang:huawei-loadbalance-deviations-NE8000";
  prefix loadbalance-devs-NE8000;

  import huawei-loadbalance {
    prefix loadbalance;
  }
  import huawei-devm-vnf {
    prefix devm-vnf;
  }
  import huawei-devm {
    prefix devm;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "This module defines deviation statements for huawei-loadbalance module.";

  revision 2019-11-06 {
    description
      "Initial revision.";
    reference "Huawei private.";
  }

  typedef ncs_template_cx-trunk-ecmp-deviations {
    type string;
    description
      "CX load balancing trunk ecmp.";
  }

  typedef ncs_rpc_notif_cx-trunk-ecmp-deviations {
    type enumeration {
      enum "ip" {
        value 5;
        description
          "IP mode.";
      }
      enum "mac" {
        value 6;
        description
          "MAC mode.";
      }
      enum "vll" {
        value 7;
        description
          "VLL mode.";
      }
      enum "tunnel-info" {
        value 8;
        description
          "Tunnel information.";
      }
      enum "tunnel-inner-ip" {
        value 9;
        description
          "Tunnel inner IP information.";
      }
      enum "gtp" {
        value 10;
        description
          "GTP tunnel.";
      }
    }
    description
      "CX load balancing trunk ecmp.";
  }

  typedef live_ncs_cx-trunk-ecmp-deviations {
    type enumeration {
      enum "ip" {
        value 5;
        description
          "IP mode.";
      }
      enum "mac" {
        value 6;
        description
          "MAC mode.";
      }
      enum "vll" {
        value 7;
        description
          "VLL mode.";
      }
      enum "tunnel-info" {
        value 8;
        description
          "Tunnel information.";
      }
      enum "tunnel-inner-ip" {
        value 9;
        description
          "Tunnel inner IP information.";
      }
      enum "gtp" {
        value 10;
        description
          "GTP tunnel.";
      }
    }
    description
      "CX load balancing trunk ecmp.";
  }

  typedef cx-trunk-ecmp-deviations {
    type enumeration {
      enum "ip" {
        value 5;
        description
          "IP mode.";
      }
      enum "mac" {
        value 6;
        description
          "MAC mode.";
      }
      enum "vll" {
        value 7;
        description
          "VLL mode.";
      }
      enum "tunnel-info" {
        value 8;
        description
          "Tunnel information.";
      }
      enum "tunnel-inner-ip" {
        value 9;
        description
          "Tunnel inner IP information.";
      }
      enum "gtp" {
        value 10;
        description
          "GTP tunnel.";
      }
    }
    description
      "CX load balancing trunk ecmp.";
  }

  deviation "/ncs:devices/ncs:template/ncs:ned-id/ncs:config/loadbalance:loadbalance/loadbalance:global-attribute/loadbalance:mpls-te-convergence-enable" {
    deviate not-supported;
  }
  deviation "/ncs:devices/ncs:device/ncs:live-status/loadbalance:loadbalance/loadbalance:global-attribute/loadbalance:mpls-te-convergence-enable" {
    deviate not-supported;
  }
  deviation "/ncs:devices/ncs:device/ncs:config/loadbalance:loadbalance/loadbalance:global-attribute/loadbalance:mpls-te-convergence-enable" {
    deviate not-supported;
  }
  deviation "/ncs:devices/ncs:template/ncs:ned-id/ncs:config/loadbalance:loadbalance/loadbalance:hash-key-ip" {
    deviate not-supported;
  }
  deviation "/ncs:devices/ncs:device/ncs:live-status/loadbalance:loadbalance/loadbalance:hash-key-ip" {
    deviate not-supported;
  }
  deviation "/ncs:devices/ncs:device/ncs:config/loadbalance:loadbalance/loadbalance:hash-key-ip" {
    deviate not-supported;
  }
  deviation "/ncs:devices/ncs:template/ncs:ned-id/ncs:config/devm:devm/devm:mpu-boards/devm:mpu-board/loadbalance:loadbalance" {
    deviate not-supported;
  }
  deviation "/ncs:devices/ncs:device/ncs:live-status/devm:devm/devm:mpu-boards/devm:mpu-board/loadbalance:loadbalance" {
    deviate not-supported;
  }
  deviation "/ncs:devices/ncs:device/ncs:config/devm:devm/devm:mpu-boards/devm:mpu-board/loadbalance:loadbalance" {
    deviate not-supported;
  }
  deviation "/ncs:devices/ncs:template/ncs:ned-id/ncs:config/devm-vnf:devm-vnf/devm-vnf:vnf-boards/devm-vnf:vnf-board/loadbalance:loadbalance" {
    deviate not-supported;
  }
  deviation "/ncs:devices/ncs:device/ncs:live-status/devm-vnf:devm-vnf/devm-vnf:vnf-boards/devm-vnf:vnf-board/loadbalance:loadbalance" {
    deviate not-supported;
  }
  deviation "/ncs:devices/ncs:device/ncs:config/devm-vnf:devm-vnf/devm-vnf:vnf-boards/devm-vnf:vnf-board/loadbalance:loadbalance" {
    deviate not-supported;
  }
  deviation "/ncs:devices/ncs:template/ncs:ned-id/ncs:config/devm:devm/devm:lpu-boards/devm:lpu-board/loadbalance:loadbalance/loadbalance:hash-fields/loadbalance:hash-field/loadbalance:trunk-ecmp" {
    deviate replace {
      type loadbalance-devs-NE8000:ncs_template_cx-trunk-ecmp-deviations;
    }
  }
  deviation "/ncs:devices/ncs:device/ncs:live-status/devm:devm/devm:lpu-boards/devm:lpu-board/loadbalance:loadbalance/loadbalance:hash-fields/loadbalance:hash-field/loadbalance:trunk-ecmp" {
    deviate replace {
      type loadbalance-devs-NE8000:live_ncs_cx-trunk-ecmp-deviations;
    }
  }
  deviation "/ncs:devices/ncs:device/ncs:config/devm:devm/devm:lpu-boards/devm:lpu-board/loadbalance:loadbalance/loadbalance:hash-fields/loadbalance:hash-field/loadbalance:trunk-ecmp" {
    deviate replace {
      type loadbalance-devs-NE8000:cx-trunk-ecmp-deviations;
    }
  }
}
