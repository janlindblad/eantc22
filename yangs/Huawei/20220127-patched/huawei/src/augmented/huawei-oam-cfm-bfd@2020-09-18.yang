module huawei-oam-cfm-bfd {
  // Generated by yanger -t ncs
  tailf:mount-id "huawei-nc-1.0:huawei-nc-1.0";
  tailf:ncs-device-type "netconf";

  namespace "urn:huawei:yang:huawei-oam-cfm-bfd";
  prefix oam-cfm-bfd;

  import huawei-extension {
    prefix ext;
  }
  import huawei-oammgr {
    prefix oammgr;
  }
  import huawei-bfd {
    prefix bfd;
  }
  import huawei-y1731 {
    prefix y1731;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Configure the operation, administration and maintenance (OAM) association function.";

  revision 2020-09-18 {
    description
      "Initial revision.";
    reference "Huawei private.";
  }
  ext:task-name "oammgr";

  typedef ncs_template_cfm-bind-bfd-type {
    type string;
    description
      "Binding type.";
  }

  typedef ncs_rpc_notif_cfm-bind-bfd-type {
    type enumeration {
      enum "CFM-BFD" {
        value 1;
        description
          "Type that CFM transfers fault information to BFD.";
      }
      enum "BFD-CFM" {
        value 2;
        description
          "Type that BFD transfers fault information to CFM.";
      }
    }
    description
      "Binding type.";
  }

  typedef live_ncs_cfm-bind-bfd-type {
    type enumeration {
      enum "CFM-BFD" {
        value 1;
        description
          "Type that CFM transfers fault information to BFD.";
      }
      enum "BFD-CFM" {
        value 2;
        description
          "Type that BFD transfers fault information to CFM.";
      }
    }
    description
      "Binding type.";
  }

  typedef cfm-bind-bfd-type {
    type enumeration {
      enum "CFM-BFD" {
        value 1;
        description
          "Type that CFM transfers fault information to BFD.";
      }
      enum "BFD-CFM" {
        value 2;
        description
          "Type that BFD transfers fault information to CFM.";
      }
    }
    description
      "Binding type.";
  }

  augment "/ncs:devices/ncs:template/ncs:ned-id/ncs:config/oammgr:oammgr" {
    description
      "Configure the operation, administration and maintenance (OAM) association function.";
    container cfm-bind-bfds {
      description
        "List of associations between CFM and BFD.";
      list cfm-bind-bfd {
        // NCS patched for predictable order
        ordered-by user;
        key "md-name ma-name bfd-session-id bind-type";
        unique "md-name ma-name bind-type";
        unique "bfd-session-id bind-type";
        description
          "Configure an instance of an association between CFM and BFD.";
        leaf md-name {
          type string;
          description
            "Configure an MD name.";
        }
        leaf ma-name {
          type string;
          description
            "Configure an MA name.";
        }
        leaf bfd-session-id {
          type string;
          // NCS drop must statement
          description
            "Configure the local discriminator of a BFD session.";
        }
        leaf bind-type {
          type ncs_template_cfm-bind-bfd-type;
          description
            "Configure a binding type.";
        }
      }
    }
  }
  augment "/ncs:devices/ncs:device/ncs:live-status/oammgr:oammgr" {
    description
      "Configure the operation, administration and maintenance (OAM) association function.";
    container cfm-bind-bfds {
      tailf:ncs-device-type "netconf";
      tailf:display-when "not(../../../ncs:module) or ../../../ncs:module[ncs:name='huawei-oam-cfm-bfd'] or (../../../ncs:live-status-protocol[not(ncs:capability)]) or (../../../ncs:live-status-protocol/ncs:capability/ncs:module[.='huawei-oam-cfm-bfd'])";
      description
        "List of associations between CFM and BFD.";
      list cfm-bind-bfd {
        key "md-name ma-name bfd-session-id bind-type";
        unique "md-name ma-name bind-type";
        unique "bfd-session-id bind-type";
        description
          "Configure an instance of an association between CFM and BFD.";
        leaf md-name {
          type leafref {
            path "/ncs:devices/ncs:device/ncs:live-status/y1731:y1731/y1731:global-enable/y1731:mds/y1731:md/y1731:name" {
              tailf:xpath-root 3;
            }
          }
          description
            "Configure an MD name.";
        }
        leaf ma-name {
          type leafref {
            path "/ncs:devices/ncs:device/ncs:live-status/y1731:y1731/y1731:global-enable/y1731:mds/y1731:md[y1731:name=current()/../md-name]/y1731:mas/y1731:ma/y1731:name" {
              tailf:xpath-root 3;
            }
          }
          description
            "Configure an MA name.";
        }
        leaf bfd-session-id {
          type uint32 {
            range "1..16384";
          }
          // NCS drop must statement
          description
            "Configure the local discriminator of a BFD session.";
        }
        leaf bind-type {
          type live_ncs_cfm-bind-bfd-type;
          description
            "Configure a binding type.";
        }
      }
    }
  }
  augment "/ncs:devices/ncs:device/ncs:config/oammgr:oammgr" {
    description
      "Configure the operation, administration and maintenance (OAM) association function.";
    container cfm-bind-bfds {
      tailf:ncs-device-type "netconf";
      tailf:display-when "not(../../../ncs:module) or ../../../ncs:module[ncs:name='huawei-oam-cfm-bfd']";
      description
        "List of associations between CFM and BFD.";
      list cfm-bind-bfd {
        key "md-name ma-name bfd-session-id bind-type";
        unique "md-name ma-name bind-type";
        unique "bfd-session-id bind-type";
        description
          "Configure an instance of an association between CFM and BFD.";
        leaf md-name {
          type leafref {
            path "/ncs:devices/ncs:device/ncs:config/y1731:y1731/y1731:global-enable/y1731:mds/y1731:md/y1731:name" {
              tailf:xpath-root 3;
            }
          }
          description
            "Configure an MD name.";
        }
        leaf ma-name {
          type leafref {
            path "/ncs:devices/ncs:device/ncs:config/y1731:y1731/y1731:global-enable/y1731:mds/y1731:md[y1731:name=current()/../md-name]/y1731:mas/y1731:ma/y1731:name" {
              tailf:xpath-root 3;
            }
          }
          description
            "Configure an MA name.";
        }
        leaf bfd-session-id {
          type uint32 {
            range "1..16384";
          }
          must '/bfd:bfd/bfd:sessions/bfd:session[bfd:local-discriminator-multicast-ipv4=current()] or /bfd:bfd/bfd:sessions/bfd:session[bfd:local-discriminator=current()] or /bfd:bfd/bfd:sessions/bfd:session[bfd:local-discriminator-static-ldp-lsp=current()]' {
            tailf:xpath-root 3;
          }
          description
            "Configure the local discriminator of a BFD session.";
        }
        leaf bind-type {
          type cfm-bind-bfd-type;
          description
            "Configure a binding type.";
        }
      }
    }
  }
}
