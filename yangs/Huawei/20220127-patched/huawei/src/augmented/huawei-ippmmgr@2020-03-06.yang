module huawei-ippmmgr {
  // Generated by yanger -t ncs
  tailf:mount-id "huawei-nc-1.0:huawei-nc-1.0";
  tailf:ncs-device-type "netconf";

  namespace "urn:huawei:yang:huawei-ippmmgr";
  prefix ippmmgr;

  import huawei-ifm {
    prefix ifm;
  }
  import huawei-ethernet {
    prefix ethernet;
  }
  import huawei-extension {
    prefix ext;
  }
  ext:task-name "forwarding";

  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "IP performance management.";

  revision 2020-03-06 {
    description
      "Change description.";
    reference "Huawei private.";
  }
  revision 2019-05-10 {
    description
      "Init revision.";
    reference "Huawei private.";
  }

  augment "/ncs:devices/ncs:device/ncs:config" {
    container ippmmgr {
      tailf:ncs-device-type "netconf";
      tailf:display-when "not(../../ncs:module) or ../../ncs:module[ncs:name='huawei-ippmmgr']";
      description
        "IP performance management.";
      container global-enable {
        description
          "Configure the protocol packets hardware multicast in global.";
        leaf status {
          type boolean;
          default "false";
          description
            "Enable/disable the global status.";
        }
      }
    }
  }
  augment "/ncs:devices/ncs:device/ncs:live-status" {
    container ippmmgr {
      tailf:ncs-device-type "netconf";
      tailf:display-when "not(../../ncs:module) or ../../ncs:module[ncs:name='huawei-ippmmgr'] or (../../ncs:live-status-protocol[not(ncs:capability)]) or (../../ncs:live-status-protocol/ncs:capability/ncs:module[.='huawei-ippmmgr'])";
      description
        "IP performance management.";
      container global-enable {
        description
          "Configure the protocol packets hardware multicast in global.";
        leaf status {
          type boolean;
          // NCS drop default statement
          description
            "Enable/disable the global status.";
        }
      }
    }
  }
  augment "/ncs:devices/ncs:template/ncs:ned-id/ncs:config" {
    container ippmmgr {
      description
        "IP performance management.";
      container global-enable {
        description
          "Configure the protocol packets hardware multicast in global.";
        leaf status {
          type string;
          // NCS drop default statement
          description
            "Enable/disable the global status.";
        }
      }
    }
  }
  augment "/ncs:devices/ncs:template/ncs:ned-id/ncs:config/ifm:ifm/ifm:interfaces/ifm:interface" {
    description
      "Protocol packets hardware multicast interface configuration.";
    container hwmc-if-enable {
      // NCS drop when statement
      description
        "Configure the protocol packets hardware multicast in interface.";
      leaf status {
        type string;
        description
          "Enable/disable the interface status.";
      }
    }
  }
  augment "/ncs:devices/ncs:device/ncs:live-status/ifm:ifm/ifm:interfaces/ifm:interface" {
    description
      "Protocol packets hardware multicast interface configuration.";
    container hwmc-if-enable {
      tailf:ncs-device-type "netconf";
      tailf:display-when "not(../../../../../ncs:module) or ../../../../../ncs:module[ncs:name='huawei-ippmmgr'] or (../../../../../ncs:live-status-protocol[not(ncs:capability)]) or (../../../../../ncs:live-status-protocol/ncs:capability/ncs:module[.='huawei-ippmmgr'])";
      // NCS drop when statement
      description
        "Configure the protocol packets hardware multicast in interface.";
      leaf status {
        type boolean;
        description
          "Enable/disable the interface status.";
      }
    }
  }
  augment "/ncs:devices/ncs:device/ncs:config/ifm:ifm/ifm:interfaces/ifm:interface" {
    description
      "Protocol packets hardware multicast interface configuration.";
    container hwmc-if-enable {
      tailf:ncs-device-type "netconf";
      tailf:display-when "not(../../../../../ncs:module) or ../../../../../ncs:module[ncs:name='huawei-ippmmgr']";
      when "../ethernet:ethernet/ethernet:l3-sub-interface/ethernet:qinq-termination or ../ethernet:ethernet/ethernet:l3-sub-interface/ethernet:dot1q-termination or ../ifm:type='Vlanif'" {
        tailf:xpath-root 3;
      }
      description
        "Configure the protocol packets hardware multicast in interface.";
      leaf status {
        type boolean;
        description
          "Enable/disable the interface status.";
      }
    }
  }
}
