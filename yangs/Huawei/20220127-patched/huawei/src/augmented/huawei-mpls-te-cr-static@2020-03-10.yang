module huawei-mpls-te-cr-static {
  // Generated by yanger -t ncs
  tailf:mount-id "huawei-nc-1.0:huawei-nc-1.0";
  tailf:ncs-device-type "netconf";

  namespace "urn:huawei:yang:huawei-mpls-te-cr-static";
  prefix mpls-te-cr-static;

  import ietf-inet-types {
    prefix inet;
  }
  import huawei-mpls {
    prefix mpls;
  }
  import huawei-mpls-te {
    prefix mpls-te;
  }
  import huawei-extension {
    prefix ext;
  }
  import huawei-tunnel-management {
    prefix tnlm;
  }
  import huawei-ifm {
    prefix ifm;
  }
  import huawei-network-instance {
    prefix ni;
  }
  import huawei-te {
    prefix te;
  }
  import huawei-te-interface {
    prefix te-interface;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Specifies the multi-protocol label switching protocol.";

  revision 2020-03-10 {
    description
      "Modify the must condition and the type range of the node tunnel-group.";
    reference "Huawei private.";
  }
  revision 2020-01-21 {
    description
      "Modify the must condition of the node cr-static.";
    reference "Huawei private.";
  }
  revision 2020-01-14 {
    description
      "Modify the value range of the node tunnel-ID.";
    reference "Huawei private.";
  }
  revision 2020-01-10 {
    description
      "Static bidirectional CR-LSPs, cr-static tunnels, and cr-static tunnel protection groups are added.";
    reference "Huawei private.";
  }
  revision 2019-12-25 {
    description
      "Init revision.";
    reference "Huawei private.";
  }
  ext:task-name "mpls-te";

  typedef ncs_template_static-mode-type {
    type string;
    description
      "The static tunnel mode.";
  }

  typedef ncs_template_lsr-role {
    type string;
    description
      "Lsr Role.";
  }

  typedef ncs_template_revert-type {
    type string;
    description
      "MPLS TE Tunnel Hot Standby Revert Mode.";
  }

  typedef ncs_rpc_notif_static-mode-type {
    type enumeration {
      enum "bidirectional" {
        value 1;
        description
          "Bidirectional.";
      }
      enum "passive-tunnel" {
        value 2;
        description
          "MPLS passive-tunnel.";
      }
    }
    description
      "The static tunnel mode.";
  }

  typedef ncs_rpc_notif_lsr-role {
    type enumeration {
      enum "ingress" {
        value 1;
        description
          "Ingress node.";
      }
      enum "transit" {
        value 2;
        description
          "Transit node.";
      }
      enum "egress" {
        value 3;
        description
          "Egress node.";
      }
    }
    description
      "Lsr Role.";
  }

  typedef ncs_rpc_notif_revert-type {
    type enumeration {
      enum "norevertive" {
        value 0;
        description
          "Traffic does not switch to the primary LSP after the primary LSP is Up.";
      }
      enum "revertive" {
        value 1;
        description
          "Traffic switches to the primary LSP after the primary LSP is Up.";
      }
    }
    description
      "MPLS TE Tunnel Hot Standby Revert Mode.";
  }

  typedef live_ncs_static-mode-type {
    type enumeration {
      enum "bidirectional" {
        value 1;
        description
          "Bidirectional.";
      }
      enum "passive-tunnel" {
        value 2;
        description
          "MPLS passive-tunnel.";
      }
    }
    description
      "The static tunnel mode.";
  }

  typedef live_ncs_lsr-role {
    type enumeration {
      enum "ingress" {
        value 1;
        description
          "Ingress node.";
      }
      enum "transit" {
        value 2;
        description
          "Transit node.";
      }
      enum "egress" {
        value 3;
        description
          "Egress node.";
      }
    }
    description
      "Lsr Role.";
  }

  typedef live_ncs_revert-type {
    type enumeration {
      enum "norevertive" {
        value 0;
        description
          "Traffic does not switch to the primary LSP after the primary LSP is Up.";
      }
      enum "revertive" {
        value 1;
        description
          "Traffic switches to the primary LSP after the primary LSP is Up.";
      }
    }
    description
      "MPLS TE Tunnel Hot Standby Revert Mode.";
  }

  typedef static-mode-type {
    type enumeration {
      enum "bidirectional" {
        value 1;
        description
          "Bidirectional.";
      }
      enum "passive-tunnel" {
        value 2;
        description
          "MPLS passive-tunnel.";
      }
    }
    description
      "The static tunnel mode.";
  }

  typedef lsr-role {
    type enumeration {
      enum "ingress" {
        value 1;
        description
          "Ingress node.";
      }
      enum "transit" {
        value 2;
        description
          "Transit node.";
      }
      enum "egress" {
        value 3;
        description
          "Egress node.";
      }
    }
    description
      "Lsr Role.";
  }

  typedef revert-type {
    type enumeration {
      enum "norevertive" {
        value 0;
        description
          "Traffic does not switch to the primary LSP after the primary LSP is Up.";
      }
      enum "revertive" {
        value 1;
        description
          "Traffic switches to the primary LSP after the primary LSP is Up.";
      }
    }
    description
      "MPLS TE Tunnel Hot Standby Revert Mode.";
  }

  augment "/ncs:devices/ncs:template/ncs:ned-id/ncs:config/mpls:mpls/mpls-te:te" {
    // NCS drop when statement
    description
      "MPLS static and MPLS ring configuration information augment to module MPLS TE.";
    container static-cr-lsps {
      // NCS drop when statement
      description
        "List of static CR-LSPs.";
      list static-cr-lsp {
        // NCS patched for predictable order
        ordered-by user;
        key "lsp-name";
        unique "lsr-type/transit/transit/in-label";
        unique "lsr-type/egress/egress/in-label";
        unique "lsr-type/egress/egress/ingress-lsr-id lsr-type/egress/egress/tunnel-id";
        description
          "Configure static CR-LSP.";
        leaf lsp-name {
          type string;
          description
            "The name of a static CR-LSP, same as the tunnel interface name.";
        }
        choice lsr-type {
          // NCS drop mandatory statement
          description
            "The LSR role of a static CR-LSP.";
          case ingress {
            description
              "The lsr-type is ingress.";
            container ingress {
              // NCS drop must statement
              // NCS drop must statement
              // NCS drop must statement
              description
                "Configure the ingress of a static CR-LSP.";
              leaf destination {
                type string;
                // NCS drop mandatory statement
                description
                  "The destination IP address.";
              }
              leaf next-hop {
                type string;
                description
                  "The next-hop IP address.";
              }
              leaf out-label {
                type string;
                // NCS drop mandatory statement
                description
                  "The value of an outgoing label.";
              }
              leaf tunnel-interface-name {
                type string;
                description
                  "The name of an staitc CR-LSP, same as the current tunnel interface name.";
              }
              leaf out-interface-name {
                type string;
                // NCS drop must statement
                // NCS drop must statement
                description
                  "The outgoing interface.";
              }
              leaf bandwidth {
                type string;
                units "kbit/s";
                // NCS drop default statement
                description
                  "The value of bandwidth.";
              }
              leaf pir {
                type string;
                units "kbit/s";
                // NCS drop default statement
                description
                  "The value of peak information.";
              }
            }
          }
          case transit {
            description
              "The lsr-type is transit.";
            container transit {
              // NCS drop must statement
              // NCS drop must statement
              description
                "Configure the transit of a static CR-LSP.";
              leaf in-label {
                type string;
                // NCS drop must statement
                // NCS drop mandatory statement
                description
                  "The value of an incoming label. The maximum value range of this object is dynamically set for different devices.";
              }
              leaf in-interface-name {
                type string;
                // NCS drop must statement
                description
                  "The incoming interface.";
              }
              leaf out-interface-name {
                type string;
                // NCS drop must statement
                // NCS drop must statement
                description
                  "The outgoing interface.";
              }
              leaf next-hop {
                type string;
                description
                  "The next-hop IP address.";
              }
              leaf out-label {
                type string;
                // NCS drop mandatory statement
                description
                  "The value of an outgoing label.";
              }
              leaf ingress-lsr-id {
                type string;
                description
                  "The CR-LSP ingress LSR ID.";
              }
              leaf egress-lsr-id {
                // NCS drop when statement
                type string;
                // NCS drop mandatory statement
                description
                  "The CR-LSP egress LSR ID.";
              }
              leaf tunnel-id {
                // NCS drop when statement
                type string;
                // NCS drop mandatory statement
                description
                  "The ingress session ID.";
              }
              leaf bandwidth {
                type string;
                units "kbit/s";
                // NCS drop default statement
                description
                  "The value of bandwidth.";
              }
              leaf pir {
                type string;
                units "kbit/s";
                // NCS drop default statement
                description
                  "The value of peak information.";
              }
            }
          }
          case sr-te-simulate-transit {
            description
              "Simulate the SR-TE forwarding capability through a static CR-LSP.";
            container sr-te-simulate-transit {
              description
                "Configure the SR-TE forwarding capability through a static CR-LSP.";
              leaf sid {
                type string;
                // NCS drop mandatory statement
                description
                  "Segment ID. The maximum value range of this object is dynamically set for different devices.";
              }
              leaf incoming-interface-name {
                type string;
                // NCS drop mandatory statement
                description
                  "Incoming interface name.";
              }
              leaf outgoing-interface-name {
                type string;
                // NCS drop mandatory statement
                description
                  "Outgoing interface name.";
              }
              leaf next-hop {
                type string;
                // NCS drop mandatory statement
                description
                  "Next hop IP address.";
              }
            }
          }
          case egress {
            description
              "The lsr-type is egress.";
            container egress {
              description
                "Configure the egress of a static CR-LSP.";
              leaf in-label {
                type string;
                // NCS drop must statement
                // NCS drop mandatory statement
                description
                  "The value of an incoming label. The maximum value range of this object is dynamically set for different devices.";
              }
              leaf in-interface-name {
                type string;
                // NCS drop must statement
                description
                  "The incoming interface.";
              }
              leaf ingress-lsr-id {
                type string;
                description
                  "The CR-LSP ingress LSR ID.";
              }
              leaf tunnel-id {
                // NCS drop when statement
                type string;
                // NCS drop mandatory statement
                description
                  "The ingress session ID.";
              }
            }
          }
        }
      }
    }
    container bidirection-static-cr-lsps {
      // NCS drop when statement
      description
        "List of bidirectional static CR-LSPs.";
      list bidirection-static-cr-lsp {
        // NCS patched for predictable order
        ordered-by user;
        key "lsp-name";
        unique "lsr-type/ingress/ingress/backward/in-label";
        unique "lsr-type/transit/transit/forward/in-label";
        unique "lsr-type/transit/transit/backward/in-label";
        unique "lsr-type/egress/egress/forward/in-label";
        description
          "Configure bidirectional static CR-LSP.";
        leaf lsp-name {
          type string;
          description
            "The name of a bidirectional static CR-LSP.";
        }
        leaf description {
          type string;
          description
            "Specifies the description information.";
        }
        leaf hard-pipe-enable {
          type string;
          // NCS drop default statement
          description
            "Enable/disable a device to use a static PW over a static bidirectional co-routed CR-LSP as a public network CR-LSP for an IP hard pipe.";
        }
        choice lsr-type {
          // NCS drop mandatory statement
          description
            "The LSR role of a bidirectional static CR-LSP.";
          case ingress {
            description
              "Ingress.";
            container ingress {
              presence "Specifies ingress as the lsr role.";
              description
                "Enable/disable ingress as the lsr role of bidirectional static cr lsp.";
              container forward {
                // NCS drop must statement
                // NCS drop must statement
                presence "Specifies ingress forward configuration.";
                description
                  "Configure the ingress forward function.";
                leaf next-hop {
                  type string;
                  description
                    "The forward next-hop IP address.";
                }
                leaf out-label {
                  type string;
                  // NCS drop mandatory statement
                  description
                    "The value of an outgoing label.";
                }
                leaf out-interface-name {
                  type string;
                  // NCS drop must statement
                  // NCS drop must statement
                  description
                    "The forward outgoing interface.";
                }
                leaf bandwidth-ct0 {
                  type string;
                  units "kbit/s";
                  description
                    "The value of forward bandwidth ct0.";
                }
                leaf pir {
                  type string;
                  units "kbit/s";
                  // NCS drop must statement
                  description
                    "The value of forward peak information.";
                }
              }
              container backward {
                // NCS drop must statement
                presence "Specifies ingress backward configuration.";
                description
                  "Configure the ingress backward function.";
                leaf in-label {
                  type string;
                  // NCS drop must statement
                  // NCS drop mandatory statement
                  description
                    "The value of an incoming label. The maximum value range of this object is dynamically set for different devices.";
                }
                leaf egress-lsr-id {
                  type string;
                  description
                    "The bidirectional static CR-LSP backward egress lsr id.";
                }
                leaf tunnel-id {
                  type string;
                  description
                    "The ingress session id.";
                }
              }
            }
          }
          case transit {
            description
              "Transit.";
            container transit {
              presence "Specifies transit as the lsr role.";
              description
                "Enable/disable transit as the lsr role of bidirectional static cr lsp.";
              container forward {
                // NCS drop must statement
                // NCS drop must statement
                // NCS drop must statement
                presence "Specifies transit forward configuration.";
                description
                  "Configure the transit forward function.";
                leaf in-label {
                  type string;
                  // NCS drop must statement
                  // NCS drop mandatory statement
                  description
                    "The value of an incoming label. The maximum value range of this object is dynamically set for different devices.";
                }
                leaf out-label {
                  type string;
                  // NCS drop mandatory statement
                  description
                    "The value of an outgoing label.";
                }
                leaf next-hop {
                  type string;
                  description
                    "The forward next-hop IP address.";
                }
                leaf out-interface-name {
                  type string;
                  // NCS drop must statement
                  // NCS drop must statement
                  description
                    "The forward outgoing interface.";
                }
                leaf ingress-lsr-id {
                  type string;
                  description
                    "The bidirectional static CR-LSP forward ingress lsr id.";
                }
                leaf egress-lsr-id {
                  type string;
                  description
                    "The bidirectional static CR-LSP forward egress lsr id.";
                }
                leaf tunnel-id {
                  type string;
                  description
                    "The ingress session id.";
                }
                leaf bandwidth-ct0 {
                  type string;
                  units "kbit/s";
                  description
                    "The value of forward ct0 bandwidth.";
                }
                leaf pir {
                  type string;
                  units "kbit/s";
                  // NCS drop must statement
                  description
                    "The value of forward peak information.";
                }
              }
              container backward {
                // NCS drop must statement
                // NCS drop must statement
                presence "Specifies transit backward configuration.";
                description
                  "Configure the transit backward function.";
                leaf in-label {
                  type string;
                  // NCS drop must statement
                  // NCS drop mandatory statement
                  description
                    "The value of an incoming label. The maximum value range of this object is dynamically set for different devices.";
                }
                leaf out-label {
                  type string;
                  // NCS drop mandatory statement
                  description
                    "The value of an outgoing label.";
                }
                leaf next-hop {
                  type string;
                  description
                    "The backward next-hop IP address.";
                }
                leaf out-interface-name {
                  type string;
                  // NCS drop must statement
                  // NCS drop must statement
                  description
                    "The outgoing interface.";
                }
                leaf bandwidth-ct0 {
                  type string;
                  units "kbit/s";
                  description
                    "The value of forward ct0 bandwidth.";
                }
                leaf pir {
                  type string;
                  units "kbit/s";
                  // NCS drop must statement
                  description
                    "The value of forward peak information.";
                }
              }
            }
          }
          case egress {
            description
              "Egress.";
            container egress {
              presence "Specifies egress as the lsr role.";
              description
                "Enable/disable egress as the lsr role of bidirectional static cr lsp.";
              container forward {
                // NCS drop must statement
                presence "Specifies egress forward configuration.";
                description
                  "Configure the egress forward function.";
                leaf in-label {
                  type string;
                  // NCS drop must statement
                  // NCS drop mandatory statement
                  description
                    "The value of an incoming label. The maximum value range of this object is dynamically set for different devices.";
                }
                leaf ingress-lsr-id {
                  type string;
                  description
                    "The bidirectional static CR-LSP forward ingress lsr id.";
                }
                leaf tunnel-id {
                  type string;
                  description
                    "The ingress session id.";
                }
              }
              container backward {
                // NCS drop must statement
                presence "Specifies egress backward configuration.";
                description
                  "Configure the egress backward function.";
                leaf next-hop {
                  type string;
                  description
                    "The backward next-hop IP address.";
                }
                leaf out-label {
                  type string;
                  // NCS drop mandatory statement
                  description
                    "The value of an outgoing label.";
                }
                leaf out-interface-name {
                  type string;
                  // NCS drop must statement
                  // NCS drop must statement
                  description
                    "The outgoing interface.";
                }
                leaf bandwidth-ct0 {
                  type string;
                  units "kbit/s";
                  description
                    "The value of forward ct0 bandwidth.";
                }
                leaf pir {
                  type string;
                  units "kbit/s";
                  // NCS drop must statement
                  description
                    "The value of forward peak information.";
                }
              }
            }
          }
        }
      }
    }
  }
  augment "/ncs:devices/ncs:device/ncs:live-status/mpls:mpls/mpls-te:te" {
    // NCS drop when statement
    description
      "MPLS static and MPLS ring configuration information augment to module MPLS TE.";
    container static-cr-lsps {
      tailf:ncs-device-type "netconf";
      tailf:display-when "not(../../../../ncs:module) or ../../../../ncs:module[ncs:name='huawei-mpls-te-cr-static'] or (../../../../ncs:live-status-protocol[not(ncs:capability)]) or (../../../../ncs:live-status-protocol/ncs:capability/ncs:module[.='huawei-mpls-te-cr-static'])";
      // NCS drop when statement
      description
        "List of static CR-LSPs.";
      list static-cr-lsp {
        key "lsp-name";
        unique "lsr-type/transit/transit/in-label";
        unique "lsr-type/egress/egress/in-label";
        unique "lsr-type/egress/egress/ingress-lsr-id lsr-type/egress/egress/tunnel-id";
        description
          "Configure static CR-LSP.";
        leaf lsp-name {
          type string {
            length "1..19";
          }
          description
            "The name of a static CR-LSP, same as the tunnel interface name.";
        }
        choice lsr-type {
          // NCS drop mandatory statement
          description
            "The LSR role of a static CR-LSP.";
          case ingress {
            description
              "The lsr-type is ingress.";
            container ingress {
              // NCS drop must statement
              // NCS drop must statement
              // NCS drop must statement
              description
                "Configure the ingress of a static CR-LSP.";
              leaf destination {
                type inet:ipv4-address-no-zone;
                // NCS drop mandatory statement
                description
                  "The destination IP address.";
              }
              leaf next-hop {
                type inet:ipv4-address-no-zone;
                description
                  "The next-hop IP address.";
              }
              leaf out-label {
                type uint32 {
                  range "16..1048575";
                }
                // NCS drop mandatory statement
                description
                  "The value of an outgoing label.";
              }
              leaf tunnel-interface-name {
                type leafref {
                  path "/ncs:devices/ncs:device/ncs:live-status/ifm:ifm/ifm:interfaces/ifm:interface/ifm:name" {
                    tailf:xpath-root 3;
                  }
                }
                description
                  "The name of an staitc CR-LSP, same as the current tunnel interface name.";
              }
              leaf out-interface-name {
                type leafref {
                  path "/ncs:devices/ncs:device/ncs:live-status/ifm:ifm/ifm:interfaces/ifm:interface/ifm:name" {
                    tailf:xpath-root 3;
                  }
                }
                // NCS drop must statement
                // NCS drop must statement
                description
                  "The outgoing interface.";
              }
              leaf bandwidth {
                type uint32 {
                  range "0..4000000000";
                }
                units "kbit/s";
                // NCS drop default statement
                description
                  "The value of bandwidth.";
              }
              leaf pir {
                type uint32 {
                  range "0..4000000000";
                }
                units "kbit/s";
                // NCS drop default statement
                description
                  "The value of peak information.";
              }
            }
          }
          case transit {
            description
              "The lsr-type is transit.";
            container transit {
              // NCS drop must statement
              // NCS drop must statement
              description
                "Configure the transit of a static CR-LSP.";
              leaf in-label {
                type uint32 {
                  range "16..1048575";
                }
                // NCS drop must statement
                // NCS drop mandatory statement
                description
                  "The value of an incoming label. The maximum value range of this object is dynamically set for different devices.";
              }
              leaf in-interface-name {
                type leafref {
                  path "/ncs:devices/ncs:device/ncs:live-status/ifm:ifm/ifm:interfaces/ifm:interface/ifm:name" {
                    tailf:xpath-root 3;
                  }
                }
                // NCS drop must statement
                description
                  "The incoming interface.";
              }
              leaf out-interface-name {
                type leafref {
                  path "/ncs:devices/ncs:device/ncs:live-status/ifm:ifm/ifm:interfaces/ifm:interface/ifm:name" {
                    tailf:xpath-root 3;
                  }
                }
                // NCS drop must statement
                // NCS drop must statement
                description
                  "The outgoing interface.";
              }
              leaf next-hop {
                type inet:ipv4-address-no-zone;
                description
                  "The next-hop IP address.";
              }
              leaf out-label {
                type uint32 {
                  range "16..1048575";
                }
                // NCS drop mandatory statement
                description
                  "The value of an outgoing label.";
              }
              leaf ingress-lsr-id {
                type inet:ipv4-address-no-zone;
                description
                  "The CR-LSP ingress LSR ID.";
              }
              leaf egress-lsr-id {
                // NCS drop when statement
                type inet:ipv4-address-no-zone;
                // NCS drop mandatory statement
                description
                  "The CR-LSP egress LSR ID.";
              }
              leaf tunnel-id {
                // NCS drop when statement
                type uint16 {
                  range "1..65535";
                }
                // NCS drop mandatory statement
                description
                  "The ingress session ID.";
              }
              leaf bandwidth {
                type uint32 {
                  range "0..4000000000";
                }
                units "kbit/s";
                // NCS drop default statement
                description
                  "The value of bandwidth.";
              }
              leaf pir {
                type uint32 {
                  range "0..4000000000";
                }
                units "kbit/s";
                // NCS drop default statement
                description
                  "The value of peak information.";
              }
            }
          }
          case sr-te-simulate-transit {
            description
              "Simulate the SR-TE forwarding capability through a static CR-LSP.";
            container sr-te-simulate-transit {
              description
                "Configure the SR-TE forwarding capability through a static CR-LSP.";
              leaf sid {
                type uint32 {
                  range "16..1048575";
                }
                // NCS drop mandatory statement
                description
                  "Segment ID. The maximum value range of this object is dynamically set for different devices.";
              }
              leaf incoming-interface-name {
                type leafref {
                  path "/ncs:devices/ncs:device/ncs:live-status/ifm:ifm/ifm:interfaces/ifm:interface/ifm:name" {
                    tailf:xpath-root 3;
                  }
                }
                // NCS drop mandatory statement
                description
                  "Incoming interface name.";
              }
              leaf outgoing-interface-name {
                type leafref {
                  path "/ncs:devices/ncs:device/ncs:live-status/ifm:ifm/ifm:interfaces/ifm:interface/ifm:name" {
                    tailf:xpath-root 3;
                  }
                }
                // NCS drop mandatory statement
                description
                  "Outgoing interface name.";
              }
              leaf next-hop {
                type inet:ip-address;
                // NCS drop mandatory statement
                description
                  "Next hop IP address.";
              }
            }
          }
          case egress {
            description
              "The lsr-type is egress.";
            container egress {
              description
                "Configure the egress of a static CR-LSP.";
              leaf in-label {
                type uint32 {
                  range "16..1048575";
                }
                // NCS drop must statement
                // NCS drop mandatory statement
                description
                  "The value of an incoming label. The maximum value range of this object is dynamically set for different devices.";
              }
              leaf in-interface-name {
                type leafref {
                  path "/ncs:devices/ncs:device/ncs:live-status/ifm:ifm/ifm:interfaces/ifm:interface/ifm:name" {
                    tailf:xpath-root 3;
                  }
                }
                // NCS drop must statement
                description
                  "The incoming interface.";
              }
              leaf ingress-lsr-id {
                type inet:ipv4-address-no-zone;
                description
                  "The CR-LSP ingress LSR ID.";
              }
              leaf tunnel-id {
                // NCS drop when statement
                type uint16 {
                  range "1..65535";
                }
                // NCS drop mandatory statement
                description
                  "The ingress session ID.";
              }
            }
          }
        }
      }
    }
    container bidirection-static-cr-lsps {
      tailf:ncs-device-type "netconf";
      tailf:display-when "not(../../../../ncs:module) or ../../../../ncs:module[ncs:name='huawei-mpls-te-cr-static'] or (../../../../ncs:live-status-protocol[not(ncs:capability)]) or (../../../../ncs:live-status-protocol/ncs:capability/ncs:module[.='huawei-mpls-te-cr-static'])";
      // NCS drop when statement
      description
        "List of bidirectional static CR-LSPs.";
      list bidirection-static-cr-lsp {
        key "lsp-name";
        unique "lsr-type/ingress/ingress/backward/in-label";
        unique "lsr-type/transit/transit/forward/in-label";
        unique "lsr-type/transit/transit/backward/in-label";
        unique "lsr-type/egress/egress/forward/in-label";
        description
          "Configure bidirectional static CR-LSP.";
        leaf lsp-name {
          type string {
            length "1..19";
          }
          description
            "The name of a bidirectional static CR-LSP.";
        }
        leaf description {
          type string {
            length "1..128";
          }
          description
            "Specifies the description information.";
        }
        leaf hard-pipe-enable {
          type boolean;
          // NCS drop default statement
          description
            "Enable/disable a device to use a static PW over a static bidirectional co-routed CR-LSP as a public network CR-LSP for an IP hard pipe.";
        }
        choice lsr-type {
          // NCS drop mandatory statement
          description
            "The LSR role of a bidirectional static CR-LSP.";
          case ingress {
            description
              "Ingress.";
            container ingress {
              presence "Specifies ingress as the lsr role.";
              description
                "Enable/disable ingress as the lsr role of bidirectional static cr lsp.";
              container forward {
                // NCS drop must statement
                // NCS drop must statement
                presence "Specifies ingress forward configuration.";
                description
                  "Configure the ingress forward function.";
                leaf next-hop {
                  type inet:ipv4-address-no-zone;
                  description
                    "The forward next-hop IP address.";
                }
                leaf out-label {
                  type uint32 {
                    range "16..1048575";
                  }
                  // NCS drop mandatory statement
                  description
                    "The value of an outgoing label.";
                }
                leaf out-interface-name {
                  type leafref {
                    path "/ncs:devices/ncs:device/ncs:live-status/ifm:ifm/ifm:interfaces/ifm:interface/ifm:name" {
                      tailf:xpath-root 3;
                    }
                  }
                  // NCS drop must statement
                  // NCS drop must statement
                  description
                    "The forward outgoing interface.";
                }
                leaf bandwidth-ct0 {
                  type uint32 {
                    range "1..4000000000";
                  }
                  units "kbit/s";
                  description
                    "The value of forward bandwidth ct0.";
                }
                leaf pir {
                  type uint32 {
                    range "1..4000000000";
                  }
                  units "kbit/s";
                  // NCS drop must statement
                  description
                    "The value of forward peak information.";
                }
              }
              container backward {
                // NCS drop must statement
                presence "Specifies ingress backward configuration.";
                description
                  "Configure the ingress backward function.";
                leaf in-label {
                  type uint32 {
                    range "16..1048575";
                  }
                  // NCS drop must statement
                  // NCS drop mandatory statement
                  description
                    "The value of an incoming label. The maximum value range of this object is dynamically set for different devices.";
                }
                leaf egress-lsr-id {
                  type inet:ipv4-address-no-zone;
                  description
                    "The bidirectional static CR-LSP backward egress lsr id.";
                }
                leaf tunnel-id {
                  type uint16 {
                    range "1..65535";
                  }
                  description
                    "The ingress session id.";
                }
              }
            }
          }
          case transit {
            description
              "Transit.";
            container transit {
              presence "Specifies transit as the lsr role.";
              description
                "Enable/disable transit as the lsr role of bidirectional static cr lsp.";
              container forward {
                // NCS drop must statement
                // NCS drop must statement
                // NCS drop must statement
                presence "Specifies transit forward configuration.";
                description
                  "Configure the transit forward function.";
                leaf in-label {
                  type uint32 {
                    range "16..1048575";
                  }
                  // NCS drop must statement
                  // NCS drop mandatory statement
                  description
                    "The value of an incoming label. The maximum value range of this object is dynamically set for different devices.";
                }
                leaf out-label {
                  type uint32 {
                    range "16..1048575";
                  }
                  // NCS drop mandatory statement
                  description
                    "The value of an outgoing label.";
                }
                leaf next-hop {
                  type inet:ipv4-address-no-zone;
                  description
                    "The forward next-hop IP address.";
                }
                leaf out-interface-name {
                  type leafref {
                    path "/ncs:devices/ncs:device/ncs:live-status/ifm:ifm/ifm:interfaces/ifm:interface/ifm:name" {
                      tailf:xpath-root 3;
                    }
                  }
                  // NCS drop must statement
                  // NCS drop must statement
                  description
                    "The forward outgoing interface.";
                }
                leaf ingress-lsr-id {
                  type inet:ipv4-address-no-zone;
                  description
                    "The bidirectional static CR-LSP forward ingress lsr id.";
                }
                leaf egress-lsr-id {
                  type inet:ipv4-address-no-zone;
                  description
                    "The bidirectional static CR-LSP forward egress lsr id.";
                }
                leaf tunnel-id {
                  type uint16 {
                    range "1..65535";
                  }
                  description
                    "The ingress session id.";
                }
                leaf bandwidth-ct0 {
                  type uint32 {
                    range "1..4000000000";
                  }
                  units "kbit/s";
                  description
                    "The value of forward ct0 bandwidth.";
                }
                leaf pir {
                  type uint32 {
                    range "1..4000000000";
                  }
                  units "kbit/s";
                  // NCS drop must statement
                  description
                    "The value of forward peak information.";
                }
              }
              container backward {
                // NCS drop must statement
                // NCS drop must statement
                presence "Specifies transit backward configuration.";
                description
                  "Configure the transit backward function.";
                leaf in-label {
                  type uint32 {
                    range "16..1048575";
                  }
                  // NCS drop must statement
                  // NCS drop mandatory statement
                  description
                    "The value of an incoming label. The maximum value range of this object is dynamically set for different devices.";
                }
                leaf out-label {
                  type uint32 {
                    range "16..1048575";
                  }
                  // NCS drop mandatory statement
                  description
                    "The value of an outgoing label.";
                }
                leaf next-hop {
                  type inet:ipv4-address-no-zone;
                  description
                    "The backward next-hop IP address.";
                }
                leaf out-interface-name {
                  type leafref {
                    path "/ncs:devices/ncs:device/ncs:live-status/ifm:ifm/ifm:interfaces/ifm:interface/ifm:name" {
                      tailf:xpath-root 3;
                    }
                  }
                  // NCS drop must statement
                  // NCS drop must statement
                  description
                    "The outgoing interface.";
                }
                leaf bandwidth-ct0 {
                  type uint32 {
                    range "1..4000000000";
                  }
                  units "kbit/s";
                  description
                    "The value of forward ct0 bandwidth.";
                }
                leaf pir {
                  type uint32 {
                    range "1..4000000000";
                  }
                  units "kbit/s";
                  // NCS drop must statement
                  description
                    "The value of forward peak information.";
                }
              }
            }
          }
          case egress {
            description
              "Egress.";
            container egress {
              presence "Specifies egress as the lsr role.";
              description
                "Enable/disable egress as the lsr role of bidirectional static cr lsp.";
              container forward {
                // NCS drop must statement
                presence "Specifies egress forward configuration.";
                description
                  "Configure the egress forward function.";
                leaf in-label {
                  type uint32 {
                    range "16..1048575";
                  }
                  // NCS drop must statement
                  // NCS drop mandatory statement
                  description
                    "The value of an incoming label. The maximum value range of this object is dynamically set for different devices.";
                }
                leaf ingress-lsr-id {
                  type inet:ipv4-address-no-zone;
                  description
                    "The bidirectional static CR-LSP forward ingress lsr id.";
                }
                leaf tunnel-id {
                  type uint16 {
                    range "1..65535";
                  }
                  description
                    "The ingress session id.";
                }
              }
              container backward {
                // NCS drop must statement
                presence "Specifies egress backward configuration.";
                description
                  "Configure the egress backward function.";
                leaf next-hop {
                  type inet:ipv4-address-no-zone;
                  description
                    "The backward next-hop IP address.";
                }
                leaf out-label {
                  type uint32 {
                    range "16..1048575";
                  }
                  // NCS drop mandatory statement
                  description
                    "The value of an outgoing label.";
                }
                leaf out-interface-name {
                  type leafref {
                    path "/ncs:devices/ncs:device/ncs:live-status/ifm:ifm/ifm:interfaces/ifm:interface/ifm:name" {
                      tailf:xpath-root 3;
                    }
                  }
                  // NCS drop must statement
                  // NCS drop must statement
                  description
                    "The outgoing interface.";
                }
                leaf bandwidth-ct0 {
                  type uint32 {
                    range "1..4000000000";
                  }
                  units "kbit/s";
                  description
                    "The value of forward ct0 bandwidth.";
                }
                leaf pir {
                  type uint32 {
                    range "1..4000000000";
                  }
                  units "kbit/s";
                  // NCS drop must statement
                  description
                    "The value of forward peak information.";
                }
              }
            }
          }
        }
      }
    }
  }
  augment "/ncs:devices/ncs:device/ncs:config/mpls:mpls/mpls-te:te" {
    when "/mpls:mpls/mpls-te:te/mpls-te:enable='true'" {
      tailf:xpath-root 3;
    }
    description
      "MPLS static and MPLS ring configuration information augment to module MPLS TE.";
    container static-cr-lsps {
      tailf:ncs-device-type "netconf";
      tailf:display-when "not(../../../../ncs:module) or ../../../../ncs:module[ncs:name='huawei-mpls-te-cr-static']";
      when "/mpls:mpls/mpls-te:te/mpls-te:enable='true'" {
        tailf:xpath-root 3;
      }
      description
        "List of static CR-LSPs.";
      list static-cr-lsp {
        key "lsp-name";
        unique "lsr-type/transit/transit/in-label";
        unique "lsr-type/egress/egress/in-label";
        unique "lsr-type/egress/egress/ingress-lsr-id lsr-type/egress/egress/tunnel-id";
        description
          "Configure static CR-LSP.";
        leaf lsp-name {
          type string {
            length "1..19";
          }
          description
            "The name of a static CR-LSP, same as the tunnel interface name.";
        }
        choice lsr-type {
          mandatory true;
          description
            "The LSR role of a static CR-LSP.";
          case ingress {
            description
              "The lsr-type is ingress.";
            container ingress {
              must '../lsp-name=tunnel-interface-name or not(tunnel-interface-name)' {
                tailf:xpath-root 3;
              }
              must 'next-hop or out-interface-name' {
                tailf:xpath-root 3;
              }
              must 'bandwidth<=pir' {
                tailf:xpath-root 3;
              }
              description
                "Configure the ingress of a static CR-LSP.";
              leaf destination {
                type inet:ipv4-address-no-zone;
                mandatory true;
                description
                  "The destination IP address.";
              }
              leaf next-hop {
                type inet:ipv4-address-no-zone;
                description
                  "The next-hop IP address.";
              }
              leaf out-label {
                type uint32 {
                  range "16..1048575";
                }
                mandatory true;
                description
                  "The value of an outgoing label.";
              }
              leaf tunnel-interface-name {
                type leafref {
                  path "/ncs:devices/ncs:device/ncs:config/ifm:ifm/ifm:interfaces/ifm:interface/ifm:name" {
                    tailf:xpath-root 3;
                  }
                }
                description
                  "The name of an staitc CR-LSP, same as the current tunnel interface name.";
              }
              leaf out-interface-name {
                type leafref {
                  path "/ncs:devices/ncs:device/ncs:config/ifm:ifm/ifm:interfaces/ifm:interface/ifm:name" {
                    tailf:xpath-root 3;
                  }
                }
                must "/ifm:ifm/ifm:interfaces/ifm:interface[ifm:name=current()]/ifm:vrf-name='_public_'" {
                  tailf:xpath-root 3;
                }
                must "/ni:network-instance/ni:instances/ni:instance[ni:name='_public_']/te:te/te-interface:interfaces/te-interface:interface[te-interface:name=current()]/te-interface:attribute/te-interface:bandwidth/te-interface:bc0>=../pir" {
                  tailf:xpath-root 3;
                }
                description
                  "The outgoing interface.";
              }
              leaf bandwidth {
                type uint32 {
                  range "0..4000000000";
                }
                units "kbit/s";
                default "0";
                description
                  "The value of bandwidth.";
              }
              leaf pir {
                type uint32 {
                  range "0..4000000000";
                }
                units "kbit/s";
                default "0";
                description
                  "The value of peak information.";
              }
            }
          }
          case transit {
            description
              "The lsr-type is transit.";
            container transit {
              must 'next-hop or out-interface-name' {
                tailf:xpath-root 3;
              }
              must 'bandwidth<=pir' {
                tailf:xpath-root 3;
              }
              description
                "Configure the transit of a static CR-LSP.";
              leaf in-label {
                type uint32 {
                  range "16..1048575";
                }
                must 'count(../../../static-cr-lsp[egress/in-label=current()])=0' {
                  tailf:xpath-root 3;
                }
                mandatory true;
                description
                  "The value of an incoming label. The maximum value range of this object is dynamically set for different devices.";
              }
              leaf in-interface-name {
                type leafref {
                  path "/ncs:devices/ncs:device/ncs:config/ifm:ifm/ifm:interfaces/ifm:interface/ifm:name" {
                    tailf:xpath-root 3;
                  }
                }
                must "/ifm:ifm/ifm:interfaces/ifm:interface[ifm:name=current()]/ifm:vrf-name='_public_'" {
                  tailf:xpath-root 3;
                }
                description
                  "The incoming interface.";
              }
              leaf out-interface-name {
                type leafref {
                  path "/ncs:devices/ncs:device/ncs:config/ifm:ifm/ifm:interfaces/ifm:interface/ifm:name" {
                    tailf:xpath-root 3;
                  }
                }
                must "/ifm:ifm/ifm:interfaces/ifm:interface[ifm:name=current()]/ifm:vrf-name='_public_'" {
                  tailf:xpath-root 3;
                }
                must "/ni:network-instance/ni:instances/ni:instance[ni:name='_public_']/te:te/te-interface:interfaces/te-interface:interface[te-interface:name=current()]/te-interface:attribute/te-interface:bandwidth/te-interface:bc0>=../pir" {
                  tailf:xpath-root 3;
                }
                description
                  "The outgoing interface.";
              }
              leaf next-hop {
                type inet:ipv4-address-no-zone;
                description
                  "The next-hop IP address.";
              }
              leaf out-label {
                type uint32 {
                  range "16..1048575";
                }
                mandatory true;
                description
                  "The value of an outgoing label.";
              }
              leaf ingress-lsr-id {
                type inet:ipv4-address-no-zone;
                description
                  "The CR-LSP ingress LSR ID.";
              }
              leaf egress-lsr-id {
                when '../ingress-lsr-id' {
                  tailf:xpath-root 3;
                }
                type inet:ipv4-address-no-zone;
                mandatory true;
                description
                  "The CR-LSP egress LSR ID.";
              }
              leaf tunnel-id {
                when '../ingress-lsr-id and ../egress-lsr-id' {
                  tailf:xpath-root 3;
                }
                type uint16 {
                  range "1..65535";
                }
                mandatory true;
                description
                  "The ingress session ID.";
              }
              leaf bandwidth {
                type uint32 {
                  range "0..4000000000";
                }
                units "kbit/s";
                default "0";
                description
                  "The value of bandwidth.";
              }
              leaf pir {
                type uint32 {
                  range "0..4000000000";
                }
                units "kbit/s";
                default "0";
                description
                  "The value of peak information.";
              }
            }
          }
          case sr-te-simulate-transit {
            description
              "Simulate the SR-TE forwarding capability through a static CR-LSP.";
            container sr-te-simulate-transit {
              description
                "Configure the SR-TE forwarding capability through a static CR-LSP.";
              leaf sid {
                type uint32 {
                  range "16..1048575";
                }
                mandatory true;
                description
                  "Segment ID. The maximum value range of this object is dynamically set for different devices.";
              }
              leaf incoming-interface-name {
                type leafref {
                  path "/ncs:devices/ncs:device/ncs:config/ifm:ifm/ifm:interfaces/ifm:interface/ifm:name" {
                    tailf:xpath-root 3;
                  }
                }
                mandatory true;
                description
                  "Incoming interface name.";
              }
              leaf outgoing-interface-name {
                type leafref {
                  path "/ncs:devices/ncs:device/ncs:config/ifm:ifm/ifm:interfaces/ifm:interface/ifm:name" {
                    tailf:xpath-root 3;
                  }
                }
                mandatory true;
                description
                  "Outgoing interface name.";
              }
              leaf next-hop {
                type inet:ip-address;
                mandatory true;
                description
                  "Next hop IP address.";
              }
            }
          }
          case egress {
            description
              "The lsr-type is egress.";
            container egress {
              description
                "Configure the egress of a static CR-LSP.";
              leaf in-label {
                type uint32 {
                  range "16..1048575";
                }
                must 'count(../../../static-cr-lsp[transit/in-label=current()])=0' {
                  tailf:xpath-root 3;
                }
                mandatory true;
                description
                  "The value of an incoming label. The maximum value range of this object is dynamically set for different devices.";
              }
              leaf in-interface-name {
                type leafref {
                  path "/ncs:devices/ncs:device/ncs:config/ifm:ifm/ifm:interfaces/ifm:interface/ifm:name" {
                    tailf:xpath-root 3;
                  }
                }
                must "/ifm:ifm/ifm:interfaces/ifm:interface[ifm:name=current()]/ifm:vrf-name='_public_'" {
                  tailf:xpath-root 3;
                }
                description
                  "The incoming interface.";
              }
              leaf ingress-lsr-id {
                type inet:ipv4-address-no-zone;
                description
                  "The CR-LSP ingress LSR ID.";
              }
              leaf tunnel-id {
                when '../ingress-lsr-id' {
                  tailf:xpath-root 3;
                }
                type uint16 {
                  range "1..65535";
                }
                mandatory true;
                description
                  "The ingress session ID.";
              }
            }
          }
        }
      }
    }
    container bidirection-static-cr-lsps {
      tailf:ncs-device-type "netconf";
      tailf:display-when "not(../../../../ncs:module) or ../../../../ncs:module[ncs:name='huawei-mpls-te-cr-static']";
      when "/mpls:mpls/mpls-te:te/mpls-te:enable='true'" {
        tailf:xpath-root 3;
      }
      description
        "List of bidirectional static CR-LSPs.";
      list bidirection-static-cr-lsp {
        key "lsp-name";
        unique "lsr-type/ingress/ingress/backward/in-label";
        unique "lsr-type/transit/transit/forward/in-label";
        unique "lsr-type/transit/transit/backward/in-label";
        unique "lsr-type/egress/egress/forward/in-label";
        description
          "Configure bidirectional static CR-LSP.";
        leaf lsp-name {
          type string {
            length "1..19";
          }
          description
            "The name of a bidirectional static CR-LSP.";
        }
        leaf description {
          type string {
            length "1..128";
          }
          description
            "Specifies the description information.";
        }
        leaf hard-pipe-enable {
          type boolean;
          default "false";
          description
            "Enable/disable a device to use a static PW over a static bidirectional co-routed CR-LSP as a public network CR-LSP for an IP hard pipe.";
        }
        choice lsr-type {
          mandatory true;
          description
            "The LSR role of a bidirectional static CR-LSP.";
          case ingress {
            description
              "Ingress.";
            container ingress {
              presence "Specifies ingress as the lsr role.";
              description
                "Enable/disable ingress as the lsr role of bidirectional static cr lsp.";
              container forward {
                must "(../../hard-pipe-enable='true' and out-interface-name) or ../../hard-pipe-enable='false'" {
                  tailf:xpath-root 3;
                }
                must '(bandwidth-ct0 and pir and bandwidth-ct0<=pir) or not(bandwidth-ct0)' {
                  tailf:xpath-root 3;
                }
                presence "Specifies ingress forward configuration.";
                description
                  "Configure the ingress forward function.";
                leaf next-hop {
                  type inet:ipv4-address-no-zone;
                  description
                    "The forward next-hop IP address.";
                }
                leaf out-label {
                  type uint32 {
                    range "16..1048575";
                  }
                  mandatory true;
                  description
                    "The value of an outgoing label.";
                }
                leaf out-interface-name {
                  type leafref {
                    path "/ncs:devices/ncs:device/ncs:config/ifm:ifm/ifm:interfaces/ifm:interface/ifm:name" {
                      tailf:xpath-root 3;
                    }
                  }
                  must "/ifm:ifm/ifm:interfaces/ifm:interface[ifm:name=current()]/ifm:vrf-name='_public_'" {
                    tailf:xpath-root 3;
                  }
                  must "(../pir and /ni:network-instance/ni:instances/ni:instance[ni:name='_public_']/te:te/te-interface:interfaces/te-interface:interface[te-interface:name=current()]/te-interface:attribute/te-interface:bandwidth/te-interface:bc0>=../pir) or not(../pir)" {
                    tailf:xpath-root 3;
                  }
                  description
                    "The forward outgoing interface.";
                }
                leaf bandwidth-ct0 {
                  type uint32 {
                    range "1..4000000000";
                  }
                  units "kbit/s";
                  description
                    "The value of forward bandwidth ct0.";
                }
                leaf pir {
                  type uint32 {
                    range "1..4000000000";
                  }
                  units "kbit/s";
                  must "../../../hard-pipe-enable='false'" {
                    tailf:xpath-root 3;
                  }
                  description
                    "The value of forward peak information.";
                }
              }
              container backward {
                must '(egress-lsr-id and tunnel-id) or (not(egress-lsr-id) and not(tunnel-id))' {
                  tailf:xpath-root 3;
                }
                presence "Specifies ingress backward configuration.";
                description
                  "Configure the ingress backward function.";
                leaf in-label {
                  type uint32 {
                    range "16..1048575";
                  }
                  must 'count(../../../../bidirection-static-cr-lsp[transit/forward/in-label=current()])=0 and count(../../../../bidirection-static-cr-lsp[transit/backward/in-label=current()])=0 and count(../../../../bidirection-static-cr-lsp[egress/forward/in-label=current()])=0' {
                    tailf:xpath-root 3;
                  }
                  mandatory true;
                  description
                    "The value of an incoming label. The maximum value range of this object is dynamically set for different devices.";
                }
                leaf egress-lsr-id {
                  type inet:ipv4-address-no-zone;
                  description
                    "The bidirectional static CR-LSP backward egress lsr id.";
                }
                leaf tunnel-id {
                  type uint16 {
                    range "1..65535";
                  }
                  description
                    "The ingress session id.";
                }
              }
            }
          }
          case transit {
            description
              "Transit.";
            container transit {
              presence "Specifies transit as the lsr role.";
              description
                "Enable/disable transit as the lsr role of bidirectional static cr lsp.";
              container forward {
                must '(next-hop or out-interface-name)' {
                  tailf:xpath-root 3;
                }
                must '(ingress-lsr-id and egress-lsr-id and tunnel-id) or (not(ingress-lsr-id) and not(egress-lsr-id) and not(tunnel-id))' {
                  tailf:xpath-root 3;
                }
                must '(bandwidth-ct0 and pir and bandwidth-ct0<=pir) or not(bandwidth-ct0)' {
                  tailf:xpath-root 3;
                }
                presence "Specifies transit forward configuration.";
                description
                  "Configure the transit forward function.";
                leaf in-label {
                  type uint32 {
                    range "16..1048575";
                  }
                  must 'count(../../../../bidirection-static-cr-lsp[ingress/backward/in-label=current()])=0 and count(../../../../bidirection-static-cr-lsp[transit/backward/in-label=current()])=0 and count(../../../../bidirection-static-cr-lsp[egress/forward/in-label=current()])=0' {
                    tailf:xpath-root 3;
                  }
                  mandatory true;
                  description
                    "The value of an incoming label. The maximum value range of this object is dynamically set for different devices.";
                }
                leaf out-label {
                  type uint32 {
                    range "16..1048575";
                  }
                  mandatory true;
                  description
                    "The value of an outgoing label.";
                }
                leaf next-hop {
                  type inet:ipv4-address-no-zone;
                  description
                    "The forward next-hop IP address.";
                }
                leaf out-interface-name {
                  type leafref {
                    path "/ncs:devices/ncs:device/ncs:config/ifm:ifm/ifm:interfaces/ifm:interface/ifm:name" {
                      tailf:xpath-root 3;
                    }
                  }
                  must "/ifm:ifm/ifm:interfaces/ifm:interface[ifm:name=current()]/ifm:vrf-name='_public_'" {
                    tailf:xpath-root 3;
                  }
                  must "(../pir and /ni:network-instance/ni:instances/ni:instance[ni:name='_public_']/te:te/te-interface:interfaces/te-interface:interface[te-interface:name=current()]/te-interface:attribute/te-interface:bandwidth/te-interface:bc0>=../pir) or not(../pir)" {
                    tailf:xpath-root 3;
                  }
                  description
                    "The forward outgoing interface.";
                }
                leaf ingress-lsr-id {
                  type inet:ipv4-address-no-zone;
                  description
                    "The bidirectional static CR-LSP forward ingress lsr id.";
                }
                leaf egress-lsr-id {
                  type inet:ipv4-address-no-zone;
                  description
                    "The bidirectional static CR-LSP forward egress lsr id.";
                }
                leaf tunnel-id {
                  type uint16 {
                    range "1..65535";
                  }
                  description
                    "The ingress session id.";
                }
                leaf bandwidth-ct0 {
                  type uint32 {
                    range "1..4000000000";
                  }
                  units "kbit/s";
                  description
                    "The value of forward ct0 bandwidth.";
                }
                leaf pir {
                  type uint32 {
                    range "1..4000000000";
                  }
                  units "kbit/s";
                  must "../../../hard-pipe-enable='false'" {
                    tailf:xpath-root 3;
                  }
                  description
                    "The value of forward peak information.";
                }
              }
              container backward {
                must '(next-hop or out-interface-name)' {
                  tailf:xpath-root 3;
                }
                must '(bandwidth-ct0 and pir and bandwidth-ct0<=pir) or not(bandwidth-ct0)' {
                  tailf:xpath-root 3;
                }
                presence "Specifies transit backward configuration.";
                description
                  "Configure the transit backward function.";
                leaf in-label {
                  type uint32 {
                    range "16..1048575";
                  }
                  must 'count(../../../../bidirection-static-cr-lsp[ingress/backward/in-label=current()])=0 and count(../../../../bidirection-static-cr-lsp[transit/forward/in-label=current()])=0 and count(../../../../bidirection-static-cr-lsp[egress/forward/in-label=current()])=0' {
                    tailf:xpath-root 3;
                  }
                  mandatory true;
                  description
                    "The value of an incoming label. The maximum value range of this object is dynamically set for different devices.";
                }
                leaf out-label {
                  type uint32 {
                    range "16..1048575";
                  }
                  mandatory true;
                  description
                    "The value of an outgoing label.";
                }
                leaf next-hop {
                  type inet:ipv4-address-no-zone;
                  description
                    "The backward next-hop IP address.";
                }
                leaf out-interface-name {
                  type leafref {
                    path "/ncs:devices/ncs:device/ncs:config/ifm:ifm/ifm:interfaces/ifm:interface/ifm:name" {
                      tailf:xpath-root 3;
                    }
                  }
                  must "/ifm:ifm/ifm:interfaces/ifm:interface[ifm:name=current()]/ifm:vrf-name='_public_'" {
                    tailf:xpath-root 3;
                  }
                  must "(../pir and /ni:network-instance/ni:instances/ni:instance[ni:name='_public_']/te:te/te-interface:interfaces/te-interface:interface[te-interface:name=current()]/te-interface:attribute/te-interface:bandwidth/te-interface:bc0>=../pir) or not(../pir)" {
                    tailf:xpath-root 3;
                  }
                  description
                    "The outgoing interface.";
                }
                leaf bandwidth-ct0 {
                  type uint32 {
                    range "1..4000000000";
                  }
                  units "kbit/s";
                  description
                    "The value of forward ct0 bandwidth.";
                }
                leaf pir {
                  type uint32 {
                    range "1..4000000000";
                  }
                  units "kbit/s";
                  must "../../../hard-pipe-enable='false'" {
                    tailf:xpath-root 3;
                  }
                  description
                    "The value of forward peak information.";
                }
              }
            }
          }
          case egress {
            description
              "Egress.";
            container egress {
              presence "Specifies egress as the lsr role.";
              description
                "Enable/disable egress as the lsr role of bidirectional static cr lsp.";
              container forward {
                must '(ingress-lsr-id and tunnel-id) or (not(ingress-lsr-id) and not(tunnel-id))' {
                  tailf:xpath-root 3;
                }
                presence "Specifies egress forward configuration.";
                description
                  "Configure the egress forward function.";
                leaf in-label {
                  type uint32 {
                    range "16..1048575";
                  }
                  must 'count(../../../../bidirection-static-cr-lsp[ingress/backward/in-label=current()])=0 and count(../../../../bidirection-static-cr-lsp[transit/forward/in-label=current()])=0 and count(../../../../bidirection-static-cr-lsp[transit/backward/in-label=current()])=0' {
                    tailf:xpath-root 3;
                  }
                  mandatory true;
                  description
                    "The value of an incoming label. The maximum value range of this object is dynamically set for different devices.";
                }
                leaf ingress-lsr-id {
                  type inet:ipv4-address-no-zone;
                  description
                    "The bidirectional static CR-LSP forward ingress lsr id.";
                }
                leaf tunnel-id {
                  type uint16 {
                    range "1..65535";
                  }
                  description
                    "The ingress session id.";
                }
              }
              container backward {
                must '(bandwidth-ct0 and pir and bandwidth-ct0<=pir) or not(bandwidth-ct0)' {
                  tailf:xpath-root 3;
                }
                presence "Specifies egress backward configuration.";
                description
                  "Configure the egress backward function.";
                leaf next-hop {
                  type inet:ipv4-address-no-zone;
                  description
                    "The backward next-hop IP address.";
                }
                leaf out-label {
                  type uint32 {
                    range "16..1048575";
                  }
                  mandatory true;
                  description
                    "The value of an outgoing label.";
                }
                leaf out-interface-name {
                  type leafref {
                    path "/ncs:devices/ncs:device/ncs:config/ifm:ifm/ifm:interfaces/ifm:interface/ifm:name" {
                      tailf:xpath-root 3;
                    }
                  }
                  must "/ifm:ifm/ifm:interfaces/ifm:interface[ifm:name=current()]/ifm:vrf-name='_public_'" {
                    tailf:xpath-root 3;
                  }
                  must "(../pir and /ni:network-instance/ni:instances/ni:instance[ni:name='_public_']/te:te/te-interface:interfaces/te-interface:interface[te-interface:name=current()]/te-interface:attribute/te-interface:bandwidth/te-interface:bc0>=../pir) or not(../pir)" {
                    tailf:xpath-root 3;
                  }
                  description
                    "The outgoing interface.";
                }
                leaf bandwidth-ct0 {
                  type uint32 {
                    range "1..4000000000";
                  }
                  units "kbit/s";
                  description
                    "The value of forward ct0 bandwidth.";
                }
                leaf pir {
                  type uint32 {
                    range "1..4000000000";
                  }
                  units "kbit/s";
                  must "../../../hard-pipe-enable='false'" {
                    tailf:xpath-root 3;
                  }
                  description
                    "The value of forward peak information.";
                }
              }
            }
          }
        }
      }
    }
  }
  augment "/ncs:devices/ncs:template/ncs:ned-id/ncs:config/ifm:ifm/ifm:interfaces/ifm:interface/tnlm:tunnel-protocol/tnlm:type/mpls-te:mpls-te/mpls-te:te-tunnel" {
    description
      "MPLS Static Tunnel Configuration.";
    container cr-static {
      // NCS drop when statement
      // NCS drop must statement
      description
        "Configure the static tunnel.";
      leaf direction {
        type ncs_template_static-mode-type;
        description
          "Tunnel static mode.";
      }
      leaf binding-bidirection-name {
        // NCS drop when statement
        type string;
        // NCS drop must statement
        description
          "Binding bidirectional static-cr-lsp egress lsr id.";
      }
      leaf reverse-lsp-name {
        type string;
        // NCS drop must statement
        description
          "Backward LSP name of a static tunnel.";
      }
      container tunnel-group {
        description
          "Configure the tunnel group.";
        leaf protection-tunnel-id {
          type string;
          // NCS drop must statement
          // NCS drop must statement
          description
            "Name of a protection tunnel in a protection group. The name is case-insensitive.";
        }
        leaf revertive-mode {
          // NCS drop when statement
          type ncs_template_revert-type;
          // NCS drop default statement
          description
            "Revertive mode.";
        }
        leaf wtr {
          // NCS drop when statement
          type string;
          units "min";
          // NCS drop default statement
          description
            "Wtr value(30s).";
        }
        leaf hold-off {
          // NCS drop when statement
          type string;
          units "100 ms";
          // NCS drop default statement
          description
            "Delay period. The value ranges from 0 to 100. Steps is 100ms.";
        }
      }
    }
  }
  augment "/ncs:devices/ncs:device/ncs:live-status/ifm:ifm/ifm:interfaces/ifm:interface/tnlm:tunnel-protocol/tnlm:type/mpls-te:mpls-te/mpls-te:te-tunnel" {
    description
      "MPLS Static Tunnel Configuration.";
    container cr-static {
      tailf:ncs-device-type "netconf";
      tailf:display-when "not(../../../../../../../../../ncs:module) or ../../../../../../../../../ncs:module[ncs:name='huawei-mpls-te-cr-static'] or (../../../../../../../../../ncs:live-status-protocol[not(ncs:capability)]) or (../../../../../../../../../ncs:live-status-protocol/ncs:capability/ncs:module[.='huawei-mpls-te-cr-static'])";
      // NCS drop when statement
      // NCS drop must statement
      description
        "Configure the static tunnel.";
      leaf direction {
        type live_ncs_static-mode-type;
        description
          "Tunnel static mode.";
      }
      leaf binding-bidirection-name {
        // NCS drop when statement
        type leafref {
          path "/ncs:devices/ncs:device/ncs:live-status/mpls:mpls/mpls-te:te/mpls-te-cr-static:bidirection-static-cr-lsps/mpls-te-cr-static:bidirection-static-cr-lsp/mpls-te-cr-static:lsp-name" {
            tailf:xpath-root 3;
          }
        }
        // NCS drop must statement
        description
          "Binding bidirectional static-cr-lsp egress lsr id.";
      }
      leaf reverse-lsp-name {
        type leafref {
          path "/ncs:devices/ncs:device/ncs:live-status/mpls:mpls/mpls-te:te/mpls-te-cr-static:static-cr-lsps/mpls-te-cr-static:static-cr-lsp/mpls-te-cr-static:lsp-name" {
            tailf:xpath-root 3;
          }
        }
        // NCS drop must statement
        description
          "Backward LSP name of a static tunnel.";
      }
      container tunnel-group {
        description
          "Configure the tunnel group.";
        leaf protection-tunnel-id {
          type uint16 {
            range "1..32768";
          }
          // NCS drop must statement
          // NCS drop must statement
          description
            "Name of a protection tunnel in a protection group. The name is case-insensitive.";
        }
        leaf revertive-mode {
          // NCS drop when statement
          type live_ncs_revert-type;
          // NCS drop default statement
          description
            "Revertive mode.";
        }
        leaf wtr {
          // NCS drop when statement
          type uint16 {
            range "0..60";
          }
          units "min";
          // NCS drop default statement
          description
            "Wtr value(30s).";
        }
        leaf hold-off {
          // NCS drop when statement
          type uint16 {
            range "0..100";
          }
          units "100 ms";
          // NCS drop default statement
          description
            "Delay period. The value ranges from 0 to 100. Steps is 100ms.";
        }
      }
    }
  }
  augment "/ncs:devices/ncs:device/ncs:config/ifm:ifm/ifm:interfaces/ifm:interface/tnlm:tunnel-protocol/tnlm:type/mpls-te:mpls-te/mpls-te:te-tunnel" {
    description
      "MPLS Static Tunnel Configuration.";
    container cr-static {
      tailf:ncs-device-type "netconf";
      tailf:display-when "not(../../../../../../../../../ncs:module) or ../../../../../../../../../ncs:module[ncs:name='huawei-mpls-te-cr-static']";
      when "../mpls-te:common-attributes/mpls-te:signal-protocol='cr-static'" {
        tailf:xpath-root 3;
      }
      must 'not(direction and reverse-lsp-name)' {
        tailf:xpath-root 3;
      }
      description
        "Configure the static tunnel.";
      leaf direction {
        type static-mode-type;
        description
          "Tunnel static mode.";
      }
      leaf binding-bidirection-name {
        when "../direction='passive-tunnel'" {
          tailf:xpath-root 3;
        }
        type leafref {
          path "/ncs:devices/ncs:device/ncs:config/mpls:mpls/mpls-te:te/mpls-te-cr-static:bidirection-static-cr-lsps/mpls-te-cr-static:bidirection-static-cr-lsp/mpls-te-cr-static:lsp-name" {
            tailf:xpath-root 3;
          }
        }
        must '/mpls:mpls/mpls-te:te/mpls-te-cr-static:bidirection-static-cr-lsps/mpls-te-cr-static:bidirection-static-cr-lsp[mpls-te-cr-static:lsp-name=current()]/mpls-te-cr-static:egress' {
          tailf:xpath-root 3;
        }
        description
          "Binding bidirectional static-cr-lsp egress lsr id.";
      }
      leaf reverse-lsp-name {
        type leafref {
          path "/ncs:devices/ncs:device/ncs:config/mpls:mpls/mpls-te:te/mpls-te-cr-static:static-cr-lsps/mpls-te-cr-static:static-cr-lsp/mpls-te-cr-static:lsp-name" {
            tailf:xpath-root 3;
          }
        }
        must '/mpls:mpls/mpls-te:te/mpls-te-cr-static:static-cr-lsps/mpls-te-cr-static:static-cr-lsp[mpls-te-cr-static:lsp-name=current()]/mpls-te-cr-static:egress/mpls-te-cr-static:in-label' {
          tailf:xpath-root 3;
        }
        description
          "Backward LSP name of a static tunnel.";
      }
      container tunnel-group {
        description
          "Configure the tunnel group.";
        leaf protection-tunnel-id {
          type uint16 {
            range "1..32768";
          }
          must '../../../mpls-te:common-attributes/mpls-te:tunnel-id and ../../../mpls-te:common-attributes/mpls-te:tunnel-id!=../protection-tunnel-id' {
            tailf:xpath-root 3;
          }
          must '../../direction or ../../reverse-lsp-name' {
            tailf:xpath-root 3;
          }
          description
            "Name of a protection tunnel in a protection group. The name is case-insensitive.";
        }
        leaf revertive-mode {
          when '../protection-tunnel-id' {
            tailf:xpath-root 3;
          }
          type revert-type;
          default "revertive";
          description
            "Revertive mode.";
        }
        leaf wtr {
          when "../revertive-mode='revertive'" {
            tailf:xpath-root 3;
          }
          type uint16 {
            range "0..60";
          }
          units "min";
          default "24";
          description
            "Wtr value(30s).";
        }
        leaf hold-off {
          when '../protection-tunnel-id' {
            tailf:xpath-root 3;
          }
          type uint16 {
            range "0..100";
          }
          units "100 ms";
          default "0";
          description
            "Delay period. The value ranges from 0 to 100. Steps is 100ms.";
        }
      }
    }
  }
}
