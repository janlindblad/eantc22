module huawei-clockboard {
  // Generated by yanger -t ncs
  tailf:mount-id "huawei-nc-1.0:huawei-nc-1.0";
  tailf:ncs-device-type "netconf";

  namespace "urn:huawei:yang:huawei-clockboard";
  prefix clockboard;

  import huawei-extension {
    prefix ext;
  }
  import huawei-pub-type {
    prefix pub-type;
  }
  import huawei-devm {
    prefix devm;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "System clock synchronization management, including frequency synchronization and time synchronization.";

  revision 2020-03-14 {
    description
      "Modify the node description.";
    reference "Huawei private.";
  }
  revision 2020-03-04 {
    description
      "Modify the node description.";
    reference "Huawei private.";
  }
  revision 2019-05-23 {
    description
      "Initial revision.";
    reference "Huawei private.";
  }
  ext:task-name "clksync";

  typedef ncs_template_devm-board-type {
    type string;
    description
      "Clock board type.";
  }

  typedef ncs_template_devm-run-state {
    type string;
    description
      "Devm run state.";
  }

  typedef ncs_rpc_notif_devm-board-type {
    type enumeration {
      enum "CLOCK" {
        value 1;
        description
          "Clock board.";
      }
      enum "UNKNOW" {
        value 0;
        description
          "Unknown board type.";
      }
    }
    description
      "Clock board type.";
  }

  typedef ncs_rpc_notif_devm-run-state {
    type enumeration {
      enum "normal" {
        value 1;
        description
          "Normal.";
      }
      enum "abnormal" {
        value 0;
        description
          "Abnormal.";
      }
      enum "unknown" {
        value 2;
        description
          "Unknown.";
      }
    }
    description
      "Devm run state.";
  }

  typedef live_ncs_devm-board-type {
    type enumeration {
      enum "CLOCK" {
        value 1;
        description
          "Clock board.";
      }
      enum "UNKNOW" {
        value 0;
        description
          "Unknown board type.";
      }
    }
    description
      "Clock board type.";
  }

  typedef live_ncs_devm-run-state {
    type enumeration {
      enum "normal" {
        value 1;
        description
          "Normal.";
      }
      enum "abnormal" {
        value 0;
        description
          "Abnormal.";
      }
      enum "unknown" {
        value 2;
        description
          "Unknown.";
      }
    }
    description
      "Devm run state.";
  }

  typedef devm-board-type {
    type enumeration {
      enum "CLOCK" {
        value 1;
        description
          "Clock board.";
      }
      enum "UNKNOW" {
        value 0;
        description
          "Unknown board type.";
      }
    }
    description
      "Clock board type.";
  }

  typedef devm-run-state {
    type enumeration {
      enum "normal" {
        value 1;
        description
          "Normal.";
      }
      enum "abnormal" {
        value 0;
        description
          "Abnormal.";
      }
      enum "unknown" {
        value 2;
        description
          "Unknown.";
      }
    }
    description
      "Devm run state.";
  }

  augment "/ncs:devices/ncs:template/ncs:ned-id/ncs:config/devm:devm" {
    description
      "Information of clockboard.";
    // NCS drop config false container clockboards
  }
  augment "/ncs:devices/ncs:device/ncs:live-status/devm:devm" {
    description
      "Information of clockboard.";
    container clockboards {
      tailf:ncs-device-type "netconf";
      tailf:display-when "not(../../../ncs:module) or ../../../ncs:module[ncs:name='huawei-clockboard'] or (../../../ncs:live-status-protocol[not(ncs:capability)]) or (../../../ncs:live-status-protocol/ncs:capability/ncs:module[.='huawei-clockboard'])";
      description
        "List of statistics of clock board.";
      list clockboard {
        key "position";
        description
          "Statistics of clock board.";
        leaf position {
          type string {
            length "0..32";
          }
          description
            "Clock board position.";
        }
        leaf ent-index {
          type uint32;
          description
            "Clock board index.";
        }
        leaf board-type {
          type live_ncs_devm-board-type;
          description
            "Type of a clock board.";
        }
        leaf up-time {
          type pub-type:live_ncs_time-tick;
          description
            "Up time of a clock board, the unit is timetick.";
        }
        leaf sram-state {
          type live_ncs_devm-run-state;
          description
            "SRAM state.";
        }
      }
    }
  }
  augment "/ncs:devices/ncs:device/ncs:config/devm:devm" {
    description
      "Information of clockboard.";
    // NCS drop config false container clockboards
  }
}
