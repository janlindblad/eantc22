module huawei-evpn-srv6 {
  // Generated by yanger -t ncs
  tailf:mount-id "huawei-nc-1.0:huawei-nc-1.0";
  tailf:ncs-device-type "netconf";

  namespace "urn:huawei:yang:huawei-evpn-srv6";
  prefix evpn-srv6;

  import huawei-network-instance {
    prefix ni;
  }
  import huawei-extension {
    prefix ext;
  }
  import huawei-evpl {
    prefix evpl;
  }
  import huawei-bgp {
    prefix bgp;
  }
  import huawei-bgp-evpn {
    prefix bgp-evpn;
  }
  import huawei-evpn {
    prefix evpn;
  }
  import huawei-srv6 {
    prefix srv6;
  }
  import ietf-inet-types {
    prefix inet;
  }
  import huawei-ifm {
    prefix ifm;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "EVPN SRv6 configuration.";

  revision 2019-03-22 {
    description
      "Initial revision.";
    reference "Huawei private.";
  }
  ext:task-name "evpnbgp";

  typedef ncs_template_apply-sid-mode {
    type string;
    description
      "Apply SID for segment-routing IPv6 in EVPN.";
  }

  typedef ncs_template_next-header-type {
    type string;
    description
      "The value of SRv6 next header type.";
  }

  typedef ncs_rpc_notif_apply-sid-mode {
    type enumeration {
      enum "per-instance" {
        value 0;
        description
          "Set apply sid per instance mode.";
      }
      enum "per-nexthop-all" {
        value 1;
        description
          "Set apply sid all nexthop mode.";
      }
      enum "per-nexthop-specify" {
        value 2;
        description
          "Set apply sid specify nexthop mode.";
      }
    }
    description
      "Apply SID for segment-routing IPv6 in EVPN.";
  }

  typedef ncs_rpc_notif_next-header-type {
    type enumeration {
      enum "exnh59" {
        value 59;
        description
          "The value of SRv6 next header type is 59.";
      }
      enum "exnh143" {
        value 143;
        description
          "The value of SRv6 next header type is 143.";
      }
    }
    description
      "The value of SRv6 next header type.";
  }

  typedef live_ncs_apply-sid-mode {
    type enumeration {
      enum "per-instance" {
        value 0;
        description
          "Set apply sid per instance mode.";
      }
      enum "per-nexthop-all" {
        value 1;
        description
          "Set apply sid all nexthop mode.";
      }
      enum "per-nexthop-specify" {
        value 2;
        description
          "Set apply sid specify nexthop mode.";
      }
    }
    description
      "Apply SID for segment-routing IPv6 in EVPN.";
  }

  typedef live_ncs_next-header-type {
    type enumeration {
      enum "exnh59" {
        value 59;
        description
          "The value of SRv6 next header type is 59.";
      }
      enum "exnh143" {
        value 143;
        description
          "The value of SRv6 next header type is 143.";
      }
    }
    description
      "The value of SRv6 next header type.";
  }

  typedef apply-sid-mode {
    type enumeration {
      enum "per-instance" {
        value 0;
        description
          "Set apply sid per instance mode.";
      }
      enum "per-nexthop-all" {
        value 1;
        description
          "Set apply sid all nexthop mode.";
      }
      enum "per-nexthop-specify" {
        value 2;
        description
          "Set apply sid specify nexthop mode.";
      }
    }
    description
      "Apply SID for segment-routing IPv6 in EVPN.";
  }

  typedef next-header-type {
    type enumeration {
      enum "exnh59" {
        value 59;
        description
          "The value of SRv6 next header type is 59.";
      }
      enum "exnh143" {
        value 143;
        description
          "The value of SRv6 next header type is 143.";
      }
    }
    description
      "The value of SRv6 next header type.";
  }

  augment "/ncs:devices/ncs:device/ncs:config" {
    container evpn-srv6 {
      tailf:ncs-device-type "netconf";
      tailf:display-when "not(../../ncs:module) or ../../ncs:module[ncs:name='huawei-evpn-srv6']";
      description
        "EVPN SRv6 configuration.";
      container base-process {
        description
          "Configure EVPN SRv6 base process.";
        leaf srv6-next-header {
          type next-header-type;
          default "exnh143";
          description
            "The value of SRv6 next header type.";
        }
      }
    }
  }
  augment "/ncs:devices/ncs:device/ncs:live-status" {
    container evpn-srv6 {
      tailf:ncs-device-type "netconf";
      tailf:display-when "not(../../ncs:module) or ../../ncs:module[ncs:name='huawei-evpn-srv6'] or (../../ncs:live-status-protocol[not(ncs:capability)]) or (../../ncs:live-status-protocol/ncs:capability/ncs:module[.='huawei-evpn-srv6'])";
      description
        "EVPN SRv6 configuration.";
      container base-process {
        description
          "Configure EVPN SRv6 base process.";
        leaf srv6-next-header {
          type live_ncs_next-header-type;
          // NCS drop default statement
          description
            "The value of SRv6 next header type.";
        }
      }
    }
  }
  augment "/ncs:devices/ncs:template/ncs:ned-id/ncs:config" {
    container evpn-srv6 {
      description
        "EVPN SRv6 configuration.";
      container base-process {
        description
          "Configure EVPN SRv6 base process.";
        leaf srv6-next-header {
          type ncs_template_next-header-type;
          // NCS drop default statement
          description
            "The value of SRv6 next header type.";
        }
      }
    }
  }
  augment "/ncs:devices/ncs:template/ncs:ned-id/ncs:config/evpl:evpl/evpl:instances/evpl:instance/evpn:evpn" {
    description
      "EVPN SRv6 configuration.";
    container locators {
      // NCS drop when statement
      description
        "List of locators used by segment-routing IPv6 for EVPN.";
      list locator {
        // NCS patched for predictable order
        ordered-by user;
        // NCS drop must statement
        key "name";
        // NCS drop max-elements statement
        description
          "Configure SRv6 locator.";
        leaf name {
          type string;
          description
            "Locator name.";
        }
      }
    }
  }
  augment "/ncs:devices/ncs:device/ncs:live-status/evpl:evpl/evpl:instances/evpl:instance/evpn:evpn" {
    description
      "EVPN SRv6 configuration.";
    container locators {
      tailf:ncs-device-type "netconf";
      tailf:display-when "not(../../../../../../ncs:module) or ../../../../../../ncs:module[ncs:name='huawei-evpn-srv6'] or (../../../../../../ncs:live-status-protocol[not(ncs:capability)]) or (../../../../../../ncs:live-status-protocol/ncs:capability/ncs:module[.='huawei-evpn-srv6'])";
      // NCS drop when statement
      description
        "List of locators used by segment-routing IPv6 for EVPN.";
      list locator {
        // NCS drop must statement
        key "name";
        // NCS drop max-elements statement
        description
          "Configure SRv6 locator.";
        leaf name {
          type leafref {
            path "/ncs:devices/ncs:device/ncs:live-status/ni:network-instance/ni:instances/ni:instance/srv6:srv6/srv6:locators/srv6:locator/srv6:name" {
              tailf:xpath-root 3;
            }
          }
          description
            "Locator name.";
        }
      }
    }
  }
  augment "/ncs:devices/ncs:device/ncs:config/evpl:evpl/evpl:instances/evpl:instance/evpn:evpn" {
    description
      "EVPN SRv6 configuration.";
    container locators {
      tailf:ncs-device-type "netconf";
      tailf:display-when "not(../../../../../../ncs:module) or ../../../../../../ncs:module[ncs:name='huawei-evpn-srv6']";
      when "../../evpl:mode='srv6-mode' and ../evpn:name" {
        tailf:xpath-root 3;
      }
      description
        "List of locators used by segment-routing IPv6 for EVPN.";
      list locator {
        must '/evpn:evpn/evpn:instances/evpn:instance[evpn:name=current()/../../evpn:name]/evpn:vpws-evpn/evpn:rd' {
          tailf:xpath-root 3;
        }
        key "name";
        max-elements 1;
        description
          "Configure SRv6 locator.";
        leaf name {
          type leafref {
            path "/ncs:devices/ncs:device/ncs:config/ni:network-instance/ni:instances/ni:instance/srv6:srv6/srv6:locators/srv6:locator/srv6:name" {
              tailf:xpath-root 3;
            }
          }
          description
            "Locator name.";
        }
      }
    }
  }
  augment "/ncs:devices/ncs:template/ncs:ned-id/ncs:config/ni:network-instance/ni:instances/ni:instance/bgp:bgp/bgp:base-process/bgp:afs/bgp:af/bgp:ipv4-unicast/bgp-evpn:evpn" {
    description
      "EVPN SRv6 configuration.";
    container locators {
      // NCS drop when statement
      description
        "List of locators used by segment-routing IPv6 for EVPN.";
      list locator {
        // NCS patched for predictable order
        ordered-by user;
        key "name";
        // NCS drop max-elements statement
        description
          "Configure SRv6 locator.";
        leaf name {
          type string;
          description
            "Locator name.";
        }
      }
    }
    container apply-sid-mode {
      // NCS drop when statement
      description
        "Configure apply SID for segment-routing IPv6 in EVPN.";
      leaf mode {
        // NCS drop when statement
        type ncs_template_apply-sid-mode;
        // NCS drop default statement
        description
          "Apply SID mode for segment-routing IPv6 in EVPN.";
      }
      container specify-nexthops {
        // NCS drop when statement
        description
          "List of locators used by segment-routing IPv6 for EVPN.";
        list specify-nexthop {
          // NCS patched for predictable order
          ordered-by user;
          key "nexthop-address";
          // NCS drop max-elements statement
          description
            "Configure apply SID for segmet-routing IPv6 in EVPN specify nexthop mode.";
          leaf nexthop-address {
            type string;
            description
              "Specify the nexthop address.";
          }
          leaf interface-name {
            type string;
            // NCS drop mandatory statement
            description
              "Out interface name of route.";
          }
        }
      }
    }
  }
  augment "/ncs:devices/ncs:device/ncs:live-status/ni:network-instance/ni:instances/ni:instance/bgp:bgp/bgp:base-process/bgp:afs/bgp:af/bgp:ipv4-unicast/bgp-evpn:evpn" {
    description
      "EVPN SRv6 configuration.";
    container locators {
      tailf:ncs-device-type "netconf";
      tailf:display-when "not(../../../../../../../../../../../ncs:module) or ../../../../../../../../../../../ncs:module[ncs:name='huawei-evpn-srv6'] or (../../../../../../../../../../../ncs:live-status-protocol[not(ncs:capability)]) or (../../../../../../../../../../../ncs:live-status-protocol/ncs:capability/ncs:module[.='huawei-evpn-srv6'])";
      // NCS drop when statement
      description
        "List of locators used by segment-routing IPv6 for EVPN.";
      list locator {
        key "name";
        // NCS drop max-elements statement
        description
          "Configure SRv6 locator.";
        leaf name {
          type leafref {
            path "/ncs:devices/ncs:device/ncs:live-status/ni:network-instance/ni:instances/ni:instance/srv6:srv6/srv6:locators/srv6:locator/srv6:name" {
              tailf:xpath-root 3;
            }
          }
          description
            "Locator name.";
        }
      }
    }
    container apply-sid-mode {
      tailf:ncs-device-type "netconf";
      tailf:display-when "not(../../../../../../../../../../../ncs:module) or ../../../../../../../../../../../ncs:module[ncs:name='huawei-evpn-srv6'] or (../../../../../../../../../../../ncs:live-status-protocol[not(ncs:capability)]) or (../../../../../../../../../../../ncs:live-status-protocol/ncs:capability/ncs:module[.='huawei-evpn-srv6'])";
      // NCS drop when statement
      description
        "Configure apply SID for segment-routing IPv6 in EVPN.";
      leaf mode {
        // NCS drop when statement
        type live_ncs_apply-sid-mode;
        // NCS drop default statement
        description
          "Apply SID mode for segment-routing IPv6 in EVPN.";
      }
      container specify-nexthops {
        // NCS drop when statement
        description
          "List of locators used by segment-routing IPv6 for EVPN.";
        list specify-nexthop {
          key "nexthop-address";
          // NCS drop max-elements statement
          description
            "Configure apply SID for segmet-routing IPv6 in EVPN specify nexthop mode.";
          leaf nexthop-address {
            type inet:ip-address-no-zone;
            description
              "Specify the nexthop address.";
          }
          leaf interface-name {
            type leafref {
              path "/ncs:devices/ncs:device/ncs:live-status/ifm:ifm/ifm:interfaces/ifm:interface/ifm:name" {
                tailf:xpath-root 3;
              }
            }
            // NCS drop mandatory statement
            description
              "Out interface name of route.";
          }
        }
      }
    }
  }
  augment "/ncs:devices/ncs:device/ncs:config/ni:network-instance/ni:instances/ni:instance/bgp:bgp/bgp:base-process/bgp:afs/bgp:af/bgp:ipv4-unicast/bgp-evpn:evpn" {
    description
      "EVPN SRv6 configuration.";
    container locators {
      tailf:ncs-device-type "netconf";
      tailf:display-when "not(../../../../../../../../../../../ncs:module) or ../../../../../../../../../../../ncs:module[ncs:name='huawei-evpn-srv6']";
      when "../../../../../../../ni:name!='_public_'" {
        tailf:xpath-root 3;
      }
      description
        "List of locators used by segment-routing IPv6 for EVPN.";
      list locator {
        key "name";
        max-elements 1;
        description
          "Configure SRv6 locator.";
        leaf name {
          type leafref {
            path "/ncs:devices/ncs:device/ncs:config/ni:network-instance/ni:instances/ni:instance/srv6:srv6/srv6:locators/srv6:locator/srv6:name" {
              tailf:xpath-root 3;
            }
          }
          description
            "Locator name.";
        }
      }
    }
    container apply-sid-mode {
      tailf:ncs-device-type "netconf";
      tailf:display-when "not(../../../../../../../../../../../ncs:module) or ../../../../../../../../../../../ncs:module[ncs:name='huawei-evpn-srv6']";
      when "../../../../../../../ni:name!='_public_' and ../../../bgp:type='ipv4uni'" {
        tailf:xpath-root 3;
      }
      description
        "Configure apply SID for segment-routing IPv6 in EVPN.";
      leaf mode {
        when '../../locators/locator/name' {
          tailf:xpath-root 3;
        }
        type apply-sid-mode;
        default "per-instance";
        description
          "Apply SID mode for segment-routing IPv6 in EVPN.";
      }
      container specify-nexthops {
        when "../mode='per-nexthop-specify'" {
          tailf:xpath-root 3;
        }
        description
          "List of locators used by segment-routing IPv6 for EVPN.";
        list specify-nexthop {
          key "nexthop-address";
          max-elements 128;
          description
            "Configure apply SID for segmet-routing IPv6 in EVPN specify nexthop mode.";
          leaf nexthop-address {
            type inet:ip-address-no-zone;
            description
              "Specify the nexthop address.";
          }
          leaf interface-name {
            type leafref {
              path "/ncs:devices/ncs:device/ncs:config/ifm:ifm/ifm:interfaces/ifm:interface/ifm:name" {
                tailf:xpath-root 3;
              }
            }
            mandatory true;
            description
              "Out interface name of route.";
          }
        }
      }
    }
  }
  augment "/ncs:devices/ncs:template/ncs:ned-id/ncs:config/ni:network-instance/ni:instances/ni:instance/bgp:bgp/bgp:base-process/bgp:afs/bgp:af/bgp:ipv6-unicast/bgp-evpn:evpn" {
    description
      "EVPN SRv6 configuration.";
    container locators {
      // NCS drop when statement
      description
        "List of locators used by segment-routing IPv6 for EVPN.";
      list locator {
        // NCS patched for predictable order
        ordered-by user;
        key "name";
        // NCS drop max-elements statement
        description
          "Configure SRv6 locator.";
        leaf name {
          type string;
          description
            "Locator name.";
        }
      }
    }
    container apply-sid-mode {
      // NCS drop when statement
      description
        "Configure apply SID for segment-routing IPv6 in EVPN.";
      leaf mode {
        // NCS drop when statement
        type ncs_template_apply-sid-mode;
        // NCS drop default statement
        description
          "Apply SID mode for segment-routing IPv6 in EVPN.";
      }
      container specify-nexthops {
        // NCS drop when statement
        description
          "List of locators used by segment-routing IPv6 for EVPN.";
        list specify-nexthop {
          // NCS patched for predictable order
          ordered-by user;
          key "nexthop-address";
          // NCS drop max-elements statement
          description
            "Configure apply SID for segmet-routing IPv6 in EVPN specify nexthop mode.";
          leaf nexthop-address {
            type string;
            description
              "Specify the nexthop IPv6 address.";
          }
          leaf interface-name {
            type string;
            // NCS drop mandatory statement
            description
              "Out interface name of route.";
          }
        }
      }
    }
  }
  augment "/ncs:devices/ncs:device/ncs:live-status/ni:network-instance/ni:instances/ni:instance/bgp:bgp/bgp:base-process/bgp:afs/bgp:af/bgp:ipv6-unicast/bgp-evpn:evpn" {
    description
      "EVPN SRv6 configuration.";
    container locators {
      tailf:ncs-device-type "netconf";
      tailf:display-when "not(../../../../../../../../../../../ncs:module) or ../../../../../../../../../../../ncs:module[ncs:name='huawei-evpn-srv6'] or (../../../../../../../../../../../ncs:live-status-protocol[not(ncs:capability)]) or (../../../../../../../../../../../ncs:live-status-protocol/ncs:capability/ncs:module[.='huawei-evpn-srv6'])";
      // NCS drop when statement
      description
        "List of locators used by segment-routing IPv6 for EVPN.";
      list locator {
        key "name";
        // NCS drop max-elements statement
        description
          "Configure SRv6 locator.";
        leaf name {
          type leafref {
            path "/ncs:devices/ncs:device/ncs:live-status/ni:network-instance/ni:instances/ni:instance/srv6:srv6/srv6:locators/srv6:locator/srv6:name" {
              tailf:xpath-root 3;
            }
          }
          description
            "Locator name.";
        }
      }
    }
    container apply-sid-mode {
      tailf:ncs-device-type "netconf";
      tailf:display-when "not(../../../../../../../../../../../ncs:module) or ../../../../../../../../../../../ncs:module[ncs:name='huawei-evpn-srv6'] or (../../../../../../../../../../../ncs:live-status-protocol[not(ncs:capability)]) or (../../../../../../../../../../../ncs:live-status-protocol/ncs:capability/ncs:module[.='huawei-evpn-srv6'])";
      // NCS drop when statement
      description
        "Configure apply SID for segment-routing IPv6 in EVPN.";
      leaf mode {
        // NCS drop when statement
        type live_ncs_apply-sid-mode;
        // NCS drop default statement
        description
          "Apply SID mode for segment-routing IPv6 in EVPN.";
      }
      container specify-nexthops {
        // NCS drop when statement
        description
          "List of locators used by segment-routing IPv6 for EVPN.";
        list specify-nexthop {
          key "nexthop-address";
          // NCS drop max-elements statement
          description
            "Configure apply SID for segmet-routing IPv6 in EVPN specify nexthop mode.";
          leaf nexthop-address {
            type inet:ipv6-address-no-zone;
            description
              "Specify the nexthop IPv6 address.";
          }
          leaf interface-name {
            type leafref {
              path "/ncs:devices/ncs:device/ncs:live-status/ifm:ifm/ifm:interfaces/ifm:interface/ifm:name" {
                tailf:xpath-root 3;
              }
            }
            // NCS drop mandatory statement
            description
              "Out interface name of route.";
          }
        }
      }
    }
  }
  augment "/ncs:devices/ncs:device/ncs:config/ni:network-instance/ni:instances/ni:instance/bgp:bgp/bgp:base-process/bgp:afs/bgp:af/bgp:ipv6-unicast/bgp-evpn:evpn" {
    description
      "EVPN SRv6 configuration.";
    container locators {
      tailf:ncs-device-type "netconf";
      tailf:display-when "not(../../../../../../../../../../../ncs:module) or ../../../../../../../../../../../ncs:module[ncs:name='huawei-evpn-srv6']";
      when "../../../../../../../ni:name!='_public_'" {
        tailf:xpath-root 3;
      }
      description
        "List of locators used by segment-routing IPv6 for EVPN.";
      list locator {
        key "name";
        max-elements 1;
        description
          "Configure SRv6 locator.";
        leaf name {
          type leafref {
            path "/ncs:devices/ncs:device/ncs:config/ni:network-instance/ni:instances/ni:instance/srv6:srv6/srv6:locators/srv6:locator/srv6:name" {
              tailf:xpath-root 3;
            }
          }
          description
            "Locator name.";
        }
      }
    }
    container apply-sid-mode {
      tailf:ncs-device-type "netconf";
      tailf:display-when "not(../../../../../../../../../../../ncs:module) or ../../../../../../../../../../../ncs:module[ncs:name='huawei-evpn-srv6']";
      when "../../../../../../../ni:name!='_public_' and ../../../bgp:type='ipv6uni'" {
        tailf:xpath-root 3;
      }
      description
        "Configure apply SID for segment-routing IPv6 in EVPN.";
      leaf mode {
        when '../../locators/locator/name' {
          tailf:xpath-root 3;
        }
        type apply-sid-mode;
        default "per-instance";
        description
          "Apply SID mode for segment-routing IPv6 in EVPN.";
      }
      container specify-nexthops {
        when "../mode='per-nexthop-specify'" {
          tailf:xpath-root 3;
        }
        description
          "List of locators used by segment-routing IPv6 for EVPN.";
        list specify-nexthop {
          key "nexthop-address";
          max-elements 128;
          description
            "Configure apply SID for segmet-routing IPv6 in EVPN specify nexthop mode.";
          leaf nexthop-address {
            type inet:ipv6-address-no-zone;
            description
              "Specify the nexthop IPv6 address.";
          }
          leaf interface-name {
            type leafref {
              path "/ncs:devices/ncs:device/ncs:config/ifm:ifm/ifm:interfaces/ifm:interface/ifm:name" {
                tailf:xpath-root 3;
              }
            }
            mandatory true;
            description
              "Out interface name of route.";
          }
        }
      }
    }
  }
  augment "/ncs:devices/ncs:template/ncs:ned-id/ncs:config/evpn:evpn/evpn:instances/evpn:instance/evpn:bd-evpn" {
    description
      "EVPN SRv6 configuration.";
    container locator {
      description
        "Configure segment-routing IPv6 locators to EVPN.";
      leaf srv6-locator {
        type string;
        // NCS drop must statement
        description
          "Locator that is used to generate a BUM (DT2M) SID. If unicast-locator is not configured, locator is used to generate a unicast (DT2U) SID.";
      }
      leaf unicast-locator {
        // NCS drop when statement
        type string;
        // NCS drop must statement
        description
          "Locator that is used to generate a unicast (DT2U) SID.";
      }
    }
  }
  augment "/ncs:devices/ncs:device/ncs:live-status/evpn:evpn/evpn:instances/evpn:instance/evpn:bd-evpn" {
    description
      "EVPN SRv6 configuration.";
    container locator {
      tailf:ncs-device-type "netconf";
      tailf:display-when "not(../../../../../../ncs:module) or ../../../../../../ncs:module[ncs:name='huawei-evpn-srv6'] or (../../../../../../ncs:live-status-protocol[not(ncs:capability)]) or (../../../../../../ncs:live-status-protocol/ncs:capability/ncs:module[.='huawei-evpn-srv6'])";
      description
        "Configure segment-routing IPv6 locators to EVPN.";
      leaf srv6-locator {
        type leafref {
          path "/ncs:devices/ncs:device/ncs:live-status/ni:network-instance/ni:instances/ni:instance/srv6:srv6/srv6:locators/srv6:locator/srv6:name" {
            tailf:xpath-root 3;
          }
        }
        // NCS drop must statement
        description
          "Locator that is used to generate a BUM (DT2M) SID. If unicast-locator is not configured, locator is used to generate a unicast (DT2U) SID.";
      }
      leaf unicast-locator {
        // NCS drop when statement
        type leafref {
          path "/ncs:devices/ncs:device/ncs:live-status/ni:network-instance/ni:instances/ni:instance/srv6:srv6/srv6:locators/srv6:locator/srv6:name" {
            tailf:xpath-root 3;
          }
        }
        // NCS drop must statement
        description
          "Locator that is used to generate a unicast (DT2U) SID.";
      }
    }
  }
  augment "/ncs:devices/ncs:device/ncs:config/evpn:evpn/evpn:instances/evpn:instance/evpn:bd-evpn" {
    description
      "EVPN SRv6 configuration.";
    container locator {
      tailf:ncs-device-type "netconf";
      tailf:display-when "not(../../../../../../ncs:module) or ../../../../../../ncs:module[ncs:name='huawei-evpn-srv6']";
      description
        "Configure segment-routing IPv6 locators to EVPN.";
      leaf srv6-locator {
        type leafref {
          path "/ncs:devices/ncs:device/ncs:config/ni:network-instance/ni:instances/ni:instance/srv6:srv6/srv6:locators/srv6:locator/srv6:name" {
            tailf:xpath-root 3;
          }
        }
        must "/ni:network-instance/ni:instances/ni:instance[ni:name='_public_']/srv6:srv6/srv6:locators/srv6:locator[srv6:name=current()]/srv6:args-length>0" {
          tailf:xpath-root 3;
        }
        description
          "Locator that is used to generate a BUM (DT2M) SID. If unicast-locator is not configured, locator is used to generate a unicast (DT2U) SID.";
      }
      leaf unicast-locator {
        when '../srv6-locator' {
          tailf:xpath-root 3;
        }
        type leafref {
          path "/ncs:devices/ncs:device/ncs:config/ni:network-instance/ni:instances/ni:instance/srv6:srv6/srv6:locators/srv6:locator/srv6:name" {
            tailf:xpath-root 3;
          }
        }
        must '(../unicast-locator and ../unicast-locator!=../srv6-locator) or not(../unicast-locator)' {
          tailf:xpath-root 3;
        }
        description
          "Locator that is used to generate a unicast (DT2U) SID.";
      }
    }
  }
}
