module huawei-nvo3 {
  // Generated by yanger -t ncs
  tailf:mount-id "huawei-nc-1.0:huawei-nc-1.0";
  tailf:ncs-device-type "netconf";

  namespace "urn:huawei:yang:huawei-nvo3";
  prefix nvo3;

  import huawei-bd {
    prefix bd;
  }
  import huawei-ifm {
    prefix ifm;
  }
  import huawei-network-instance {
    prefix ni;
  }
  import huawei-pub-type {
    prefix pub-type;
  }
  import ietf-inet-types {
    prefix inet;
  }
  import huawei-extension {
    prefix ext;
  }
  import huawei-evpl {
    prefix evpl;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Management for data center network virtualization over Layer 3.";

  revision 2020-03-06 {
    description
      "The modifications in the schema file are synchronized to the YANG file.";
    reference "Huawei private.";
  }
  revision 2019-03-01 {
    description
      "Initial revision.";
    reference "Huawei private.";
  }
  ext:task-name "nvo3";

  typedef ncs_template_vni-state {
    type string;
    description
      "The state for VNI.";
  }

  typedef ncs_template_tunnel-type {
    type string;
    description
      "VXLAN tunnel type.";
  }

  typedef ncs_template_tunnel-mode {
    type string;
    description
      "VXLAN tunnel mode.";
  }

  typedef ncs_template_peer-learning-type {
    type string;
    description
      "The type of peers Learning via BGP.";
  }

  typedef ncs_template_nqa-state-type {
    type string;
    description
      "The NQA state.";
  }

  typedef ncs_template_preference-type {
    type string;
    description
      "Preference type.";
  }

  typedef ncs_rpc_notif_vni-state {
    type enumeration {
      enum "down" {
        value 0;
        description
          "The state is down.";
      }
      enum "up" {
        value 1;
        description
          "The state is up.";
      }
    }
    description
      "The state for VNI.";
  }

  typedef ncs_rpc_notif_tunnel-type {
    type enumeration {
      enum "dynamic" {
        value 0;
        description
          "Learning via protocols.";
      }
      enum "static" {
        value 1;
        description
          "Created by users.";
      }
    }
    description
      "VXLAN tunnel type.";
  }

  typedef ncs_rpc_notif_tunnel-mode {
    type enumeration {
      enum "default-mode" {
        value 0;
        description
          "Default mode.";
      }
      enum "cu-mode" {
        value 1;
        description
          "Control-User separation mode.";
      }
    }
    description
      "VXLAN tunnel mode.";
  }

  typedef ncs_rpc_notif_peer-learning-type {
    type enumeration {
      enum "peer" {
        value 1;
        description
          "Learning peers for multicast via BGP.";
      }
    }
    description
      "The type of peers Learning via BGP.";
  }

  typedef ncs_rpc_notif_nqa-state-type {
    type enumeration {
      enum "unknown" {
        value 0;
        description
          "The NQA state is unknown.";
      }
      enum "down" {
        value 1;
        description
          "The NQA state is down.";
      }
      enum "up" {
        value 2;
        description
          "The NQA state is up.";
      }
    }
    description
      "The NQA state.";
  }

  typedef ncs_rpc_notif_preference-type {
    type enumeration {
      enum "primary" {
        value 1;
        description
          "Primary enable.";
      }
      enum "secondary" {
        value 2;
        description
          "Secondary enable.";
      }
      enum "bypass" {
        value 4;
        description
          "Bypass enable.";
      }
    }
    description
      "Preference type.";
  }

  typedef live_ncs_vni-state {
    type enumeration {
      enum "down" {
        value 0;
        description
          "The state is down.";
      }
      enum "up" {
        value 1;
        description
          "The state is up.";
      }
    }
    description
      "The state for VNI.";
  }

  typedef live_ncs_tunnel-type {
    type enumeration {
      enum "dynamic" {
        value 0;
        description
          "Learning via protocols.";
      }
      enum "static" {
        value 1;
        description
          "Created by users.";
      }
    }
    description
      "VXLAN tunnel type.";
  }

  typedef live_ncs_tunnel-mode {
    type enumeration {
      enum "default-mode" {
        value 0;
        description
          "Default mode.";
      }
      enum "cu-mode" {
        value 1;
        description
          "Control-User separation mode.";
      }
    }
    description
      "VXLAN tunnel mode.";
  }

  typedef live_ncs_peer-learning-type {
    type enumeration {
      enum "peer" {
        value 1;
        description
          "Learning peers for multicast via BGP.";
      }
    }
    description
      "The type of peers Learning via BGP.";
  }

  typedef live_ncs_nqa-state-type {
    type enumeration {
      enum "unknown" {
        value 0;
        description
          "The NQA state is unknown.";
      }
      enum "down" {
        value 1;
        description
          "The NQA state is down.";
      }
      enum "up" {
        value 2;
        description
          "The NQA state is up.";
      }
    }
    description
      "The NQA state.";
  }

  typedef live_ncs_preference-type {
    type enumeration {
      enum "primary" {
        value 1;
        description
          "Primary enable.";
      }
      enum "secondary" {
        value 2;
        description
          "Secondary enable.";
      }
      enum "bypass" {
        value 4;
        description
          "Bypass enable.";
      }
    }
    description
      "Preference type.";
  }

  typedef vni-state {
    type enumeration {
      enum "down" {
        value 0;
        description
          "The state is down.";
      }
      enum "up" {
        value 1;
        description
          "The state is up.";
      }
    }
    description
      "The state for VNI.";
  }

  typedef tunnel-type {
    type enumeration {
      enum "dynamic" {
        value 0;
        description
          "Learning via protocols.";
      }
      enum "static" {
        value 1;
        description
          "Created by users.";
      }
    }
    description
      "VXLAN tunnel type.";
  }

  typedef tunnel-mode {
    type enumeration {
      enum "default-mode" {
        value 0;
        description
          "Default mode.";
      }
      enum "cu-mode" {
        value 1;
        description
          "Control-User separation mode.";
      }
    }
    description
      "VXLAN tunnel mode.";
  }

  typedef peer-learning-type {
    type enumeration {
      enum "peer" {
        value 1;
        description
          "Learning peers for multicast via BGP.";
      }
    }
    description
      "The type of peers Learning via BGP.";
  }

  typedef nqa-state-type {
    type enumeration {
      enum "unknown" {
        value 0;
        description
          "The NQA state is unknown.";
      }
      enum "down" {
        value 1;
        description
          "The NQA state is down.";
      }
      enum "up" {
        value 2;
        description
          "The NQA state is up.";
      }
    }
    description
      "The NQA state.";
  }

  typedef preference-type {
    type enumeration {
      enum "primary" {
        value 1;
        description
          "Primary enable.";
      }
      enum "secondary" {
        value 2;
        description
          "Secondary enable.";
      }
      enum "bypass" {
        value 4;
        description
          "Bypass enable.";
      }
    }
    description
      "Preference type.";
  }

  augment "/ncs:devices/ncs:device/ncs:config" {
    container nvo3 {
      tailf:ncs-device-type "netconf";
      tailf:display-when "not(../../ncs:module) or ../../ncs:module[ncs:name='huawei-nvo3']";
      description
        "Management of NVO3.";
      container vni-instances {
        description
          "List of virtual extensible local area network.";
        list vni-instance {
          key "vni source-nve";
          description
            "Configure the information of virtual extensible local area network.";
          leaf vni {
            type uint32 {
              range "1..16777215";
            }
            description
              "VXLAN network identifier.";
          }
          leaf source-nve {
            type leafref {
              path "/ncs:devices/ncs:device/ncs:config/ifm:ifm/ifm:interfaces/ifm:interface/ifm:name" {
                tailf:xpath-root 3;
              }
            }
            must "/ifm:ifm/ifm:interfaces/ifm:interface[ifm:name=current()]/ifm:type='Nve'" {
              tailf:xpath-root 3;
            }
            description
              "The name of interface NVE, as VXLAN tunnel source point.";
          }
          // NCS drop config false leaf state
          leaf protocol-bgp {
            type peer-learning-type;
            description
              "Learning VTEPs via BGP for communication in a same VNI.";
          }
          container static-peers {
            description
              "List of VTEPs created by users for multicast in a same VNI.";
            list static-peer {
              key "address";
              description
                "Configure VTEP by users for multicast.";
              leaf address {
                type inet:ipv4-address-no-zone;
                description
                  "The address of VTEP.";
              }
            }
          }
          container static-ipv6-peers {
            description
              "List of VTEPs created by users for multicast in a same VNI.";
            list static-ipv6-peer {
              key "address";
              description
                "Configure VTEP by users for multicast.";
              leaf address {
                type inet:ipv6-address-no-zone;
                description
                  "The IPv6 address of VTEP.";
              }
            }
          }
          container static-evpl-peers {
            description
              "List of VTEPs created by users for ethernet virtual private line in the same VNI.";
            list static-evpl-peer {
              key "address";
              max-elements 1;
              description
                "Configure VTEP by users for ethernet virtual private line.";
              leaf address {
                type inet:ipv4-address-no-zone;
                must '(not(../../../static-peers/static-peer) and not(../../../protocol-bgp)) or not(../address)' {
                  tailf:xpath-root 3;
                }
                description
                  "The address of VTEP.";
              }
              leaf preference {
                ext:operation-exclude "update|delete";
                type preference-type;
                default "primary";
                description
                  "The preference of VXLAN tunnel.";
              }
            }
          }
        }
      }
      container vni-labels {
        description
          "List of VXLAN network identifiers.";
        list vni-label {
          key "vni";
          description
            "Configure VXLAN network identifier.";
          leaf vni {
            type uint32 {
              range "1..16777215";
            }
            description
              "VXLAN network identifier.";
          }
        }
      }
      // NCS drop config false container vteps
      container global-attribute {
        description
          "Configure global attribute of VXLAN.";
        leaf exact-sub-enable {
          type boolean;
          default "false";
          description
            "Enable/disable exact route subscribe.";
        }
      }
      // NCS drop config false container tunnels
    }
  }
  augment "/ncs:devices/ncs:device/ncs:live-status" {
    container nvo3 {
      tailf:ncs-device-type "netconf";
      tailf:display-when "not(../../ncs:module) or ../../ncs:module[ncs:name='huawei-nvo3'] or (../../ncs:live-status-protocol[not(ncs:capability)]) or (../../ncs:live-status-protocol/ncs:capability/ncs:module[.='huawei-nvo3'])";
      description
        "Management of NVO3.";
      container vni-instances {
        description
          "List of virtual extensible local area network.";
        list vni-instance {
          key "vni source-nve";
          description
            "Configure the information of virtual extensible local area network.";
          leaf vni {
            type uint32 {
              range "1..16777215";
            }
            description
              "VXLAN network identifier.";
          }
          leaf source-nve {
            type leafref {
              path "/ncs:devices/ncs:device/ncs:live-status/ifm:ifm/ifm:interfaces/ifm:interface/ifm:name" {
                tailf:xpath-root 3;
              }
            }
            // NCS drop must statement
            description
              "The name of interface NVE, as VXLAN tunnel source point.";
          }
          leaf state {
            type live_ncs_vni-state;
            description
              "The state of the VNI. When the VTEP address in the VNI is reachable, the state is up, the opposite is down.";
          }
          leaf protocol-bgp {
            type live_ncs_peer-learning-type;
            description
              "Learning VTEPs via BGP for communication in a same VNI.";
          }
          container static-peers {
            description
              "List of VTEPs created by users for multicast in a same VNI.";
            list static-peer {
              key "address";
              description
                "Configure VTEP by users for multicast.";
              leaf address {
                type inet:ipv4-address-no-zone;
                description
                  "The address of VTEP.";
              }
            }
          }
          container static-ipv6-peers {
            description
              "List of VTEPs created by users for multicast in a same VNI.";
            list static-ipv6-peer {
              key "address";
              description
                "Configure VTEP by users for multicast.";
              leaf address {
                type inet:ipv6-address-no-zone;
                description
                  "The IPv6 address of VTEP.";
              }
            }
          }
          container static-evpl-peers {
            description
              "List of VTEPs created by users for ethernet virtual private line in the same VNI.";
            list static-evpl-peer {
              key "address";
              // NCS drop max-elements statement
              description
                "Configure VTEP by users for ethernet virtual private line.";
              leaf address {
                type inet:ipv4-address-no-zone;
                // NCS drop must statement
                description
                  "The address of VTEP.";
              }
              leaf preference {
                ext:operation-exclude "update|delete";
                type live_ncs_preference-type;
                // NCS drop default statement
                description
                  "The preference of VXLAN tunnel.";
              }
            }
          }
        }
      }
      container vni-labels {
        description
          "List of VXLAN network identifiers.";
        list vni-label {
          key "vni";
          description
            "Configure VXLAN network identifier.";
          leaf vni {
            type uint32 {
              range "1..16777215";
            }
            description
              "VXLAN network identifier.";
          }
        }
      }
      container vteps {
        description
          "Statistics of VTEPs.";
        container peers {
          description
            "List of VTEPs for multicast in a same VNI.";
          list peer {
            key "vni source destination";
            description
              "Operational data of VTEPs for multicast with the same VNI.";
            leaf vni {
              type uint32 {
                range "1..16777215";
              }
              description
                "VXLAN network identifier.";
            }
            leaf source {
              type inet:ip-address-no-zone;
              description
                "The address of VXLAN tunnel source point.";
            }
            leaf destination {
              type inet:ip-address-no-zone;
              description
                "The address of VTEP.";
            }
            leaf type {
              type live_ncs_tunnel-type;
              description
                "The type of VXLAN tunnel.";
            }
            leaf out-vni {
              type uint32 {
                range "1..16777215";
              }
              description
                "VXLAN network identifier for mapping.";
            }
          }
        }
        container cu-peers {
          description
            "List of VNI Peers Table of CU Mode.";
          list cu-peer {
            key "vni source destination";
            description
              "Operational data of VNI Peer Table of CU Mode.";
            leaf vni {
              type uint32 {
                range "1..16777215";
              }
              description
                "The identification of VXLAN tunnel.";
            }
            leaf source {
              type inet:ip-address-no-zone;
              description
                "The address of VXLAN tunnel source point.";
            }
            leaf destination {
              type inet:ip-address-no-zone;
              description
                "The address of VTEP.";
            }
            leaf type {
              type live_ncs_tunnel-type;
              description
                "VXLAN tunnel type.";
            }
            leaf out-vni {
              type uint32 {
                range "1..16777215";
              }
              description
                "VXLAN network identifier for mapping.";
            }
            leaf nqa-state {
              type live_ncs_nqa-state-type;
              description
                "The NQA state:unknown, down or up.";
            }
            leaf packet-loss-ratio {
              type uint8 {
                range "0..100";
              }
              units "%";
              description
                "The NQA packet loss ratio.";
            }
          }
        }
        container evpl-peers {
          description
            "List of VTEPs for ethernet virtual private line in a same VNI.";
          list evpl-peer {
            key "id";
            description
              "Operational data of VTEPs for Ethernet virtual private lines with the same VNI.";
            leaf id {
              type uint32 {
                range "1..16777215";
              }
              description
                "The identification of the EVPL instance.";
            }
            leaf vni {
              type uint32 {
                range "1..16777215";
              }
              description
                "Local VNI for communication.";
            }
            leaf source {
              type inet:ip-address-no-zone;
              description
                "The address of VXLAN tunnel source point.";
            }
            leaf peer {
              type inet:ip-address-no-zone;
              description
                "The address of primary VTEP.";
            }
            leaf out-vni {
              type uint32 {
                range "1..16777215";
              }
              description
                "Primary VNI for mapping.";
            }
            leaf backup-peer {
              type inet:ip-address-no-zone;
              description
                "The address of backup VTEP.";
            }
            leaf backup-out-vni {
              type uint32 {
                range "1..16777215";
              }
              description
                "Backup VNI for mapping.";
            }
            leaf bypass-peer {
              type inet:ip-address-no-zone;
              description
                "The address of bypass VTEP.";
            }
            leaf bypass-out-vni {
              type uint32 {
                range "1..16777215";
              }
              description
                "Bypass VNI for mapping.";
            }
          }
        }
      }
      container global-attribute {
        description
          "Configure global attribute of VXLAN.";
        leaf exact-sub-enable {
          type boolean;
          // NCS drop default statement
          description
            "Enable/disable exact route subscribe.";
        }
      }
      container tunnels {
        description
          "List of VXLAN tunnel information.";
        list tunnel {
          key "id";
          description
            "Statistics of VXLAN tunnels.";
          leaf id {
            type uint32 {
              range "1..4294967295";
            }
            description
              "The identification of VXLAN tunnel.";
          }
          leaf source {
            type inet:ip-address-no-zone;
            description
              "The address of VXLAN tunnel source point.";
            ext:support-filter "true";
          }
          leaf destination {
            type inet:ip-address-no-zone;
            description
              "The address of VTEP.";
            ext:support-filter "true";
          }
          leaf mode {
            type live_ncs_tunnel-mode;
            description
              "VXLAN tunnel mode.";
            ext:support-filter "true";
          }
          leaf state {
            type live_ncs_vni-state;
            description
              "VXLAN tunnel state. When the address of VTEP is reachable, the state is up, otherwise is down.";
          }
          leaf type {
            type live_ncs_tunnel-type;
            description
              "VXLAN tunnel type.";
          }
          leaf up-time {
            type string {
              length "1..10";
            }
            description
              "The continuous time as VXLAN tunnel is reachable.";
          }
        }
      }
    }
  }
  augment "/ncs:devices/ncs:template/ncs:ned-id/ncs:config" {
    container nvo3 {
      description
        "Management of NVO3.";
      container vni-instances {
        description
          "List of virtual extensible local area network.";
        list vni-instance {
          // NCS patched for predictable order
          ordered-by user;
          key "vni source-nve";
          description
            "Configure the information of virtual extensible local area network.";
          leaf vni {
            type string;
            description
              "VXLAN network identifier.";
          }
          leaf source-nve {
            type string;
            // NCS drop must statement
            description
              "The name of interface NVE, as VXLAN tunnel source point.";
          }
          // NCS drop config false leaf state
          leaf protocol-bgp {
            type ncs_template_peer-learning-type;
            description
              "Learning VTEPs via BGP for communication in a same VNI.";
          }
          container static-peers {
            description
              "List of VTEPs created by users for multicast in a same VNI.";
            list static-peer {
              // NCS patched for predictable order
              ordered-by user;
              key "address";
              description
                "Configure VTEP by users for multicast.";
              leaf address {
                type string;
                description
                  "The address of VTEP.";
              }
            }
          }
          container static-ipv6-peers {
            description
              "List of VTEPs created by users for multicast in a same VNI.";
            list static-ipv6-peer {
              // NCS patched for predictable order
              ordered-by user;
              key "address";
              description
                "Configure VTEP by users for multicast.";
              leaf address {
                type string;
                description
                  "The IPv6 address of VTEP.";
              }
            }
          }
          container static-evpl-peers {
            description
              "List of VTEPs created by users for ethernet virtual private line in the same VNI.";
            list static-evpl-peer {
              // NCS patched for predictable order
              ordered-by user;
              key "address";
              // NCS drop max-elements statement
              description
                "Configure VTEP by users for ethernet virtual private line.";
              leaf address {
                type string;
                // NCS drop must statement
                description
                  "The address of VTEP.";
              }
              leaf preference {
                ext:operation-exclude "update|delete";
                type ncs_template_preference-type;
                // NCS drop default statement
                description
                  "The preference of VXLAN tunnel.";
              }
            }
          }
        }
      }
      container vni-labels {
        description
          "List of VXLAN network identifiers.";
        list vni-label {
          // NCS patched for predictable order
          ordered-by user;
          key "vni";
          description
            "Configure VXLAN network identifier.";
          leaf vni {
            type string;
            description
              "VXLAN network identifier.";
          }
        }
      }
      // NCS drop config false container vteps
      container global-attribute {
        description
          "Configure global attribute of VXLAN.";
        leaf exact-sub-enable {
          type string;
          // NCS drop default statement
          description
            "Enable/disable exact route subscribe.";
        }
      }
      // NCS drop config false container tunnels
    }
  }
  augment "/ncs:devices/ncs:template/ncs:ned-id/ncs:config/ifm:ifm/ifm:interfaces/ifm:interface" {
    description
      "The NVO3 configuration for interface.";
    container nve {
      // NCS drop when statement
      description
        "Configure NVO3 for interface NVE.";
      container attribute {
        // NCS drop must statement
        // NCS drop must statement
        description
          "Configure VTEPs for interface NVE.";
        leaf source-vtep-ip {
          type string;
          description
            "The address of interface NVE, as VXLAN tunnel source point.";
        }
        leaf source-vtep-ipv6 {
          type string;
          description
            "The IPv6 address of interface NVE, as VXLAN tunnel source point.";
        }
        leaf phys-address {
          type pub-type:ncs_template_mac-address;
          description
            "The interface's address at its protocol sub-layer. For example, for an 802.x interface, this object normally contains a Media Access Control (MAC) address.";
        }
        leaf bypass-vtep-ip {
          type string;
          description
            "The address of interface NVE, as source point in bypass VXLAN tunnel.";
        }
        leaf bypass-vtep-ipv6 {
          type string;
          description
            "The IPv6 address of interface NVE, as source point in bypass VXLAN tunnel.";
        }
      }
      container pip {
        // NCS drop must statement
        description
          "Configure primary IP address as bypass VXLAN tunnel.";
        leaf source-ip {
          type string;
          // NCS drop must statement
          description
            "The address of interface NVE, as VXLAN tunnel source point.";
          ext:operation-exclude "delete";
        }
        leaf peer-ip {
          type string;
          // NCS drop must statement
          description
            "The address of interface NVE, as VXLAN tunnel peer point.";
          ext:operation-exclude "delete";
        }
      }
    }
    container nvo3-gateway {
      // NCS drop when statement
      description
        "Configure anycast gateway features for NVO3.";
      leaf vxlan-anycast-gateway {
        type string;
        // NCS drop default statement
        description
          "Enable/disable VXLAN anycast gateway features.";
      }
      leaf common-anycast-gateway {
        type string;
        // NCS drop default statement
        description
          "Enable/disable common anycast gateway features.";
      }
    }
  }
  augment "/ncs:devices/ncs:device/ncs:live-status/ifm:ifm/ifm:interfaces/ifm:interface" {
    description
      "The NVO3 configuration for interface.";
    container nve {
      tailf:ncs-device-type "netconf";
      tailf:display-when "not(../../../../../ncs:module) or ../../../../../ncs:module[ncs:name='huawei-nvo3'] or (../../../../../ncs:live-status-protocol[not(ncs:capability)]) or (../../../../../ncs:live-status-protocol/ncs:capability/ncs:module[.='huawei-nvo3'])";
      // NCS drop when statement
      description
        "Configure NVO3 for interface NVE.";
      container attribute {
        // NCS drop must statement
        // NCS drop must statement
        description
          "Configure VTEPs for interface NVE.";
        leaf source-vtep-ip {
          type inet:ipv4-address-no-zone;
          description
            "The address of interface NVE, as VXLAN tunnel source point.";
        }
        leaf source-vtep-ipv6 {
          type inet:ipv6-address-no-zone;
          description
            "The IPv6 address of interface NVE, as VXLAN tunnel source point.";
        }
        leaf phys-address {
          type pub-type:live_ncs_mac-address;
          description
            "The interface's address at its protocol sub-layer. For example, for an 802.x interface, this object normally contains a Media Access Control (MAC) address.";
        }
        leaf bypass-vtep-ip {
          type inet:ipv4-address-no-zone;
          description
            "The address of interface NVE, as source point in bypass VXLAN tunnel.";
        }
        leaf bypass-vtep-ipv6 {
          type inet:ipv6-address-no-zone;
          description
            "The IPv6 address of interface NVE, as source point in bypass VXLAN tunnel.";
        }
      }
      container pip {
        // NCS drop must statement
        description
          "Configure primary IP address as bypass VXLAN tunnel.";
        leaf source-ip {
          type inet:ipv4-address-no-zone;
          // NCS drop must statement
          description
            "The address of interface NVE, as VXLAN tunnel source point.";
          ext:operation-exclude "delete";
        }
        leaf peer-ip {
          type inet:ipv4-address-no-zone;
          // NCS drop must statement
          description
            "The address of interface NVE, as VXLAN tunnel peer point.";
          ext:operation-exclude "delete";
        }
      }
    }
    container nvo3-gateway {
      tailf:ncs-device-type "netconf";
      tailf:display-when "not(../../../../../ncs:module) or ../../../../../ncs:module[ncs:name='huawei-nvo3'] or (../../../../../ncs:live-status-protocol[not(ncs:capability)]) or (../../../../../ncs:live-status-protocol/ncs:capability/ncs:module[.='huawei-nvo3'])";
      // NCS drop when statement
      description
        "Configure anycast gateway features for NVO3.";
      leaf vxlan-anycast-gateway {
        type boolean;
        // NCS drop default statement
        description
          "Enable/disable VXLAN anycast gateway features.";
      }
      leaf common-anycast-gateway {
        type boolean;
        // NCS drop default statement
        description
          "Enable/disable common anycast gateway features.";
      }
    }
  }
  augment "/ncs:devices/ncs:device/ncs:config/ifm:ifm/ifm:interfaces/ifm:interface" {
    description
      "The NVO3 configuration for interface.";
    container nve {
      tailf:ncs-device-type "netconf";
      tailf:display-when "not(../../../../../ncs:module) or ../../../../../ncs:module[ncs:name='huawei-nvo3']";
      when "../ifm:type='Nve'" {
        tailf:xpath-root 3;
      }
      description
        "Configure NVO3 for interface NVE.";
      container attribute {
        must '(./source-vtep-ip and ./bypass-vtep-ip and ./source-vtep-ip != ./bypass-vtep-ip) or not(./source-vtep-ip) or not(./bypass-vtep-ip) ' {
          tailf:xpath-root 3;
        }
        must '(./source-vtep-ipv6 and ./bypass-vtep-ipv6 and ./source-vtep-ipv6 != ./bypass-vtep-ipv6) or not(./source-vtep-ipv6) or not(./bypass-vtep-ipv6) ' {
          tailf:xpath-root 3;
        }
        description
          "Configure VTEPs for interface NVE.";
        leaf source-vtep-ip {
          type inet:ipv4-address-no-zone;
          description
            "The address of interface NVE, as VXLAN tunnel source point.";
        }
        leaf source-vtep-ipv6 {
          type inet:ipv6-address-no-zone;
          description
            "The IPv6 address of interface NVE, as VXLAN tunnel source point.";
        }
        leaf phys-address {
          type pub-type:mac-address;
          description
            "The interface's address at its protocol sub-layer. For example, for an 802.x interface, this object normally contains a Media Access Control (MAC) address.";
        }
        leaf bypass-vtep-ip {
          type inet:ipv4-address-no-zone;
          description
            "The address of interface NVE, as source point in bypass VXLAN tunnel.";
        }
        leaf bypass-vtep-ipv6 {
          type inet:ipv6-address-no-zone;
          description
            "The IPv6 address of interface NVE, as source point in bypass VXLAN tunnel.";
        }
      }
      container pip {
        must '((./source-ip and ./peer-ip) and (./source-ip != ./peer-ip)) or (not(./source-ip) and not(./peer-ip))' {
          tailf:xpath-root 3;
        }
        description
          "Configure primary IP address as bypass VXLAN tunnel.";
        leaf source-ip {
          type inet:ipv4-address-no-zone;
          must 'not (../../attribute[source-vtep-ip != current()])' {
            tailf:xpath-root 3;
          }
          description
            "The address of interface NVE, as VXLAN tunnel source point.";
          ext:operation-exclude "delete";
        }
        leaf peer-ip {
          type inet:ipv4-address-no-zone;
          must 'not (../../attribute[source-vtep-ip != current()])' {
            tailf:xpath-root 3;
          }
          description
            "The address of interface NVE, as VXLAN tunnel peer point.";
          ext:operation-exclude "delete";
        }
      }
    }
    container nvo3-gateway {
      tailf:ncs-device-type "netconf";
      tailf:display-when "not(../../../../../ncs:module) or ../../../../../ncs:module[ncs:name='huawei-nvo3']";
      when "../ifm:type='Vbdif'" {
        tailf:xpath-root 3;
      }
      description
        "Configure anycast gateway features for NVO3.";
      leaf vxlan-anycast-gateway {
        type boolean;
        default "false";
        description
          "Enable/disable VXLAN anycast gateway features.";
      }
      leaf common-anycast-gateway {
        type boolean;
        default "false";
        description
          "Enable/disable common anycast gateway features.";
      }
    }
  }
  augment "/ncs:devices/ncs:template/ncs:ned-id/ncs:config/bd:bd/bd:instances/bd:instance" {
    description
      "The NVO3 configuration for bridge domains.";
    container nvo3 {
      description
        "Configure NVO3 for a BD.";
      list vni-list {
        // NCS patched for predictable order
        ordered-by user;
        key "vni";
        // NCS drop max-elements statement
        description
          "Configure the list of VNI that a bridge domain corresponds.";
        leaf vni {
          type string;
          description
            "VXLAN network identifier.";
        }
        leaf split-horizon {
          type string;
          // NCS drop default statement
          description
            "Enable/disable split horizon mode.";
        }
      }
    }
  }
  augment "/ncs:devices/ncs:device/ncs:live-status/bd:bd/bd:instances/bd:instance" {
    description
      "The NVO3 configuration for bridge domains.";
    container nvo3 {
      tailf:ncs-device-type "netconf";
      tailf:display-when "not(../../../../../ncs:module) or ../../../../../ncs:module[ncs:name='huawei-nvo3'] or (../../../../../ncs:live-status-protocol[not(ncs:capability)]) or (../../../../../ncs:live-status-protocol/ncs:capability/ncs:module[.='huawei-nvo3'])";
      description
        "Configure NVO3 for a BD.";
      list vni-list {
        key "vni";
        // NCS drop max-elements statement
        description
          "Configure the list of VNI that a bridge domain corresponds.";
        leaf vni {
          type uint32 {
            range "1..16777215";
          }
          description
            "VXLAN network identifier.";
        }
        leaf split-horizon {
          type boolean;
          // NCS drop default statement
          description
            "Enable/disable split horizon mode.";
        }
      }
    }
  }
  augment "/ncs:devices/ncs:device/ncs:config/bd:bd/bd:instances/bd:instance" {
    description
      "The NVO3 configuration for bridge domains.";
    container nvo3 {
      tailf:ncs-device-type "netconf";
      tailf:display-when "not(../../../../../ncs:module) or ../../../../../ncs:module[ncs:name='huawei-nvo3']";
      description
        "Configure NVO3 for a BD.";
      list vni-list {
        key "vni";
        max-elements 1;
        description
          "Configure the list of VNI that a bridge domain corresponds.";
        leaf vni {
          type uint32 {
            range "1..16777215";
          }
          description
            "VXLAN network identifier.";
        }
        leaf split-horizon {
          type boolean;
          default "false";
          description
            "Enable/disable split horizon mode.";
        }
      }
    }
  }
  augment "/ncs:devices/ncs:template/ncs:ned-id/ncs:config/ni:network-instance/ni:instances/ni:instance" {
    description
      "The NVO3 configuration for network instances.";
    container nvo3 {
      // NCS drop when statement
      description
        "Configure NVO3 for a network instance.";
      list vni-list {
        // NCS patched for predictable order
        ordered-by user;
        key "vni";
        // NCS drop max-elements statement
        description
          "Configure NVO3 for a network instance.";
        leaf vni {
          type string;
          description
            "VXLAN network identifier.";
        }
      }
    }
  }
  augment "/ncs:devices/ncs:device/ncs:live-status/ni:network-instance/ni:instances/ni:instance" {
    description
      "The NVO3 configuration for network instances.";
    container nvo3 {
      tailf:ncs-device-type "netconf";
      tailf:display-when "not(../../../../../ncs:module) or ../../../../../ncs:module[ncs:name='huawei-nvo3'] or (../../../../../ncs:live-status-protocol[not(ncs:capability)]) or (../../../../../ncs:live-status-protocol/ncs:capability/ncs:module[.='huawei-nvo3'])";
      // NCS drop when statement
      description
        "Configure NVO3 for a network instance.";
      list vni-list {
        key "vni";
        // NCS drop max-elements statement
        description
          "Configure NVO3 for a network instance.";
        leaf vni {
          type uint32 {
            range "1..16777215";
          }
          description
            "VXLAN network identifier.";
        }
      }
    }
  }
  augment "/ncs:devices/ncs:device/ncs:config/ni:network-instance/ni:instances/ni:instance" {
    description
      "The NVO3 configuration for network instances.";
    container nvo3 {
      tailf:ncs-device-type "netconf";
      tailf:display-when "not(../../../../../ncs:module) or ../../../../../ncs:module[ncs:name='huawei-nvo3']";
      when "../ni:name != '_public_'" {
        tailf:xpath-root 3;
      }
      description
        "Configure NVO3 for a network instance.";
      list vni-list {
        key "vni";
        max-elements 1;
        description
          "Configure NVO3 for a network instance.";
        leaf vni {
          type uint32 {
            range "1..16777215";
          }
          description
            "VXLAN network identifier.";
        }
      }
    }
  }
  augment "/ncs:devices/ncs:template/ncs:ned-id/ncs:config/evpl:evpl/evpl:instances/evpl:instance" {
    // NCS drop when statement
    description
      "The NVO3 configuration for EVPL instances.";
    container nvo3 {
      description
        "Configure NVO3 for an EVPL instance.";
      container attribute {
        description
          "Configure the attribute for an EVPL instance in VXLAN mode.";
        leaf vtep-ip {
          type string;
          description
            "The address of VXLAN tunnel source point. When not configured, the address of interface NVE is used as default.";
        }
      }
      container vni-lists {
        description
          "List of VXLAN network identifiers.";
        list vni-list {
          // NCS patched for predictable order
          ordered-by user;
          key "vni";
          // NCS drop max-elements statement
          description
            "Configure a VNI list for an EVPL instance in VXLAN mode.";
          leaf vni {
            type string;
            description
              "VXLAN network identifier.";
          }
        }
      }
    }
  }
  augment "/ncs:devices/ncs:device/ncs:live-status/evpl:evpl/evpl:instances/evpl:instance" {
    // NCS drop when statement
    description
      "The NVO3 configuration for EVPL instances.";
    container nvo3 {
      tailf:ncs-device-type "netconf";
      tailf:display-when "not(../../../../../ncs:module) or ../../../../../ncs:module[ncs:name='huawei-nvo3'] or (../../../../../ncs:live-status-protocol[not(ncs:capability)]) or (../../../../../ncs:live-status-protocol/ncs:capability/ncs:module[.='huawei-nvo3'])";
      description
        "Configure NVO3 for an EVPL instance.";
      container attribute {
        description
          "Configure the attribute for an EVPL instance in VXLAN mode.";
        leaf vtep-ip {
          type inet:ipv4-address-no-zone;
          description
            "The address of VXLAN tunnel source point. When not configured, the address of interface NVE is used as default.";
        }
      }
      container vni-lists {
        description
          "List of VXLAN network identifiers.";
        list vni-list {
          key "vni";
          // NCS drop max-elements statement
          description
            "Configure a VNI list for an EVPL instance in VXLAN mode.";
          leaf vni {
            type uint32 {
              range "1..16777215";
            }
            description
              "VXLAN network identifier.";
          }
        }
      }
    }
  }
  augment "/ncs:devices/ncs:device/ncs:config/evpl:evpl/evpl:instances/evpl:instance" {
    when "./evpl:mode = 'vxlan-mode'" {
      tailf:xpath-root 3;
    }
    description
      "The NVO3 configuration for EVPL instances.";
    container nvo3 {
      tailf:ncs-device-type "netconf";
      tailf:display-when "not(../../../../../ncs:module) or ../../../../../ncs:module[ncs:name='huawei-nvo3']";
      description
        "Configure NVO3 for an EVPL instance.";
      container attribute {
        description
          "Configure the attribute for an EVPL instance in VXLAN mode.";
        leaf vtep-ip {
          type inet:ipv4-address-no-zone;
          description
            "The address of VXLAN tunnel source point. When not configured, the address of interface NVE is used as default.";
        }
      }
      container vni-lists {
        description
          "List of VXLAN network identifiers.";
        list vni-list {
          key "vni";
          max-elements 1;
          description
            "Configure a VNI list for an EVPL instance in VXLAN mode.";
          leaf vni {
            type uint32 {
              range "1..16777215";
            }
            description
              "VXLAN network identifier.";
          }
        }
      }
    }
  }
}
