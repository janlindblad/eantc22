module huawei-ifm-deviations-NE8000 {
  // Generated by yanger -t ncs
  tailf:mount-id "huawei-nc-1.0:huawei-nc-1.0";
  tailf:ncs-device-type "netconf";

  namespace "urn:huawei:yang:huawei-ifm-deviations-NE8000";
  prefix ifm-devs-NE8000;

  import huawei-ifm {
    prefix ifm;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Common interface management, which includes the public configuration of interfaces.";

  revision 2019-05-06 {
    description
      "Init revision.";
    reference "Huawei private.";
  }

  typedef ncs_template_error-down-type-deviations {
    type string;
    description
      "Interface error down type.";
  }

  typedef ncs_rpc_notif_error-down-type-deviations {
    type enumeration {
      enum "bpdu-protection" {
        value 0;
        description
          "BPDU protection.";
      }
      enum "l2-loop-occured" {
        value 74;
        description
          "L2 loop.";
      }
    }
    description
      "Interface error down type.";
  }

  typedef live_ncs_error-down-type-deviations {
    type enumeration {
      enum "bpdu-protection" {
        value 0;
        description
          "BPDU protection.";
      }
      enum "l2-loop-occured" {
        value 74;
        description
          "L2 loop.";
      }
    }
    description
      "Interface error down type.";
  }

  typedef error-down-type-deviations {
    type enumeration {
      enum "bpdu-protection" {
        value 0;
        description
          "BPDU protection.";
      }
      enum "l2-loop-occured" {
        value 74;
        description
          "L2 loop.";
      }
    }
    description
      "Interface error down type.";
  }

  deviation "/ncs:devices/ncs:template/ncs:ned-id/ncs:config/ifm:ifm/ifm:global/ifm:sub-interface-link-trap-enable" {
    deviate not-supported;
  }
  deviation "/ncs:devices/ncs:device/ncs:live-status/ifm:ifm/ifm:global/ifm:sub-interface-link-trap-enable" {
    deviate not-supported;
  }
  deviation "/ncs:devices/ncs:device/ncs:config/ifm:ifm/ifm:global/ifm:sub-interface-link-trap-enable" {
    deviate not-supported;
  }
  deviation "/ncs:devices/ncs:template/ncs:ned-id/ncs:config/ifm:ifm/ifm:interfaces/ifm:interface/ifm:network-layer-status" {
    deviate not-supported;
  }
  deviation "/ncs:devices/ncs:device/ncs:live-status/ifm:ifm/ifm:interfaces/ifm:interface/ifm:network-layer-status" {
    deviate not-supported;
  }
  deviation "/ncs:devices/ncs:device/ncs:config/ifm:ifm/ifm:interfaces/ifm:interface/ifm:network-layer-status" {
    deviate not-supported;
  }
  deviation "/ncs:devices/ncs:template/ncs:ned-id/ncs:config/ifm:ifm/ifm:interfaces/ifm:interface/ifm:protocol-up-delay-time" {
    deviate not-supported;
  }
  deviation "/ncs:devices/ncs:device/ncs:live-status/ifm:ifm/ifm:interfaces/ifm:interface/ifm:protocol-up-delay-time" {
    deviate not-supported;
  }
  deviation "/ncs:devices/ncs:device/ncs:config/ifm:ifm/ifm:interfaces/ifm:interface/ifm:protocol-up-delay-time" {
    deviate not-supported;
  }
  deviation "/ncs:devices/ncs:device/ncs:live-status/ifm:ifm/ifm:interfaces/ifm:interface/ifm:dynamic/ifm:sub-if-counts" {
    deviate not-supported;
  }
  deviation "/ncs:devices/ncs:template/ncs:ned-id/ncs:config/ifm:ifm/ifm:auto-recovery-times/ifm:auto-recovery-time/ifm:error-down-type" {
    deviate replace {
      type ifm-devs-NE8000:ncs_template_error-down-type-deviations;
    }
  }
  deviation "/ncs:devices/ncs:device/ncs:live-status/ifm:ifm/ifm:auto-recovery-times/ifm:auto-recovery-time/ifm:error-down-type" {
    deviate replace {
      type ifm-devs-NE8000:live_ncs_error-down-type-deviations;
    }
  }
  deviation "/ncs:devices/ncs:device/ncs:config/ifm:ifm/ifm:auto-recovery-times/ifm:auto-recovery-time/ifm:error-down-type" {
    deviate replace {
      type ifm-devs-NE8000:error-down-type-deviations;
    }
  }
  deviation "/ncs:devices/ncs:device/ncs:live-status/ifm:ifm/ifm:interfaces/ifm:interface/ifm:error-down/ifm:cause" {
    deviate replace {
      type ifm-devs-NE8000:live_ncs_error-down-type-deviations;
    }
  }
  deviation "/ncs:devices/ncs:device/ncs:rpc/ifm:rpc-reset-if-counters-by-type/ifm:reset-if-counters-by-type/ifm:input/ifm:if-type" {
    deviate add {
      must "../ifm:if-type='Ethernet' or ../ifm:if-type ='GigabitEthernet' or ../ifm:if-type='Eth-Trunk' or ../ifm:if-type='Ip-Trunk' or ../ifm:if-type='Pos' or ../ifm:if-type='Tunnel' or ../ifm:if-type='NULL' or ../ifm:if-type='LoopBack' or ../ifm:if-type='Vlanif' or ../ifm:if-type='100GE' or ../ifm:if-type='40GE' or ../ifm:if-type='25GE' or ../ifm:if-type='MTunnel' or ../ifm:if-type='Cpos' or ../ifm:if-type='E1' or ../ifm:if-type='Serial' or ../ifm:if-type='Mp-group' or ../ifm:if-type='Virtual-Ethernet' or ../ifm:if-type='Ima-group' or ../ifm:if-type='Remote-Ap' or ../ifm:if-type='VBridge' or ../ifm:if-type='Atm-Bundle' or ../ifm:if-type='Lmpif' or ../ifm:if-type='T1' or ../ifm:if-type='T3' or ../ifm:if-type='Global-VE' or ../ifm:if-type='Vbdif' or ../ifm:if-type='E3' or ../ifm:if-type='Pos-Trunk' or ../ifm:if-type='Trunk-Serial' or ../ifm:if-type='Global-Ima-Group' or ../ifm:if-type='Global-Mp-Group' or ../ifm:if-type='Nve' or ../ifm:if-type='Wdm' or ../ifm:if-type='Virtual-Template' or ../ifm:if-type='XGigabitEthernet' or ../ifm:if-type='FlexE' or ../ifm:if-type='50|100GE' or ../ifm:if-type='50GE' or ../ifm:if-type='PW-VE' or ../ifm:if-type='400GE' or ../ifm:if-type='HPGE'" {
        tailf:xpath-root 3;
      }
    }
  }
  deviation "/ncs:devices/ncs:device/ncs:rpc/ifm:rpc-reset-if-mib-counters-by-type/ifm:reset-if-mib-counters-by-type/ifm:input/ifm:if-type" {
    deviate add {
      must "../ifm:if-type='Ethernet' or ../ifm:if-type ='GigabitEthernet' or ../ifm:if-type='Eth-Trunk' or ../ifm:if-type='Ip-Trunk' or ../ifm:if-type='Pos' or ../ifm:if-type='Tunnel' or ../ifm:if-type='NULL' or ../ifm:if-type='LoopBack' or ../ifm:if-type='Vlanif' or ../ifm:if-type='100GE' or ../ifm:if-type='40GE' or ../ifm:if-type='25GE' or ../ifm:if-type='MTunnel' or ../ifm:if-type='Serial' or ../ifm:if-type='Mp-group' or ../ifm:if-type='Virtual-Ethernet' or ../ifm:if-type='Ima-group' or ../ifm:if-type='Remote-Ap' or ../ifm:if-type='VBridge' or ../ifm:if-type='Atm-Bundle' or ../ifm:if-type='Lmpif' or ../ifm:if-type='T3' or ../ifm:if-type='Global-VE' or ../ifm:if-type='Vbdif' or ../ifm:if-type='Pos-Trunk' or ../ifm:if-type='Trunk-Serial' or ../ifm:if-type='Global-Ima-Group' or ../ifm:if-type='Global-Mp-Group' or ../ifm:if-type='Nve' or ../ifm:if-type='Virtual-Template' or ../ifm:if-type='XGigabitEthernet' or ../ifm:if-type='FlexE' or ../ifm:if-type='50|100GE' or ../ifm:if-type='50GE' or ../ifm:if-type='PW-VE' or ../ifm:if-type='400GE' or ../ifm:if-type='HPGE'" {
        tailf:xpath-root 3;
      }
    }
  }
  deviation "/ncs:devices/ncs:template/ncs:ned-id/ncs:config/ifm:ifm/ifm:interfaces/ifm:interface/ifm:trap-threshold/ifm:input-rising-rate" {
    deviate replace {
      // NCS drop default statement
    }
  }
  deviation "/ncs:devices/ncs:device/ncs:live-status/ifm:ifm/ifm:interfaces/ifm:interface/ifm:trap-threshold/ifm:input-rising-rate" {
    deviate replace {
      // NCS drop default statement
    }
  }
  deviation "/ncs:devices/ncs:device/ncs:config/ifm:ifm/ifm:interfaces/ifm:interface/ifm:trap-threshold/ifm:input-rising-rate" {
    deviate replace {
      default "90";
    }
  }
  deviation "/ncs:devices/ncs:template/ncs:ned-id/ncs:config/ifm:ifm/ifm:interfaces/ifm:interface/ifm:trap-threshold/ifm:input-resume-rate" {
    deviate replace {
      // NCS drop default statement
    }
  }
  deviation "/ncs:devices/ncs:device/ncs:live-status/ifm:ifm/ifm:interfaces/ifm:interface/ifm:trap-threshold/ifm:input-resume-rate" {
    deviate replace {
      // NCS drop default statement
    }
  }
  deviation "/ncs:devices/ncs:device/ncs:config/ifm:ifm/ifm:interfaces/ifm:interface/ifm:trap-threshold/ifm:input-resume-rate" {
    deviate replace {
      default "80";
    }
  }
  deviation "/ncs:devices/ncs:template/ncs:ned-id/ncs:config/ifm:ifm/ifm:interfaces/ifm:interface/ifm:trap-threshold/ifm:output-rising-rate" {
    deviate replace {
      // NCS drop default statement
    }
  }
  deviation "/ncs:devices/ncs:device/ncs:live-status/ifm:ifm/ifm:interfaces/ifm:interface/ifm:trap-threshold/ifm:output-rising-rate" {
    deviate replace {
      // NCS drop default statement
    }
  }
  deviation "/ncs:devices/ncs:device/ncs:config/ifm:ifm/ifm:interfaces/ifm:interface/ifm:trap-threshold/ifm:output-rising-rate" {
    deviate replace {
      default "90";
    }
  }
  deviation "/ncs:devices/ncs:template/ncs:ned-id/ncs:config/ifm:ifm/ifm:interfaces/ifm:interface/ifm:trap-threshold/ifm:output-resume-rate" {
    deviate replace {
      // NCS drop default statement
    }
  }
  deviation "/ncs:devices/ncs:device/ncs:live-status/ifm:ifm/ifm:interfaces/ifm:interface/ifm:trap-threshold/ifm:output-resume-rate" {
    deviate replace {
      // NCS drop default statement
    }
  }
  deviation "/ncs:devices/ncs:device/ncs:config/ifm:ifm/ifm:interfaces/ifm:interface/ifm:trap-threshold/ifm:output-resume-rate" {
    deviate replace {
      default "80";
    }
  }
}
