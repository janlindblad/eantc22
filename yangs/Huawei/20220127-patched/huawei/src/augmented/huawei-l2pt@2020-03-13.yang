module huawei-l2pt {
  // Generated by yanger -t ncs
  tailf:mount-id "huawei-nc-1.0:huawei-nc-1.0";
  tailf:ncs-device-type "netconf";

  namespace "urn:huawei:yang:huawei-l2pt";
  prefix l2pt;

  import huawei-pub-type {
    prefix pub-type;
  }
  import huawei-ifm {
    prefix ifm;
  }
  import huawei-ethernet {
    prefix ethernet;
  }
  import huawei-extension {
    prefix ext;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "L2 protocol tunnel.";

  revision 2020-03-13 {
    description
      "Modify description.";
    reference "Huawei private.";
  }
  revision 2019-04-23 {
    description
      "Initial revision.";
    reference "Huawei private.";
  }
  ext:task-name "ethernet";

  typedef ncs_template_bpdu-role-type {
    type string;
    description
      "Role type.";
  }

  typedef ncs_template_protocol-type {
    type string;
    description
      "Protocol Type.";
  }

  typedef ncs_template_action-mode {
    type string;
    description
      "Action mode.";
  }

  typedef ncs_template_encapsulation-type {
    type string;
    description
      "Encapsulation type.";
  }

  typedef ncs_rpc_notif_bpdu-role-type {
    type enumeration {
      enum "customer" {
        value 0;
        description
          "The bridge role is a customer.";
      }
      enum "provider" {
        value 1;
        description
          "The bridge role is a provider.";
      }
    }
    description
      "Role type.";
  }

  typedef ncs_rpc_notif_protocol-type {
    type enumeration {
      enum "EOAM3AH" {
        value 1;
        description
          "Ethernet in the First mile OAM.";
      }
      enum "LLDP" {
        value 2;
        description
          "Link Layer discovery protocol.";
      }
      enum "GMRP" {
        value 3;
        description
          "GARP multicast registration protocol.";
      }
      enum "GVRP" {
        value 4;
        description
          "GARP VLAN registration protocol.";
      }
      enum "DLDP" {
        value 5;
        description
          "Device link detection protocol.";
      }
      enum "HGMP" {
        value 6;
        description
          "HUAWEI group management protocol.";
      }
      enum "VTP" {
        value 7;
        description
          "VLAN trunking protocol.";
      }
      enum "DTP" {
        value 8;
        description
          "Dynamic trunking protocol.";
      }
      enum "CDP" {
        value 9;
        description
          "Cisco discovery protocol.";
      }
      enum "UDLD" {
        value 10;
        description
          "Unidirectional link detection.";
      }
      enum "PAGP" {
        value 11;
        description
          "Port aggregation protocol.";
      }
      enum "PVST-PLUS" {
        value 12;
        description
          "Per VLAN spanning tree plus.";
      }
      enum "STP" {
        value 13;
        description
          "Spanning tree protocol.";
      }
      enum "LACP" {
        value 14;
        description
          "Link aggregation control protocol.";
      }
      enum "MVRP" {
        value 15;
        description
          "Multiple VLAN registration protocol.";
      }
      enum "MMRP" {
        value 16;
        description
          "Multiple MAC registration protocol.";
      }
      enum "E-LMI" {
        value 17;
        description
          "Ethernet local management interface.";
      }
      enum "802.1X" {
        value 18;
        description
          "802.1X protocol.";
      }
      enum "SSTP" {
        value 19;
        description
          "Secure socket tunneling protocol.";
      }
    }
    description
      "Protocol Type.";
  }

  typedef ncs_rpc_notif_action-mode {
    type enumeration {
      enum "enable" {
        value 0;
        description
          "Enable mode.";
      }
      enum "drop" {
        value 1;
        description
          "Drop mode.";
      }
      enum "reverse" {
        value 2;
        description
          "Reverse mode.";
      }
      enum "reverse-drop" {
        value 3;
        description
          "Reverse drop mode.";
      }
    }
    description
      "Action mode.";
  }

  typedef ncs_rpc_notif_encapsulation-type {
    type enumeration {
      enum "ETHERNETII" {
        value 1;
        description
          "EthernetII type.";
      }
      enum "LLC" {
        value 2;
        description
          "Logical link control type.";
      }
      enum "SNAP" {
        value 3;
        description
          "Sub-network access protocol.";
      }
    }
    description
      "Encapsulation type.";
  }

  typedef live_ncs_bpdu-role-type {
    type enumeration {
      enum "customer" {
        value 0;
        description
          "The bridge role is a customer.";
      }
      enum "provider" {
        value 1;
        description
          "The bridge role is a provider.";
      }
    }
    description
      "Role type.";
  }

  typedef live_ncs_protocol-type {
    type enumeration {
      enum "EOAM3AH" {
        value 1;
        description
          "Ethernet in the First mile OAM.";
      }
      enum "LLDP" {
        value 2;
        description
          "Link Layer discovery protocol.";
      }
      enum "GMRP" {
        value 3;
        description
          "GARP multicast registration protocol.";
      }
      enum "GVRP" {
        value 4;
        description
          "GARP VLAN registration protocol.";
      }
      enum "DLDP" {
        value 5;
        description
          "Device link detection protocol.";
      }
      enum "HGMP" {
        value 6;
        description
          "HUAWEI group management protocol.";
      }
      enum "VTP" {
        value 7;
        description
          "VLAN trunking protocol.";
      }
      enum "DTP" {
        value 8;
        description
          "Dynamic trunking protocol.";
      }
      enum "CDP" {
        value 9;
        description
          "Cisco discovery protocol.";
      }
      enum "UDLD" {
        value 10;
        description
          "Unidirectional link detection.";
      }
      enum "PAGP" {
        value 11;
        description
          "Port aggregation protocol.";
      }
      enum "PVST-PLUS" {
        value 12;
        description
          "Per VLAN spanning tree plus.";
      }
      enum "STP" {
        value 13;
        description
          "Spanning tree protocol.";
      }
      enum "LACP" {
        value 14;
        description
          "Link aggregation control protocol.";
      }
      enum "MVRP" {
        value 15;
        description
          "Multiple VLAN registration protocol.";
      }
      enum "MMRP" {
        value 16;
        description
          "Multiple MAC registration protocol.";
      }
      enum "E-LMI" {
        value 17;
        description
          "Ethernet local management interface.";
      }
      enum "802.1X" {
        value 18;
        description
          "802.1X protocol.";
      }
      enum "SSTP" {
        value 19;
        description
          "Secure socket tunneling protocol.";
      }
    }
    description
      "Protocol Type.";
  }

  typedef live_ncs_action-mode {
    type enumeration {
      enum "enable" {
        value 0;
        description
          "Enable mode.";
      }
      enum "drop" {
        value 1;
        description
          "Drop mode.";
      }
      enum "reverse" {
        value 2;
        description
          "Reverse mode.";
      }
      enum "reverse-drop" {
        value 3;
        description
          "Reverse drop mode.";
      }
    }
    description
      "Action mode.";
  }

  typedef live_ncs_encapsulation-type {
    type enumeration {
      enum "ETHERNETII" {
        value 1;
        description
          "EthernetII type.";
      }
      enum "LLC" {
        value 2;
        description
          "Logical link control type.";
      }
      enum "SNAP" {
        value 3;
        description
          "Sub-network access protocol.";
      }
    }
    description
      "Encapsulation type.";
  }

  typedef bpdu-role-type {
    type enumeration {
      enum "customer" {
        value 0;
        description
          "The bridge role is a customer.";
      }
      enum "provider" {
        value 1;
        description
          "The bridge role is a provider.";
      }
    }
    description
      "Role type.";
  }

  typedef protocol-type {
    type enumeration {
      enum "EOAM3AH" {
        value 1;
        description
          "Ethernet in the First mile OAM.";
      }
      enum "LLDP" {
        value 2;
        description
          "Link Layer discovery protocol.";
      }
      enum "GMRP" {
        value 3;
        description
          "GARP multicast registration protocol.";
      }
      enum "GVRP" {
        value 4;
        description
          "GARP VLAN registration protocol.";
      }
      enum "DLDP" {
        value 5;
        description
          "Device link detection protocol.";
      }
      enum "HGMP" {
        value 6;
        description
          "HUAWEI group management protocol.";
      }
      enum "VTP" {
        value 7;
        description
          "VLAN trunking protocol.";
      }
      enum "DTP" {
        value 8;
        description
          "Dynamic trunking protocol.";
      }
      enum "CDP" {
        value 9;
        description
          "Cisco discovery protocol.";
      }
      enum "UDLD" {
        value 10;
        description
          "Unidirectional link detection.";
      }
      enum "PAGP" {
        value 11;
        description
          "Port aggregation protocol.";
      }
      enum "PVST-PLUS" {
        value 12;
        description
          "Per VLAN spanning tree plus.";
      }
      enum "STP" {
        value 13;
        description
          "Spanning tree protocol.";
      }
      enum "LACP" {
        value 14;
        description
          "Link aggregation control protocol.";
      }
      enum "MVRP" {
        value 15;
        description
          "Multiple VLAN registration protocol.";
      }
      enum "MMRP" {
        value 16;
        description
          "Multiple MAC registration protocol.";
      }
      enum "E-LMI" {
        value 17;
        description
          "Ethernet local management interface.";
      }
      enum "802.1X" {
        value 18;
        description
          "802.1X protocol.";
      }
      enum "SSTP" {
        value 19;
        description
          "Secure socket tunneling protocol.";
      }
    }
    description
      "Protocol Type.";
  }

  typedef action-mode {
    type enumeration {
      enum "enable" {
        value 0;
        description
          "Enable mode.";
      }
      enum "drop" {
        value 1;
        description
          "Drop mode.";
      }
      enum "reverse" {
        value 2;
        description
          "Reverse mode.";
      }
      enum "reverse-drop" {
        value 3;
        description
          "Reverse drop mode.";
      }
    }
    description
      "Action mode.";
  }

  typedef encapsulation-type {
    type enumeration {
      enum "ETHERNETII" {
        value 1;
        description
          "EthernetII type.";
      }
      enum "LLC" {
        value 2;
        description
          "Logical link control type.";
      }
      enum "SNAP" {
        value 3;
        description
          "Sub-network access protocol.";
      }
    }
    description
      "Encapsulation type.";
  }

  augment "/ncs:devices/ncs:device/ncs:config" {
    container l2pt {
      tailf:ncs-device-type "netconf";
      tailf:display-when "not(../../ncs:module) or ../../ncs:module[ncs:name='huawei-l2pt']";
      description
        "L2 protocol tunnel.";
      container bpdu-attribute {
        description
          "Configure BPDU tunnel global attribute.";
        leaf bridge-role {
          type bpdu-role-type;
          default "customer";
          description
            "Bridge role that can be a customer or provider.";
        }
        leaf group-mac {
          type pub-type:mac-address {
            pattern '[0-9a-f][1|3|5|7|9|b|d|f][0-9a-f]{2}(-[0-9a-f]{4}){2}';
          }
          default "0100-0ccd-cdd0";
          description
            "BPDU well-known destination MAC address, Multicast MAC address, excluding 0180-c200-0000 to 0180-c200-002f and ffff-ffff-ffff.";
        }
      }
      // NCS drop config false container 'well-known-protocol'
    }
  }
  augment "/ncs:devices/ncs:device/ncs:live-status" {
    container l2pt {
      tailf:ncs-device-type "netconf";
      tailf:display-when "not(../../ncs:module) or ../../ncs:module[ncs:name='huawei-l2pt'] or (../../ncs:live-status-protocol[not(ncs:capability)]) or (../../ncs:live-status-protocol/ncs:capability/ncs:module[.='huawei-l2pt'])";
      description
        "L2 protocol tunnel.";
      container bpdu-attribute {
        description
          "Configure BPDU tunnel global attribute.";
        leaf bridge-role {
          type live_ncs_bpdu-role-type;
          // NCS drop default statement
          description
            "Bridge role that can be a customer or provider.";
        }
        leaf group-mac {
          type pub-type:live_ncs_mac-address;
          // NCS drop default statement
          description
            "BPDU well-known destination MAC address, Multicast MAC address, excluding 0180-c200-0000 to 0180-c200-002f and ffff-ffff-ffff.";
        }
      }
      container well-known-protocol {
        description
          "Statistics of L2PT well-known protocol attributes.";
        container protocols {
          description
            "List of protocol informations.";
          list protocol {
            key "protocol-type";
            description
              "Statistics of protocol information.";
            leaf protocol-type {
              type live_ncs_protocol-type;
              description
                "Well-known protocol name.";
            }
            leaf group-mac {
              type pub-type:live_ncs_mac-address;
              description
                "User-definded protocol group MAC address.";
            }
            leaf protocol-mac {
              type pub-type:live_ncs_mac-address;
              description
                "MAC address of protocol.";
            }
            leaf encapsulation-type {
              type live_ncs_encapsulation-type;
              description
                "Ethernet encapsulation type of layer 2 packets.";
            }
            leaf ethernet-type {
              type pub-type:live_ncs_hex-binary;
              description
                "Protocol type of EthernetII.";
            }
            leaf snap-type {
              type pub-type:live_ncs_hex-binary;
              description
                "The type of sub-network access protocol.";
            }
            leaf dsap-value {
              type pub-type:live_ncs_hex-binary;
              description
                "The value of destination service access point value.";
            }
            leaf ssap-value {
              type pub-type:live_ncs_hex-binary;
              description
                "The value of source service access point.";
            }
          }
        }
      }
    }
  }
  augment "/ncs:devices/ncs:template/ncs:ned-id/ncs:config" {
    container l2pt {
      description
        "L2 protocol tunnel.";
      container bpdu-attribute {
        description
          "Configure BPDU tunnel global attribute.";
        leaf bridge-role {
          type ncs_template_bpdu-role-type;
          // NCS drop default statement
          description
            "Bridge role that can be a customer or provider.";
        }
        leaf group-mac {
          type pub-type:ncs_template_mac-address;
          // NCS drop default statement
          description
            "BPDU well-known destination MAC address, Multicast MAC address, excluding 0180-c200-0000 to 0180-c200-002f and ffff-ffff-ffff.";
        }
      }
      // NCS drop config false container 'well-known-protocol'
    }
  }
  augment "/ncs:devices/ncs:template/ncs:ned-id/ncs:config/ifm:ifm/ifm:interfaces/ifm:interface/ethernet:ethernet/ethernet:main-interface/ethernet:l2-attribute" {
    description
      "BPDU tunnel interface attribute.";
    container bpdu-tunnel {
      description
        "Configure BPDU tunnel attribute.";
      choice bpdu-enable {
        description
          "Bpdu enable type.";
        case enable {
          description
            "Enable the BPDU tunnel function.";
          leaf enable {
            type empty;
            description
              "Enable the BPDU tunnel function.";
          }
        }
      }
    }
  }
  augment "/ncs:devices/ncs:device/ncs:live-status/ifm:ifm/ifm:interfaces/ifm:interface/ethernet:ethernet/ethernet:main-interface/ethernet:l2-attribute" {
    description
      "BPDU tunnel interface attribute.";
    container bpdu-tunnel {
      tailf:ncs-device-type "netconf";
      tailf:display-when "not(../../../../../../../../ncs:module) or ../../../../../../../../ncs:module[ncs:name='huawei-l2pt'] or (../../../../../../../../ncs:live-status-protocol[not(ncs:capability)]) or (../../../../../../../../ncs:live-status-protocol/ncs:capability/ncs:module[.='huawei-l2pt'])";
      description
        "Configure BPDU tunnel attribute.";
      choice bpdu-enable {
        description
          "Bpdu enable type.";
        case enable {
          description
            "Enable the BPDU tunnel function.";
          leaf enable {
            type empty;
            description
              "Enable the BPDU tunnel function.";
          }
        }
      }
    }
  }
  augment "/ncs:devices/ncs:device/ncs:config/ifm:ifm/ifm:interfaces/ifm:interface/ethernet:ethernet/ethernet:main-interface/ethernet:l2-attribute" {
    description
      "BPDU tunnel interface attribute.";
    container bpdu-tunnel {
      tailf:ncs-device-type "netconf";
      tailf:display-when "not(../../../../../../../../ncs:module) or ../../../../../../../../ncs:module[ncs:name='huawei-l2pt']";
      description
        "Configure BPDU tunnel attribute.";
      choice bpdu-enable {
        description
          "Bpdu enable type.";
        case enable {
          description
            "Enable the BPDU tunnel function.";
          leaf enable {
            type empty;
            description
              "Enable the BPDU tunnel function.";
          }
        }
      }
    }
  }
  augment "/ncs:devices/ncs:template/ncs:ned-id/ncs:config/ifm:ifm/ifm:interfaces/ifm:interface/ethernet:ethernet" {
    description
      "BPDU tunnel interface attribute.";
    container l2pt {
      description
        "Configure BPDU tunnel attribute.";
      container well-known-protocols {
        description
          "List of well-known protocol configurations.";
        list well-known-protocol {
          // NCS patched for predictable order
          ordered-by user;
          key "protocol-type";
          description
            "Configure well-known protocol.";
          leaf protocol-type {
            type ncs_template_protocol-type;
            description
              "Well-known protocol type.";
          }
          leaf action {
            type ncs_template_action-mode;
            // NCS drop mandatory statement
            description
              "Action mode.";
          }
          leaf drop-threshold {
            // NCS drop when statement
            type string;
            description
              "Drop threshold. Maximum packets can be passed in a second.";
          }
        }
      }
    }
  }
  augment "/ncs:devices/ncs:device/ncs:live-status/ifm:ifm/ifm:interfaces/ifm:interface/ethernet:ethernet" {
    description
      "BPDU tunnel interface attribute.";
    container l2pt {
      tailf:ncs-device-type "netconf";
      tailf:display-when "not(../../../../../../ncs:module) or ../../../../../../ncs:module[ncs:name='huawei-l2pt'] or (../../../../../../ncs:live-status-protocol[not(ncs:capability)]) or (../../../../../../ncs:live-status-protocol/ncs:capability/ncs:module[.='huawei-l2pt'])";
      description
        "Configure BPDU tunnel attribute.";
      container well-known-protocols {
        description
          "List of well-known protocol configurations.";
        list well-known-protocol {
          key "protocol-type";
          description
            "Configure well-known protocol.";
          leaf protocol-type {
            type live_ncs_protocol-type;
            description
              "Well-known protocol type.";
          }
          leaf action {
            type live_ncs_action-mode;
            // NCS drop mandatory statement
            description
              "Action mode.";
          }
          leaf drop-threshold {
            // NCS drop when statement
            type uint32 {
              range "1..4096";
            }
            description
              "Drop threshold. Maximum packets can be passed in a second.";
          }
        }
      }
    }
  }
  augment "/ncs:devices/ncs:device/ncs:config/ifm:ifm/ifm:interfaces/ifm:interface/ethernet:ethernet" {
    description
      "BPDU tunnel interface attribute.";
    container l2pt {
      tailf:ncs-device-type "netconf";
      tailf:display-when "not(../../../../../../ncs:module) or ../../../../../../ncs:module[ncs:name='huawei-l2pt']";
      description
        "Configure BPDU tunnel attribute.";
      container well-known-protocols {
        description
          "List of well-known protocol configurations.";
        list well-known-protocol {
          key "protocol-type";
          description
            "Configure well-known protocol.";
          leaf protocol-type {
            type protocol-type;
            description
              "Well-known protocol type.";
          }
          leaf action {
            type action-mode;
            mandatory true;
            description
              "Action mode.";
          }
          leaf drop-threshold {
            when "../action='enable'" {
              tailf:xpath-root 3;
            }
            type uint32 {
              range "1..4096";
            }
            description
              "Drop threshold. Maximum packets can be passed in a second.";
          }
        }
      }
    }
  }
}
