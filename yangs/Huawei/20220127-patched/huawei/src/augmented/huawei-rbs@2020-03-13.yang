module huawei-rbs {
  // Generated by yanger -t ncs
  tailf:mount-id "huawei-nc-1.0:huawei-nc-1.0";
  tailf:ncs-device-type "netconf";

  namespace "urn:huawei:yang:huawei-rbs";
  prefix rbs;

  import huawei-ifm {
    prefix ifm;
  }
  import huawei-pub-type {
    prefix pub-type;
  }
  import ietf-inet-types {
    prefix inet;
  }
  import ietf-yang-types {
    prefix yang;
  }
  import huawei-extension {
    prefix ext;
  }
  import huawei-etrunk {
    prefix etrunk;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Remote backup service, providing service backup between the master and backup devices, such as ARP entry backup.";

  revision 2020-03-13 {
    description
      "Initial revision.";
    reference "Huawei private.";
  }
  ext:task-name "rbs";

  typedef ncs_template_tcp-state {
    type string;
    description
      "TCP connection status.";
  }

  typedef ncs_template_rbp-state {
    type string;
    description
      "RBP status.";
  }

  typedef ncs_template_backup-mode {
    type string;
    description
      "Backup mode.";
  }

  typedef ncs_template_service-type {
    type string;
    description
      "RBP service type.";
  }

  typedef ncs_template_vrrp-mac-type {
    type string;
    description
      "VRRP association mode.";
  }

  typedef ncs_template_batch-backup-type {
    type string;
    description
      "Service type batch backup.";
  }

  typedef ncs_template_batch-backup-rpc-type {
    type string;
    description
      "Service type batch backup.";
  }

  typedef ncs_rpc_notif_tcp-state {
    type enumeration {
      enum "initial" {
        value 0;
        description
          "Initial state, a TCP connection status.";
      }
      enum "listening" {
        value 1;
        description
          "Listening state, a TCP connection status.";
      }
      enum "connecting" {
        value 2;
        description
          "Connecting state, meaning that the client is connecting to the server.";
      }
      enum "connected" {
        value 3;
        description
          "Connected state, a TCP connection status.";
      }
    }
    description
      "TCP connection status.";
  }

  typedef ncs_rpc_notif_rbp-state {
    type enumeration {
      enum "init" {
        value 0;
        description
          "Initial state, an RBP status.";
      }
      enum "slave" {
        value 1;
        description
          "Slave state, an RBP status.";
      }
      enum "master" {
        value 2;
        description
          "Master state, an RBP status.";
      }
    }
    description
      "RBP status.";
  }

  typedef ncs_rpc_notif_backup-mode {
    type enumeration {
      enum "hot" {
        value 1;
        description
          "Hot peer backup mode.";
      }
      enum "warm" {
        value 2;
        description
          "Warm peer backup mode.";
      }
      enum "virtual" {
        value 3;
        description
          "Virtual peer backup mode.";
      }
    }
    description
      "Backup mode.";
  }

  typedef ncs_rpc_notif_service-type {
    type enumeration {
      enum "all" {
        value 0;
        description
          "All services that can be backed up.";
      }
      enum "bras" {
        value 1;
        description
          "BRAS services that can be backed up.";
      }
      enum "igmp-snooping" {
        value 2;
        description
          "IGMP snooping services that can be backed up.";
      }
      enum "arp" {
        value 5;
        description
          "ARP services that can be backed up.";
      }
      enum "multicast" {
        value 9;
        description
          "MULTICAST services that can be backed up.";
      }
      enum "l2tp" {
        value 10;
        description
          "L2TP services that can be backed up.";
      }
      enum "igmp" {
        value 21;
        description
          "IGMP services that can be backed up.";
      }
      enum "lacp" {
        value 24;
        description
          "LACP services that can be backed up.";
      }
      enum "no-host-multicast" {
        value 25;
        description
          "No host multicast services that can be backed up.";
      }
      enum "dhcp-server" {
        value 26;
        description
          "DHCP-SERVER services that can be backed up.";
      }
      enum "ipsec" {
        value 30;
        description
          "Ipsec service that can backed up.";
      }
      enum "nd" {
        value 32;
        description
          "Nd service that can backed up.";
      }
      enum "dhcpv6-relay" {
        value 34;
        description
          "DHCPv6-relay service that can backed up.";
      }
    }
    description
      "RBP service type.";
  }

  typedef ncs_rpc_notif_vrrp-mac-type {
    type enumeration {
      enum "none" {
        value 0;
        description
          "VRRP association not based on odd/even MAC addresses.";
      }
      enum "even" {
        value 1;
        description
          "VRRP association based on even MAC addresses.";
      }
      enum "odd" {
        value 2;
        description
          "VRRP association based on odd MAC addresses.";
      }
    }
    description
      "VRRP association mode.";
  }

  typedef ncs_rpc_notif_batch-backup-type {
    type enumeration {
      enum "bras" {
        value 1;
        description
          "BRAS services that can be batch backed up.";
      }
      enum "igmp-snooping" {
        value 2;
        description
          "IGMP snooping services that can be batch backed up.";
      }
      enum "multicast" {
        value 9;
        description
          "MULTICAST services that can be batch backed up.";
      }
      enum "l2tp" {
        value 10;
        description
          "L2TP services that can be batch backed up.";
      }
      enum "dhcp-server" {
        value 26;
        description
          "DHCP-SERVER services that can be batch backed up.";
      }
      enum "dhcpv6-relay" {
        value 34;
        description
          "DHCPV6 relay services that can be batch backed up.";
      }
    }
    description
      "Service type batch backup.";
  }

  typedef ncs_rpc_notif_batch-backup-rpc-type {
    type enumeration {
      enum "all" {
        value 0;
        description
          "All services that can be batch backed up now.";
      }
      enum "bras" {
        value 1;
        description
          "BRAS services that can be batch backed up now.";
      }
      enum "igmp-snooping" {
        value 2;
        description
          "IGMP snooping services that can be batch backed up.";
      }
      enum "arp" {
        value 5;
        description
          "ARP services that can be batch backed up.";
      }
      enum "multicast" {
        value 9;
        description
          "MULTICAST services that can be batch backed up.";
      }
      enum "l2tp" {
        value 10;
        description
          "L2TP services that can be batch backed up.";
      }
      enum "dhcp-server" {
        value 26;
        description
          "DHCP-SERVER services that can be batch backed up.";
      }
      enum "ipsec" {
        value 30;
        description
          "IPSEC relay services that can be batch backed up.";
      }
      enum "nd" {
        value 32;
        description
          "ND services that can be batch backed up.";
      }
      enum "dhcpv6-relay" {
        value 34;
        description
          "DHCPV6 relay services that can be batch backed up.";
      }
    }
    description
      "Service type batch backup.";
  }

  typedef live_ncs_tcp-state {
    type enumeration {
      enum "initial" {
        value 0;
        description
          "Initial state, a TCP connection status.";
      }
      enum "listening" {
        value 1;
        description
          "Listening state, a TCP connection status.";
      }
      enum "connecting" {
        value 2;
        description
          "Connecting state, meaning that the client is connecting to the server.";
      }
      enum "connected" {
        value 3;
        description
          "Connected state, a TCP connection status.";
      }
    }
    description
      "TCP connection status.";
  }

  typedef live_ncs_rbp-state {
    type enumeration {
      enum "init" {
        value 0;
        description
          "Initial state, an RBP status.";
      }
      enum "slave" {
        value 1;
        description
          "Slave state, an RBP status.";
      }
      enum "master" {
        value 2;
        description
          "Master state, an RBP status.";
      }
    }
    description
      "RBP status.";
  }

  typedef live_ncs_backup-mode {
    type enumeration {
      enum "hot" {
        value 1;
        description
          "Hot peer backup mode.";
      }
      enum "warm" {
        value 2;
        description
          "Warm peer backup mode.";
      }
      enum "virtual" {
        value 3;
        description
          "Virtual peer backup mode.";
      }
    }
    description
      "Backup mode.";
  }

  typedef live_ncs_service-type {
    type enumeration {
      enum "all" {
        value 0;
        description
          "All services that can be backed up.";
      }
      enum "bras" {
        value 1;
        description
          "BRAS services that can be backed up.";
      }
      enum "igmp-snooping" {
        value 2;
        description
          "IGMP snooping services that can be backed up.";
      }
      enum "arp" {
        value 5;
        description
          "ARP services that can be backed up.";
      }
      enum "multicast" {
        value 9;
        description
          "MULTICAST services that can be backed up.";
      }
      enum "l2tp" {
        value 10;
        description
          "L2TP services that can be backed up.";
      }
      enum "igmp" {
        value 21;
        description
          "IGMP services that can be backed up.";
      }
      enum "lacp" {
        value 24;
        description
          "LACP services that can be backed up.";
      }
      enum "no-host-multicast" {
        value 25;
        description
          "No host multicast services that can be backed up.";
      }
      enum "dhcp-server" {
        value 26;
        description
          "DHCP-SERVER services that can be backed up.";
      }
      enum "ipsec" {
        value 30;
        description
          "Ipsec service that can backed up.";
      }
      enum "nd" {
        value 32;
        description
          "Nd service that can backed up.";
      }
      enum "dhcpv6-relay" {
        value 34;
        description
          "DHCPv6-relay service that can backed up.";
      }
    }
    description
      "RBP service type.";
  }

  typedef live_ncs_vrrp-mac-type {
    type enumeration {
      enum "none" {
        value 0;
        description
          "VRRP association not based on odd/even MAC addresses.";
      }
      enum "even" {
        value 1;
        description
          "VRRP association based on even MAC addresses.";
      }
      enum "odd" {
        value 2;
        description
          "VRRP association based on odd MAC addresses.";
      }
    }
    description
      "VRRP association mode.";
  }

  typedef live_ncs_batch-backup-type {
    type enumeration {
      enum "bras" {
        value 1;
        description
          "BRAS services that can be batch backed up.";
      }
      enum "igmp-snooping" {
        value 2;
        description
          "IGMP snooping services that can be batch backed up.";
      }
      enum "multicast" {
        value 9;
        description
          "MULTICAST services that can be batch backed up.";
      }
      enum "l2tp" {
        value 10;
        description
          "L2TP services that can be batch backed up.";
      }
      enum "dhcp-server" {
        value 26;
        description
          "DHCP-SERVER services that can be batch backed up.";
      }
      enum "dhcpv6-relay" {
        value 34;
        description
          "DHCPV6 relay services that can be batch backed up.";
      }
    }
    description
      "Service type batch backup.";
  }

  typedef live_ncs_batch-backup-rpc-type {
    type enumeration {
      enum "all" {
        value 0;
        description
          "All services that can be batch backed up now.";
      }
      enum "bras" {
        value 1;
        description
          "BRAS services that can be batch backed up now.";
      }
      enum "igmp-snooping" {
        value 2;
        description
          "IGMP snooping services that can be batch backed up.";
      }
      enum "arp" {
        value 5;
        description
          "ARP services that can be batch backed up.";
      }
      enum "multicast" {
        value 9;
        description
          "MULTICAST services that can be batch backed up.";
      }
      enum "l2tp" {
        value 10;
        description
          "L2TP services that can be batch backed up.";
      }
      enum "dhcp-server" {
        value 26;
        description
          "DHCP-SERVER services that can be batch backed up.";
      }
      enum "ipsec" {
        value 30;
        description
          "IPSEC relay services that can be batch backed up.";
      }
      enum "nd" {
        value 32;
        description
          "ND services that can be batch backed up.";
      }
      enum "dhcpv6-relay" {
        value 34;
        description
          "DHCPV6 relay services that can be batch backed up.";
      }
    }
    description
      "Service type batch backup.";
  }

  typedef tcp-state {
    type enumeration {
      enum "initial" {
        value 0;
        description
          "Initial state, a TCP connection status.";
      }
      enum "listening" {
        value 1;
        description
          "Listening state, a TCP connection status.";
      }
      enum "connecting" {
        value 2;
        description
          "Connecting state, meaning that the client is connecting to the server.";
      }
      enum "connected" {
        value 3;
        description
          "Connected state, a TCP connection status.";
      }
    }
    description
      "TCP connection status.";
  }

  typedef rbp-state {
    type enumeration {
      enum "init" {
        value 0;
        description
          "Initial state, an RBP status.";
      }
      enum "slave" {
        value 1;
        description
          "Slave state, an RBP status.";
      }
      enum "master" {
        value 2;
        description
          "Master state, an RBP status.";
      }
    }
    description
      "RBP status.";
  }

  typedef backup-mode {
    type enumeration {
      enum "hot" {
        value 1;
        description
          "Hot peer backup mode.";
      }
      enum "warm" {
        value 2;
        description
          "Warm peer backup mode.";
      }
      enum "virtual" {
        value 3;
        description
          "Virtual peer backup mode.";
      }
    }
    description
      "Backup mode.";
  }

  typedef service-type {
    type enumeration {
      enum "all" {
        value 0;
        description
          "All services that can be backed up.";
      }
      enum "bras" {
        value 1;
        description
          "BRAS services that can be backed up.";
      }
      enum "igmp-snooping" {
        value 2;
        description
          "IGMP snooping services that can be backed up.";
      }
      enum "arp" {
        value 5;
        description
          "ARP services that can be backed up.";
      }
      enum "multicast" {
        value 9;
        description
          "MULTICAST services that can be backed up.";
      }
      enum "l2tp" {
        value 10;
        description
          "L2TP services that can be backed up.";
      }
      enum "igmp" {
        value 21;
        description
          "IGMP services that can be backed up.";
      }
      enum "lacp" {
        value 24;
        description
          "LACP services that can be backed up.";
      }
      enum "no-host-multicast" {
        value 25;
        description
          "No host multicast services that can be backed up.";
      }
      enum "dhcp-server" {
        value 26;
        description
          "DHCP-SERVER services that can be backed up.";
      }
      enum "ipsec" {
        value 30;
        description
          "Ipsec service that can backed up.";
      }
      enum "nd" {
        value 32;
        description
          "Nd service that can backed up.";
      }
      enum "dhcpv6-relay" {
        value 34;
        description
          "DHCPv6-relay service that can backed up.";
      }
    }
    description
      "RBP service type.";
  }

  typedef vrrp-mac-type {
    type enumeration {
      enum "none" {
        value 0;
        description
          "VRRP association not based on odd/even MAC addresses.";
      }
      enum "even" {
        value 1;
        description
          "VRRP association based on even MAC addresses.";
      }
      enum "odd" {
        value 2;
        description
          "VRRP association based on odd MAC addresses.";
      }
    }
    description
      "VRRP association mode.";
  }

  typedef batch-backup-type {
    type enumeration {
      enum "bras" {
        value 1;
        description
          "BRAS services that can be batch backed up.";
      }
      enum "igmp-snooping" {
        value 2;
        description
          "IGMP snooping services that can be batch backed up.";
      }
      enum "multicast" {
        value 9;
        description
          "MULTICAST services that can be batch backed up.";
      }
      enum "l2tp" {
        value 10;
        description
          "L2TP services that can be batch backed up.";
      }
      enum "dhcp-server" {
        value 26;
        description
          "DHCP-SERVER services that can be batch backed up.";
      }
      enum "dhcpv6-relay" {
        value 34;
        description
          "DHCPV6 relay services that can be batch backed up.";
      }
    }
    description
      "Service type batch backup.";
  }

  typedef batch-backup-rpc-type {
    type enumeration {
      enum "all" {
        value 0;
        description
          "All services that can be batch backed up now.";
      }
      enum "bras" {
        value 1;
        description
          "BRAS services that can be batch backed up now.";
      }
      enum "igmp-snooping" {
        value 2;
        description
          "IGMP snooping services that can be batch backed up.";
      }
      enum "arp" {
        value 5;
        description
          "ARP services that can be batch backed up.";
      }
      enum "multicast" {
        value 9;
        description
          "MULTICAST services that can be batch backed up.";
      }
      enum "l2tp" {
        value 10;
        description
          "L2TP services that can be batch backed up.";
      }
      enum "dhcp-server" {
        value 26;
        description
          "DHCP-SERVER services that can be batch backed up.";
      }
      enum "ipsec" {
        value 30;
        description
          "IPSEC relay services that can be batch backed up.";
      }
      enum "nd" {
        value 32;
        description
          "ND services that can be batch backed up.";
      }
      enum "dhcpv6-relay" {
        value 34;
        description
          "DHCPV6 relay services that can be batch backed up.";
      }
    }
    description
      "Service type batch backup.";
  }

  augment "/ncs:devices/ncs:device/ncs:rpc" {
    container rpc-batch-backup-now {
      tailf:ncs-device-type "netconf";
      tailf:display-when "not(../../ncs:module) or ../../ncs:module[ncs:name='huawei-rbs']";
      tailf:action batch-backup-now {
        tailf:actionpoint ncsproxy {
          tailf:internal;
        }
        description
          "The batch-backup service-type now command immediately backs up user services on an RBS.";
        ext:node-ref "/rbs:rbs/rbs:services/rbs:service/rbs:batch-backups";
        input {
          leaf rbs-name {
            type string;
            mandatory true;
            description
              "RBS instance name.";
          }
          leaf service-type {
            type ncs_rpc_notif_batch-backup-rpc-type;
            mandatory true;
            description
              "Type of services that are synchronized now.";
          }
        }
      }
    }
  }
  augment "/ncs:devices/ncs:device-group/ncs:ned-id/ncs:rpc" {
    container rpc-batch-backup-now {
      tailf:ncs-device-type "netconf";
      tailf:display-when "/ncs:devices/ncs:device[ncs:name=current()/../../../ncs:member]/ncs:module[ncs:name='huawei-rbs']";
      tailf:action batch-backup-now {
        tailf:actionpoint ncsproxy {
          tailf:internal;
        }
        description
          "The batch-backup service-type now command immediately backs up user services on an RBS.";
        ext:node-ref "/rbs:rbs/rbs:services/rbs:service/rbs:batch-backups";
        input {
          leaf rbs-name {
            type string;
            mandatory true;
            description
              "RBS instance name.";
          }
          leaf service-type {
            type ncs_rpc_notif_batch-backup-rpc-type;
            mandatory true;
            description
              "Type of services that are synchronized now.";
          }
        }
      }
    }
  }
  augment "/ncs:devices/ncs:device/ncs:config" {
    container rbs {
      tailf:ncs-device-type "netconf";
      tailf:display-when "not(../../ncs:module) or ../../ncs:module[ncs:name='huawei-rbs']";
      description
        "Remote backup service, providing service backup between the master and backup devices, such as ARP entry backup.";
      container services {
        description
          "List of RBS, including information about all remote backup services on a device.";
        list service {
          key "name";
          description
            "Configure RBS instance list, which can be configured or queried.";
          leaf name {
            type string {
              length "1..32";
              pattern '[0-9a-z_.\-]+';
            }
            description
              "RBS instance name.";
          }
          leaf peer-ip {
            type inet:ip-address-no-zone;
            must '(../peer-ip and ../source-ip and ../tcp-port and ../peer-ip!=../source-ip) or (not (../peer-ip) and not (../source-ip) and not (../tcp-port))' {
              tailf:xpath-root 3;
            }
            description
              "Peer IP/IPv6 address of a TCP connection.";
          }
          leaf source-ip {
            type inet:ip-address-no-zone;
            must '(../peer-ip and ../source-ip and ../tcp-port and ../peer-ip!=../source-ip) or (not (../peer-ip) and not (../source-ip) and not (../tcp-port))' {
              tailf:xpath-root 3;
            }
            description
              "Local IP/IPv6 address of a TCP connection.";
          }
          leaf tcp-port {
            type uint32 {
              range "1024..55535";
            }
            must '(../peer-ip and ../source-ip and ../tcp-port and ../peer-ip!=../source-ip) or (not (../peer-ip) and not (../source-ip) and not (../tcp-port))' {
              tailf:xpath-root 3;
            }
            description
              "Port number of a TCP connection.";
          }
          leaf shut-down {
            type boolean;
            default "false";
            description
              "Enable/disable an RBS connection.";
          }
          // NCS drop config false leaf index
          // NCS drop config false leaf 'tcp-state'
          // NCS drop config false leaf 'last-up-time'
          // NCS drop config false leaf 'last-down-time'
          // NCS drop config false leaf 'last-down-reason'
          container batch-backups {
            description
              "List of periodic service synchronization configurations.";
            list batch-backup {
              key "service-type";
              description
                "Configure periodic service synchronization configuration instance.";
              leaf service-type {
                type batch-backup-type;
                description
                  "Type of services that are periodically synchronized.";
              }
              leaf backup-time {
                type pub-type:time;
                mandatory true;
                description
                  "Backup start time.";
              }
            }
          }
        }
      }
      container profiles {
        description
          "List of remote backup profiles.";
        list profile {
          key "name";
          description
            "Configure RBP instance.";
          leaf name {
            type string {
              length "1..128";
              pattern '[0-9a-z_.\-]+';
            }
            description
              "RBP instance name.";
          }
          leaf service-name {
            type leafref {
              path "../../../services/service/name";
            }
            must '(../service-name and ../backup-id) or (not(../service-name) and not(../backup-id))' {
              tailf:xpath-root 3;
            }
            description
              "Name of the RBS bound to an RBP.";
            ext:support-filter "true";
          }
          leaf backup-id {
            type uint32 {
              range "1..4095";
            }
            must '(../service-name and ../backup-id) or (not(../service-name) and not(../backup-id))' {
              tailf:xpath-root 3;
            }
            description
              "RBS ID.";
          }
          leaf mode {
            type backup-mode;
            default "hot";
            description
              "Backup mode of an RBP.";
          }
          // NCS drop config false leaf index
          // NCS drop config false leaf 'local-state'
          // NCS drop config false leaf 'peer-state'
          choice track-type {
            description
              "Arbitrate protocol configuration.";
            case e-trunk {
              description
                "Etrunk type that rbs profile tracking.";
              leaf etrunk-id {
                type leafref {
                  path "/ncs:devices/ncs:device/ncs:config/etrunk:etrunk/etrunk:instances/etrunk:instance/etrunk:id" {
                    tailf:xpath-root 3;
                  }
                }
                mandatory true;
                description
                  "Etrunk ID.";
              }
              leaf ethtrunk-name {
                type leafref {
                  path "/ncs:devices/ncs:device/ncs:config/etrunk:etrunk/etrunk:instances/etrunk:instance[etrunk:id=current()/../etrunk-id]/etrunk:interfaces/etrunk:interface/etrunk:if-name" {
                    tailf:xpath-root 3;
                  }
                }
                mandatory true;
                description
                  "Eth-trunk name.";
              }
            }
            case vrrp {
              description
                "Specify VRRP as arbitrate protocol.";
              container vrrps {
                description
                  "List of associated VRRP backup groups.";
                list vrrp {
                  key "id";
                  unique "mac-type";
                  max-elements 2;
                  description
                    "Configure associated VRRP backup group instance.";
                  leaf id {
                    type uint8 {
                      range "1..255";
                    }
                    must "(count(../../vrrp)=2 and not(../rbs:mac-type='none')) or count(../../vrrp)<=1" {
                      tailf:xpath-root 3;
                    }
                    description
                      "ID of the associated VRRP backup group.";
                  }
                  leaf if-name {
                    type leafref {
                      path "/ncs:devices/ncs:device/ncs:config/ifm:ifm/ifm:interfaces/ifm:interface/ifm:name" {
                        tailf:xpath-root 3;
                      }
                    }
                    mandatory true;
                    description
                      "Name of the interface where the associated VRRP backup group resides.";
                  }
                  leaf mac-type {
                    ext:operation-exclude "update" {
                      description
                        "The mac type cannot be updated.";
                    }
                    type vrrp-mac-type;
                    default "none";
                    description
                      "VRRP association mode.";
                  }
                  // NCS drop config false leaf 'local-state'
                  // NCS drop config false leaf 'peer-state'
                }
              }
            }
          }
          container service-types {
            description
              "List of RBS types.";
            list service-type {
              key "type";
              description
                "Configure remote backup service.";
              leaf type {
                type service-type;
                description
                  "RBS type.";
              }
            }
          }
        }
      }
      container rbs4-session-car {
        must 'pir >= cir and pbs >= cbs' {
          tailf:xpath-root 3;
        }
        description
          "Configure session CAR.";
        leaf enable {
          type boolean;
          default "true";
          description
            "Enable/disable session CAR.";
        }
        leaf cir {
          type uint32 {
            range "0..1000000";
          }
          units "kbit/s";
          default "12";
          description
            "Specify the session CAR CIR value.";
        }
        leaf cbs {
          type uint32 {
            range "0..9000000";
          }
          units "Byte";
          default "1500";
          description
            "Specify the session CAR CBS value.";
        }
        leaf pir {
          type uint32 {
            range "0..1000000";
          }
          units "kbit/s";
          default "6000";
          description
            "Specify the session CAR PIR value.";
        }
        leaf pbs {
          type uint32 {
            range "0..9000000";
          }
          units "Byte";
          default "750000";
          description
            "Specify the session CAR PBS value.";
        }
      }
      container rbs6-session-car {
        must 'pir >= cir and pbs >= cbs' {
          tailf:xpath-root 3;
        }
        description
          "Configure session CAR.";
        leaf enable {
          type boolean;
          default "true";
          description
            "Enable/disable session CAR.";
        }
        leaf cir {
          type uint32 {
            range "0..1000000";
          }
          units "kbit/s";
          default "12";
          description
            "Specify the session CAR CIR value.";
        }
        leaf cbs {
          type uint32 {
            range "0..9000000";
          }
          units "Byte";
          default "1500";
          description
            "Specify the session CAR CBS value.";
        }
        leaf pir {
          type uint32 {
            range "0..1000000";
          }
          units "kbit/s";
          default "6000";
          description
            "Specify the session CAR PIR value.";
        }
        leaf pbs {
          type uint32 {
            range "0..9000000";
          }
          units "Byte";
          default "750000";
          description
            "Specify the session CAR PBS value.";
        }
      }
    }
  }
  augment "/ncs:devices/ncs:device/ncs:live-status" {
    container rbs {
      tailf:ncs-device-type "netconf";
      tailf:display-when "not(../../ncs:module) or ../../ncs:module[ncs:name='huawei-rbs'] or (../../ncs:live-status-protocol[not(ncs:capability)]) or (../../ncs:live-status-protocol/ncs:capability/ncs:module[.='huawei-rbs'])";
      description
        "Remote backup service, providing service backup between the master and backup devices, such as ARP entry backup.";
      container services {
        description
          "List of RBS, including information about all remote backup services on a device.";
        list service {
          key "name";
          description
            "Configure RBS instance list, which can be configured or queried.";
          leaf name {
            type string {
              length "1..32";
              pattern '[0-9a-z_.\-]+';
            }
            description
              "RBS instance name.";
          }
          leaf peer-ip {
            type inet:ip-address-no-zone;
            // NCS drop must statement
            description
              "Peer IP/IPv6 address of a TCP connection.";
          }
          leaf source-ip {
            type inet:ip-address-no-zone;
            // NCS drop must statement
            description
              "Local IP/IPv6 address of a TCP connection.";
          }
          leaf tcp-port {
            type uint32 {
              range "1024..55535";
            }
            // NCS drop must statement
            description
              "Port number of a TCP connection.";
          }
          leaf shut-down {
            type boolean;
            // NCS drop default statement
            description
              "Enable/disable an RBS connection.";
          }
          leaf index {
            type uint32;
            description
              "RBS instance index, which is automatically allocated by the system. It can be queried but cannot be configured.";
          }
          leaf tcp-state {
            type live_ncs_tcp-state;
            description
              "TCP connection status.";
          }
          leaf last-up-time {
            type yang:date-and-time;
            description
              "Last up time.";
          }
          leaf last-down-time {
            type yang:date-and-time;
            description
              "Last down time.";
          }
          leaf last-down-reason {
            type string {
              length "1..64";
            }
            description
              "Last down reason.";
          }
          container batch-backups {
            description
              "List of periodic service synchronization configurations.";
            list batch-backup {
              key "service-type";
              description
                "Configure periodic service synchronization configuration instance.";
              leaf service-type {
                type live_ncs_batch-backup-type;
                description
                  "Type of services that are periodically synchronized.";
              }
              leaf backup-time {
                type pub-type:live_ncs_time;
                // NCS drop mandatory statement
                description
                  "Backup start time.";
              }
            }
          }
        }
      }
      container profiles {
        description
          "List of remote backup profiles.";
        list profile {
          key "name";
          description
            "Configure RBP instance.";
          leaf name {
            type string {
              length "1..128";
              pattern '[0-9a-z_.\-]+';
            }
            description
              "RBP instance name.";
          }
          leaf service-name {
            type leafref {
              path "../../../services/service/name";
            }
            // NCS drop must statement
            description
              "Name of the RBS bound to an RBP.";
            ext:support-filter "true";
          }
          leaf backup-id {
            type uint32 {
              range "1..4095";
            }
            // NCS drop must statement
            description
              "RBS ID.";
          }
          leaf mode {
            type live_ncs_backup-mode;
            // NCS drop default statement
            description
              "Backup mode of an RBP.";
          }
          leaf index {
            type uint32;
            description
              "RBP index, which is automatically allocated by the system. It can be queried but cannot be configured.";
          }
          leaf local-state {
            type live_ncs_rbp-state;
            description
              "Local RBP status when the associated protocol is not VRRP.";
          }
          leaf peer-state {
            type live_ncs_rbp-state;
            description
              "Peer RBP status when the associated protocol is not VRRP.";
          }
          choice track-type {
            description
              "Arbitrate protocol configuration.";
            case e-trunk {
              description
                "Etrunk type that rbs profile tracking.";
              leaf etrunk-id {
                type leafref {
                  path "/ncs:devices/ncs:device/ncs:live-status/etrunk:etrunk/etrunk:instances/etrunk:instance/etrunk:id" {
                    tailf:xpath-root 3;
                  }
                }
                // NCS drop mandatory statement
                description
                  "Etrunk ID.";
              }
              leaf ethtrunk-name {
                type leafref {
                  path "/ncs:devices/ncs:device/ncs:live-status/etrunk:etrunk/etrunk:instances/etrunk:instance[etrunk:id=current()/../etrunk-id]/etrunk:interfaces/etrunk:interface/etrunk:if-name" {
                    tailf:xpath-root 3;
                  }
                }
                // NCS drop mandatory statement
                description
                  "Eth-trunk name.";
              }
            }
            case vrrp {
              description
                "Specify VRRP as arbitrate protocol.";
              container vrrps {
                description
                  "List of associated VRRP backup groups.";
                list vrrp {
                  key "id";
                  unique "mac-type";
                  // NCS drop max-elements statement
                  description
                    "Configure associated VRRP backup group instance.";
                  leaf id {
                    type uint8 {
                      range "1..255";
                    }
                    // NCS drop must statement
                    description
                      "ID of the associated VRRP backup group.";
                  }
                  leaf if-name {
                    type leafref {
                      path "/ncs:devices/ncs:device/ncs:live-status/ifm:ifm/ifm:interfaces/ifm:interface/ifm:name" {
                        tailf:xpath-root 3;
                      }
                    }
                    // NCS drop mandatory statement
                    description
                      "Name of the interface where the associated VRRP backup group resides.";
                  }
                  leaf mac-type {
                    ext:operation-exclude "update" {
                      description
                        "The mac type cannot be updated.";
                    }
                    type live_ncs_vrrp-mac-type;
                    // NCS drop default statement
                    description
                      "VRRP association mode.";
                  }
                  leaf local-state {
                    type live_ncs_rbp-state;
                    description
                      "Local RBP status.";
                  }
                  leaf peer-state {
                    type live_ncs_rbp-state;
                    description
                      "Peer RBP status.";
                  }
                }
              }
            }
          }
          container service-types {
            description
              "List of RBS types.";
            list service-type {
              key "type";
              description
                "Configure remote backup service.";
              leaf type {
                type live_ncs_service-type;
                description
                  "RBS type.";
              }
            }
          }
        }
      }
      container rbs4-session-car {
        // NCS drop must statement
        description
          "Configure session CAR.";
        leaf enable {
          type boolean;
          // NCS drop default statement
          description
            "Enable/disable session CAR.";
        }
        leaf cir {
          type uint32 {
            range "0..1000000";
          }
          units "kbit/s";
          // NCS drop default statement
          description
            "Specify the session CAR CIR value.";
        }
        leaf cbs {
          type uint32 {
            range "0..9000000";
          }
          units "Byte";
          // NCS drop default statement
          description
            "Specify the session CAR CBS value.";
        }
        leaf pir {
          type uint32 {
            range "0..1000000";
          }
          units "kbit/s";
          // NCS drop default statement
          description
            "Specify the session CAR PIR value.";
        }
        leaf pbs {
          type uint32 {
            range "0..9000000";
          }
          units "Byte";
          // NCS drop default statement
          description
            "Specify the session CAR PBS value.";
        }
      }
      container rbs6-session-car {
        // NCS drop must statement
        description
          "Configure session CAR.";
        leaf enable {
          type boolean;
          // NCS drop default statement
          description
            "Enable/disable session CAR.";
        }
        leaf cir {
          type uint32 {
            range "0..1000000";
          }
          units "kbit/s";
          // NCS drop default statement
          description
            "Specify the session CAR CIR value.";
        }
        leaf cbs {
          type uint32 {
            range "0..9000000";
          }
          units "Byte";
          // NCS drop default statement
          description
            "Specify the session CAR CBS value.";
        }
        leaf pir {
          type uint32 {
            range "0..1000000";
          }
          units "kbit/s";
          // NCS drop default statement
          description
            "Specify the session CAR PIR value.";
        }
        leaf pbs {
          type uint32 {
            range "0..9000000";
          }
          units "Byte";
          // NCS drop default statement
          description
            "Specify the session CAR PBS value.";
        }
      }
    }
  }
  augment "/ncs:devices/ncs:template/ncs:ned-id/ncs:config" {
    container rbs {
      description
        "Remote backup service, providing service backup between the master and backup devices, such as ARP entry backup.";
      container services {
        description
          "List of RBS, including information about all remote backup services on a device.";
        list service {
          // NCS patched for predictable order
          ordered-by user;
          key "name";
          description
            "Configure RBS instance list, which can be configured or queried.";
          leaf name {
            type string;
            description
              "RBS instance name.";
          }
          leaf peer-ip {
            type string;
            // NCS drop must statement
            description
              "Peer IP/IPv6 address of a TCP connection.";
          }
          leaf source-ip {
            type string;
            // NCS drop must statement
            description
              "Local IP/IPv6 address of a TCP connection.";
          }
          leaf tcp-port {
            type string;
            // NCS drop must statement
            description
              "Port number of a TCP connection.";
          }
          leaf shut-down {
            type string;
            // NCS drop default statement
            description
              "Enable/disable an RBS connection.";
          }
          // NCS drop config false leaf index
          // NCS drop config false leaf 'tcp-state'
          // NCS drop config false leaf 'last-up-time'
          // NCS drop config false leaf 'last-down-time'
          // NCS drop config false leaf 'last-down-reason'
          container batch-backups {
            description
              "List of periodic service synchronization configurations.";
            list batch-backup {
              // NCS patched for predictable order
              ordered-by user;
              key "service-type";
              description
                "Configure periodic service synchronization configuration instance.";
              leaf service-type {
                type ncs_template_batch-backup-type;
                description
                  "Type of services that are periodically synchronized.";
              }
              leaf backup-time {
                type pub-type:ncs_template_time;
                // NCS drop mandatory statement
                description
                  "Backup start time.";
              }
            }
          }
        }
      }
      container profiles {
        description
          "List of remote backup profiles.";
        list profile {
          // NCS patched for predictable order
          ordered-by user;
          key "name";
          description
            "Configure RBP instance.";
          leaf name {
            type string;
            description
              "RBP instance name.";
          }
          leaf service-name {
            type string;
            // NCS drop must statement
            description
              "Name of the RBS bound to an RBP.";
            ext:support-filter "true";
          }
          leaf backup-id {
            type string;
            // NCS drop must statement
            description
              "RBS ID.";
          }
          leaf mode {
            type ncs_template_backup-mode;
            // NCS drop default statement
            description
              "Backup mode of an RBP.";
          }
          // NCS drop config false leaf index
          // NCS drop config false leaf 'local-state'
          // NCS drop config false leaf 'peer-state'
          choice track-type {
            description
              "Arbitrate protocol configuration.";
            case e-trunk {
              description
                "Etrunk type that rbs profile tracking.";
              leaf etrunk-id {
                type string;
                // NCS drop mandatory statement
                description
                  "Etrunk ID.";
              }
              leaf ethtrunk-name {
                type string;
                // NCS drop mandatory statement
                description
                  "Eth-trunk name.";
              }
            }
            case vrrp {
              description
                "Specify VRRP as arbitrate protocol.";
              container vrrps {
                description
                  "List of associated VRRP backup groups.";
                list vrrp {
                  // NCS patched for predictable order
                  ordered-by user;
                  key "id";
                  unique "mac-type";
                  // NCS drop max-elements statement
                  description
                    "Configure associated VRRP backup group instance.";
                  leaf id {
                    type string;
                    // NCS drop must statement
                    description
                      "ID of the associated VRRP backup group.";
                  }
                  leaf if-name {
                    type string;
                    // NCS drop mandatory statement
                    description
                      "Name of the interface where the associated VRRP backup group resides.";
                  }
                  leaf mac-type {
                    ext:operation-exclude "update" {
                      description
                        "The mac type cannot be updated.";
                    }
                    type ncs_template_vrrp-mac-type;
                    // NCS drop default statement
                    description
                      "VRRP association mode.";
                  }
                  // NCS drop config false leaf 'local-state'
                  // NCS drop config false leaf 'peer-state'
                }
              }
            }
          }
          container service-types {
            description
              "List of RBS types.";
            list service-type {
              // NCS patched for predictable order
              ordered-by user;
              key "type";
              description
                "Configure remote backup service.";
              leaf type {
                type ncs_template_service-type;
                description
                  "RBS type.";
              }
            }
          }
        }
      }
      container rbs4-session-car {
        // NCS drop must statement
        description
          "Configure session CAR.";
        leaf enable {
          type string;
          // NCS drop default statement
          description
            "Enable/disable session CAR.";
        }
        leaf cir {
          type string;
          units "kbit/s";
          // NCS drop default statement
          description
            "Specify the session CAR CIR value.";
        }
        leaf cbs {
          type string;
          units "Byte";
          // NCS drop default statement
          description
            "Specify the session CAR CBS value.";
        }
        leaf pir {
          type string;
          units "kbit/s";
          // NCS drop default statement
          description
            "Specify the session CAR PIR value.";
        }
        leaf pbs {
          type string;
          units "Byte";
          // NCS drop default statement
          description
            "Specify the session CAR PBS value.";
        }
      }
      container rbs6-session-car {
        // NCS drop must statement
        description
          "Configure session CAR.";
        leaf enable {
          type string;
          // NCS drop default statement
          description
            "Enable/disable session CAR.";
        }
        leaf cir {
          type string;
          units "kbit/s";
          // NCS drop default statement
          description
            "Specify the session CAR CIR value.";
        }
        leaf cbs {
          type string;
          units "Byte";
          // NCS drop default statement
          description
            "Specify the session CAR CBS value.";
        }
        leaf pir {
          type string;
          units "kbit/s";
          // NCS drop default statement
          description
            "Specify the session CAR PIR value.";
        }
        leaf pbs {
          type string;
          units "Byte";
          // NCS drop default statement
          description
            "Specify the session CAR PBS value.";
        }
      }
    }
  }
  augment "/ncs:devices/ncs:template/ncs:ned-id/ncs:config/ifm:ifm/ifm:interfaces/ifm:interface" {
    description
      "RBP extend parameters on interface.";
    container rbs {
      description
        "Configure list of interfaces bound to an RBP.";
      container bind-rbp {
        description
          "Configure interface bound to an RBP.";
        leaf name {
          type string;
          // NCS drop must statement
          description
            "Name of an interface bound to an RBP.";
          ext:support-filter "true";
        }
      }
    }
  }
  augment "/ncs:devices/ncs:device/ncs:live-status/ifm:ifm/ifm:interfaces/ifm:interface" {
    description
      "RBP extend parameters on interface.";
    container rbs {
      tailf:ncs-device-type "netconf";
      tailf:display-when "not(../../../../../ncs:module) or ../../../../../ncs:module[ncs:name='huawei-rbs'] or (../../../../../ncs:live-status-protocol[not(ncs:capability)]) or (../../../../../ncs:live-status-protocol/ncs:capability/ncs:module[.='huawei-rbs'])";
      description
        "Configure list of interfaces bound to an RBP.";
      container bind-rbp {
        description
          "Configure interface bound to an RBP.";
        leaf name {
          type leafref {
            path "/ncs:devices/ncs:device/ncs:live-status/rbs:rbs/rbs:profiles/rbs:profile/rbs:name" {
              tailf:xpath-root 3;
            }
          }
          // NCS drop must statement
          description
            "Name of an interface bound to an RBP.";
          ext:support-filter "true";
        }
      }
    }
  }
  augment "/ncs:devices/ncs:device/ncs:config/ifm:ifm/ifm:interfaces/ifm:interface" {
    description
      "RBP extend parameters on interface.";
    container rbs {
      tailf:ncs-device-type "netconf";
      tailf:display-when "not(../../../../../ncs:module) or ../../../../../ncs:module[ncs:name='huawei-rbs']";
      description
        "Configure list of interfaces bound to an RBP.";
      container bind-rbp {
        description
          "Configure interface bound to an RBP.";
        leaf name {
          type leafref {
            path "/ncs:devices/ncs:device/ncs:config/rbs:rbs/rbs:profiles/rbs:profile/rbs:name" {
              tailf:xpath-root 3;
            }
          }
          must "not(/rbs:rbs/rbs:profiles/rbs:profile[rbs:name=current()]/rbs:vrrps) or (/rbs:rbs/rbs:profiles/rbs:profile[rbs:name=current()]/rbs:vrrps/rbs:vrrp[rbs:mac-type='none'])" {
            tailf:xpath-root 3;
          }
          description
            "Name of an interface bound to an RBP.";
          ext:support-filter "true";
        }
      }
    }
  }
}
