module huawei-bras-dhcpv6-access {
  // Generated by yanger -t ncs
  tailf:mount-id "huawei-nc-1.0:huawei-nc-1.0";
  tailf:ncs-device-type "netconf";

  namespace "urn:huawei:yang:huawei-bras-dhcpv6-access";
  prefix bras-dhcpv6-access;

  import huawei-ifm {
    prefix ifm;
  }
  import huawei-aaa {
    prefix aaa;
  }
  import huawei-bras-basic-access {
    prefix bras-basic-access;
  }
  import huawei-pub-type {
    prefix pub-type;
  }
  import ietf-inet-types {
    prefix inet;
  }
  import huawei-extension {
    prefix ext;
  }
  import ietf-yang-types {
    prefix yang;
  }
  import huawei-devm {
    prefix devm;
  }
  import huawei-network-instance {
    prefix ni;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Configure the DHCPv6 user access.";

  revision 2020-02-22 {
    description
      "Description modification.";
    reference "Huawei private.";
  }
  revision 2019-10-17 {
    description
      "Second revision.";
    reference "Huawei private.";
  }
  revision 2019-04-02 {
    description
      "Initial revision.";
    reference "Huawei private.";
  }
  ext:task-name "bras-control";

  grouping ncs_template_vendor-class-group {
    description
      "Vendor class group.";
    container vendor-class {
      description
        "Configure a mapping between the vendor-class attribute and a DHCPv6 option a code as well as the offset value.";
      leaf option-code-value {
        type string;
        // NCS drop default statement
        description
          "Specifies a DHCPv6 option code.";
      }
      leaf offset-value {
        type string;
        description
          "Specifies the offset value of the vendor-class attribute.";
      }
    }
  }

  grouping ncs_template_option18-interface-group {
    description
      "Option 18 interface group.";
    container option18-interface {
      description
        "Configure DHCP Option 18 version3.";
      leaf interface-id {
        type string;
        description
          "DHCP Option 18 Interfacevalue self define.";
      }
    }
  }

  grouping ncs_template_option37-remote-id-group {
    description
      "Option 37 remote id group.";
    container option37-remote-id {
      description
        "Configure DHCP Option 37 version3.";
      leaf remote-id {
        type string;
        description
          "DHCP Option 37 remote ID value self define.";
      }
    }
  }

  grouping ncs_template_option37-relay-mode-group {
    description
      "Option 37 relay mode grouping.";
    container option37-relay-mode {
      description
        "Configure Option 37 relay mode.";
      leaf delete-enterprise-number-enable {
        type string;
        // NCS drop default statement
        description
          "Enable/disable a device to delete enterprise number carried in the Option 37 field from a DHCPv6 solicit or request message.";
      }
    }
  }

  grouping ncs_template_lease-proxy-group {
    description
      "Configure DHCPv6 lease proxy group.";
    container lease-proxy {
      // NCS drop must statement
      description
        "Configure DHCPv6 lease proxy.";
      leaf prefer-time {
        type string;
        units "s";
        description
          "Specifies the prefer lease proxy time.";
      }
      leaf valid-time {
        type string;
        units "s";
        description
          "Specifies the valid lease proxy time.";
      }
      leaf user-detect {
        // NCS drop when statement
        type string;
        // NCS drop default statement
        description
          "Enable/disable the user detect function.";
      }
    }
  }

  grouping ncs_rpc_notif_vendor-class-group {
    description
      "Vendor class group.";
    container vendor-class {
      description
        "Configure a mapping between the vendor-class attribute and a DHCPv6 option a code as well as the offset value.";
      leaf option-code-value {
        type uint8 {
          range "1..255";
        }
        default "16";
        description
          "Specifies a DHCPv6 option code.";
      }
      leaf offset-value {
        type uint8 {
          range "1..254";
        }
        description
          "Specifies the offset value of the vendor-class attribute.";
      }
    }
  }

  grouping ncs_rpc_notif_option18-interface-group {
    description
      "Option 18 interface group.";
    container option18-interface {
      description
        "Configure DHCP Option 18 version3.";
      leaf interface-id {
        type string {
          length "1..64";
        }
        description
          "DHCP Option 18 Interfacevalue self define.";
      }
    }
  }

  grouping ncs_rpc_notif_option37-remote-id-group {
    description
      "Option 37 remote id group.";
    container option37-remote-id {
      description
        "Configure DHCP Option 37 version3.";
      leaf remote-id {
        type string {
          length "1..64";
        }
        description
          "DHCP Option 37 remote ID value self define.";
      }
    }
  }

  grouping ncs_rpc_notif_option37-relay-mode-group {
    description
      "Option 37 relay mode grouping.";
    container option37-relay-mode {
      description
        "Configure Option 37 relay mode.";
      leaf delete-enterprise-number-enable {
        type boolean;
        default "false";
        description
          "Enable/disable a device to delete enterprise number carried in the Option 37 field from a DHCPv6 solicit or request message.";
      }
    }
  }

  grouping ncs_rpc_notif_lease-proxy-group {
    description
      "Configure DHCPv6 lease proxy group.";
    container lease-proxy {
      must '(./prefer-time and ./valid-time and ./prefer-time <= ./valid-time) or (not(./prefer-time) and not(./valid-time))' {
        tailf:xpath-root 3;
      }
      description
        "Configure DHCPv6 lease proxy.";
      leaf prefer-time {
        type uint16 {
          range "40..3600";
        }
        units "s";
        description
          "Specifies the prefer lease proxy time.";
      }
      leaf valid-time {
        type uint16 {
          range "60..3620";
        }
        units "s";
        description
          "Specifies the valid lease proxy time.";
      }
      leaf user-detect {
        when '../valid-time' {
          tailf:xpath-root 3;
        }
        type boolean;
        default "false";
        description
          "Enable/disable the user detect function.";
      }
    }
  }

  grouping live_ncs_vendor-class-group {
    description
      "Vendor class group.";
    container vendor-class {
      description
        "Configure a mapping between the vendor-class attribute and a DHCPv6 option a code as well as the offset value.";
      leaf option-code-value {
        type uint8 {
          range "1..255";
        }
        // NCS drop default statement
        description
          "Specifies a DHCPv6 option code.";
      }
      leaf offset-value {
        type uint8 {
          range "1..254";
        }
        description
          "Specifies the offset value of the vendor-class attribute.";
      }
    }
  }

  grouping live_ncs_option18-interface-group {
    description
      "Option 18 interface group.";
    container option18-interface {
      description
        "Configure DHCP Option 18 version3.";
      leaf interface-id {
        type string {
          length "1..64";
        }
        description
          "DHCP Option 18 Interfacevalue self define.";
      }
    }
  }

  grouping live_ncs_option37-remote-id-group {
    description
      "Option 37 remote id group.";
    container option37-remote-id {
      description
        "Configure DHCP Option 37 version3.";
      leaf remote-id {
        type string {
          length "1..64";
        }
        description
          "DHCP Option 37 remote ID value self define.";
      }
    }
  }

  grouping live_ncs_option37-relay-mode-group {
    description
      "Option 37 relay mode grouping.";
    container option37-relay-mode {
      description
        "Configure Option 37 relay mode.";
      leaf delete-enterprise-number-enable {
        type boolean;
        // NCS drop default statement
        description
          "Enable/disable a device to delete enterprise number carried in the Option 37 field from a DHCPv6 solicit or request message.";
      }
    }
  }

  grouping live_ncs_lease-proxy-group {
    description
      "Configure DHCPv6 lease proxy group.";
    container lease-proxy {
      // NCS drop must statement
      description
        "Configure DHCPv6 lease proxy.";
      leaf prefer-time {
        type uint16 {
          range "40..3600";
        }
        units "s";
        description
          "Specifies the prefer lease proxy time.";
      }
      leaf valid-time {
        type uint16 {
          range "60..3620";
        }
        units "s";
        description
          "Specifies the valid lease proxy time.";
      }
      leaf user-detect {
        // NCS drop when statement
        type boolean;
        // NCS drop default statement
        description
          "Enable/disable the user detect function.";
      }
    }
  }

  grouping vendor-class-group {
    description
      "Vendor class group.";
    container vendor-class {
      description
        "Configure a mapping between the vendor-class attribute and a DHCPv6 option a code as well as the offset value.";
      leaf option-code-value {
        type uint8 {
          range "1..255";
        }
        default "16";
        description
          "Specifies a DHCPv6 option code.";
      }
      leaf offset-value {
        type uint8 {
          range "1..254";
        }
        description
          "Specifies the offset value of the vendor-class attribute.";
      }
    }
  }

  grouping option18-interface-group {
    description
      "Option 18 interface group.";
    container option18-interface {
      description
        "Configure DHCP Option 18 version3.";
      leaf interface-id {
        type string {
          length "1..64";
        }
        description
          "DHCP Option 18 Interfacevalue self define.";
      }
    }
  }

  grouping option37-remote-id-group {
    description
      "Option 37 remote id group.";
    container option37-remote-id {
      description
        "Configure DHCP Option 37 version3.";
      leaf remote-id {
        type string {
          length "1..64";
        }
        description
          "DHCP Option 37 remote ID value self define.";
      }
    }
  }

  grouping option37-relay-mode-group {
    description
      "Option 37 relay mode grouping.";
    container option37-relay-mode {
      description
        "Configure Option 37 relay mode.";
      leaf delete-enterprise-number-enable {
        type boolean;
        default "false";
        description
          "Enable/disable a device to delete enterprise number carried in the Option 37 field from a DHCPv6 solicit or request message.";
      }
    }
  }

  grouping lease-proxy-group {
    description
      "Configure DHCPv6 lease proxy group.";
    container lease-proxy {
      must '(./prefer-time and ./valid-time and ./prefer-time <= ./valid-time) or (not(./prefer-time) and not(./valid-time))' {
        tailf:xpath-root 3;
      }
      description
        "Configure DHCPv6 lease proxy.";
      leaf prefer-time {
        type uint16 {
          range "40..3600";
        }
        units "s";
        description
          "Specifies the prefer lease proxy time.";
      }
      leaf valid-time {
        type uint16 {
          range "60..3620";
        }
        units "s";
        description
          "Specifies the valid lease proxy time.";
      }
      leaf user-detect {
        when '../valid-time' {
          tailf:xpath-root 3;
        }
        type boolean;
        default "false";
        description
          "Enable/disable the user detect function.";
      }
    }
  }

  augment "/ncs:devices/ncs:device/ncs:rpc" {
    container rpc-reset-ipv6-reconf-timeout {
      tailf:ncs-device-type "netconf";
      tailf:display-when "not(../../ncs:module) or ../../ncs:module[ncs:name='huawei-bras-dhcpv6-access']";
      tailf:action reset-ipv6-reconf-timeout {
        tailf:actionpoint ncsproxy {
          tailf:internal;
        }
        description
          "Clears the records of clients that do not respond to reconfigure messages within the timeout period.";
        input {
          leaf all-timeout-record {
            type boolean;
            mandatory true;
            description
              "Clears the information about the clients that do not respond to reconfigure messages within the timeout period.";
          }
        }
      }
    }
  }
  augment "/ncs:devices/ncs:device-group/ncs:ned-id/ncs:rpc" {
    container rpc-reset-ipv6-reconf-timeout {
      tailf:ncs-device-type "netconf";
      tailf:display-when "/ncs:devices/ncs:device[ncs:name=current()/../../../ncs:member]/ncs:module[ncs:name='huawei-bras-dhcpv6-access']";
      tailf:action reset-ipv6-reconf-timeout {
        tailf:actionpoint ncsproxy {
          tailf:internal;
        }
        description
          "Clears the records of clients that do not respond to reconfigure messages within the timeout period.";
        input {
          leaf all-timeout-record {
            type boolean;
            mandatory true;
            description
              "Clears the information about the clients that do not respond to reconfigure messages within the timeout period.";
          }
        }
      }
    }
  }
  augment "/ncs:devices/ncs:device/ncs:config" {
    container bras-dhcpv6-access {
      tailf:ncs-device-type "netconf";
      tailf:display-when "not(../../ncs:module) or ../../ncs:module[ncs:name='huawei-bras-dhcpv6-access']";
      description
        "Configure the DHCPv6 user access.";
      container global-option {
        description
          "Configure bras DHCPv6 access.";
        container option37-decode {
          description
            "Configure Option 37 in DHCPv6 solicit or request packet decode.";
          leaf decode-any-format {
            type boolean;
            default "false";
            description
              "Enable/disable Option 37 any format decode.";
          }
          leaf conflict-offline {
            type enumeration {
              enum "ipv6" {
                value 0;
                description
                  "Only detects whether the IPv6 address assigned to a user from a DHCPv6 remote address pool and an IPv6 prefix pool conflicts with that of another user.";
              }
              enum "ipv6-and-radius" {
                value 1;
                description
                  "Detects whether the IPv6 address assigned to a user from a DHCPv6 remote address pool, an IPv6 prefix pool, or by the RADIUS server conflicts with that of another user.";
              }
            }
            description
              "The DHCPv6 conflict-ip-address offline user command configures the router to log out an online user and deny access of a new user. It detects that the IPv6 address assigned to the new user from a DHCPv6 remote address pool, an IPv6 prefix pool, or by the RADIUS server is the same as the IPv6 address of the online user.";
          }
        }
      }
      container global {
        description
          "Configure bras DHCPv6 access global.";
        container option {
          description
            "Configure the options.";
          container option17-decode {
            description
              "Configure the device to parse the Option 17 field.";
            leaf option17-decode {
              type boolean;
              default "false";
              description
                "Enable/disable the device to parse the Option 17 field based on the format defined by the DSL forum.";
            }
            leaf wait-request-time {
              type uint8 {
                range "5..60";
              }
              units "s";
              default "55";
              description
                "Specifies the DHCPv6 wait request time.";
            }
            leaf server-option {
              type uint16 {
                range "17";
              }
              description
                "The option code retained in DHCPv6 server response messages.";
            }
          }
          container option-priority {
            description
              "Configure the highest, medium, and lowest priorities for the DHCPv6 option delivered by the RADIUS server, configure in the domain scenario, and configure in the address pool scenario, respectively.";
            leaf enable {
              type boolean;
              default "false";
              description
                "Enable/disable the highest, medium, and lowest priorities for the DHCPv6 option delivered by the RADIUS server, configure in the domain scenario, and configure in the address pool scenario, respectively.";
            }
          }
          container vendor-class {
            description
              "Configure a mapping between the vendor-class attribute and a DHCPv6 option a code as well as the offset value.";
            leaf option-code {
              type uint8 {
                range "1..255";
              }
              default "16";
              description
                "Specifies a DHCPv6 option code.";
            }
            leaf offset-value {
              type uint8 {
                range "1..254";
              }
              description
                "Specifies the offset value of the vendor-class attribute.";
            }
          }
        }
        container user-offline {
          description
            "Configure user offLine.";
          leaf duid-mismatch {
            type boolean;
            default "false";
            description
              "Enable/disable logging out the online user with the same MAC address but different DUIDs as that of a received DHCPv6 request packet.";
          }
        }
        container client-duid-replace {
          description
            "Configure the router that functions as a DHCPv6 relay agent to replace the client DUID in a DHCPv6 message sent from a client with the one it generates for that client before sending the message to a server.";
          leaf enable {
            type boolean;
            default "false";
            description
              "Enable/disable replace client.";
          }
        }
        container solict-speed {
          description
            "Configure DHCPv6 solicit speed.";
          leaf packet-num {
            type uint32 {
              range "1..3000";
            }
            must '((../packet-num) and (../second)) or (not(../packet-num) and not(../second))' {
              tailf:xpath-root 3;
            }
            description
              "Specifies the maximum number of solicit packets that are received within a specified time period.";
          }
          leaf second {
            type uint32 {
              range "1..10";
            }
            units "s";
            must '((../packet-num) and (../second)) or (not(../packet-num) and not(../second))' {
              tailf:xpath-root 3;
            }
            description
              "Specified time period.";
          }
        }
        container through-packet {
          description
            "Configure the router to transparently transmit DHCPv6 packets.";
          leaf enable {
            type boolean;
            default "true";
            description
              "Enable/disable through packet.";
          }
        }
        container rebind-no-user-reply {
          description
            "Configure the DHCPv6 rebind no-user action send an reply message in response to a client's DHCPv6 rebind message if a corresponding user entry does not exist on the device.";
          leaf enable {
            type boolean;
            default "false";
            description
              "Enable/disable the DHCPv6 rebind no-user action send an reply message in response to a client's DHCPv6 rebind message if a corresponding user entry does not exist on the device.";
          }
        }
        container reconfigure {
          presence "Create DHCPv6 reconfigure policy.";
          description
            "Enable/disable DHCPv6 reconfigure policy.";
          leaf retransmit-times {
            type uint8 {
              range "1..8";
            }
            default "8";
            description
              "Set the number of retransmission times of DHCPv6 reconfigure packets sent to users.";
          }
        }
        container lease-management {
          description
            "Configure the access frame IPv6 lease manage pool exclude function for remote IPv6 addresses pools.";
          leaf enable {
            type boolean;
            default "false";
            description
              "Enable/disable to manage the leases of RADIUS-delivered IPv6 addresses that are not in the supported address pools.";
          }
        }
        container whitelist-session-car {
          must './cir <= ./pir' {
            tailf:xpath-root 3;
          }
          must './cbs <= ./pbs' {
            tailf:xpath-root 3;
          }
          description
            "Configure DHCPv6 access whitelist session-car.";
          leaf enable {
            type boolean;
            default "true";
            description
              "Enable/disable DHCPv6 access whitelist session-car.";
          }
          leaf cir {
            type uint32 {
              range "0..1000000";
            }
            units "kbit/s";
            default "256";
            description
              "DHCPv6 protocol packets committed information rate.";
          }
          leaf cbs {
            type uint32 {
              range "0..9000000";
            }
            units "Byte";
            default "32000";
            description
              "DHCPv6 protocol packets committed burst size.";
          }
          leaf pir {
            type uint32 {
              range "0..1000000";
            }
            units "kbit/s";
            default "512";
            description
              "DHCPv6 protocol packets peak information rate.";
          }
          leaf pbs {
            type uint32 {
              range "0..9000000";
            }
            units "Byte";
            default "64000";
            description
              "DHCPv6 protocol packets peak burst size.";
          }
        }
        container duid-missmatch {
          description
            "Configure a BRAS device to continue to parse a DHCPv6 message in which the server identifier cannot be identified.";
          leaf reply {
            type boolean;
            default "false";
            description
              "Enable/disable a BRAS device to continue to parse a DHCPv6 message in which the server identifier cannot be identified.";
          }
        }
        container reply-status-code {
          description
            "Configure the device not to respond with an Advertise packet if the Status Code in the Advertise packet is UnspecFail after receiving a DHCPv6 Solicit packet from a DHCPv6 user.";
          leaf reply-disable {
            type boolean;
            default "false";
            description
              "Enable/disable the device not to respond with an Advertise packet if the Status Code in the Advertise packet is UnspecFail after receiving a DHCPv6 Solicit packet from a DHCPv6 user.";
          }
        }
      }
      container rapid-commit {
        description
          "Configure the DHCPv6 server to support a rapid two-message exchange (solicit, reply).";
        leaf enable {
          type boolean;
          default "false";
          description
            "Enable/disable the DHCPv6 server to support a rapid two-message exchange (solicit, reply).";
        }
      }
      container relay {
        status obsolete;
        description
          "Configure DHCPv6 Relay. This container is obsolete and the new container named relay-option on the interfaces.";
        container relay-options {
          status obsolete;
          description
            "List of the relay-forward packets. A packet sent to the DHCPv6 server in the bas relay scenario, the Option 18 and Option 37 attributes are inserted according to the OSP format.";
          list relay-option {
            key "interface-name";
            status obsolete;
            description
              "Configure the relay-forward packet sent to the DHCPv6 server in the bas relay scenario, the Option 18 and Option 37 attributes are inserted according to the OSP format.";
            leaf interface-name {
              type leafref {
                path "/ncs:devices/ncs:device/ncs:config/ifm:ifm/ifm:interfaces/ifm:interface/ifm:name" {
                  tailf:xpath-root 3;
                }
              }
              must "/ifm:ifm/ifm:interfaces/ifm:interface[ifm:name=current()]/ifm:type='GigabitEthernet' or
/ifm:ifm/ifm:interfaces/ifm:interface[ifm:name=current()]/ifm:type='10GE' or
/ifm:ifm/ifm:interfaces/ifm:interface[ifm:name=current()]/ifm:type='25GE' or
/ifm:ifm/ifm:interfaces/ifm:interface[ifm:name=current()]/ifm:type='PW-VE' or
/ifm:ifm/ifm:interfaces/ifm:interface[ifm:name=current()]/ifm:type='FlexE' or
/ifm:ifm/ifm:interfaces/ifm:interface[ifm:name=current()]/ifm:type='Ethernet' or
/ifm:ifm/ifm:interfaces/ifm:interface[ifm:name=current()]/ifm:type='Eth-Trunk'" {
                tailf:xpath-root 3;
              }
              status obsolete;
              description
                "Specifies an interface name.";
            }
            leaf remote-id-type {
              type enumeration {
                enum "neba" {
                  value 1;
                  description
                    "Specifies the remote-id padding to string NEBA.";
                }
                enum "vula" {
                  value 2;
                  description
                    "Specifies the remote-id padding to string VULA.";
                }
              }
              default "neba";
              status obsolete;
              description
                "Specifies the remote-id padding to string NEBA or VULA.";
            }
          }
        }
      }
      // NCS drop config false container 'reconf-timeout-users'
      // NCS drop config false container 'lease-proxy-users'
      // NCS drop config false container 'access-lease-proxy-users'
      // NCS drop config false container 'access-lease-proxy-user-statistics'
    }
  }
  augment "/ncs:devices/ncs:device/ncs:live-status" {
    container bras-dhcpv6-access {
      tailf:ncs-device-type "netconf";
      tailf:display-when "not(../../ncs:module) or ../../ncs:module[ncs:name='huawei-bras-dhcpv6-access'] or (../../ncs:live-status-protocol[not(ncs:capability)]) or (../../ncs:live-status-protocol/ncs:capability/ncs:module[.='huawei-bras-dhcpv6-access'])";
      description
        "Configure the DHCPv6 user access.";
      container global-option {
        description
          "Configure bras DHCPv6 access.";
        container option37-decode {
          description
            "Configure Option 37 in DHCPv6 solicit or request packet decode.";
          leaf decode-any-format {
            type boolean;
            // NCS drop default statement
            description
              "Enable/disable Option 37 any format decode.";
          }
          leaf conflict-offline {
            type enumeration {
              enum "ipv6" {
                value 0;
                description
                  "Only detects whether the IPv6 address assigned to a user from a DHCPv6 remote address pool and an IPv6 prefix pool conflicts with that of another user.";
              }
              enum "ipv6-and-radius" {
                value 1;
                description
                  "Detects whether the IPv6 address assigned to a user from a DHCPv6 remote address pool, an IPv6 prefix pool, or by the RADIUS server conflicts with that of another user.";
              }
            }
            description
              "The DHCPv6 conflict-ip-address offline user command configures the router to log out an online user and deny access of a new user. It detects that the IPv6 address assigned to the new user from a DHCPv6 remote address pool, an IPv6 prefix pool, or by the RADIUS server is the same as the IPv6 address of the online user.";
          }
        }
      }
      container global {
        description
          "Configure bras DHCPv6 access global.";
        container option {
          description
            "Configure the options.";
          container option17-decode {
            description
              "Configure the device to parse the Option 17 field.";
            leaf option17-decode {
              type boolean;
              // NCS drop default statement
              description
                "Enable/disable the device to parse the Option 17 field based on the format defined by the DSL forum.";
            }
            leaf wait-request-time {
              type uint8 {
                range "5..60";
              }
              units "s";
              // NCS drop default statement
              description
                "Specifies the DHCPv6 wait request time.";
            }
            leaf server-option {
              type uint16 {
                range "17";
              }
              description
                "The option code retained in DHCPv6 server response messages.";
            }
          }
          container option-priority {
            description
              "Configure the highest, medium, and lowest priorities for the DHCPv6 option delivered by the RADIUS server, configure in the domain scenario, and configure in the address pool scenario, respectively.";
            leaf enable {
              type boolean;
              // NCS drop default statement
              description
                "Enable/disable the highest, medium, and lowest priorities for the DHCPv6 option delivered by the RADIUS server, configure in the domain scenario, and configure in the address pool scenario, respectively.";
            }
          }
          container vendor-class {
            description
              "Configure a mapping between the vendor-class attribute and a DHCPv6 option a code as well as the offset value.";
            leaf option-code {
              type uint8 {
                range "1..255";
              }
              // NCS drop default statement
              description
                "Specifies a DHCPv6 option code.";
            }
            leaf offset-value {
              type uint8 {
                range "1..254";
              }
              description
                "Specifies the offset value of the vendor-class attribute.";
            }
          }
        }
        container user-offline {
          description
            "Configure user offLine.";
          leaf duid-mismatch {
            type boolean;
            // NCS drop default statement
            description
              "Enable/disable logging out the online user with the same MAC address but different DUIDs as that of a received DHCPv6 request packet.";
          }
        }
        container client-duid-replace {
          description
            "Configure the router that functions as a DHCPv6 relay agent to replace the client DUID in a DHCPv6 message sent from a client with the one it generates for that client before sending the message to a server.";
          leaf enable {
            type boolean;
            // NCS drop default statement
            description
              "Enable/disable replace client.";
          }
        }
        container solict-speed {
          description
            "Configure DHCPv6 solicit speed.";
          leaf packet-num {
            type uint32 {
              range "1..3000";
            }
            // NCS drop must statement
            description
              "Specifies the maximum number of solicit packets that are received within a specified time period.";
          }
          leaf second {
            type uint32 {
              range "1..10";
            }
            units "s";
            // NCS drop must statement
            description
              "Specified time period.";
          }
        }
        container through-packet {
          description
            "Configure the router to transparently transmit DHCPv6 packets.";
          leaf enable {
            type boolean;
            // NCS drop default statement
            description
              "Enable/disable through packet.";
          }
        }
        container rebind-no-user-reply {
          description
            "Configure the DHCPv6 rebind no-user action send an reply message in response to a client's DHCPv6 rebind message if a corresponding user entry does not exist on the device.";
          leaf enable {
            type boolean;
            // NCS drop default statement
            description
              "Enable/disable the DHCPv6 rebind no-user action send an reply message in response to a client's DHCPv6 rebind message if a corresponding user entry does not exist on the device.";
          }
        }
        container reconfigure {
          presence "Create DHCPv6 reconfigure policy.";
          description
            "Enable/disable DHCPv6 reconfigure policy.";
          leaf retransmit-times {
            type uint8 {
              range "1..8";
            }
            // NCS drop default statement
            description
              "Set the number of retransmission times of DHCPv6 reconfigure packets sent to users.";
          }
        }
        container lease-management {
          description
            "Configure the access frame IPv6 lease manage pool exclude function for remote IPv6 addresses pools.";
          leaf enable {
            type boolean;
            // NCS drop default statement
            description
              "Enable/disable to manage the leases of RADIUS-delivered IPv6 addresses that are not in the supported address pools.";
          }
        }
        container whitelist-session-car {
          // NCS drop must statement
          // NCS drop must statement
          description
            "Configure DHCPv6 access whitelist session-car.";
          leaf enable {
            type boolean;
            // NCS drop default statement
            description
              "Enable/disable DHCPv6 access whitelist session-car.";
          }
          leaf cir {
            type uint32 {
              range "0..1000000";
            }
            units "kbit/s";
            // NCS drop default statement
            description
              "DHCPv6 protocol packets committed information rate.";
          }
          leaf cbs {
            type uint32 {
              range "0..9000000";
            }
            units "Byte";
            // NCS drop default statement
            description
              "DHCPv6 protocol packets committed burst size.";
          }
          leaf pir {
            type uint32 {
              range "0..1000000";
            }
            units "kbit/s";
            // NCS drop default statement
            description
              "DHCPv6 protocol packets peak information rate.";
          }
          leaf pbs {
            type uint32 {
              range "0..9000000";
            }
            units "Byte";
            // NCS drop default statement
            description
              "DHCPv6 protocol packets peak burst size.";
          }
        }
        container duid-missmatch {
          description
            "Configure a BRAS device to continue to parse a DHCPv6 message in which the server identifier cannot be identified.";
          leaf reply {
            type boolean;
            // NCS drop default statement
            description
              "Enable/disable a BRAS device to continue to parse a DHCPv6 message in which the server identifier cannot be identified.";
          }
        }
        container reply-status-code {
          description
            "Configure the device not to respond with an Advertise packet if the Status Code in the Advertise packet is UnspecFail after receiving a DHCPv6 Solicit packet from a DHCPv6 user.";
          leaf reply-disable {
            type boolean;
            // NCS drop default statement
            description
              "Enable/disable the device not to respond with an Advertise packet if the Status Code in the Advertise packet is UnspecFail after receiving a DHCPv6 Solicit packet from a DHCPv6 user.";
          }
        }
      }
      container rapid-commit {
        description
          "Configure the DHCPv6 server to support a rapid two-message exchange (solicit, reply).";
        leaf enable {
          type boolean;
          // NCS drop default statement
          description
            "Enable/disable the DHCPv6 server to support a rapid two-message exchange (solicit, reply).";
        }
      }
      container relay {
        status obsolete;
        description
          "Configure DHCPv6 Relay. This container is obsolete and the new container named relay-option on the interfaces.";
        container relay-options {
          status obsolete;
          description
            "List of the relay-forward packets. A packet sent to the DHCPv6 server in the bas relay scenario, the Option 18 and Option 37 attributes are inserted according to the OSP format.";
          list relay-option {
            key "interface-name";
            status obsolete;
            description
              "Configure the relay-forward packet sent to the DHCPv6 server in the bas relay scenario, the Option 18 and Option 37 attributes are inserted according to the OSP format.";
            leaf interface-name {
              type leafref {
                path "/ncs:devices/ncs:device/ncs:live-status/ifm:ifm/ifm:interfaces/ifm:interface/ifm:name" {
                  tailf:xpath-root 3;
                }
              }
              // NCS drop must statement
              status obsolete;
              description
                "Specifies an interface name.";
            }
            leaf remote-id-type {
              type enumeration {
                enum "neba" {
                  value 1;
                  description
                    "Specifies the remote-id padding to string NEBA.";
                }
                enum "vula" {
                  value 2;
                  description
                    "Specifies the remote-id padding to string VULA.";
                }
              }
              // NCS drop default statement
              status obsolete;
              description
                "Specifies the remote-id padding to string NEBA or VULA.";
            }
          }
        }
      }
      container reconf-timeout-users {
        description
          "List of statistics for clients that do not respond to reconfigure messages within the timeout period.";
        list reconf-timeout-user {
          key "index user-id";
          description
            "Display the statistics for clients that do not respond to reconfigure messages within the timeout period.";
          leaf index {
            type uint32 {
              range "0..4294967295";
            }
            description
              "Index of Record.";
          }
          leaf user-id {
            type uint32 {
              range "0..4294967295";
            }
            description
              "User ID of the client that does not respond to a Reconfigure message within the timeout period.";
          }
          leaf user-mac {
            type pub-type:live_ncs_mac-address;
            description
              "MAC address of the client that does not respond to a Reconfigure message within the timeout period.";
            ext:support-filter "true";
          }
          leaf session-id {
            type uint32;
            description
              "Session ID of the client that does not respond to a Reconfigure message within the timeout period.";
            ext:support-filter "true";
          }
          leaf ipv6-address {
            type inet:ipv6-address-no-zone;
            description
              "IPv6 address of the client that does not respond to a Reconfigure message within the timeout period.";
          }
          leaf ipv6-prefix {
            type inet:ipv6-address-no-zone;
            description
              "Prefix of the IPv6 address of the client that does not respond to a reconfigure message within the timeout period.";
          }
          leaf record-time {
            type string {
              length "1..31";
            }
            description
              "Recorded time when client timeouts occur.";
          }
        }
      }
      container lease-proxy-users {
        description
          "List of lease proxy users.";
        list lease-proxy-user {
          key "slot-id user-id";
          description
            "Operational data of lease proxy users.";
          leaf slot-id {
            type string {
              length "1..16";
            }
            description
              "Slot of the lease proxy user.";
          }
          leaf user-id {
            type uint32 {
              range "0..4294967295";
            }
            description
              "User ID of the lease proxy user.";
          }
          leaf mac-address {
            type pub-type:live_ncs_mac-address;
            description
              "MAC address of the lease proxy user.";
            ext:support-filter "true";
          }
          leaf interface {
            type string {
              length "1..64";
            }
            description
              "Interface of the lease proxy user.";
            ext:support-filter "true";
          }
          leaf pe-vlan {
            type uint16;
            description
              "PE-VLAN of the lease proxy user.";
            ext:support-filter "true";
          }
          leaf ce-vlan {
            type uint16;
            description
              "CE-VLAN of the lease proxy user.";
            ext:support-filter "true";
          }
          leaf start-time {
            type yang:date-and-time;
            description
              "Original lease start time.";
          }
          leaf last-renew-time {
            type yang:date-and-time;
            description
              "Original lease last renew time.";
          }
          leaf preferred-lifetime {
            type uint32;
            description
              "Preferred lifetime of the lease proxy user.";
          }
          leaf valid-lifetime {
            type uint32;
            description
              "Valid lifetime of the lease proxy user.";
          }
          leaf original-t1 {
            type uint32;
            description
              "OriginalT1 of the lease proxy user.";
          }
        }
      }
      container access-lease-proxy-users {
        description
          "List of access lease proxy users.";
        list access-lease-proxy-user {
          key "user-id";
          description
            "Operational data of access lease proxy users.";
          leaf user-id {
            type uint32 {
              range "0..4294967295";
            }
            description
              "User ID of the lease proxy user.";
          }
          leaf interface {
            type string {
              length "1..64";
            }
            description
              "Interface of the lease proxy user.";
            ext:support-filter "true";
          }
          leaf domain-name {
            type leafref {
              path "/ncs:devices/ncs:device/ncs:live-status/aaa:aaa/aaa:domains/aaa:domain/aaa:name" {
                tailf:xpath-root 3;
              }
            }
            description
              "Domain name of the lease proxy user.";
            ext:support-filter "true";
          }
          leaf vpn-instance {
            type leafref {
              path "/ncs:devices/ncs:device/ncs:live-status/ni:network-instance/ni:instances/ni:instance/ni:name" {
                tailf:xpath-root 3;
              }
            }
            description
              "VPN instance name.";
            ext:support-filter "true";
          }
          leaf mac-address {
            type pub-type:live_ncs_mac-address;
            description
              "MAC address of the lease proxy user.";
          }
          leaf proxy-type {
            type enumeration {
              enum "ipv4-stack" {
                value 1;
                description
                  "Specifies the proxy type of IPv4 stack.";
              }
              enum "ipv6-stack" {
                value 2;
                description
                  "Specifies the proxy type of IPv6 stack.";
              }
              enum "dual-stack" {
                value 3;
                description
                  "Specifies the proxy type of dual-stack.";
              }
            }
            description
              "Proxy type of the lease proxy user.";
            ext:support-filter "true";
          }
          leaf ipv4-address {
            type inet:ip-address-no-zone;
            description
              "IPv4 address of the lease proxy user.";
          }
          leaf ipv6-address {
            type inet:ipv6-address-no-zone;
            description
              "IPv6 address of the lease proxy user.";
          }
          leaf ipv6-prefix {
            type inet:ipv6-prefix;
            description
              "IPv6 prefix of the lease proxy user.";
          }
          leaf pe-vlan {
            type uint16;
            description
              "PE-VLAN of the lease proxy user.";
          }
          leaf ce-vlan {
            type uint16;
            description
              "CE-VLAN of the lease proxy user.";
          }
          leaf ipv4-lease {
            type uint32;
            description
              "IPv4 lease time of the lease proxy user.";
          }
          leaf preferred-lifetime {
            type uint32;
            description
              "Preferred lifetime of the lease proxy user.";
          }
          leaf valid-lifetime {
            type uint32;
            description
              "Valid lifetime of the lease proxy user.";
          }
        }
      }
      container access-lease-proxy-user-statistics {
        description
          "Statistics of access lease proxy user.";
        leaf total-lease-proxy-users {
          type uint32;
          description
            "The count of total lease proxy users.";
        }
        leaf dual-stack-users {
          type uint32;
          description
            "The count of dual stack type lease proxy users.";
        }
        leaf ipv4-stack-users {
          type uint32;
          description
            "The count of IPv4 stack type lease proxy users.";
        }
        leaf ipv6-stack-users {
          type uint32;
          description
            "The count of IPv6 stack type lease proxy users.";
        }
      }
    }
  }
  augment "/ncs:devices/ncs:template/ncs:ned-id/ncs:config" {
    container bras-dhcpv6-access {
      description
        "Configure the DHCPv6 user access.";
      container global-option {
        description
          "Configure bras DHCPv6 access.";
        container option37-decode {
          description
            "Configure Option 37 in DHCPv6 solicit or request packet decode.";
          leaf decode-any-format {
            type string;
            // NCS drop default statement
            description
              "Enable/disable Option 37 any format decode.";
          }
          leaf conflict-offline {
            type string;
            description
              "The DHCPv6 conflict-ip-address offline user command configures the router to log out an online user and deny access of a new user. It detects that the IPv6 address assigned to the new user from a DHCPv6 remote address pool, an IPv6 prefix pool, or by the RADIUS server is the same as the IPv6 address of the online user.";
          }
        }
      }
      container global {
        description
          "Configure bras DHCPv6 access global.";
        container option {
          description
            "Configure the options.";
          container option17-decode {
            description
              "Configure the device to parse the Option 17 field.";
            leaf option17-decode {
              type string;
              // NCS drop default statement
              description
                "Enable/disable the device to parse the Option 17 field based on the format defined by the DSL forum.";
            }
            leaf wait-request-time {
              type string;
              units "s";
              // NCS drop default statement
              description
                "Specifies the DHCPv6 wait request time.";
            }
            leaf server-option {
              type string;
              description
                "The option code retained in DHCPv6 server response messages.";
            }
          }
          container option-priority {
            description
              "Configure the highest, medium, and lowest priorities for the DHCPv6 option delivered by the RADIUS server, configure in the domain scenario, and configure in the address pool scenario, respectively.";
            leaf enable {
              type string;
              // NCS drop default statement
              description
                "Enable/disable the highest, medium, and lowest priorities for the DHCPv6 option delivered by the RADIUS server, configure in the domain scenario, and configure in the address pool scenario, respectively.";
            }
          }
          container vendor-class {
            description
              "Configure a mapping between the vendor-class attribute and a DHCPv6 option a code as well as the offset value.";
            leaf option-code {
              type string;
              // NCS drop default statement
              description
                "Specifies a DHCPv6 option code.";
            }
            leaf offset-value {
              type string;
              description
                "Specifies the offset value of the vendor-class attribute.";
            }
          }
        }
        container user-offline {
          description
            "Configure user offLine.";
          leaf duid-mismatch {
            type string;
            // NCS drop default statement
            description
              "Enable/disable logging out the online user with the same MAC address but different DUIDs as that of a received DHCPv6 request packet.";
          }
        }
        container client-duid-replace {
          description
            "Configure the router that functions as a DHCPv6 relay agent to replace the client DUID in a DHCPv6 message sent from a client with the one it generates for that client before sending the message to a server.";
          leaf enable {
            type string;
            // NCS drop default statement
            description
              "Enable/disable replace client.";
          }
        }
        container solict-speed {
          description
            "Configure DHCPv6 solicit speed.";
          leaf packet-num {
            type string;
            // NCS drop must statement
            description
              "Specifies the maximum number of solicit packets that are received within a specified time period.";
          }
          leaf second {
            type string;
            units "s";
            // NCS drop must statement
            description
              "Specified time period.";
          }
        }
        container through-packet {
          description
            "Configure the router to transparently transmit DHCPv6 packets.";
          leaf enable {
            type string;
            // NCS drop default statement
            description
              "Enable/disable through packet.";
          }
        }
        container rebind-no-user-reply {
          description
            "Configure the DHCPv6 rebind no-user action send an reply message in response to a client's DHCPv6 rebind message if a corresponding user entry does not exist on the device.";
          leaf enable {
            type string;
            // NCS drop default statement
            description
              "Enable/disable the DHCPv6 rebind no-user action send an reply message in response to a client's DHCPv6 rebind message if a corresponding user entry does not exist on the device.";
          }
        }
        container reconfigure {
          presence "Create DHCPv6 reconfigure policy.";
          description
            "Enable/disable DHCPv6 reconfigure policy.";
          leaf retransmit-times {
            type string;
            // NCS drop default statement
            description
              "Set the number of retransmission times of DHCPv6 reconfigure packets sent to users.";
          }
        }
        container lease-management {
          description
            "Configure the access frame IPv6 lease manage pool exclude function for remote IPv6 addresses pools.";
          leaf enable {
            type string;
            // NCS drop default statement
            description
              "Enable/disable to manage the leases of RADIUS-delivered IPv6 addresses that are not in the supported address pools.";
          }
        }
        container whitelist-session-car {
          // NCS drop must statement
          // NCS drop must statement
          description
            "Configure DHCPv6 access whitelist session-car.";
          leaf enable {
            type string;
            // NCS drop default statement
            description
              "Enable/disable DHCPv6 access whitelist session-car.";
          }
          leaf cir {
            type string;
            units "kbit/s";
            // NCS drop default statement
            description
              "DHCPv6 protocol packets committed information rate.";
          }
          leaf cbs {
            type string;
            units "Byte";
            // NCS drop default statement
            description
              "DHCPv6 protocol packets committed burst size.";
          }
          leaf pir {
            type string;
            units "kbit/s";
            // NCS drop default statement
            description
              "DHCPv6 protocol packets peak information rate.";
          }
          leaf pbs {
            type string;
            units "Byte";
            // NCS drop default statement
            description
              "DHCPv6 protocol packets peak burst size.";
          }
        }
        container duid-missmatch {
          description
            "Configure a BRAS device to continue to parse a DHCPv6 message in which the server identifier cannot be identified.";
          leaf reply {
            type string;
            // NCS drop default statement
            description
              "Enable/disable a BRAS device to continue to parse a DHCPv6 message in which the server identifier cannot be identified.";
          }
        }
        container reply-status-code {
          description
            "Configure the device not to respond with an Advertise packet if the Status Code in the Advertise packet is UnspecFail after receiving a DHCPv6 Solicit packet from a DHCPv6 user.";
          leaf reply-disable {
            type string;
            // NCS drop default statement
            description
              "Enable/disable the device not to respond with an Advertise packet if the Status Code in the Advertise packet is UnspecFail after receiving a DHCPv6 Solicit packet from a DHCPv6 user.";
          }
        }
      }
      container rapid-commit {
        description
          "Configure the DHCPv6 server to support a rapid two-message exchange (solicit, reply).";
        leaf enable {
          type string;
          // NCS drop default statement
          description
            "Enable/disable the DHCPv6 server to support a rapid two-message exchange (solicit, reply).";
        }
      }
      container relay {
        status obsolete;
        description
          "Configure DHCPv6 Relay. This container is obsolete and the new container named relay-option on the interfaces.";
        container relay-options {
          status obsolete;
          description
            "List of the relay-forward packets. A packet sent to the DHCPv6 server in the bas relay scenario, the Option 18 and Option 37 attributes are inserted according to the OSP format.";
          list relay-option {
            // NCS patched for predictable order
            ordered-by user;
            key "interface-name";
            status obsolete;
            description
              "Configure the relay-forward packet sent to the DHCPv6 server in the bas relay scenario, the Option 18 and Option 37 attributes are inserted according to the OSP format.";
            leaf interface-name {
              type string;
              // NCS drop must statement
              status obsolete;
              description
                "Specifies an interface name.";
            }
            leaf remote-id-type {
              type string;
              // NCS drop default statement
              status obsolete;
              description
                "Specifies the remote-id padding to string NEBA or VULA.";
            }
          }
        }
      }
      // NCS drop config false container 'reconf-timeout-users'
      // NCS drop config false container 'lease-proxy-users'
      // NCS drop config false container 'access-lease-proxy-users'
      // NCS drop config false container 'access-lease-proxy-user-statistics'
    }
  }
  augment "/ncs:devices/ncs:template/ncs:ned-id/ncs:config/aaa:aaa/aaa:domains/aaa:domain/bras-basic-access:bas" {
    description
      "Creates a domain and enters the domain scenario; alternatively, you can enter the scenario of an existing domain. Exceptionally, in this module it cannot be deleted or removed to delete its child.";
    container dhcpv6-access {
      description
        "Configure DHCPv6 access.";
      container packet-policy {
        description
          "Configure the router to transparently transmit DHCPv6 packets.";
        leaf nd-ra-link-prefix {
          type string;
          // NCS drop default statement
          description
            "Enable/disable to send route advertisement with link prefix for IPoE users.";
        }
        leaf circuit-id {
          type string;
          // NCS drop default statement
          description
            "Enable/disable circuit id.";
        }
        leaf remote-id {
          type string;
          // NCS drop default statement
          description
            "Enable/disable remote id.";
        }
      }
      container zero-lease-v6enhance {
        description
          "Configure CoA messages delivered by the RADIUS server.";
        leaf enable {
          type string;
          // NCS drop default statement
          description
            "Enable/disable a device to log out a dual-stack user from IPv6 stacks and send a DHCPv6 Reconfigure message to the user when the RADIUS server delivers a zero lease in a CoA message.";
        }
      }
      uses ncs_template_lease-proxy-group;
    }
  }
  augment "/ncs:devices/ncs:device/ncs:live-status/aaa:aaa/aaa:domains/aaa:domain/bras-basic-access:bas" {
    description
      "Creates a domain and enters the domain scenario; alternatively, you can enter the scenario of an existing domain. Exceptionally, in this module it cannot be deleted or removed to delete its child.";
    container dhcpv6-access {
      tailf:ncs-device-type "netconf";
      tailf:display-when "not(../../../../../../ncs:module) or ../../../../../../ncs:module[ncs:name='huawei-bras-dhcpv6-access'] or (../../../../../../ncs:live-status-protocol[not(ncs:capability)]) or (../../../../../../ncs:live-status-protocol/ncs:capability/ncs:module[.='huawei-bras-dhcpv6-access'])";
      description
        "Configure DHCPv6 access.";
      container packet-policy {
        description
          "Configure the router to transparently transmit DHCPv6 packets.";
        leaf nd-ra-link-prefix {
          type boolean;
          // NCS drop default statement
          description
            "Enable/disable to send route advertisement with link prefix for IPoE users.";
        }
        leaf circuit-id {
          type boolean;
          // NCS drop default statement
          description
            "Enable/disable circuit id.";
        }
        leaf remote-id {
          type boolean;
          // NCS drop default statement
          description
            "Enable/disable remote id.";
        }
      }
      container zero-lease-v6enhance {
        description
          "Configure CoA messages delivered by the RADIUS server.";
        leaf enable {
          type boolean;
          // NCS drop default statement
          description
            "Enable/disable a device to log out a dual-stack user from IPv6 stacks and send a DHCPv6 Reconfigure message to the user when the RADIUS server delivers a zero lease in a CoA message.";
        }
      }
      uses live_ncs_lease-proxy-group;
    }
  }
  augment "/ncs:devices/ncs:device/ncs:config/aaa:aaa/aaa:domains/aaa:domain/bras-basic-access:bas" {
    description
      "Creates a domain and enters the domain scenario; alternatively, you can enter the scenario of an existing domain. Exceptionally, in this module it cannot be deleted or removed to delete its child.";
    container dhcpv6-access {
      tailf:ncs-device-type "netconf";
      tailf:display-when "not(../../../../../../ncs:module) or ../../../../../../ncs:module[ncs:name='huawei-bras-dhcpv6-access']";
      description
        "Configure DHCPv6 access.";
      container packet-policy {
        description
          "Configure the router to transparently transmit DHCPv6 packets.";
        leaf nd-ra-link-prefix {
          type boolean;
          default "false";
          description
            "Enable/disable to send route advertisement with link prefix for IPoE users.";
        }
        leaf circuit-id {
          type boolean;
          default "false";
          description
            "Enable/disable circuit id.";
        }
        leaf remote-id {
          type boolean;
          default "false";
          description
            "Enable/disable remote id.";
        }
      }
      container zero-lease-v6enhance {
        description
          "Configure CoA messages delivered by the RADIUS server.";
        leaf enable {
          type boolean;
          default "false";
          description
            "Enable/disable a device to log out a dual-stack user from IPv6 stacks and send a DHCPv6 Reconfigure message to the user when the RADIUS server delivers a zero lease in a CoA message.";
        }
      }
      uses lease-proxy-group;
    }
  }
  augment "/ncs:devices/ncs:template/ncs:ned-id/ncs:config/ifm:ifm/ifm:interfaces/ifm:interface/bras-basic-access:bas/bras-basic-access:access-type/bras-basic-access:layer2-subscriber/bras-basic-access:layer2-subscriber" {
    description
      "Create a BAS interface and display the BAS interface scenario. Exceptionally, in this module it cannot be deleted or removed to delete its child.";
    container dhcpv6-access {
      description
        "Configure DHCPv6 access.";
      uses ncs_template_vendor-class-group;
      uses ncs_template_option18-interface-group;
      uses ncs_template_option37-remote-id-group;
      uses ncs_template_option37-relay-mode-group;
      uses ncs_template_lease-proxy-group;
    }
  }
  augment "/ncs:devices/ncs:device/ncs:live-status/ifm:ifm/ifm:interfaces/ifm:interface/bras-basic-access:bas/bras-basic-access:access-type/bras-basic-access:layer2-subscriber/bras-basic-access:layer2-subscriber" {
    description
      "Create a BAS interface and display the BAS interface scenario. Exceptionally, in this module it cannot be deleted or removed to delete its child.";
    container dhcpv6-access {
      tailf:ncs-device-type "netconf";
      tailf:display-when "not(../../../../../../../../../ncs:module) or ../../../../../../../../../ncs:module[ncs:name='huawei-bras-dhcpv6-access'] or (../../../../../../../../../ncs:live-status-protocol[not(ncs:capability)]) or (../../../../../../../../../ncs:live-status-protocol/ncs:capability/ncs:module[.='huawei-bras-dhcpv6-access'])";
      description
        "Configure DHCPv6 access.";
      uses live_ncs_vendor-class-group;
      uses live_ncs_option18-interface-group;
      uses live_ncs_option37-remote-id-group;
      uses live_ncs_option37-relay-mode-group;
      uses live_ncs_lease-proxy-group;
    }
  }
  augment "/ncs:devices/ncs:device/ncs:config/ifm:ifm/ifm:interfaces/ifm:interface/bras-basic-access:bas/bras-basic-access:access-type/bras-basic-access:layer2-subscriber/bras-basic-access:layer2-subscriber" {
    description
      "Create a BAS interface and display the BAS interface scenario. Exceptionally, in this module it cannot be deleted or removed to delete its child.";
    container dhcpv6-access {
      tailf:ncs-device-type "netconf";
      tailf:display-when "not(../../../../../../../../../ncs:module) or ../../../../../../../../../ncs:module[ncs:name='huawei-bras-dhcpv6-access']";
      description
        "Configure DHCPv6 access.";
      uses vendor-class-group;
      uses option18-interface-group;
      uses option37-remote-id-group;
      uses option37-relay-mode-group;
      uses lease-proxy-group;
    }
  }
  augment "/ncs:devices/ncs:template/ncs:ned-id/ncs:config/ifm:ifm/ifm:interfaces/ifm:interface/bras-basic-access:bas/bras-basic-access:access-type/bras-basic-access:layer2-leaseline/bras-basic-access:layer2-leaseline" {
    description
      "Create a BAS interface and display the BAS interface scenario. Exceptionally, in this module it cannot be deleted or removed to delete its child.";
    container dhcpv6-access {
      description
        "Configure DHCPv6 access.";
      uses ncs_template_option18-interface-group;
      uses ncs_template_option37-remote-id-group;
      uses ncs_template_option37-relay-mode-group;
    }
  }
  augment "/ncs:devices/ncs:device/ncs:live-status/ifm:ifm/ifm:interfaces/ifm:interface/bras-basic-access:bas/bras-basic-access:access-type/bras-basic-access:layer2-leaseline/bras-basic-access:layer2-leaseline" {
    description
      "Create a BAS interface and display the BAS interface scenario. Exceptionally, in this module it cannot be deleted or removed to delete its child.";
    container dhcpv6-access {
      tailf:ncs-device-type "netconf";
      tailf:display-when "not(../../../../../../../../../ncs:module) or ../../../../../../../../../ncs:module[ncs:name='huawei-bras-dhcpv6-access'] or (../../../../../../../../../ncs:live-status-protocol[not(ncs:capability)]) or (../../../../../../../../../ncs:live-status-protocol/ncs:capability/ncs:module[.='huawei-bras-dhcpv6-access'])";
      description
        "Configure DHCPv6 access.";
      uses live_ncs_option18-interface-group;
      uses live_ncs_option37-remote-id-group;
      uses live_ncs_option37-relay-mode-group;
    }
  }
  augment "/ncs:devices/ncs:device/ncs:config/ifm:ifm/ifm:interfaces/ifm:interface/bras-basic-access:bas/bras-basic-access:access-type/bras-basic-access:layer2-leaseline/bras-basic-access:layer2-leaseline" {
    description
      "Create a BAS interface and display the BAS interface scenario. Exceptionally, in this module it cannot be deleted or removed to delete its child.";
    container dhcpv6-access {
      tailf:ncs-device-type "netconf";
      tailf:display-when "not(../../../../../../../../../ncs:module) or ../../../../../../../../../ncs:module[ncs:name='huawei-bras-dhcpv6-access']";
      description
        "Configure DHCPv6 access.";
      uses option18-interface-group;
      uses option37-remote-id-group;
      uses option37-relay-mode-group;
    }
  }
  augment "/ncs:devices/ncs:template/ncs:ned-id/ncs:config/ifm:ifm/ifm:interfaces/ifm:interface/bras-basic-access:bras" {
    description
      "Configure DHCPv6 access on inferface.";
    container dhcpv6-access {
      description
        "Configure DHCPv6 access.";
      container options {
        // NCS drop when statement
        description
          "List of options insert to the relay-forward packet sent to the DHCPv6 server on the interfaces.";
        list option {
          // NCS patched for predictable order
          ordered-by user;
          key "code";
          description
            "Configure options insert to the relay-forward packet sent to the DHCPv6 server on the interfaces.";
          leaf code {
            type string;
            description
              "Dhcpv6 option code.";
          }
        }
      }
      container relay-option {
        // NCS drop when statement
        description
          "Configure options insert to the relay-forward packet sent to the DHCPv6 server on the interfaces.";
        leaf remote-id-type {
          type string;
          description
            "Specifies the remote-id padding to string NEBA or VULA.";
        }
      }
    }
  }
  augment "/ncs:devices/ncs:device/ncs:live-status/ifm:ifm/ifm:interfaces/ifm:interface/bras-basic-access:bras" {
    description
      "Configure DHCPv6 access on inferface.";
    container dhcpv6-access {
      tailf:ncs-device-type "netconf";
      tailf:display-when "not(../../../../../../ncs:module) or ../../../../../../ncs:module[ncs:name='huawei-bras-dhcpv6-access'] or (../../../../../../ncs:live-status-protocol[not(ncs:capability)]) or (../../../../../../ncs:live-status-protocol/ncs:capability/ncs:module[.='huawei-bras-dhcpv6-access'])";
      description
        "Configure DHCPv6 access.";
      container options {
        // NCS drop when statement
        description
          "List of options insert to the relay-forward packet sent to the DHCPv6 server on the interfaces.";
        list option {
          key "code";
          description
            "Configure options insert to the relay-forward packet sent to the DHCPv6 server on the interfaces.";
          leaf code {
            type uint16 {
              range "79";
            }
            description
              "Dhcpv6 option code.";
          }
        }
      }
      container relay-option {
        // NCS drop when statement
        description
          "Configure options insert to the relay-forward packet sent to the DHCPv6 server on the interfaces.";
        leaf remote-id-type {
          type enumeration {
            enum "neba" {
              value 1;
              description
                "Specifies the remote-id padding to string NEBA.";
            }
            enum "vula" {
              value 2;
              description
                "Specifies the remote-id padding to string VULA.";
            }
          }
          description
            "Specifies the remote-id padding to string NEBA or VULA.";
        }
      }
    }
  }
  augment "/ncs:devices/ncs:device/ncs:config/ifm:ifm/ifm:interfaces/ifm:interface/bras-basic-access:bras" {
    description
      "Configure DHCPv6 access on inferface.";
    container dhcpv6-access {
      tailf:ncs-device-type "netconf";
      tailf:display-when "not(../../../../../../ncs:module) or ../../../../../../ncs:module[ncs:name='huawei-bras-dhcpv6-access']";
      description
        "Configure DHCPv6 access.";
      container options {
        when "../../../ifm:type='Ethernet' or
../../../ifm:type='GigabitEthernet' or
../../../ifm:type='Eth-Trunk' or
../../../ifm:type='100GE' or
../../../ifm:type='10GE' or
../../../ifm:type='Virtual-Ethernet' or
../../../ifm:type='Global-VE' or
../../../ifm:type='10x10GE' or
../../../ifm:type='4x25GE' or
../../../ifm:type='25GE' or
../../../ifm:type='XGigabitEthernet' or
../../../ifm:type='FlexE' or
../../../ifm:type='PW-VE'" {
          tailf:xpath-root 3;
        }
        description
          "List of options insert to the relay-forward packet sent to the DHCPv6 server on the interfaces.";
        list option {
          key "code";
          description
            "Configure options insert to the relay-forward packet sent to the DHCPv6 server on the interfaces.";
          leaf code {
            type uint16 {
              range "79";
            }
            description
              "Dhcpv6 option code.";
          }
        }
      }
      container relay-option {
        when "../../../ifm:type='Ethernet' or
../../../ifm:type='GigabitEthernet' or
../../../ifm:type='Eth-Trunk' or
../../../ifm:type='100GE' or
../../../ifm:type='10GE' or
../../../ifm:type='Virtual-Ethernet' or
../../../ifm:type='Global-VE' or
../../../ifm:type='10x10GE' or
../../../ifm:type='4x25GE' or
../../../ifm:type='25GE' or
../../../ifm:type='XGigabitEthernet' or
../../../ifm:type='FlexE' or
../../../ifm:type='PW-VE'" {
          tailf:xpath-root 3;
        }
        description
          "Configure options insert to the relay-forward packet sent to the DHCPv6 server on the interfaces.";
        leaf remote-id-type {
          type enumeration {
            enum "neba" {
              value 1;
              description
                "Specifies the remote-id padding to string NEBA.";
            }
            enum "vula" {
              value 2;
              description
                "Specifies the remote-id padding to string VULA.";
            }
          }
          description
            "Specifies the remote-id padding to string NEBA or VULA.";
        }
      }
    }
  }
  augment "/ncs:devices/ncs:template/ncs:ned-id/ncs:config/devm:devm/devm:lpu-boards/devm:lpu-board" {
    description
      "DHCPv6 lease proxy.";
    container dhcpv6-access {
      description
        "Configure DHCPv6 access.";
      leaf lease-proxy-rate {
        type string;
        units "pps";
        // NCS drop default statement
        description
          "DHCPv6 lease proxy rate.";
      }
    }
  }
  augment "/ncs:devices/ncs:device/ncs:live-status/devm:devm/devm:lpu-boards/devm:lpu-board" {
    description
      "DHCPv6 lease proxy.";
    container dhcpv6-access {
      tailf:ncs-device-type "netconf";
      tailf:display-when "not(../../../../../ncs:module) or ../../../../../ncs:module[ncs:name='huawei-bras-dhcpv6-access'] or (../../../../../ncs:live-status-protocol[not(ncs:capability)]) or (../../../../../ncs:live-status-protocol/ncs:capability/ncs:module[.='huawei-bras-dhcpv6-access'])";
      description
        "Configure DHCPv6 access.";
      leaf lease-proxy-rate {
        type uint16 {
          range "128..2048";
        }
        units "pps";
        // NCS drop default statement
        description
          "DHCPv6 lease proxy rate.";
      }
    }
  }
  augment "/ncs:devices/ncs:device/ncs:config/devm:devm/devm:lpu-boards/devm:lpu-board" {
    description
      "DHCPv6 lease proxy.";
    container dhcpv6-access {
      tailf:ncs-device-type "netconf";
      tailf:display-when "not(../../../../../ncs:module) or ../../../../../ncs:module[ncs:name='huawei-bras-dhcpv6-access']";
      description
        "Configure DHCPv6 access.";
      leaf lease-proxy-rate {
        type uint16 {
          range "128..2048";
        }
        units "pps";
        default "256";
        description
          "DHCPv6 lease proxy rate.";
      }
    }
  }
  augment "/ncs:devices/ncs:template/ncs:ned-id/ncs:config/devm:devm/devm:mpu-boards/devm:mpu-board" {
    description
      "DHCPv6 lease proxy.";
    container dhcpv6-access {
      description
        "Configure DHCPv6 access.";
      leaf lease-proxy-rate {
        type string;
        units "pps";
        // NCS drop default statement
        description
          "DHCPv6 lease proxy rate.";
      }
    }
  }
  augment "/ncs:devices/ncs:device/ncs:live-status/devm:devm/devm:mpu-boards/devm:mpu-board" {
    description
      "DHCPv6 lease proxy.";
    container dhcpv6-access {
      tailf:ncs-device-type "netconf";
      tailf:display-when "not(../../../../../ncs:module) or ../../../../../ncs:module[ncs:name='huawei-bras-dhcpv6-access'] or (../../../../../ncs:live-status-protocol[not(ncs:capability)]) or (../../../../../ncs:live-status-protocol/ncs:capability/ncs:module[.='huawei-bras-dhcpv6-access'])";
      description
        "Configure DHCPv6 access.";
      leaf lease-proxy-rate {
        type uint16 {
          range "128..2048";
        }
        units "pps";
        // NCS drop default statement
        description
          "DHCPv6 lease proxy rate.";
      }
    }
  }
  augment "/ncs:devices/ncs:device/ncs:config/devm:devm/devm:mpu-boards/devm:mpu-board" {
    description
      "DHCPv6 lease proxy.";
    container dhcpv6-access {
      tailf:ncs-device-type "netconf";
      tailf:display-when "not(../../../../../ncs:module) or ../../../../../ncs:module[ncs:name='huawei-bras-dhcpv6-access']";
      description
        "Configure DHCPv6 access.";
      leaf lease-proxy-rate {
        type uint16 {
          range "128..2048";
        }
        units "pps";
        default "256";
        description
          "DHCPv6 lease proxy rate.";
      }
    }
  }
}
