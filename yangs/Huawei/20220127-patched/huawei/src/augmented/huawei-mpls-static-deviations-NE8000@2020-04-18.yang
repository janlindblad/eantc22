module huawei-mpls-static-deviations-NE8000 {
  // Generated by yanger -t ncs
  tailf:mount-id "huawei-nc-1.0:huawei-nc-1.0";
  tailf:ncs-device-type "netconf";

  namespace "urn:huawei:yang:huawei-mpls-static-deviations-NE8000";
  prefix mpls-static-devs-NE8000;

  import huawei-mpls {
    prefix mpls;
  }
  import huawei-mpls-static {
    prefix mpls-static;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Specifies the multi-protocol label switching protocol.";

  revision 2020-04-18 {
    description
      "Initial revision.";
    reference "Huawei private.";
  }

  deviation "/ncs:devices/ncs:template/ncs:ned-id/ncs:config/mpls:mpls/mpls-static:static/mpls-static:lsps/mpls-static:lsp/mpls-static:egress/mpls-static:in-label" {
    deviate replace {
      type string;
    }
  }
  deviation "/ncs:devices/ncs:device/ncs:live-status/mpls:mpls/mpls-static:static/mpls-static:lsps/mpls-static:lsp/mpls-static:egress/mpls-static:in-label" {
    deviate replace {
      type uint32 {
        range "16..65551";
      }
    }
  }
  deviation "/ncs:devices/ncs:device/ncs:config/mpls:mpls/mpls-static:static/mpls-static:lsps/mpls-static:lsp/mpls-static:egress/mpls-static:in-label" {
    deviate replace {
      type uint32 {
        range "16..65551";
      }
    }
  }
  deviation "/ncs:devices/ncs:template/ncs:ned-id/ncs:config/mpls:mpls/mpls-static:static/mpls-static:lsps/mpls-static:lsp/mpls-static:transit/mpls-static:in-label" {
    deviate replace {
      type string;
    }
  }
  deviation "/ncs:devices/ncs:device/ncs:live-status/mpls:mpls/mpls-static:static/mpls-static:lsps/mpls-static:lsp/mpls-static:transit/mpls-static:in-label" {
    deviate replace {
      type uint32 {
        range "16..65551";
      }
    }
  }
  deviation "/ncs:devices/ncs:device/ncs:config/mpls:mpls/mpls-static:static/mpls-static:lsps/mpls-static:lsp/mpls-static:transit/mpls-static:in-label" {
    deviate replace {
      type uint32 {
        range "16..65551";
      }
    }
  }
}
