module huawei-ietf-hardware-deviations-NE8000 {
  // Generated by yanger -t ncs
  tailf:mount-id "huawei-nc-1.0:huawei-nc-1.0";
  tailf:ncs-device-type "netconf";

  namespace "urn:huawei:yang:huawei-ietf-hardware-deviations-NE8000";
  prefix hardware-devs-NE8000;

  import ietf-hardware {
    prefix hw;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Configuration deviations of the driver file.";

  revision 2020-04-13 {
    description
      "Initial revision.";
    reference "Huawei private.";
  }

  deviation "/ncs:devices/ncs:template/ncs:ned-id/ncs:config/hw:hardware/hw:component" {
    // NCS drop config false deviate replace
  }
  deviation "/ncs:devices/ncs:device/ncs:live-status/hw:hardware/hw:component" {
    deviate replace;
  }
  deviation "/ncs:devices/ncs:device/ncs:config/hw:hardware/hw:component" {
    // NCS drop config false deviate replace
  }
  deviation "/ncs:devices/ncs:template/ncs:ned-id/ncs:config/hw:hardware/hw:component/hw:name" {
    // NCS drop config false deviate replace
  }
  deviation "/ncs:devices/ncs:device/ncs:live-status/hw:hardware/hw:component/hw:name" {
    deviate replace;
  }
  deviation "/ncs:devices/ncs:device/ncs:config/hw:hardware/hw:component/hw:name" {
    // NCS drop config false deviate replace
  }
  deviation "/ncs:devices/ncs:template/ncs:ned-id/ncs:config/hw:hardware/hw:component/hw:state" {
    // NCS drop config false deviate replace
  }
  deviation "/ncs:devices/ncs:device/ncs:live-status/hw:hardware/hw:component/hw:state" {
    deviate replace;
  }
  deviation "/ncs:devices/ncs:device/ncs:config/hw:hardware/hw:component/hw:state" {
    // NCS drop config false deviate replace
  }
  deviation "/ncs:devices/ncs:device/ncs:live-status/hw:hardware/hw:component/hw:state/hw:state-last-changed" {
    deviate not-supported;
  }
  deviation "/ncs:devices/ncs:device/ncs:live-status/hw:hardware/hw:component/hw:state/hw:usage-state" {
    deviate not-supported;
  }
  deviation "/ncs:devices/ncs:device/ncs:live-status/hw:hardware/hw:component/hw:sensor-data" {
    deviate not-supported;
  }
  deviation "/ncs:devices/ncs:device/ncs:notifications/ncs:received-notifications/ncs:notification/ncs:data/hw:hardware-state-change" {
    deviate not-supported;
  }
  deviation "/ncs:devices/ncs:device/ncs:netconf-notifications/ncs:received-notifications/ncs:notification/ncs:data/hw:hardware-state-change" {
    deviate not-supported;
  }
  deviation "/ncs:devices/ncs:device/ncs:notifications/ncs:received-notifications/ncs:notification/ncs:data/hw:hardware-state-oper-enabled" {
    deviate not-supported;
  }
  deviation "/ncs:devices/ncs:device/ncs:netconf-notifications/ncs:received-notifications/ncs:notification/ncs:data/hw:hardware-state-oper-enabled" {
    deviate not-supported;
  }
  deviation "/ncs:devices/ncs:device/ncs:notifications/ncs:received-notifications/ncs:notification/ncs:data/hw:hardware-state-oper-disabled" {
    deviate not-supported;
  }
  deviation "/ncs:devices/ncs:device/ncs:netconf-notifications/ncs:received-notifications/ncs:notification/ncs:data/hw:hardware-state-oper-disabled" {
    deviate not-supported;
  }
}
