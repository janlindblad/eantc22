module huawei-te {
  // Generated by yanger -t ncs
  tailf:mount-id "huawei-nc-1.0:huawei-nc-1.0";
  tailf:ncs-device-type "netconf";

  namespace "urn:huawei:yang:huawei-te";
  prefix te;

  import ietf-inet-types {
    prefix inet;
  }
  import huawei-extension {
    prefix ext;
  }
  import huawei-network-instance {
    prefix ni;
  }
  include huawei-te-type;
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Specifies the traffic engineering configuration.";

  revision 2020-04-02 {
    description
      "Fixed the mode node condition for explicit path.";
    reference "Huawei private.";
  }
  revision 2020-03-28 {
    description
      "Fixed some problems.";
    reference "Huawei private.";
  }
  revision 2020-03-10 {
    description
      "Fixed some nodes description.";
    reference "Huawei private.";
  }
  revision 2019-11-13 {
    description
      "Add te attribute global configuration.";
    reference "Huawei private.";
  }
  revision 2019-06-14 {
    description
      "Init revision.";
    reference "Huawei private.";
  }
  ext:task-name "mpls-te";

  augment "/ncs:devices/ncs:device/ncs:config" {
    container te {
      tailf:ncs-device-type "netconf";
      tailf:display-when "not(../../ncs:module) or ../../ncs:module[ncs:name='huawei-te']";
      description
        "TE attribute.";
      container global {
        description
          "Configure the global TE information.";
        leaf te-attribute-enable {
          type boolean;
          default "false";
          description
            "Enable/disable TE attribute.";
        }
        leaf ipv6-router-id {
          type inet:ipv6-address;
          description
            "TE IPv6 Router ID.";
        }
      }
      container explicit-paths {
        description
          "List of explicit path.";
        list explicit-path {
          key "name";
          description
            "Configure explicit path. When a TE LSP is to be established, specify route hop constraints for the LSP.";
          leaf name {
            type string {
              length "1..128";
              pattern '[^ \?]*';
            }
            description
              "Explicit path name.";
          }
          container hops {
            description
              "List of Route hop.";
            list hop {
              key "index";
              unique "address";
              max-elements 96;
              description
                "Configure route hop. Operations such as CFG restart and mixed command configuration may cause the index value to change.";
              leaf index {
                type uint32 {
                  range "1..65535";
                }
                description
                  "Route hop index.";
              }
              leaf mode {
                ext:operation-exclude "update";
                type er-hop-mode;
                mandatory true;
                description
                  "Route hop mode, IPv4 or IPv6 address, segment label or SID IPv6 label.";
              }
              leaf er-hop-type {
                when "../mode='ipv4-ipv6-address'" {
                  tailf:xpath-root 3;
                }
                type er-hop-type;
                default "include-strict";
                description
                  "Route hop type. Stictly included: A route hop must be included in a LSP path. Loosely included: A route hop is included in a LSP path if the hop meets path constraints and excluded if the hop does not meet path constraints. Excluded: A route hop is excluded fron the LSP path.";
              }
              leaf interface-type {
                when "../mode='ipv4-ipv6-address' and ../er-hop-type!='exclude'" {
                  tailf:xpath-root 3;
                }
                type er-hop-interface-type;
                default "default";
                description
                  "Route hop interface type.";
              }
              leaf address-type {
                when "../mode='ipv4-ipv6-address'" {
                  tailf:xpath-root 3;
                }
                type te-hop-address-type;
                default "ipv4";
                description
                  "Address type. IPv4 is only supported.";
              }
              leaf address {
                when "../mode='ipv4-ipv6-address'" {
                  tailf:xpath-root 3;
                }
                type inet:ip-address;
                mandatory true;
                description
                  "IP address of a route hop.";
              }
              leaf sid-label-type {
                when "../mode='sid-label'" {
                  tailf:xpath-root 3;
                }
                type er-sid-label-type;
                default "adjacency";
                description
                  "SID label type of the explicit route hop.";
              }
              leaf sid-label {
                when '../sid-label-type' {
                  tailf:xpath-root 3;
                }
                type uint32 {
                  range "16..1048575";
                }
                mandatory true;
                description
                  "SID label of the explicit route hop.";
              }
              leaf sid-ipv6 {
                when "../mode='sid-ipv6'" {
                  tailf:xpath-root 3;
                }
                type inet:ipv6-address-no-zone;
                mandatory true;
                description
                  "SID IPv6 label of the explicit route hop.";
              }
              leaf sid-ipv6-label-type {
                when "../mode='sid-ipv6'" {
                  tailf:xpath-root 3;
                }
                type er-sid-ipv6-label-type;
                default "none";
                description
                  "SID IPv6 label type of the explicit route hop.";
              }
            }
          }
        }
      }
      container affinity-define {
        presence "Enter path-constraint affinity-mapping view.";
        description
          "Configure affinity define function.";
        leaf description {
          type string {
            length "1..80";
          }
          description
            "Description the affinity mapping information.";
        }
        container affinity-mappings {
          description
            "List of the affinity mappings configuration.";
          list affinity-mapping {
            key "attribute-name";
            unique "bit-sequence";
            description
              "Configure the affinity mapping.";
            leaf attribute-name {
              type string {
                length "1..31";
                pattern '[^ ?]*';
              }
              description
                "Configure the attribute name.";
            }
            leaf bit-sequence {
              type uint32 {
                range "0..127";
              }
              mandatory true;
              description
                "Configure the bit sequence.";
            }
          }
        }
      }
    }
  }
  augment "/ncs:devices/ncs:device/ncs:live-status" {
    container te {
      tailf:ncs-device-type "netconf";
      tailf:display-when "not(../../ncs:module) or ../../ncs:module[ncs:name='huawei-te'] or (../../ncs:live-status-protocol[not(ncs:capability)]) or (../../ncs:live-status-protocol/ncs:capability/ncs:module[.='huawei-te'])";
      description
        "TE attribute.";
      container global {
        description
          "Configure the global TE information.";
        leaf te-attribute-enable {
          type boolean;
          // NCS drop default statement
          description
            "Enable/disable TE attribute.";
        }
        leaf ipv6-router-id {
          type inet:ipv6-address;
          description
            "TE IPv6 Router ID.";
        }
      }
      container explicit-paths {
        description
          "List of explicit path.";
        list explicit-path {
          key "name";
          description
            "Configure explicit path. When a TE LSP is to be established, specify route hop constraints for the LSP.";
          leaf name {
            type string {
              length "1..128";
              pattern '[^ \?]*';
            }
            description
              "Explicit path name.";
          }
          container hops {
            description
              "List of Route hop.";
            list hop {
              key "index";
              unique "address";
              // NCS drop max-elements statement
              description
                "Configure route hop. Operations such as CFG restart and mixed command configuration may cause the index value to change.";
              leaf index {
                type uint32 {
                  range "1..65535";
                }
                description
                  "Route hop index.";
              }
              leaf mode {
                ext:operation-exclude "update";
                type live_ncs_er-hop-mode;
                // NCS drop mandatory statement
                description
                  "Route hop mode, IPv4 or IPv6 address, segment label or SID IPv6 label.";
              }
              leaf er-hop-type {
                // NCS drop when statement
                type live_ncs_er-hop-type;
                // NCS drop default statement
                description
                  "Route hop type. Stictly included: A route hop must be included in a LSP path. Loosely included: A route hop is included in a LSP path if the hop meets path constraints and excluded if the hop does not meet path constraints. Excluded: A route hop is excluded fron the LSP path.";
              }
              leaf interface-type {
                // NCS drop when statement
                type live_ncs_er-hop-interface-type;
                // NCS drop default statement
                description
                  "Route hop interface type.";
              }
              leaf address-type {
                // NCS drop when statement
                type live_ncs_te-hop-address-type;
                // NCS drop default statement
                description
                  "Address type. IPv4 is only supported.";
              }
              leaf address {
                // NCS drop when statement
                type inet:ip-address;
                // NCS drop mandatory statement
                description
                  "IP address of a route hop.";
              }
              leaf sid-label-type {
                // NCS drop when statement
                type live_ncs_er-sid-label-type;
                // NCS drop default statement
                description
                  "SID label type of the explicit route hop.";
              }
              leaf sid-label {
                // NCS drop when statement
                type uint32 {
                  range "16..1048575";
                }
                // NCS drop mandatory statement
                description
                  "SID label of the explicit route hop.";
              }
              leaf sid-ipv6 {
                // NCS drop when statement
                type inet:ipv6-address-no-zone;
                // NCS drop mandatory statement
                description
                  "SID IPv6 label of the explicit route hop.";
              }
              leaf sid-ipv6-label-type {
                // NCS drop when statement
                type live_ncs_er-sid-ipv6-label-type;
                // NCS drop default statement
                description
                  "SID IPv6 label type of the explicit route hop.";
              }
            }
          }
        }
      }
      container affinity-define {
        presence "Enter path-constraint affinity-mapping view.";
        description
          "Configure affinity define function.";
        leaf description {
          type string {
            length "1..80";
          }
          description
            "Description the affinity mapping information.";
        }
        container affinity-mappings {
          description
            "List of the affinity mappings configuration.";
          list affinity-mapping {
            key "attribute-name";
            unique "bit-sequence";
            description
              "Configure the affinity mapping.";
            leaf attribute-name {
              type string {
                length "1..31";
                pattern '[^ ?]*';
              }
              description
                "Configure the attribute name.";
            }
            leaf bit-sequence {
              type uint32 {
                range "0..127";
              }
              // NCS drop mandatory statement
              description
                "Configure the bit sequence.";
            }
          }
        }
      }
    }
  }
  augment "/ncs:devices/ncs:template/ncs:ned-id/ncs:config" {
    container te {
      description
        "TE attribute.";
      container global {
        description
          "Configure the global TE information.";
        leaf te-attribute-enable {
          type string;
          // NCS drop default statement
          description
            "Enable/disable TE attribute.";
        }
        leaf ipv6-router-id {
          type string;
          description
            "TE IPv6 Router ID.";
        }
      }
      container explicit-paths {
        description
          "List of explicit path.";
        list explicit-path {
          // NCS patched for predictable order
          ordered-by user;
          key "name";
          description
            "Configure explicit path. When a TE LSP is to be established, specify route hop constraints for the LSP.";
          leaf name {
            type string;
            description
              "Explicit path name.";
          }
          container hops {
            description
              "List of Route hop.";
            list hop {
              // NCS patched for predictable order
              ordered-by user;
              key "index";
              unique "address";
              // NCS drop max-elements statement
              description
                "Configure route hop. Operations such as CFG restart and mixed command configuration may cause the index value to change.";
              leaf index {
                type string;
                description
                  "Route hop index.";
              }
              leaf mode {
                ext:operation-exclude "update";
                type ncs_template_er-hop-mode;
                // NCS drop mandatory statement
                description
                  "Route hop mode, IPv4 or IPv6 address, segment label or SID IPv6 label.";
              }
              leaf er-hop-type {
                // NCS drop when statement
                type ncs_template_er-hop-type;
                // NCS drop default statement
                description
                  "Route hop type. Stictly included: A route hop must be included in a LSP path. Loosely included: A route hop is included in a LSP path if the hop meets path constraints and excluded if the hop does not meet path constraints. Excluded: A route hop is excluded fron the LSP path.";
              }
              leaf interface-type {
                // NCS drop when statement
                type ncs_template_er-hop-interface-type;
                // NCS drop default statement
                description
                  "Route hop interface type.";
              }
              leaf address-type {
                // NCS drop when statement
                type ncs_template_te-hop-address-type;
                // NCS drop default statement
                description
                  "Address type. IPv4 is only supported.";
              }
              leaf address {
                // NCS drop when statement
                type string;
                // NCS drop mandatory statement
                description
                  "IP address of a route hop.";
              }
              leaf sid-label-type {
                // NCS drop when statement
                type ncs_template_er-sid-label-type;
                // NCS drop default statement
                description
                  "SID label type of the explicit route hop.";
              }
              leaf sid-label {
                // NCS drop when statement
                type string;
                // NCS drop mandatory statement
                description
                  "SID label of the explicit route hop.";
              }
              leaf sid-ipv6 {
                // NCS drop when statement
                type string;
                // NCS drop mandatory statement
                description
                  "SID IPv6 label of the explicit route hop.";
              }
              leaf sid-ipv6-label-type {
                // NCS drop when statement
                type ncs_template_er-sid-ipv6-label-type;
                // NCS drop default statement
                description
                  "SID IPv6 label type of the explicit route hop.";
              }
            }
          }
        }
      }
      container affinity-define {
        presence "Enter path-constraint affinity-mapping view.";
        description
          "Configure affinity define function.";
        leaf description {
          type string;
          description
            "Description the affinity mapping information.";
        }
        container affinity-mappings {
          description
            "List of the affinity mappings configuration.";
          list affinity-mapping {
            // NCS patched for predictable order
            ordered-by user;
            key "attribute-name";
            unique "bit-sequence";
            description
              "Configure the affinity mapping.";
            leaf attribute-name {
              type string;
              description
                "Configure the attribute name.";
            }
            leaf bit-sequence {
              type string;
              // NCS drop mandatory statement
              description
                "Configure the bit sequence.";
            }
          }
        }
      }
    }
  }
  augment "/ncs:devices/ncs:template/ncs:ned-id/ncs:config/ni:network-instance/ni:instances/ni:instance" {
    description
      "TE Configuration information augment to network instance.";
    container te {
      description
        "Configure TE function information.";
    }
  }
  augment "/ncs:devices/ncs:device/ncs:live-status/ni:network-instance/ni:instances/ni:instance" {
    description
      "TE Configuration information augment to network instance.";
    container te {
      tailf:ncs-device-type "netconf";
      tailf:display-when "not(../../../../../ncs:module) or ../../../../../ncs:module[ncs:name='huawei-te'] or (../../../../../ncs:live-status-protocol[not(ncs:capability)]) or (../../../../../ncs:live-status-protocol/ncs:capability/ncs:module[.='huawei-te'])";
      description
        "Configure TE function information.";
    }
  }
  augment "/ncs:devices/ncs:device/ncs:config/ni:network-instance/ni:instances/ni:instance" {
    description
      "TE Configuration information augment to network instance.";
    container te {
      tailf:ncs-device-type "netconf";
      tailf:display-when "not(../../../../../ncs:module) or ../../../../../ncs:module[ncs:name='huawei-te']";
      description
        "Configure TE function information.";
    }
  }
}
