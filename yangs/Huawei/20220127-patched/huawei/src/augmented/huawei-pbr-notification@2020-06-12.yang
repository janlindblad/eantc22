module huawei-pbr-notification {
  // Generated by yanger -t ncs
  tailf:mount-id "huawei-nc-1.0:huawei-nc-1.0";
  tailf:ncs-device-type "netconf";

  yang-version 1;
  namespace "urn:huawei:yang:huawei-pbr-notification";
  prefix pbr-notification;

  import huawei-extension {
    prefix ext;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Notification of pbr.";

  revision 2020-06-12 {
    description
      "Add new nodes.";
    reference "Huawei private.";
  }
  revision 2019-11-06 {
    description
      "Initial revision.";
    reference "Huawei private.";
  }
  ext:task-name "qos";

  typedef ncs_template_redirect-type {
    type string;
    description
      "Redirect type.";
  }

  typedef ncs_rpc_notif_redirect-type {
    type enumeration {
      enum "ipv4" {
        value 0;
        description
          "IPv4.";
      }
      enum "ipv6" {
        value 1;
        description
          "IPv6.";
      }
    }
    description
      "Redirect type.";
  }

  typedef live_ncs_redirect-type {
    type enumeration {
      enum "ipv4" {
        value 0;
        description
          "IPv4.";
      }
      enum "ipv6" {
        value 1;
        description
          "IPv6.";
      }
    }
    description
      "Redirect type.";
  }

  typedef redirect-type {
    type enumeration {
      enum "ipv4" {
        value 0;
        description
          "IPv4.";
      }
      enum "ipv6" {
        value 1;
        description
          "IPv6.";
      }
    }
    description
      "Redirect type.";
  }

  augment "/ncs:devices/ncs:device/ncs:notifications/ncs:received-notifications/ncs:notification/ncs:data" {
    container xqos-redirect-nexthop-lack-resource-alarm-resume {
      presence "";
      config false;
      description
        "Resources are sufficient or the configuration of redirecting traffic to the next hop is deleted.";
      leaf behavior-name {
        type string {
          length "1..127";
        }
        description
          "Behavior name.";
      }
      leaf slot-id {
        type string {
          length "1..16";
        }
        description
          "Slot ID.";
      }
      leaf redirect-type {
        type ncs_rpc_notif_redirect-type;
        description
          "Redirect type.";
      }
    }
  }
  augment "/ncs:devices/ncs:device/ncs:notifications/ncs:received-notifications/ncs:notification/ncs:data" {
    container xqos-redirect-nexthop-lack-resource-alarm {
      presence "";
      config false;
      description
        "Redirecting traffic to the next hop is invalid due to insufficient NHP resources.";
      leaf behavior-name {
        type string {
          length "1..127";
        }
        description
          "Behavior name.";
      }
      leaf slot-id {
        type string {
          length "1..16";
        }
        description
          "Slot ID.";
      }
      leaf redirect-type {
        type ncs_rpc_notif_redirect-type;
        description
          "Redirect type.";
      }
    }
  }
  augment "/ncs:devices/ncs:device/ncs:notifications/ncs:received-notifications/ncs:notification/ncs:data" {
    container xqos-redirect-nexthop-invalid-alarm-resume {
      presence "";
      config false;
      description
        "The redirect nexthop address matches the network segment of the outbound interface or the redirect configuration has been cleared.";
      leaf behavior-name {
        type string {
          length "1..127";
        }
        description
          "Behavior name.";
      }
      leaf redirect {
        type ncs_rpc_notif_redirect-type;
        description
          "Redirect type.";
      }
      leaf interface-name {
        type string {
          length "1..511";
        }
        description
          "Interface name.";
      }
    }
  }
  augment "/ncs:devices/ncs:device/ncs:notifications/ncs:received-notifications/ncs:notification/ncs:data" {
    container xqos-redirect-nexthop-invalid-alarm {
      presence "";
      config false;
      description
        "The redirect nexthop address did not match the network segment of the outbound interface.";
      leaf behavior-name {
        type string {
          length "1..127";
        }
        description
          "Behavior name.";
      }
      leaf redirect {
        type ncs_rpc_notif_redirect-type;
        description
          "Redirect type.";
      }
      leaf interface-name {
        type string {
          length "1..511";
        }
        description
          "Interface name.";
      }
    }
  }
  augment "/ncs:devices/ncs:device/ncs:netconf-notifications/ncs:received-notifications/ncs:notification/ncs:data" {
    container xqos-redirect-nexthop-lack-resource-alarm-resume {
      presence "";
      config false;
      description
        "Resources are sufficient or the configuration of redirecting traffic to the next hop is deleted.";
      leaf behavior-name {
        type string {
          length "1..127";
        }
        description
          "Behavior name.";
      }
      leaf slot-id {
        type string {
          length "1..16";
        }
        description
          "Slot ID.";
      }
      leaf redirect-type {
        type ncs_rpc_notif_redirect-type;
        description
          "Redirect type.";
      }
    }
  }
  augment "/ncs:devices/ncs:device/ncs:netconf-notifications/ncs:received-notifications/ncs:notification/ncs:data" {
    container xqos-redirect-nexthop-lack-resource-alarm {
      presence "";
      config false;
      description
        "Redirecting traffic to the next hop is invalid due to insufficient NHP resources.";
      leaf behavior-name {
        type string {
          length "1..127";
        }
        description
          "Behavior name.";
      }
      leaf slot-id {
        type string {
          length "1..16";
        }
        description
          "Slot ID.";
      }
      leaf redirect-type {
        type ncs_rpc_notif_redirect-type;
        description
          "Redirect type.";
      }
    }
  }
  augment "/ncs:devices/ncs:device/ncs:netconf-notifications/ncs:received-notifications/ncs:notification/ncs:data" {
    container xqos-redirect-nexthop-invalid-alarm-resume {
      presence "";
      config false;
      description
        "The redirect nexthop address matches the network segment of the outbound interface or the redirect configuration has been cleared.";
      leaf behavior-name {
        type string {
          length "1..127";
        }
        description
          "Behavior name.";
      }
      leaf redirect {
        type ncs_rpc_notif_redirect-type;
        description
          "Redirect type.";
      }
      leaf interface-name {
        type string {
          length "1..511";
        }
        description
          "Interface name.";
      }
    }
  }
  augment "/ncs:devices/ncs:device/ncs:netconf-notifications/ncs:received-notifications/ncs:notification/ncs:data" {
    container xqos-redirect-nexthop-invalid-alarm {
      presence "";
      config false;
      description
        "The redirect nexthop address did not match the network segment of the outbound interface.";
      leaf behavior-name {
        type string {
          length "1..127";
        }
        description
          "Behavior name.";
      }
      leaf redirect {
        type ncs_rpc_notif_redirect-type;
        description
          "Redirect type.";
      }
      leaf interface-name {
        type string {
          length "1..511";
        }
        description
          "Interface name.";
      }
    }
  }
}
