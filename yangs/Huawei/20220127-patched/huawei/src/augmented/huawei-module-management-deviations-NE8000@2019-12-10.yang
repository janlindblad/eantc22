module huawei-module-management-deviations-NE8000 {
  // Generated by yanger -t ncs
  tailf:mount-id "huawei-nc-1.0:huawei-nc-1.0";
  tailf:ncs-device-type "netconf";

  namespace "urn:huawei:yang:huawei-module-management-deviations-NE8000";
  prefix module-management-devs-NE8000;

  import huawei-module-management {
    prefix module-management;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Module deviations.";

  revision 2019-12-10 {
    description
      "Initial revision.";
    reference "Huawei private.";
  }

  deviation "/ncs:devices/ncs:device/ncs:live-status/module-management:module-management/module-management:operation-schedules/module-management:operation-schedule/module-management:name" {
    deviate not-supported;
  }
  deviation "/ncs:devices/ncs:device/ncs:live-status/module-management:module-management/module-management:download-package-schedule" {
    deviate not-supported;
  }
  deviation "/ncs:devices/ncs:device/ncs:live-status/module-management:module-management/module-management:download-package-load-path" {
    deviate not-supported;
  }
  deviation "/ncs:devices/ncs:device/ncs:rpc/module-management:rpc-download-module-file/module-management:download-module-file" {
    deviate not-supported;
  }
}
