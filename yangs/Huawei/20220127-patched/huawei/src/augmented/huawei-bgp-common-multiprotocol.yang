submodule huawei-bgp-common-multiprotocol {
  // Generated by yanger -t ncs
  tailf:mount-id "huawei-nc-1.0:huawei-nc-1.0";

  yang-version 1;
  belongs-to huawei-bgp {
    prefix bgp;
  }

  import huawei-routing-policy {
    prefix rtp;
  }
  include huawei-bgp-type;
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Inter-AS routing protocol that exchanges Network Layer Reachability Information (NLRI) with other BGP systems.";

  revision 2021-02-03 {
    description
      "Initial revision.";
    reference "Huawei private.";
  }

  grouping ncs_template_advertise-dependent-filter-type {
    description
      "The advertise-dependent-filter-type configuration.";
    container advertise-dependent-filter {
      presence "Enable peer advertising dependent filter.";
      description
        "Configure peer advertising dependent filter.";
      leaf dependent-filter-switch {
        type bgp:ncs_template_peer-attr-enable-type;
        // NCS drop mandatory statement
        description
          "Specify a switch type.";
      }
      leaf dependent-filter {
        // NCS drop when statement
        type string;
        // NCS drop mandatory statement
        description
          "Specify a dependent route-filter name.";
      }
      leaf dependent-filter-type {
        // NCS drop when statement
        type bgp:ncs_template_dependent-prefix-filter-type;
        // NCS drop mandatory statement
        description
          "Specify a dependent route-filter mode.";
      }
      leaf condition-filter {
        // NCS drop when statement
        type string;
        description
          "Specify a condition route-filter name.";
      }
    }
    // NCS drop config false container 'advertise-dependent-filter-state'
  }

  grouping ncs_template_advertise-dependent-filter-group-type {
    description
      "The advertise-dependent-filter-group-type configuration.";
    container advertise-dependent-filter {
      presence "Enable peer group advertising dependent filter.";
      description
        "Configure peer group advertising dependent filter.";
      leaf dependent-filter {
        type string;
        // NCS drop mandatory statement
        description
          "Specify a dependent route-filter name.";
      }
      leaf dependent-filter-type {
        type bgp:ncs_template_dependent-prefix-filter-type;
        // NCS drop mandatory statement
        description
          "Specify a depentent route-filter mode.";
      }
      leaf condition-filter {
        type string;
        description
          "Specify a condition route-filter name.";
      }
    }
  }

  grouping ncs_template_advertise-dependent-filter6-type {
    description
      "The advertise-dependent-filter-type configuration.";
    container advertise-dependent-filter6 {
      presence "Enable peer advertising dependent filter.";
      description
        "Configure peer advertising dependent filter.";
      leaf dependent-filter-switch {
        type bgp:ncs_template_peer-attr-enable-type;
        // NCS drop mandatory statement
        description
          "Specify a switch type.";
      }
      leaf dependent-filter6 {
        // NCS drop when statement
        type string;
        // NCS drop mandatory statement
        description
          "Specify a dependent route-filter name.";
      }
      leaf dependent-filter-type {
        // NCS drop when statement
        type bgp:ncs_template_dependent-prefix-filter-type;
        // NCS drop mandatory statement
        description
          "Specify a dependent route-filter mode.";
      }
      leaf condition-filter6 {
        // NCS drop when statement
        type string;
        description
          "Specify a condition route-filter name.";
      }
    }
    // NCS drop config false container 'advertise-dependent-filter6-state'
  }

  grouping ncs_template_advertise-dependent-filter6-group-type {
    description
      "The advertise-dependent-filter-group-type configuration.";
    container advertise-dependent-filter6 {
      presence "Enable peer group advertising dependent filter.";
      description
        "Configure peer group advertising dependent filter.";
      leaf dependent-filter6 {
        type string;
        // NCS drop mandatory statement
        description
          "Specify a dependent route-filter name.";
      }
      leaf dependent-filter-type {
        type bgp:ncs_template_dependent-prefix-filter-type;
        // NCS drop mandatory statement
        description
          "Specify a dependent route-filter mode.";
      }
      leaf condition-filter6 {
        type string;
        description
          "Specify a condition route-filter name.";
      }
    }
  }

  grouping ncs_rpc_notif_advertise-dependent-filter-type {
    description
      "The advertise-dependent-filter-type configuration.";
    container advertise-dependent-filter {
      presence "Enable peer advertising dependent filter.";
      description
        "Configure peer advertising dependent filter.";
      leaf dependent-filter-switch {
        type bgp:ncs_rpc_notif_peer-attr-enable-type;
        mandatory true;
        description
          "Specify a switch type.";
      }
      leaf dependent-filter {
        when "../dependent-filter-switch='enable'" {
          tailf:xpath-root 3;
        }
        type string;
        mandatory true;
        description
          "Specify a dependent route-filter name.";
      }
      leaf dependent-filter-type {
        when "../dependent-filter-switch='enable'" {
          tailf:xpath-root 3;
        }
        type bgp:ncs_rpc_notif_dependent-prefix-filter-type;
        mandatory true;
        description
          "Specify a dependent route-filter mode.";
      }
      leaf condition-filter {
        when "../dependent-filter-switch='enable'" {
          tailf:xpath-root 3;
        }
        type string;
        description
          "Specify a condition route-filter name.";
      }
    }
    container advertise-dependent-filter-state {
      config false;
      description
        "Peer advertising dependent filter state.";
      leaf dependent-filter {
        type string;
        description
          "Specify a dependent route-filter name.";
      }
      leaf dependent-filter-type {
        type bgp:ncs_rpc_notif_dependent-prefix-filter-type;
        description
          "Specify a dependent route-filter mode.";
      }
      leaf condition-filter {
        type string;
        description
          "Specify a condition route-filter name.";
      }
    }
  }

  grouping ncs_rpc_notif_advertise-dependent-filter-group-type {
    description
      "The advertise-dependent-filter-group-type configuration.";
    container advertise-dependent-filter {
      presence "Enable peer group advertising dependent filter.";
      description
        "Configure peer group advertising dependent filter.";
      leaf dependent-filter {
        type string;
        mandatory true;
        description
          "Specify a dependent route-filter name.";
      }
      leaf dependent-filter-type {
        type bgp:ncs_rpc_notif_dependent-prefix-filter-type;
        mandatory true;
        description
          "Specify a depentent route-filter mode.";
      }
      leaf condition-filter {
        type string;
        description
          "Specify a condition route-filter name.";
      }
    }
  }

  grouping ncs_rpc_notif_advertise-dependent-filter6-type {
    description
      "The advertise-dependent-filter-type configuration.";
    container advertise-dependent-filter6 {
      presence "Enable peer advertising dependent filter.";
      description
        "Configure peer advertising dependent filter.";
      leaf dependent-filter-switch {
        type bgp:ncs_rpc_notif_peer-attr-enable-type;
        mandatory true;
        description
          "Specify a switch type.";
      }
      leaf dependent-filter6 {
        when "../dependent-filter-switch='enable'" {
          tailf:xpath-root 3;
        }
        type string;
        mandatory true;
        description
          "Specify a dependent route-filter name.";
      }
      leaf dependent-filter-type {
        when "../dependent-filter-switch='enable'" {
          tailf:xpath-root 3;
        }
        type bgp:ncs_rpc_notif_dependent-prefix-filter-type;
        mandatory true;
        description
          "Specify a dependent route-filter mode.";
      }
      leaf condition-filter6 {
        when "../dependent-filter-switch='enable'" {
          tailf:xpath-root 3;
        }
        type string;
        description
          "Specify a condition route-filter name.";
      }
    }
    container advertise-dependent-filter6-state {
      config false;
      description
        "Peer advertising dependent filter state.";
      leaf dependent-filter6 {
        type string;
        description
          "Specify a dependent route-filter name.";
      }
      leaf dependent-filter-type {
        type bgp:ncs_rpc_notif_dependent-prefix-filter-type;
        description
          "Specify a dependent route-filter mode.";
      }
      leaf condition-filter6 {
        type string;
        description
          "Specify a condition route-filter name.";
      }
    }
  }

  grouping ncs_rpc_notif_advertise-dependent-filter6-group-type {
    description
      "The advertise-dependent-filter-group-type configuration.";
    container advertise-dependent-filter6 {
      presence "Enable peer group advertising dependent filter.";
      description
        "Configure peer group advertising dependent filter.";
      leaf dependent-filter6 {
        type string;
        mandatory true;
        description
          "Specify a dependent route-filter name.";
      }
      leaf dependent-filter-type {
        type bgp:ncs_rpc_notif_dependent-prefix-filter-type;
        mandatory true;
        description
          "Specify a dependent route-filter mode.";
      }
      leaf condition-filter6 {
        type string;
        description
          "Specify a condition route-filter name.";
      }
    }
  }

  grouping live_ncs_advertise-dependent-filter-type {
    description
      "The advertise-dependent-filter-type configuration.";
    container advertise-dependent-filter {
      presence "Enable peer advertising dependent filter.";
      description
        "Configure peer advertising dependent filter.";
      leaf dependent-filter-switch {
        type bgp:live_ncs_peer-attr-enable-type;
        // NCS drop mandatory statement
        description
          "Specify a switch type.";
      }
      leaf dependent-filter {
        // NCS drop when statement
        type leafref {
          path "/ncs:devices/ncs:device/ncs:live-status/rtp:routing-policy/rtp:ipv4-prefix-lists/rtp:ipv4-prefix-list/rtp:name" {
            tailf:xpath-root 3;
          }
        }
        // NCS drop mandatory statement
        description
          "Specify a dependent route-filter name.";
      }
      leaf dependent-filter-type {
        // NCS drop when statement
        type bgp:live_ncs_dependent-prefix-filter-type;
        // NCS drop mandatory statement
        description
          "Specify a dependent route-filter mode.";
      }
      leaf condition-filter {
        // NCS drop when statement
        type leafref {
          path "/ncs:devices/ncs:device/ncs:live-status/rtp:routing-policy/rtp:ipv4-prefix-lists/rtp:ipv4-prefix-list/rtp:name" {
            tailf:xpath-root 3;
          }
        }
        description
          "Specify a condition route-filter name.";
      }
    }
    container advertise-dependent-filter-state {
      description
        "Peer advertising dependent filter state.";
      leaf dependent-filter {
        type leafref {
          path "/ncs:devices/ncs:device/ncs:live-status/rtp:routing-policy/rtp:ipv4-prefix-lists/rtp:ipv4-prefix-list/rtp:name" {
            tailf:xpath-root 3;
          }
        }
        description
          "Specify a dependent route-filter name.";
      }
      leaf dependent-filter-type {
        type bgp:live_ncs_dependent-prefix-filter-type;
        description
          "Specify a dependent route-filter mode.";
      }
      leaf condition-filter {
        type leafref {
          path "/ncs:devices/ncs:device/ncs:live-status/rtp:routing-policy/rtp:ipv4-prefix-lists/rtp:ipv4-prefix-list/rtp:name" {
            tailf:xpath-root 3;
          }
        }
        description
          "Specify a condition route-filter name.";
      }
    }
  }

  grouping live_ncs_advertise-dependent-filter-group-type {
    description
      "The advertise-dependent-filter-group-type configuration.";
    container advertise-dependent-filter {
      presence "Enable peer group advertising dependent filter.";
      description
        "Configure peer group advertising dependent filter.";
      leaf dependent-filter {
        type leafref {
          path "/ncs:devices/ncs:device/ncs:live-status/rtp:routing-policy/rtp:ipv4-prefix-lists/rtp:ipv4-prefix-list/rtp:name" {
            tailf:xpath-root 3;
          }
        }
        // NCS drop mandatory statement
        description
          "Specify a dependent route-filter name.";
      }
      leaf dependent-filter-type {
        type bgp:live_ncs_dependent-prefix-filter-type;
        // NCS drop mandatory statement
        description
          "Specify a depentent route-filter mode.";
      }
      leaf condition-filter {
        type leafref {
          path "/ncs:devices/ncs:device/ncs:live-status/rtp:routing-policy/rtp:ipv4-prefix-lists/rtp:ipv4-prefix-list/rtp:name" {
            tailf:xpath-root 3;
          }
        }
        description
          "Specify a condition route-filter name.";
      }
    }
  }

  grouping live_ncs_advertise-dependent-filter6-type {
    description
      "The advertise-dependent-filter-type configuration.";
    container advertise-dependent-filter6 {
      presence "Enable peer advertising dependent filter.";
      description
        "Configure peer advertising dependent filter.";
      leaf dependent-filter-switch {
        type bgp:live_ncs_peer-attr-enable-type;
        // NCS drop mandatory statement
        description
          "Specify a switch type.";
      }
      leaf dependent-filter6 {
        // NCS drop when statement
        type leafref {
          path "/ncs:devices/ncs:device/ncs:live-status/rtp:routing-policy/rtp:ipv6-prefix-lists/rtp:ipv6-prefix-list/rtp:name" {
            tailf:xpath-root 3;
          }
        }
        // NCS drop mandatory statement
        description
          "Specify a dependent route-filter name.";
      }
      leaf dependent-filter-type {
        // NCS drop when statement
        type bgp:live_ncs_dependent-prefix-filter-type;
        // NCS drop mandatory statement
        description
          "Specify a dependent route-filter mode.";
      }
      leaf condition-filter6 {
        // NCS drop when statement
        type leafref {
          path "/ncs:devices/ncs:device/ncs:live-status/rtp:routing-policy/rtp:ipv6-prefix-lists/rtp:ipv6-prefix-list/rtp:name" {
            tailf:xpath-root 3;
          }
        }
        description
          "Specify a condition route-filter name.";
      }
    }
    container advertise-dependent-filter6-state {
      description
        "Peer advertising dependent filter state.";
      leaf dependent-filter6 {
        type leafref {
          path "/ncs:devices/ncs:device/ncs:live-status/rtp:routing-policy/rtp:ipv6-prefix-lists/rtp:ipv6-prefix-list/rtp:name" {
            tailf:xpath-root 3;
          }
        }
        description
          "Specify a dependent route-filter name.";
      }
      leaf dependent-filter-type {
        type bgp:live_ncs_dependent-prefix-filter-type;
        description
          "Specify a dependent route-filter mode.";
      }
      leaf condition-filter6 {
        type leafref {
          path "/ncs:devices/ncs:device/ncs:live-status/rtp:routing-policy/rtp:ipv6-prefix-lists/rtp:ipv6-prefix-list/rtp:name" {
            tailf:xpath-root 3;
          }
        }
        description
          "Specify a condition route-filter name.";
      }
    }
  }

  grouping live_ncs_advertise-dependent-filter6-group-type {
    description
      "The advertise-dependent-filter-group-type configuration.";
    container advertise-dependent-filter6 {
      presence "Enable peer group advertising dependent filter.";
      description
        "Configure peer group advertising dependent filter.";
      leaf dependent-filter6 {
        type leafref {
          path "/ncs:devices/ncs:device/ncs:live-status/rtp:routing-policy/rtp:ipv6-prefix-lists/rtp:ipv6-prefix-list/rtp:name" {
            tailf:xpath-root 3;
          }
        }
        // NCS drop mandatory statement
        description
          "Specify a dependent route-filter name.";
      }
      leaf dependent-filter-type {
        type bgp:live_ncs_dependent-prefix-filter-type;
        // NCS drop mandatory statement
        description
          "Specify a dependent route-filter mode.";
      }
      leaf condition-filter6 {
        type leafref {
          path "/ncs:devices/ncs:device/ncs:live-status/rtp:routing-policy/rtp:ipv6-prefix-lists/rtp:ipv6-prefix-list/rtp:name" {
            tailf:xpath-root 3;
          }
        }
        description
          "Specify a condition route-filter name.";
      }
    }
  }

  grouping advertise-dependent-filter-type {
    description
      "The advertise-dependent-filter-type configuration.";
    container advertise-dependent-filter {
      presence "Enable peer advertising dependent filter.";
      description
        "Configure peer advertising dependent filter.";
      leaf dependent-filter-switch {
        type bgp:peer-attr-enable-type;
        mandatory true;
        description
          "Specify a switch type.";
      }
      leaf dependent-filter {
        when "../dependent-filter-switch='enable'" {
          tailf:xpath-root 3;
        }
        type leafref {
          path "/ncs:devices/ncs:device/ncs:config/rtp:routing-policy/rtp:ipv4-prefix-lists/rtp:ipv4-prefix-list/rtp:name" {
            tailf:xpath-root 3;
          }
        }
        mandatory true;
        description
          "Specify a dependent route-filter name.";
      }
      leaf dependent-filter-type {
        when "../dependent-filter-switch='enable'" {
          tailf:xpath-root 3;
        }
        type bgp:dependent-prefix-filter-type;
        mandatory true;
        description
          "Specify a dependent route-filter mode.";
      }
      leaf condition-filter {
        when "../dependent-filter-switch='enable'" {
          tailf:xpath-root 3;
        }
        type leafref {
          path "/ncs:devices/ncs:device/ncs:config/rtp:routing-policy/rtp:ipv4-prefix-lists/rtp:ipv4-prefix-list/rtp:name" {
            tailf:xpath-root 3;
          }
        }
        description
          "Specify a condition route-filter name.";
      }
    }
    // NCS drop config false container 'advertise-dependent-filter-state'
  }

  grouping advertise-dependent-filter-group-type {
    description
      "The advertise-dependent-filter-group-type configuration.";
    container advertise-dependent-filter {
      presence "Enable peer group advertising dependent filter.";
      description
        "Configure peer group advertising dependent filter.";
      leaf dependent-filter {
        type leafref {
          path "/ncs:devices/ncs:device/ncs:config/rtp:routing-policy/rtp:ipv4-prefix-lists/rtp:ipv4-prefix-list/rtp:name" {
            tailf:xpath-root 3;
          }
        }
        mandatory true;
        description
          "Specify a dependent route-filter name.";
      }
      leaf dependent-filter-type {
        type bgp:dependent-prefix-filter-type;
        mandatory true;
        description
          "Specify a depentent route-filter mode.";
      }
      leaf condition-filter {
        type leafref {
          path "/ncs:devices/ncs:device/ncs:config/rtp:routing-policy/rtp:ipv4-prefix-lists/rtp:ipv4-prefix-list/rtp:name" {
            tailf:xpath-root 3;
          }
        }
        description
          "Specify a condition route-filter name.";
      }
    }
  }

  grouping advertise-dependent-filter6-type {
    description
      "The advertise-dependent-filter-type configuration.";
    container advertise-dependent-filter6 {
      presence "Enable peer advertising dependent filter.";
      description
        "Configure peer advertising dependent filter.";
      leaf dependent-filter-switch {
        type bgp:peer-attr-enable-type;
        mandatory true;
        description
          "Specify a switch type.";
      }
      leaf dependent-filter6 {
        when "../dependent-filter-switch='enable'" {
          tailf:xpath-root 3;
        }
        type leafref {
          path "/ncs:devices/ncs:device/ncs:config/rtp:routing-policy/rtp:ipv6-prefix-lists/rtp:ipv6-prefix-list/rtp:name" {
            tailf:xpath-root 3;
          }
        }
        mandatory true;
        description
          "Specify a dependent route-filter name.";
      }
      leaf dependent-filter-type {
        when "../dependent-filter-switch='enable'" {
          tailf:xpath-root 3;
        }
        type bgp:dependent-prefix-filter-type;
        mandatory true;
        description
          "Specify a dependent route-filter mode.";
      }
      leaf condition-filter6 {
        when "../dependent-filter-switch='enable'" {
          tailf:xpath-root 3;
        }
        type leafref {
          path "/ncs:devices/ncs:device/ncs:config/rtp:routing-policy/rtp:ipv6-prefix-lists/rtp:ipv6-prefix-list/rtp:name" {
            tailf:xpath-root 3;
          }
        }
        description
          "Specify a condition route-filter name.";
      }
    }
    // NCS drop config false container 'advertise-dependent-filter6-state'
  }

  grouping advertise-dependent-filter6-group-type {
    description
      "The advertise-dependent-filter-group-type configuration.";
    container advertise-dependent-filter6 {
      presence "Enable peer group advertising dependent filter.";
      description
        "Configure peer group advertising dependent filter.";
      leaf dependent-filter6 {
        type leafref {
          path "/ncs:devices/ncs:device/ncs:config/rtp:routing-policy/rtp:ipv6-prefix-lists/rtp:ipv6-prefix-list/rtp:name" {
            tailf:xpath-root 3;
          }
        }
        mandatory true;
        description
          "Specify a dependent route-filter name.";
      }
      leaf dependent-filter-type {
        type bgp:dependent-prefix-filter-type;
        mandatory true;
        description
          "Specify a dependent route-filter mode.";
      }
      leaf condition-filter6 {
        type leafref {
          path "/ncs:devices/ncs:device/ncs:config/rtp:routing-policy/rtp:ipv6-prefix-lists/rtp:ipv6-prefix-list/rtp:name" {
            tailf:xpath-root 3;
          }
        }
        description
          "Specify a condition route-filter name.";
      }
    }
  }
}
