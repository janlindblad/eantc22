module huawei-l2-multicast-forward {
  // Generated by yanger -t ncs
  tailf:mount-id "huawei-nc-1.0:huawei-nc-1.0";
  tailf:ncs-device-type "netconf";

  namespace "urn:huawei:yang:huawei-l2-multicast-forward";
  prefix l2-multicast-forward;

  import huawei-vlan {
    prefix vlan;
  }
  import huawei-extension {
    prefix ext;
  }
  import huawei-devm {
    prefix devm;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "L2 multicast VLAN fwroding.";

  revision 2019-07-01 {
    description
      "Init revision.";
    reference "Huawei private.";
  }
  ext:task-name "l2mc";

  typedef ncs_template_l2mc-forward-mode {
    type string;
    description
      "Forwarding mode.";
  }

  typedef ncs_template_sg-type {
    type string;
    description
      "Port type.";
  }

  typedef ncs_rpc_notif_l2mc-forward-mode {
    type enumeration {
      enum "ip" {
        value 1;
        description
          "Forwarding based on IP addresses.";
      }
      enum "mac" {
        value 2;
        description
          "Forwarding based on MAC addresses.";
      }
    }
    description
      "Forwarding mode.";
  }

  typedef ncs_rpc_notif_sg-type {
    type enumeration {
      enum "SG" {
        value 1;
        description
          "Multicast entry in which both group and source addresses are specified.";
      }
      enum "source-wildcard" {
        value 2;
        description
          "Multicast entry in which only a group address is specified.";
      }
      enum "rt-port" {
        value 3;
        description
          "Router port.";
      }
    }
    description
      "Port type.";
  }

  typedef live_ncs_l2mc-forward-mode {
    type enumeration {
      enum "ip" {
        value 1;
        description
          "Forwarding based on IP addresses.";
      }
      enum "mac" {
        value 2;
        description
          "Forwarding based on MAC addresses.";
      }
    }
    description
      "Forwarding mode.";
  }

  typedef live_ncs_sg-type {
    type enumeration {
      enum "SG" {
        value 1;
        description
          "Multicast entry in which both group and source addresses are specified.";
      }
      enum "source-wildcard" {
        value 2;
        description
          "Multicast entry in which only a group address is specified.";
      }
      enum "rt-port" {
        value 3;
        description
          "Router port.";
      }
    }
    description
      "Port type.";
  }

  typedef l2mc-forward-mode {
    type enumeration {
      enum "ip" {
        value 1;
        description
          "Forwarding based on IP addresses.";
      }
      enum "mac" {
        value 2;
        description
          "Forwarding based on MAC addresses.";
      }
    }
    description
      "Forwarding mode.";
  }

  typedef sg-type {
    type enumeration {
      enum "SG" {
        value 1;
        description
          "Multicast entry in which both group and source addresses are specified.";
      }
      enum "source-wildcard" {
        value 2;
        description
          "Multicast entry in which only a group address is specified.";
      }
      enum "rt-port" {
        value 3;
        description
          "Router port.";
      }
    }
    description
      "Port type.";
  }

  augment "/ncs:devices/ncs:device/ncs:config" {
    container l2-multicast-forward {
      tailf:ncs-device-type "netconf";
      tailf:display-when "not(../../ncs:module) or ../../ncs:module[ncs:name='huawei-l2-multicast-forward']";
      description
        "Global configuration of l2mc forward.";
      container select-boards {
        description
          "Configure boards selected for l2mc.";
        leaf-list slot {
          type leafref {
            path "/ncs:devices/ncs:device/ncs:config/devm:devm/devm:lpu-boards/devm:lpu-board/devm:position" {
              tailf:xpath-root 3;
            }
          }
          max-elements 20;
          description
            "Configure slot ID.";
        }
      }
    }
  }
  augment "/ncs:devices/ncs:device/ncs:live-status" {
    container l2-multicast-forward {
      tailf:ncs-device-type "netconf";
      tailf:display-when "not(../../ncs:module) or ../../ncs:module[ncs:name='huawei-l2-multicast-forward'] or (../../ncs:live-status-protocol[not(ncs:capability)]) or (../../ncs:live-status-protocol/ncs:capability/ncs:module[.='huawei-l2-multicast-forward'])";
      description
        "Global configuration of l2mc forward.";
      container select-boards {
        description
          "Configure boards selected for l2mc.";
        leaf-list slot {
          type leafref {
            path "/ncs:devices/ncs:device/ncs:live-status/devm:devm/devm:lpu-boards/devm:lpu-board/devm:position" {
              tailf:xpath-root 3;
            }
          }
          // NCS drop max-elements statement
          description
            "Configure slot ID.";
        }
      }
    }
  }
  augment "/ncs:devices/ncs:template/ncs:ned-id/ncs:config" {
    container l2-multicast-forward {
      description
        "Global configuration of l2mc forward.";
      container select-boards {
        description
          "Configure boards selected for l2mc.";
        leaf-list slot {
          // NCS patched for predictable order
          ordered-by user;
          type string;
          // NCS drop max-elements statement
          description
            "Configure slot ID.";
        }
      }
    }
  }
  augment "/ncs:devices/ncs:template/ncs:ned-id/ncs:config/vlan:vlan/vlan:vlans/vlan:vlan" {
    description
      "Multicast forward configuration to the VLAN module.";
    container multicast-forward {
      description
        "Configure multicast load splitting trunks in a VLAN.";
      container port-isolate-state {
        description
          "Configure the isolation of non-multicast traffic in a VLAN.";
        leaf enable {
          type string;
          // NCS drop default statement
          description
            "Enable/disable isolate non-multicast traffic.";
        }
      }
    }
  }
  augment "/ncs:devices/ncs:device/ncs:live-status/vlan:vlan/vlan:vlans/vlan:vlan" {
    description
      "Multicast forward configuration to the VLAN module.";
    container multicast-forward {
      tailf:ncs-device-type "netconf";
      tailf:display-when "not(../../../../../ncs:module) or ../../../../../ncs:module[ncs:name='huawei-l2-multicast-forward'] or (../../../../../ncs:live-status-protocol[not(ncs:capability)]) or (../../../../../ncs:live-status-protocol/ncs:capability/ncs:module[.='huawei-l2-multicast-forward'])";
      description
        "Configure multicast load splitting trunks in a VLAN.";
      container port-isolate-state {
        description
          "Configure the isolation of non-multicast traffic in a VLAN.";
        leaf enable {
          type boolean;
          // NCS drop default statement
          description
            "Enable/disable isolate non-multicast traffic.";
        }
      }
    }
  }
  augment "/ncs:devices/ncs:device/ncs:config/vlan:vlan/vlan:vlans/vlan:vlan" {
    description
      "Multicast forward configuration to the VLAN module.";
    container multicast-forward {
      tailf:ncs-device-type "netconf";
      tailf:display-when "not(../../../../../ncs:module) or ../../../../../ncs:module[ncs:name='huawei-l2-multicast-forward']";
      description
        "Configure multicast load splitting trunks in a VLAN.";
      container port-isolate-state {
        description
          "Configure the isolation of non-multicast traffic in a VLAN.";
        leaf enable {
          type boolean;
          default "false";
          description
            "Enable/disable isolate non-multicast traffic.";
        }
      }
    }
  }
}
