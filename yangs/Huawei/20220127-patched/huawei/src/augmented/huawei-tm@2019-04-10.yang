module huawei-tm {
  // Generated by yanger -t ncs
  tailf:mount-id "huawei-nc-1.0:huawei-nc-1.0";
  tailf:ncs-device-type "netconf";

  namespace "urn:huawei:yang:huawei-tm";
  prefix tm;

  import ietf-yang-types {
    prefix yang;
  }
  import huawei-pub-type {
    prefix pub-type;
  }
  import huawei-extension {
    prefix ext;
  }
  include huawei-tm-type;
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Time management (TM) component.";

  revision 2019-04-10 {
    description
      "Init revision.";
    reference "Huawei private.";
  }
  ext:task-name "system";

  augment "/ncs:devices/ncs:device/ncs:rpc" {
    container rpc-date-time {
      tailf:ncs-device-type "netconf";
      tailf:display-when "not(../../ncs:module) or ../../ncs:module[ncs:name='huawei-tm']";
      tailf:action date-time {
        tailf:actionpoint ncsproxy {
          tailf:internal;
        }
        description
          "Date and time information.";
        input {
          leaf date-time {
            type yang:date-and-time;
            mandatory true;
            description
              "Date and time to be set.";
          }
        }
      }
    }
  }
  augment "/ncs:devices/ncs:device-group/ncs:ned-id/ncs:rpc" {
    container rpc-date-time {
      tailf:ncs-device-type "netconf";
      tailf:display-when "/ncs:devices/ncs:device[ncs:name=current()/../../../ncs:member]/ncs:module[ncs:name='huawei-tm']";
      tailf:action date-time {
        tailf:actionpoint ncsproxy {
          tailf:internal;
        }
        description
          "Date and time information.";
        input {
          leaf date-time {
            type yang:date-and-time;
            mandatory true;
            description
              "Date and time to be set.";
          }
        }
      }
    }
  }
  augment "/ncs:devices/ncs:device/ncs:config" {
    container tm {
      tailf:ncs-device-type "netconf";
      tailf:display-when "not(../../ncs:module) or ../../ncs:module[ncs:name='huawei-tm']";
      description
        "Time management (TM) component.";
      container timezone-configuration {
        description
          "Configure time zone.";
        leaf timezone-name {
          type string {
            length "1..32";
          }
          default "DefaultZoneName";
          description
            "Specify the name of a time zone. The length of string is from 1 to 32 characters.";
        }
        leaf option {
          type tm-timezone-option;
          default "add";
          description
            "Indicate whether to add or subtract the offset.";
        }
        leaf timezone-offset {
          type pub-type:time;
          default "00:00:00";
          description
            "Specify the offset between the time of the specified time zone and the UTC time. It is in the format of HH:MM:SS. HH indicates hours and its value ranges from 0 to 18. MM and SS indicate minutes and seconds and their value ranges from 0 to 59.";
        }
      }
      container dst-configuration {
        must "((type='OneYear' and start-year and start-month and start-day and start-time and end-year and end-month and end-day and end-time and dst-offset)
or(type='Repeat-date' and start-month and start-day and start-time and end-month and end-day and end-time and dst-offset)
or(type='Repeat-week' and start-month and start-weeknum and start-weekday and start-time and end-month and end-weeknum and end-weekday and end-time and dst-offset)
or not(dst-name))" {
          tailf:xpath-root 3;
        }
        description
          "Configure daylight saving time (DST). The end date must be later than the start date.
           If the type is OneYear, the start date and end date must be within one year. If the start-year and end-year are in the same year, end-month and start-month must be different.
           If the type is Repeat-date, the end-month and start-month must be different, and the dates cannot be set to February 29.
           If the type is Repeat-week, end-month and start-month must be different.
           The dst-offset must be less than the time difference between the end time and the start time.";
        leaf dst-name {
          type string {
            length "1..32";
          }
          description
            "Specify a DST name. The length of string is from 1 to 32 characters.";
        }
        leaf type {
          when '../dst-name' {
            tailf:xpath-root 3;
          }
          type tm-dst-type;
          description
            "Specify whether this setting is for one year or repeating.";
        }
        leaf start-year {
          when '../dst-name' {
            tailf:xpath-root 3;
          }
          type uint16 {
            range "2000..2037";
          }
          ext:dynamic-default {
            ext:default-value "2000" {
              when "../type='Repeat-date' or ../type='Repeat-week'" {
                tailf:xpath-root 3;
              }
              description
                "The start year default value is 2000 in repeat dst type.";
            }
          }
          description
            "Specify the daylight saving start year.";
        }
        leaf start-month {
          when '../dst-name' {
            tailf:xpath-root 3;
          }
          type tm-start-month;
          description
            "Specify the daylight saving start month.";
        }
        leaf start-day {
          when "../type='OneYear' and ../dst-name or ../type='Repeat-date' and ../dst-name" {
            tailf:xpath-root 3;
          }
          type tm-date;
          description
            "Specify the daylight saving start date. It is in the format of DD.";
        }
        leaf start-weeknum {
          when "../type='Repeat-week' and ../dst-name" {
            tailf:xpath-root 3;
          }
          type tm-weeknum;
          description
            "Specify the start week number in the specified month.";
        }
        leaf start-weekday {
          when "../type='Repeat-week' and ../dst-name" {
            tailf:xpath-root 3;
          }
          type tm-start-weekday;
          description
            "Specify the start weekday.";
        }
        leaf start-time {
          when '../dst-name' {
            tailf:xpath-root 3;
          }
          type pub-type:time-hhmm {
            pattern '(([0-1][0-9])|(2[0-3])|[0-9]):([0-5][0-9]|[0-9])';
          }
          description
            "Specify the daylight saving start time. It is in the format of HH:MM.";
        }
        leaf end-year {
          when '../dst-name' {
            tailf:xpath-root 3;
          }
          type uint16 {
            range "2000..2037";
          }
          ext:dynamic-default {
            ext:default-value "2037" {
              when "../type='Repeat-date' or ../type='Repeat-week'" {
                tailf:xpath-root 3;
              }
              description
                "The start year default value is 2037 in repeat dst type.";
            }
          }
          description
            "Specify the daylight saving end year.";
        }
        leaf end-month {
          when '../dst-name' {
            tailf:xpath-root 3;
          }
          type tm-end-month;
          description
            "Specify the daylight saving end month.";
        }
        leaf end-day {
          when "../type='OneYear' and ../dst-name or ../type='Repeat-date' and ../dst-name" {
            tailf:xpath-root 3;
          }
          type tm-date;
          description
            "Specify the daylight saving end date.";
        }
        leaf end-weeknum {
          when "../type='Repeat-week' and ../dst-name" {
            tailf:xpath-root 3;
          }
          type tm-weeknum;
          description
            "Specify the end week number in the specified month.";
        }
        leaf end-weekday {
          when "../type='Repeat-week' and ../dst-name" {
            tailf:xpath-root 3;
          }
          type tm-end-weekday;
          description
            "Specify the end weekday.";
        }
        leaf end-time {
          when '../dst-name' {
            tailf:xpath-root 3;
          }
          type pub-type:time-hhmm {
            pattern '(([0-1][0-9])|(2[0-3])|[0-9]):([0-5][0-9]|[0-9])';
          }
          description
            "Specify the daylight saving end time.";
        }
        leaf dst-offset {
          when '../dst-name' {
            tailf:xpath-root 3;
          }
          type pub-type:time-hhmm {
            pattern '(([0-1][0-9])|(2[0-3])|[0-9]):([0-5][0-9]|[0-9])';
          }
          description
            "Specify the time added to the summer time.";
        }
      }
      // NCS drop config false container 'date-and-time'
    }
  }
  augment "/ncs:devices/ncs:device/ncs:live-status" {
    container tm {
      tailf:ncs-device-type "netconf";
      tailf:display-when "not(../../ncs:module) or ../../ncs:module[ncs:name='huawei-tm'] or (../../ncs:live-status-protocol[not(ncs:capability)]) or (../../ncs:live-status-protocol/ncs:capability/ncs:module[.='huawei-tm'])";
      description
        "Time management (TM) component.";
      container timezone-configuration {
        description
          "Configure time zone.";
        leaf timezone-name {
          type string {
            length "1..32";
          }
          // NCS drop default statement
          description
            "Specify the name of a time zone. The length of string is from 1 to 32 characters.";
        }
        leaf option {
          type live_ncs_tm-timezone-option;
          // NCS drop default statement
          description
            "Indicate whether to add or subtract the offset.";
        }
        leaf timezone-offset {
          type pub-type:live_ncs_time;
          // NCS drop default statement
          description
            "Specify the offset between the time of the specified time zone and the UTC time. It is in the format of HH:MM:SS. HH indicates hours and its value ranges from 0 to 18. MM and SS indicate minutes and seconds and their value ranges from 0 to 59.";
        }
      }
      container dst-configuration {
        // NCS drop must statement
        description
          "Configure daylight saving time (DST). The end date must be later than the start date.
           If the type is OneYear, the start date and end date must be within one year. If the start-year and end-year are in the same year, end-month and start-month must be different.
           If the type is Repeat-date, the end-month and start-month must be different, and the dates cannot be set to February 29.
           If the type is Repeat-week, end-month and start-month must be different.
           The dst-offset must be less than the time difference between the end time and the start time.";
        leaf dst-name {
          type string {
            length "1..32";
          }
          description
            "Specify a DST name. The length of string is from 1 to 32 characters.";
        }
        leaf type {
          // NCS drop when statement
          type live_ncs_tm-dst-type;
          description
            "Specify whether this setting is for one year or repeating.";
        }
        leaf start-year {
          // NCS drop when statement
          type uint16 {
            range "2000..2037";
          }
          ext:dynamic-default {
            ext:default-value "2000" {
              // NCS drop when statement
              description
                "The start year default value is 2000 in repeat dst type.";
            }
          }
          description
            "Specify the daylight saving start year.";
        }
        leaf start-month {
          // NCS drop when statement
          type live_ncs_tm-start-month;
          description
            "Specify the daylight saving start month.";
        }
        leaf start-day {
          // NCS drop when statement
          type live_ncs_tm-date;
          description
            "Specify the daylight saving start date. It is in the format of DD.";
        }
        leaf start-weeknum {
          // NCS drop when statement
          type live_ncs_tm-weeknum;
          description
            "Specify the start week number in the specified month.";
        }
        leaf start-weekday {
          // NCS drop when statement
          type live_ncs_tm-start-weekday;
          description
            "Specify the start weekday.";
        }
        leaf start-time {
          // NCS drop when statement
          type pub-type:live_ncs_time-hhmm;
          description
            "Specify the daylight saving start time. It is in the format of HH:MM.";
        }
        leaf end-year {
          // NCS drop when statement
          type uint16 {
            range "2000..2037";
          }
          ext:dynamic-default {
            ext:default-value "2037" {
              // NCS drop when statement
              description
                "The start year default value is 2037 in repeat dst type.";
            }
          }
          description
            "Specify the daylight saving end year.";
        }
        leaf end-month {
          // NCS drop when statement
          type live_ncs_tm-end-month;
          description
            "Specify the daylight saving end month.";
        }
        leaf end-day {
          // NCS drop when statement
          type live_ncs_tm-date;
          description
            "Specify the daylight saving end date.";
        }
        leaf end-weeknum {
          // NCS drop when statement
          type live_ncs_tm-weeknum;
          description
            "Specify the end week number in the specified month.";
        }
        leaf end-weekday {
          // NCS drop when statement
          type live_ncs_tm-end-weekday;
          description
            "Specify the end weekday.";
        }
        leaf end-time {
          // NCS drop when statement
          type pub-type:live_ncs_time-hhmm;
          description
            "Specify the daylight saving end time.";
        }
        leaf dst-offset {
          // NCS drop when statement
          type pub-type:live_ncs_time-hhmm;
          description
            "Specify the time added to the summer time.";
        }
      }
      container date-and-time {
        description
          "Statistics of date and time.";
        leaf current-time {
          type yang:date-and-time;
          description
            "Specify the current date and time.";
        }
        leaf weekday {
          type live_ncs_tm-day-week;
          description
            "Specify the day of a week.";
        }
      }
    }
  }
  augment "/ncs:devices/ncs:template/ncs:ned-id/ncs:config" {
    container tm {
      description
        "Time management (TM) component.";
      container timezone-configuration {
        description
          "Configure time zone.";
        leaf timezone-name {
          type string;
          // NCS drop default statement
          description
            "Specify the name of a time zone. The length of string is from 1 to 32 characters.";
        }
        leaf option {
          type ncs_template_tm-timezone-option;
          // NCS drop default statement
          description
            "Indicate whether to add or subtract the offset.";
        }
        leaf timezone-offset {
          type pub-type:ncs_template_time;
          // NCS drop default statement
          description
            "Specify the offset between the time of the specified time zone and the UTC time. It is in the format of HH:MM:SS. HH indicates hours and its value ranges from 0 to 18. MM and SS indicate minutes and seconds and their value ranges from 0 to 59.";
        }
      }
      container dst-configuration {
        // NCS drop must statement
        description
          "Configure daylight saving time (DST). The end date must be later than the start date.
           If the type is OneYear, the start date and end date must be within one year. If the start-year and end-year are in the same year, end-month and start-month must be different.
           If the type is Repeat-date, the end-month and start-month must be different, and the dates cannot be set to February 29.
           If the type is Repeat-week, end-month and start-month must be different.
           The dst-offset must be less than the time difference between the end time and the start time.";
        leaf dst-name {
          type string;
          description
            "Specify a DST name. The length of string is from 1 to 32 characters.";
        }
        leaf type {
          // NCS drop when statement
          type ncs_template_tm-dst-type;
          description
            "Specify whether this setting is for one year or repeating.";
        }
        leaf start-year {
          // NCS drop when statement
          type string;
          ext:dynamic-default {
            ext:default-value "2000" {
              // NCS drop when statement
              description
                "The start year default value is 2000 in repeat dst type.";
            }
          }
          description
            "Specify the daylight saving start year.";
        }
        leaf start-month {
          // NCS drop when statement
          type ncs_template_tm-start-month;
          description
            "Specify the daylight saving start month.";
        }
        leaf start-day {
          // NCS drop when statement
          type ncs_template_tm-date;
          description
            "Specify the daylight saving start date. It is in the format of DD.";
        }
        leaf start-weeknum {
          // NCS drop when statement
          type ncs_template_tm-weeknum;
          description
            "Specify the start week number in the specified month.";
        }
        leaf start-weekday {
          // NCS drop when statement
          type ncs_template_tm-start-weekday;
          description
            "Specify the start weekday.";
        }
        leaf start-time {
          // NCS drop when statement
          type pub-type:ncs_template_time-hhmm;
          description
            "Specify the daylight saving start time. It is in the format of HH:MM.";
        }
        leaf end-year {
          // NCS drop when statement
          type string;
          ext:dynamic-default {
            ext:default-value "2037" {
              // NCS drop when statement
              description
                "The start year default value is 2037 in repeat dst type.";
            }
          }
          description
            "Specify the daylight saving end year.";
        }
        leaf end-month {
          // NCS drop when statement
          type ncs_template_tm-end-month;
          description
            "Specify the daylight saving end month.";
        }
        leaf end-day {
          // NCS drop when statement
          type ncs_template_tm-date;
          description
            "Specify the daylight saving end date.";
        }
        leaf end-weeknum {
          // NCS drop when statement
          type ncs_template_tm-weeknum;
          description
            "Specify the end week number in the specified month.";
        }
        leaf end-weekday {
          // NCS drop when statement
          type ncs_template_tm-end-weekday;
          description
            "Specify the end weekday.";
        }
        leaf end-time {
          // NCS drop when statement
          type pub-type:ncs_template_time-hhmm;
          description
            "Specify the daylight saving end time.";
        }
        leaf dst-offset {
          // NCS drop when statement
          type pub-type:ncs_template_time-hhmm;
          description
            "Specify the time added to the summer time.";
        }
      }
      // NCS drop config false container 'date-and-time'
    }
  }
}
