module huawei-nc {
  yang-version 1.1;
  namespace "http://tail-f.com/ns/ned-id/huawei-nc";
  prefix huawei-nc;

  import tailf-common {
    prefix tailf;
  }

  import tailf-ncs-ned {
    prefix ned;
  }

  identity huawei-nc {
    tailf:abstract;
    base ned:netconf-ned-id;
  }
}
