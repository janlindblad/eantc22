/*
Copyright (C) 2019-2021 Huawei Technologies Co., Ltd. All rights reserved.
*/
module huawei-bgp-notification {
  yang-version 1;
  namespace "urn:huawei:yang:huawei-bgp-notification";
  prefix bgp-notification;
  import ietf-inet-types {
    prefix inet;
  }
  import huawei-extension {
    prefix ext;
  }
  organization
    "Huawei Technologies Co., Ltd.";
  contact
    "Huawei Industrial Base
    Bantian, Longgang
    Shenzhen 518129
    People's Republic of China
    Website: http://www.huawei.com
    Email: support@huawei.com";
  description
    "Notification of bgp-notification.";
  revision 2021-03-27 {
    description
      "A field was added to BGP peer state change alarms.";
    reference
      "Huawei private.";
  }
  revision 2020-05-16 {
    description
      "Modify alarm's name for peer route base on address family.";
    reference
      "Huawei private.";
  }
  revision 2020-04-17 {
    description
      "Add alarm for peer route base on address family.";
    reference
      "Huawei private.";
  }
  revision 2019-03-22 {
    description
      "Initial revision.";
    reference
      "Huawei private.";
  }
  ext:task-name  "bgp";
  typedef addr-family-type {
    type enumeration {
      enum "unspecified" {
        value 0;
        description
          "Not specified value.";
      }
      enum "ipv4" {
        value 1;
        description
          "IPv4 address family.";
      }
      enum "ipv6" {
        value 2;
        description
          "IPv6 address family.";
      }
      enum "l2vpnad" {
        value 25;
        description
          "L2VPNAD address family.";
      }
      enum "l2vpn" {
        value 196;
        description
          "L2VPN address family.";
      }
      enum "ls" {
        value 16388;
        description
          "Link-state address family.";
      }
      enum "rpd" {
        value 36879;
        description
          "RPD address family.";
      }
    }
    description
      "The type of address family.";
  }
  typedef sub-addr-family-type {
    type enumeration {
      enum "unspecified" {
        value 0;
        description
          "Not specified value.";
      }
      enum "unicast" {
        value 1;
        description
          "Unicast subsequent address family.";
      }
      enum "multicast" {
        value 2;
        description
          "Multicast subsequent address family.";
      }
      enum "unicast-multicast" {
        value 3;
        description
          "Unicast & Multicast subsequent address family.";
      }
      enum "mpls" {
        value 4;
        description
          "MPLS subsequent address family.";
      }
      enum "mvpn" {
        value 5;
        description
          "MVPN subsequent address family.";
      }
      enum "l2vpnad" {
        value 65;
        description
          "L2VPNAD subsequent address family.";
      }
      enum "mdt" {
        value 66;
        description
          "Link-state subsequent address family.";
      }
      enum "evpn" {
        value 70;
        description
          "EVPN subsequent address family.";
      }
      enum "ls" {
        value 71;
        description
          "Link-state subsequent address family.";
      }
      enum "srpolicy" {
        value 73;
        description
          "BGP SRPOLICY subsequent address family.";
      }
      enum "sd-wan" {
        value 74;
        description
          "SD-WAN subsequent address family.";
      }
      enum "vpnv4" {
        value 128;
        description
          "Vpnv4 subsequent address family.";
      }
      enum "vpnv4-multicast" {
        value 129;
        description
          "VPNV4 Multicast subsequent address family.";
      }
      enum "vt" {
        value 132;
        description
          "VPN ORF subsequent address family.";
      }
      enum "flowv4" {
        value 133;
        description
          "Flowv4 subsequent address family.";
      }
      enum "flow-vpn" {
        value 134;
        description
          "FLOWVPN subsequent address family.";
      }
      enum "rpd" {
        value 179;
        description
          "RPD subsequent address family.";
      }
    }
    description
      "The type of subsequent address family.";
  }
  typedef ip-address-type {
    type enumeration {
      enum "unknown" {
        value 0;
        description
          "Unknown IP address type.";
      }
      enum "ipv4" {
        value 1;
        description
          "IPv4 address type.";
      }
      enum "ipv6" {
        value 2;
        description
          "IPv6 address type.";
      }
    }
    description
      "The type of IP address.";
  }
  typedef notification-peer-state-type {
    type enumeration {
      enum "idle" {
        value 1;
        description
          "Idle state.";
      }
      enum "connect" {
        value 2;
        description
          "Connecting state.";
      }
      enum "active" {
        value 3;
        description
          "Active state.";
      }
      enum "opensent" {
        value 4;
        description
          "OpenSent state.";
      }
      enum "openconfirm" {
        value 5;
        description
          "OpenConfirm state.";
      }
      enum "established" {
        value 6;
        description
          "Established state.";
      }
      enum "idle-admin" {
        value 7;
        description
          "Idle (Admin) state.";
      }
      enum "idle-ovlmt" {
        value 8;
        description
          "Idle (Ovlmt) state.";
      }
      enum "no-neg" {
        value 9;
        description
          "No neg state.";
      }
    }
    description
      "The state of peer.";
  }
  notification established {
    description
      "The BGP FSM enters the Established state.";
    leaf peer-ipv4-addr {
      type inet:ipv4-address-no-zone;
      description
        "Peer address.";
    }
    leaf peer-last-error {
      type string {
        length "0..100";
      }
      description
        "Value of the Error Code field in the Notification packet generated when the peer relationship is interrupted last time. The value is expressed in the format of [ErrorCode][ErrorSubCode]. [ErrorCode] refers to the error code and [ErrorSubCode] refers to the error subcode. Take the integer 35 as an example, figure 3 is the error code and figure 5 is the error subcode. For detailed information about the error code, refer to BGP Error Code. If the value is 0, it indicates that no error occurs.";
    }
    leaf peer-state {
      type uint32;
      description
        "Status of the BGP peer relationship.";
    }
    leaf instance-id {
      type string {
        length "1..31";
      }
      description
        "Instance ID.";
    }
    leaf addr-family-afi {
      type uint32;
      description
        "Address family.";
    }
    leaf addr-family-safi {
      type uint32;
      description
        "Sub address family.";
    }
    leaf peer-addr-type {
      type uint32;
      description
        "Peer address type.";
    }
    leaf peer-ipv4-ipv6-addr {
      type inet:ip-address-no-zone;
      description
        "Peer address.";
    }
    leaf reason {
      type string {
        length "0..100";
      }
      description
        "Reason why the peer relationship is interrupted. - Configuration lead peer down: The configuration causes the peer disconnection. - Receive notification: Notification packets are received. - Receive error packet: Error packets are received. - Hold timer expire: The Hold timer expires. - Remote peer not reachable: The remote peer is unreachable. - Direct connect-interface down: The directly connected interface is Down. - Route limit: The number of routes exceeds the upper limit.";
    }
    leaf local-if-index {
      type uint32;
      description
        "Local interface index.";
    }
    leaf local-if-name {
      type string {
        length "1..63";
      }
      description
        "Local interface name.";
    }
    leaf description {
      type string {
        length "0..255";
      }
      description
        "Peer description.";
    }
  }
  notification backward {
    description
      "The BGP FSM moves from a higher numbered state to a lower numbered state.";
    leaf peer-ipv4-addr {
      type inet:ipv4-address-no-zone;
      description
        "Peer address.";
    }
    leaf peer-last-error {
      type string {
        length "0..100";
      }
      description
        "Value of the Error Code field in the Notification packet generated when the peer relationship is interrupted last time. The value is expressed in the format of [ErrorCode][ErrorSubCode]. [ErrorCode] refers to the error code and [ErrorSubCode] refers to the error subcode. Take the integer 35 as an example, figure 3 is the error code and figure 5 is the error subcode. For detailed information about the error code, refer to BGP Error Code. If the value is 0, it indicates that no error occurs.";
    }
    leaf peer-state {
      type uint32;
      description
        "Status of the BGP peer relationship.";
    }
    leaf instance-id {
      type string {
        length "1..31";
      }
      description
        "Instance ID.";
    }
    leaf addr-family-afi {
      type uint32;
      description
        "Address family.";
    }
    leaf addr-family-safi {
      type uint32;
      description
        "Sub address family.";
    }
    leaf peer-addr-type {
      type uint32;
      description
        "Peer address type.";
    }
    leaf peer-ipv4-ipv6-addr {
      type inet:ip-address-no-zone;
      description
        "Peer address.";
    }
    leaf reason {
      type string {
        length "0..100";
      }
      description
        "Reason why the peer relationship is interrupted. - Configuration lead peer down: The configuration causes the peer disconnection. - Receive notification: Notification packets are received. - Receive error packet: Error packets are received. - Hold timer expire: The Hold timer expires. - Remote peer not reachable: The remote peer is unreachable. - Direct connect-interface down: The directly connected interface is Down. - Route limit: The number of routes exceeds the upper limit.";
    }
    leaf local-if-index {
      type uint32;
      description
        "Local interface index.";
    }
    leaf local-if-name {
      type string {
        length "1..63";
      }
      description
        "Local interface name.";
    }
    leaf description {
      type string {
        length "0..255";
      }
      description
        "Peer description.";
    }
  }
  notification peer-established {
    description
      "The BGP FSM enters the Established state.";
    leaf instance-id {
      type uint32;
      description
        "Instance ID.";
    }
    leaf addr-family-afi {
      type addr-family-type;
      description
        "Address family.";
    }
    leaf addr-family-safi {
      type sub-addr-family-type;
      description
        "Sub address family.";
    }
    leaf peer-addr-type {
      type ip-address-type;
      description
        "Peer address type.";
    }
    leaf peer-ipv4-ipv6-addr {
      type inet:ip-address-no-zone;
      description
        "Peer address.";
    }
    leaf peer-last-error {
      type string {
        length "0..100";
      }
      description
        "Value of the Error Code field in the Notification packet generated when the peer relationship is interrupted last time. The value is expressed in the format of [ErrorCode][ErrorSubCode]. [ErrorCode] refers to the error code and [ErrorSubCode] refers to the error subcode. Take the integer 35 as an example, figure 3 is the error code and figure 5 is the error subcode. For detailed information about the error code, refer to BGP Error Code. If the value is 0, it indicates that no error occurs.";
    }
    leaf peer-state {
      type notification-peer-state-type;
      description
        "Status of the BGP peer relationship.";
    }
    leaf reason {
      type string {
        length "0..100";
      }
      description
        "Reason why the peer relationship is interrupted. - Configuration lead peer down: The configuration causes the peer disconnection. - Receive notification: Notification packets are received. - Receive error packet: Error packets are received. - Hold timer expire: The Hold timer expires. - Remote peer not reachable: The remote peer is unreachable. - Direct connect-interface down: The directly connected interface is Down. - Route limit: The number of routes exceeds the upper limit.";
    }
    leaf local-if-index {
      type uint32;
      description
        "Local interface index.";
    }
    leaf local-if-name {
      type string {
        length "1..63";
      }
      description
        "Local interface name.";
    }
    leaf description {
      type string {
        length "0..255";
      }
      description
        "Peer description.";
    }
  }
  notification peer-backward {
    description
      "The BGP FSM moves from a higher numbered state to a lower numbered state.";
    leaf instance-id {
      type uint32;
      description
        "Instance ID.";
    }
    leaf addr-family-afi {
      type addr-family-type;
      description
        "Address family.";
    }
    leaf addr-family-safi {
      type sub-addr-family-type;
      description
        "Sub address family.";
    }
    leaf peer-addr-type {
      type ip-address-type;
      description
        "Peer address type.";
    }
    leaf peer-ipv4-ipv6-addr {
      type inet:ip-address-no-zone;
      description
        "Peer address.";
    }
    leaf peer-last-error {
      type string {
        length "0..100";
      }
      description
        "Value of the Error Code field in the Notification packet generated when the peer relationship is interrupted last time. The value is expressed in the format of [ErrorCode][ErrorSubCode]. [ErrorCode] refers to the error code and [ErrorSubCode] refers to the error subcode. Take the integer 35 as an example, figure 3 is the error code and figure 5 is the error subcode. For detailed information about the error code, refer to BGP Error Code. If the value is 0, it indicates that no error occurs.";
    }
    leaf peer-state {
      type notification-peer-state-type;
      description
        "Status of the BGP peer relationship.";
    }
    leaf reason {
      type string {
        length "0..100";
      }
      description
        "Reason why the peer relationship is interrupted. - Configuration lead peer down: The configuration causes the peer disconnection. - Receive notification: Notification packets are received. - Receive error packet: Error packets are received. - Hold timer expire: The Hold timer expires. - Remote peer not reachable: The remote peer is unreachable. - Direct connect-interface down: The directly connected interface is Down. - Route limit: The number of routes exceeds the upper limit.";
    }
    leaf local-if-index {
      type uint32;
      description
        "Local interface index.";
    }
    leaf local-if-name {
      type string {
        length "1..63";
      }
      description
        "Local interface name.";
    }
    leaf description {
      type string {
        length "0..255";
      }
      description
        "Peer description.";
    }
  }
  notification bgp-peer-af-route-exceed {
    description
      "The number of routes received from peers in a BGP address family reached the maximum value.";
    leaf address-family {
      type string {
        length "1..63";
      }
      description
        "Address family.";
    }
    leaf route-limit-num {
      type uint32;
      description
        "The maximum route number.";
    }
    leaf instance-name {
      type string {
        length "1..63";
      }
      description
        'BGP instance name: The value "-" indicates the default BGP instance, whereas the other values indicate BGP multi-instances.';
    }
  }
  notification bgp-peer-af-route-exceed-clear {
    description
      "The number of routes received from peers in a BGP address family fell below the maximum value.";
    leaf address-family {
      type string {
        length "1..63";
      }
      description
        "Address family.";
    }
    leaf route-limit-num {
      type uint32;
      description
        "The maximum route number.";
    }
    leaf instance-name {
      type string {
        length "1..63";
      }
      description
        'BGP instance name: The value "-" indicates the default BGP instance, whereas the other values indicate BGP multi-instances.';
    }
  }
  notification bgp-peer-af-route-threshold-exceed {
    description
      "The number of routes received from peers in a BGP address family reached the alarm threshold.";
    leaf address-family {
      type string {
        length "1..63";
      }
      description
        "Address family.";
    }
    leaf route-limit-num {
      type uint32;
      description
        "The maximum route number.";
    }
    leaf route-limit-threshold {
      type uint32;
      description
        "Alarm threshold.";
    }
    leaf instance-name {
      type string {
        length "1..63";
      }
      description
        'BGP instance name: The value "-" indicates the default BGP instance, whereas the other values indicate BGP multi-instances.';
    }
  }
  notification bgp-peer-af-route-threshold-exceed-clear {
    description
      "The number of routes received from peers in a BGP address family fell below the alarm threshold.";
    leaf address-family {
      type string {
        length "1..63";
      }
      description
        "Address family.";
    }
    leaf route-limit-num {
      type uint32;
      description
        "The maximum route number.";
    }
    leaf route-limit-threshold {
      type uint32;
      description
        "Alarm threshold.";
    }
    leaf instance-name {
      type string {
        length "1..63";
      }
      description
        'BGP instance name: The value "-" indicates the default BGP instance, whereas the other values indicate BGP multi-instances.';
    }
  }
  notification bgp-peer-af-per-route-threshold-exceed {
    description
      "The number of specified routes received from peers in a BGP address family reached the alarm threshold.";
    leaf address-family {
      type string {
        length "1..63";
      }
      description
        "Address family.";
    }
    leaf route-type {
      type string {
        length "1..63";
      }
      description
        "Route type.";
    }
    leaf route-limit-num {
      type uint32;
      description
        "The maximum route number.";
    }
    leaf route-limit-threshold {
      type uint32;
      description
        "Alarm threshold.";
    }
    leaf instance-name {
      type string {
        length "1..63";
      }
      description
        'BGP instance name: The value "-" indicates the default BGP instance, whereas the other values indicate BGP multi-instances.';
    }
  }
  notification bgp-peer-af-per-route-threshold-exceed-clear {
    description
      "The number of specified routes received from peers in a BGP address family fell below the alarm threshold.";
    leaf address-family {
      type string {
        length "1..63";
      }
      description
        "Address family.";
    }
    leaf route-type {
      type string {
        length "1..63";
      }
      description
        "Route type.";
    }
    leaf route-limit-num {
      type uint32;
      description
        "The maximum route number.";
    }
    leaf route-limit-threshold {
      type uint32;
      description
        "Alarm threshold.";
    }
    leaf instance-name {
      type string {
        length "1..63";
      }
      description
        'BGP instance name: The value "-" indicates the default BGP instance, whereas the other values indicate BGP multi-instances.';
    }
  }
  notification bgp-peer-af-per-route-exceed {
    description
      "The number of specified routes received from peers in a BGP address family reached the maximum value.";
    leaf address-family {
      type string {
        length "1..63";
      }
      description
        "Address family.";
    }
    leaf route-type {
      type string {
        length "1..63";
      }
      description
        "Route type.";
    }
    leaf route-limit-num {
      type uint32;
      description
        "The maximum route number.";
    }
    leaf instance-name {
      type string {
        length "1..63";
      }
      description
        'BGP instance name: The value "-" indicates the default BGP instance, whereas the other values indicate BGP multi-instances.';
    }
  }
  notification bgp-peer-af-per-route-exceed-clear {
    description
      "The number of specified routes received from peers in a BGP address family fell below the maximum value.";
    leaf address-family {
      type string {
        length "1..63";
      }
      description
        "Address family.";
    }
    leaf route-type {
      type string {
        length "1..63";
      }
      description
        "Route type.";
    }
    leaf route-limit-num {
      type uint32;
      description
        "The maximum route number.";
    }
    leaf instance-name {
      type string {
        length "1..63";
      }
      description
        'BGP instance name: The value "-" indicates the default BGP instance, whereas the other values indicate BGP multi-instances.';
    }
  }
  notification bgp-discard-received-route {
    description
      "BGP discards the received routes.";
    leaf instance-name {
      type string {
        length "1..63";
      }
      description
        'BGP instance name: The value "-" indicates the default BGP instance, whereas the other values indicate BGP multi-instances.';
    }
    leaf addr-family-afi {
      type addr-family-type;
      description
        "Address family.";
    }
    leaf addr-family-safi {
      type sub-addr-family-type;
      description
        "Sub-address family.";
    }
    leaf discard-reason {
      type string {
        length "1..63";
      }
      description
        "Discard reason.";
    }
  }
  notification bgp-discard-received-route-clear {
    description
      "BGP resume to process received routes.";
    leaf instance-name {
      type string {
        length "1..63";
      }
      description
        'BGP instance name: The value "-" indicates the default BGP instance, whereas the other values indicate BGP multi-instances.';
    }
    leaf addr-family-afi {
      type addr-family-type;
      description
        "Address family.";
    }
    leaf addr-family-safi {
      type sub-addr-family-type;
      description
        "Sub-address family.";
    }
    leaf discard-reason {
      type string {
        length "1..63";
      }
      description
        "Discard reason.";
    }
  }
}
