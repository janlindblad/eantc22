/*
Copyright (C) 2019 Huawei Technologies Co., Ltd. All rights reserved.
*/
module huawei-openconfig-mpls-types-ext {
  namespace "urn:huawei:yang:huawei-openconfig-mpls-types-ext";
  prefix "hw-oc-mplst-ext";
  import openconfig-mpls-types {
    prefix "oc-mplst";
  }
  import huawei-extension {
    prefix ext;
  }
  organization
    "Huawei Technologies Co., Ltd.";
  contact
    "Huawei Industrial Base
     Bantian, Longgang
     Shenzhen 518129
     People's Republic of China
     Website: http://www.huawei.com
     Email: support@huawei.com
     ";
  description
    "GRPC.";
  revision 2019-03-01 {
    description
      "Initial revision.";
    reference
      "Huawei private.";
  }
  ext:task-name "mpls-base";
  identity NONNULL {
    base oc-mplst:NULL_LABEL_TYPE;
    description "Non-null label is used.";
  }
}
