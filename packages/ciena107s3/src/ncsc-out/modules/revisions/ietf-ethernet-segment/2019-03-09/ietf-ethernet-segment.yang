module ietf-ethernet-segment {
  // Generated by yanger -t ncs
  tailf:mount-id "ciena107s3-nc-1.0:ciena107s3-nc-1.0";
  tailf:ncs-device-type "netconf";

  namespace "urn:ietf:params:xml:ns:yang:ietf-ethernet-segment";
  prefix es;

  import ietf-yang-types {
    prefix yang;
  }
  import ietf-inet-types {
    prefix inet;
  }
  import ietf-routing-types {
    prefix rt-types;
  }
  import ietf-interfaces {
    prefix if;
  }
  import ietf-pseudowires {
    prefix pw;
  }
  import tailf-common {
    prefix tailf;
  }
  import tailf-ncs {
    prefix ncs;
  }

  organization
    "ietf";
  contact
    "ietf";
  description
    "ethernet segment";

  revision 2019-03-09 {
    description
      " - Create an ethernet-segment type and change references    to ethernet-segment-identifier  - Updated Route-target lists to rt-types:vpn-route-targets ";
    reference "";
  }
  revision 2018-02-20 {
    description
      " - Change the type of attachment circuit to    if:interface-ref ";
    reference "";
  }
  revision 2017-10-21 {
    description
      " - Updated ethernet segment's AC/PW members to    accommodate more than one AC or more than one    PW  - Added the new preference based DF election    method  - Referenced pseudowires in the new    ietf-pseudowires.yang model  - Moved model to NMDA style specified in    draft-dsdt-nmda-guidelines-01.txt ";
    reference "";
  }
  revision 2017-03-08 {
    description
      " - Updated to use BGP parameters from    ietf-routing-types.yang instead of from    ietf-evpn.yang  - Updated ethernet segment's AC/PW members to    accommodate more than one AC or more than one    PW  - Added the new preference based DF election    method ";
    reference "";
  }
  revision 2016-07-08 {
    description
      "   - Added the configuration option to enable or      disable per-EVI/EAD route    - Added PBB parameter backbone-src-mac    - Added operational state branch, initially      to match the configuration branch";
    reference "";
  }
  revision 2016-06-23 {
    description
      "WG document adoption";
    reference "";
  }
  revision 2015-10-15 {
    description
      "Initial revision";
    reference "";
  }

  typedef ncs_template_status-type {
    type string;
    description
      "status type";
  }

  typedef ncs_template_df-election-method-type {
    type string;
    description
      "The DF election method type";
  }

  typedef ncs_template_ethernet-segment-identifier-type {
    type string;
    description
      "10-octet Ethernet segment identifier (esi),
       ex: 00:5a:5a:5a:5a:5a:5a:5a:5a:5a";
  }

  typedef ncs_rpc_notif_status-type {
    type enumeration {
      enum "up" {
        description
          "Status is up";
      }
      enum "down" {
        description
          "Status is down";
      }
    }
    description
      "status type";
  }

  typedef ncs_rpc_notif_df-election-method-type {
    type enumeration {
      enum "default" {
        value 0;
        description
          "The default DF election method";
      }
      enum "highest-random-weight" {
        value 1;
        description
          "The highest random weight (HRW) method";
        reference "draft-mohanty-bess-evpn-df-election";
      }
      enum "preference" {
        value 2;
        description
          "The preference based method";
        reference "draft-rabadan-bess-evpn-pref-df";
      }
    }
    description
      "The DF election method type";
  }

  typedef ncs_rpc_notif_ethernet-segment-identifier-type {
    type yang:hex-string {
      length "29";
    }
    description
      "10-octet Ethernet segment identifier (esi),
       ex: 00:5a:5a:5a:5a:5a:5a:5a:5a:5a";
  }

  typedef live_ncs_status-type {
    type enumeration {
      enum "up" {
        description
          "Status is up";
      }
      enum "down" {
        description
          "Status is down";
      }
    }
    description
      "status type";
  }

  typedef live_ncs_df-election-method-type {
    type enumeration {
      enum "default" {
        value 0;
        description
          "The default DF election method";
      }
      enum "highest-random-weight" {
        value 1;
        description
          "The highest random weight (HRW) method";
        reference "draft-mohanty-bess-evpn-df-election";
      }
      enum "preference" {
        value 2;
        description
          "The preference based method";
        reference "draft-rabadan-bess-evpn-pref-df";
      }
    }
    description
      "The DF election method type";
  }

  typedef live_ncs_ethernet-segment-identifier-type {
    type yang:hex-string {
      length "29";
    }
    description
      "10-octet Ethernet segment identifier (esi),
       ex: 00:5a:5a:5a:5a:5a:5a:5a:5a:5a";
  }

  typedef status-type {
    type enumeration {
      enum "up" {
        description
          "Status is up";
      }
      enum "down" {
        description
          "Status is down";
      }
    }
    description
      "status type";
  }

  typedef df-election-method-type {
    type enumeration {
      enum "default" {
        value 0;
        description
          "The default DF election method";
      }
      enum "highest-random-weight" {
        value 1;
        description
          "The highest random weight (HRW) method";
        reference "draft-mohanty-bess-evpn-df-election";
      }
      enum "preference" {
        value 2;
        description
          "The preference based method";
        reference "draft-rabadan-bess-evpn-pref-df";
      }
    }
    description
      "The DF election method type";
  }

  typedef ethernet-segment-identifier-type {
    type yang:hex-string {
      length "29";
    }
    description
      "10-octet Ethernet segment identifier (esi),
       ex: 00:5a:5a:5a:5a:5a:5a:5a:5a:5a";
  }

  augment "/ncs:devices/ncs:device/ncs:config" {
    container ethernet-segments {
      tailf:ncs-device-type "netconf";
      tailf:display-when "not(../../ncs:module) or ../../ncs:module[ncs:name='ietf-ethernet-segment']";
      description
        "ethernet-segment";
      list ethernet-segment {
        key "name";
        leaf name {
          type string;
          description
            "Name of the ethernet segment";
        }
        // NCS drop config false leaf 'service-type'
        // NCS drop config false leaf status
        choice ac-or-pw {
          description
            "ac-or-pw";
          case ac {
            leaf-list ac {
              type if:interface-ref;
              description
                "Name of attachment circuit";
            }
          }
          case pw {
            leaf-list pw {
              type pw:pseudowire-ref;
              description
                "Reference to a pseudowire";
            }
          }
        }
        // NCS drop config false leaf 'interface-status'
        leaf ethernet-segment-identifier {
          type ethernet-segment-identifier-type;
          description
            "Ethernet segment identifier (esi)";
        }
        choice active-mode {
          mandatory true;
          description
            "Choice of active mode";
          case single-active {
            leaf single-active-mode {
              type empty;
              description
                "single-active-mode";
            }
          }
          case all-active {
            leaf all-active-mode {
              type empty;
              description
                "all-active-mode";
            }
          }
        }
        container pbb-parameters {
          tailf:display-when "not(../../../ncs:module) or boolean(/ncs:devices/ncs:device[ncs:name=current()/../../../ncs:name]/capability/feature='ethernet-segment-pbb-params')";
          description
            "PBB configuration";
          leaf backbone-src-mac {
            type yang:mac-address;
            description
              "backbone-src-mac, only if this is a PBB";
          }
        }
        container bgp-parameters {
          description
            "BGP parameters";
          container common {
            description
              "BGP parameters common to all pseudowires";
            list rd-rt {
              tailf:display-when "not(../../../../ncs:module) or boolean(/ncs:devices/ncs:device[ncs:name=current()/../../../../ncs:name]/capability/feature='ethernet-segment-bgp-params')";
              key "route-distinguisher";
              leaf route-distinguisher {
                type rt-types:route-distinguisher;
                description
                  "Route distinguisher";
              }
              uses rt-types:vpn-route-targets;
              description
                "A list of route distinguishers and corresponding VPN route targets";
            }
          }
        }
        container df-election {
          description
            "df-election";
          leaf df-election-method {
            type df-election-method-type;
            description
              "The DF election method";
          }
          leaf preference {
            when "../df-election-method = 'preference'" {
              tailf:xpath-root 3;
              description
                "The preference value is only applicable to the preference based method";
            }
            type uint16;
            description
              "The DF preference";
          }
          leaf revertive {
            when "../df-election-method = 'preference'" {
              tailf:xpath-root 3;
              description
                "The revertive value is only applicable to the preference method";
            }
            type boolean;
            default "true";
            description
              "The 'preempt' or 'revertive' behavior";
          }
          leaf election-wait-time {
            type uint32;
            description
              "election-wait-time";
          }
        }
        leaf ead-evi-route {
          type boolean;
          default "false";
          description
            "Enable (true) or disable (false) ead-evi-route";
        }
        // NCS drop config false leaf 'esi-label'
        // NCS drop config false list member
        // NCS drop config false list df
        description
          "An ethernet segment";
      }
    }
  }
  augment "/ncs:devices/ncs:device/ncs:live-status" {
    container ethernet-segments {
      tailf:ncs-device-type "netconf";
      tailf:display-when "not(../../ncs:module) or ../../ncs:module[ncs:name='ietf-ethernet-segment'] or (../../ncs:live-status-protocol[not(ncs:capability)]) or (../../ncs:live-status-protocol/ncs:capability/ncs:module[.='ietf-ethernet-segment'])";
      description
        "ethernet-segment";
      list ethernet-segment {
        key "name";
        leaf name {
          type string;
          description
            "Name of the ethernet segment";
        }
        leaf service-type {
          type string;
          description
            "service-type";
        }
        leaf status {
          type live_ncs_status-type;
          description
            "Ethernet segment status";
        }
        choice ac-or-pw {
          description
            "ac-or-pw";
          case ac {
            leaf-list ac {
              type if:live_ncs_interface-ref;
              description
                "Name of attachment circuit";
            }
          }
          case pw {
            leaf-list pw {
              type pw:live_ncs_pseudowire-ref;
              description
                "Reference to a pseudowire";
            }
          }
        }
        leaf interface-status {
          type live_ncs_status-type;
          description
            "interface status";
        }
        leaf ethernet-segment-identifier {
          type live_ncs_ethernet-segment-identifier-type;
          description
            "Ethernet segment identifier (esi)";
        }
        choice active-mode {
          // NCS drop mandatory statement
          description
            "Choice of active mode";
          case single-active {
            leaf single-active-mode {
              type empty;
              description
                "single-active-mode";
            }
          }
          case all-active {
            leaf all-active-mode {
              type empty;
              description
                "all-active-mode";
            }
          }
        }
        container pbb-parameters {
          // NCS drop if-feature statement
          description
            "PBB configuration";
          leaf backbone-src-mac {
            type yang:mac-address;
            description
              "backbone-src-mac, only if this is a PBB";
          }
        }
        container bgp-parameters {
          description
            "BGP parameters";
          container common {
            description
              "BGP parameters common to all pseudowires";
            list rd-rt {
              // NCS drop if-feature statement
              key "route-distinguisher";
              leaf route-distinguisher {
                type rt-types:live_ncs_route-distinguisher;
                description
                  "Route distinguisher";
              }
              uses rt-types:live_ncs_vpn-route-targets;
              description
                "A list of route distinguishers and corresponding VPN route targets";
            }
          }
        }
        container df-election {
          description
            "df-election";
          leaf df-election-method {
            type live_ncs_df-election-method-type;
            description
              "The DF election method";
          }
          leaf preference {
            // NCS drop when statement
            type uint16;
            description
              "The DF preference";
          }
          leaf revertive {
            // NCS drop when statement
            type boolean;
            // NCS drop default statement
            description
              "The 'preempt' or 'revertive' behavior";
          }
          leaf election-wait-time {
            type uint32;
            description
              "election-wait-time";
          }
        }
        leaf ead-evi-route {
          type boolean;
          // NCS drop default statement
          description
            "Enable (true) or disable (false) ead-evi-route";
        }
        leaf esi-label {
          type rt-types:live_ncs_mpls-label;
          description
            "esi-label";
        }
        list member {
          leaf ip-address {
            type inet:ip-address;
            description
              "ip-address";
          }
          description
            "member of the ethernet segment";
        }
        list df {
          leaf service-identifier {
            type uint32;
            description
              "service-identifier";
          }
          leaf vlan {
            type uint32;
            description
              "vlan";
          }
          leaf ip-address {
            type inet:ip-address;
            description
              "ip-address";
          }
          description
            "df of an evpn instance's vlan";
        }
        description
          "An ethernet segment";
      }
    }
  }
  augment "/ncs:devices/ncs:template/ncs:ned-id/ncs:config" {
    container ethernet-segments {
      description
        "ethernet-segment";
      list ethernet-segment {
        // NCS patched for predictable order
        ordered-by user;
        key "name";
        leaf name {
          type string;
          description
            "Name of the ethernet segment";
        }
        // NCS drop config false leaf 'service-type'
        // NCS drop config false leaf status
        choice ac-or-pw {
          description
            "ac-or-pw";
          case ac {
            leaf-list ac {
              // NCS patched for predictable order
              ordered-by user;
              type if:ncs_template_interface-ref;
              description
                "Name of attachment circuit";
            }
          }
          case pw {
            leaf-list pw {
              // NCS patched for predictable order
              ordered-by user;
              type pw:ncs_template_pseudowire-ref;
              description
                "Reference to a pseudowire";
            }
          }
        }
        // NCS drop config false leaf 'interface-status'
        leaf ethernet-segment-identifier {
          type ncs_template_ethernet-segment-identifier-type;
          description
            "Ethernet segment identifier (esi)";
        }
        choice active-mode {
          // NCS drop mandatory statement
          description
            "Choice of active mode";
          case single-active {
            leaf single-active-mode {
              type empty;
              description
                "single-active-mode";
            }
          }
          case all-active {
            leaf all-active-mode {
              type empty;
              description
                "all-active-mode";
            }
          }
        }
        container pbb-parameters {
          // NCS drop if-feature statement
          description
            "PBB configuration";
          leaf backbone-src-mac {
            type string;
            description
              "backbone-src-mac, only if this is a PBB";
          }
        }
        container bgp-parameters {
          description
            "BGP parameters";
          container common {
            description
              "BGP parameters common to all pseudowires";
            list rd-rt {
              // NCS patched for predictable order
              ordered-by user;
              // NCS drop if-feature statement
              key "route-distinguisher";
              leaf route-distinguisher {
                type rt-types:ncs_template_route-distinguisher;
                description
                  "Route distinguisher";
              }
              uses rt-types:ncs_template_vpn-route-targets;
              description
                "A list of route distinguishers and corresponding VPN route targets";
            }
          }
        }
        container df-election {
          description
            "df-election";
          leaf df-election-method {
            type ncs_template_df-election-method-type;
            description
              "The DF election method";
          }
          leaf preference {
            // NCS drop when statement
            type string;
            description
              "The DF preference";
          }
          leaf revertive {
            // NCS drop when statement
            type string;
            // NCS drop default statement
            description
              "The 'preempt' or 'revertive' behavior";
          }
          leaf election-wait-time {
            type string;
            description
              "election-wait-time";
          }
        }
        leaf ead-evi-route {
          type string;
          // NCS drop default statement
          description
            "Enable (true) or disable (false) ead-evi-route";
        }
        // NCS drop config false leaf 'esi-label'
        // NCS drop config false list member
        // NCS drop config false list df
        description
          "An ethernet segment";
      }
    }
  }

  feature ethernet-segment-pbb-params {
    description
      "Ethernet segment's PBB parameters";
  }

  feature ethernet-segment-bgp-params {
    description
      "Ethernet segment's BGP parameters";
  }
}
