module ciena-bw-calculation-mode {
  // Generated by yanger -t ncs
  tailf:mount-id "ciena107s3-nc-1.0:ciena107s3-nc-1.0";
  tailf:ncs-device-type "netconf";

  namespace "http://www.ciena.com/ns/yang/ciena-bw-calculation-mode";
  prefix ciena-bw-calculation-mode;

  import tailf-common {
    prefix tailf;
  }
  import tailf-ncs {
    prefix ncs;
  }

  organization
    "Ciena Corporation";
  contact
    "Web URL: http://www.ciena.com/
     E-mail:  yang@ciena.com
     Postal:  7035 Ridge Road
             Hanover, Maryland 21076
             U.S.A.

     Phone:   +1 800-921-1144
     Fax:     +1 410-694-5750";
  description
    "This YANG module defines the nodes for
     BW Calculation Mode.

     Copyright (c) 2017 Ciena Corporation.  All rights
     reserved.

     All information contained herein is, and remains
     the property of Ciena Corporation. Dissemination of this
     information or reproduction of this material is strictly
     forbidden unless prior written permission is obtained from
     Ciena Corporation.";

  revision 2016-12-08 {
    description
      "Initial version";
  }

  augment "/ncs:devices/ncs:device/ncs:config" {
    container bw-calculation-mode {
      tailf:ncs-device-type "netconf";
      tailf:display-when "not(../../ncs:module) or ../../ncs:module[ncs:name='ciena-bw-calculation-mode']";
      description
        "Bandwidth calculation mode for QoS (metering and shaping)";
      leaf eqos-bw-calculation-mode {
        type identityref {
          base bw-calculation-modes;
        }
        default "transport";
        description
          "Egress QoS Bandwidth calculation mode selection. (Egress Shaping)";
      }
      leaf iqos-bw-calculation-mode {
        type identityref {
          base bw-calculation-modes;
        }
        default "transport";
        description
          "Ingress QoS Bandwidth calculation mode selection. (Ingress Metering)";
      }
    }
  }
  augment "/ncs:devices/ncs:device/ncs:live-status" {
    container bw-calculation-mode {
      tailf:ncs-device-type "netconf";
      tailf:display-when "not(../../ncs:module) or ../../ncs:module[ncs:name='ciena-bw-calculation-mode'] or (../../ncs:live-status-protocol[not(ncs:capability)]) or (../../ncs:live-status-protocol/ncs:capability/ncs:module[.='ciena-bw-calculation-mode'])";
      description
        "Bandwidth calculation mode for QoS (metering and shaping)";
      leaf eqos-bw-calculation-mode {
        type identityref {
          base bw-calculation-modes;
        }
        // NCS drop default statement
        description
          "Egress QoS Bandwidth calculation mode selection. (Egress Shaping)";
      }
      leaf iqos-bw-calculation-mode {
        type identityref {
          base bw-calculation-modes;
        }
        // NCS drop default statement
        description
          "Ingress QoS Bandwidth calculation mode selection. (Ingress Metering)";
      }
    }
  }
  augment "/ncs:devices/ncs:template/ncs:ned-id/ncs:config" {
    container bw-calculation-mode {
      description
        "Bandwidth calculation mode for QoS (metering and shaping)";
      leaf eqos-bw-calculation-mode {
        type string;
        // NCS drop default statement
        description
          "Egress QoS Bandwidth calculation mode selection. (Egress Shaping)";
      }
      leaf iqos-bw-calculation-mode {
        type string;
        // NCS drop default statement
        description
          "Ingress QoS Bandwidth calculation mode selection. (Ingress Metering)";
      }
    }
  }

  identity payload {
    base bw-calculation-modes;
    description
      "Bandwidth calculation mode is payload.";
  }

  identity transport {
    base bw-calculation-modes;
    description
      "Bandwidth calculation mode is transport.";
  }

  identity bw-calculation-modes {
    description
      "Modes of bandwidth calculation.";
  }
}
