module ciena-tdm-global {
  // Generated by yanger -t ncs
  tailf:mount-id "ciena107s3-nc-1.0:ciena107s3-nc-1.0";
  tailf:ncs-device-type "netconf";

  namespace "http://www.ciena.com/ns/yang/ciena-tdm-global";
  prefix tdm-global;

  import openconfig-interfaces {
    prefix oc-if;
  }
  import tailf-common {
    prefix tailf;
  }
  import tailf-ncs {
    prefix ncs;
  }

  organization
    "Ciena Corporation";
  contact
    "Web URL: http://www.ciena.com/
     E-mail:  yang@ciena.com
     Postal:  7035 Ridge Road
     Hanover, Maryland 21076
     U.S.A.
     Phone:   +1 800-921-1144
     Fax:     +1 410-694-5750";
  description
    "This YANG module defines Ciena's data definition for the
     management of TDM interfaces.

     Copyright (c) 2019 Ciena Corporation.  All rights
     reserved.

     All information contained herein is, and remains
     the property of Ciena Corporation. Dissemination of this
     information or reproduction of this material is strictly
     forbidden unless prior written permission is obtained from
     Ciena Corporation.";

  revision 2019-10-17 {
    description
      "Initial version.";
    reference "Ciena Functional Specification.";
  }

  typedef ncs_template_interface-ref {
    type oc-if:ncs_template_base-interface-ref;
    description
      "L3 Interface reference type.";
  }

  typedef ncs_rpc_notif_interface-ref {
    type oc-if:ncs_rpc_notif_base-interface-ref;
    description
      "L3 Interface reference type.";
  }

  typedef live_ncs_interface-ref {
    type oc-if:live_ncs_base-interface-ref;
    description
      "L3 Interface reference type.";
  }

  typedef interface-ref {
    type oc-if:base-interface-ref;
    description
      "L3 Interface reference type.";
  }

  augment "/ncs:devices/ncs:device/ncs:config" {
    container tdm-global {
      tailf:ncs-device-type "netconf";
      tailf:display-when "not(../../ncs:module) or ../../ncs:module[ncs:name='ciena-tdm-global']";
      description
        "TDM global configuration data.";
      leaf mode {
        type enumeration {
          enum "ansi" {
            description
              "ANSI";
          }
          enum "etsi" {
            description
              "ETSI";
          }
        }
        default "ansi";
        description
          "Select ANSI or ETSI mode.";
      }
      leaf ctpid {
        type enumeration {
          enum "0x8100" {
            description
              "0x8100";
          }
          enum "0x88a8" {
            description
              "0x88a8";
          }
          enum "0x9100" {
            description
              "0x9100";
          }
        }
        default "0x8100";
        description
          "Default customer TPID.  This may be overridden on an individual pseudowire.";
      }
      leaf sfp-auto-upgrade {
        type boolean;
        default "true";
        description
          "Default is auto-upgrade of SFP firmware on bootup.";
      }
      leaf mgmt-interface {
        type interface-ref;
        description
          "Interface for Managing Smart SFPs.";
      }
    }
  }
  augment "/ncs:devices/ncs:device/ncs:live-status" {
    container tdm-global {
      tailf:ncs-device-type "netconf";
      tailf:display-when "not(../../ncs:module) or ../../ncs:module[ncs:name='ciena-tdm-global'] or (../../ncs:live-status-protocol[not(ncs:capability)]) or (../../ncs:live-status-protocol/ncs:capability/ncs:module[.='ciena-tdm-global'])";
      description
        "TDM global configuration data.";
      leaf mode {
        type enumeration {
          enum "ansi" {
            description
              "ANSI";
          }
          enum "etsi" {
            description
              "ETSI";
          }
        }
        // NCS drop default statement
        description
          "Select ANSI or ETSI mode.";
      }
      leaf ctpid {
        type enumeration {
          enum "0x8100" {
            description
              "0x8100";
          }
          enum "0x88a8" {
            description
              "0x88a8";
          }
          enum "0x9100" {
            description
              "0x9100";
          }
        }
        // NCS drop default statement
        description
          "Default customer TPID.  This may be overridden on an individual pseudowire.";
      }
      leaf sfp-auto-upgrade {
        type boolean;
        // NCS drop default statement
        description
          "Default is auto-upgrade of SFP firmware on bootup.";
      }
      leaf mgmt-interface {
        type live_ncs_interface-ref;
        description
          "Interface for Managing Smart SFPs.";
      }
    }
  }
  augment "/ncs:devices/ncs:template/ncs:ned-id/ncs:config" {
    container tdm-global {
      description
        "TDM global configuration data.";
      leaf mode {
        type string;
        // NCS drop default statement
        description
          "Select ANSI or ETSI mode.";
      }
      leaf ctpid {
        type string;
        // NCS drop default statement
        description
          "Default customer TPID.  This may be overridden on an individual pseudowire.";
      }
      leaf sfp-auto-upgrade {
        type string;
        // NCS drop default statement
        description
          "Default is auto-upgrade of SFP firmware on bootup.";
      }
      leaf mgmt-interface {
        type ncs_template_interface-ref;
        description
          "Interface for Managing Smart SFPs.";
      }
    }
  }
}
