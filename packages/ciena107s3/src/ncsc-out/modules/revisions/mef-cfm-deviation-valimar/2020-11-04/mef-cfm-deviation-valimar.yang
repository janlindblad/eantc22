module mef-cfm-deviation-valimar {
  // Generated by yanger -t ncs
  tailf:mount-id "ciena107s3-nc-1.0:ciena107s3-nc-1.0";
  tailf:ncs-device-type "netconf";

  namespace "urn:ciena:params:xml:ns:yang:ciena-pn:mef-cfm-dev-valimar";
  prefix mef-cfm-dev-valimar;

  import mef-cfm {
    prefix mef-cfm;
  }
  import ciena-mef-fp {
    prefix ciena-mef-fp;
  }
  import tailf-common {
    prefix tailf;
  }
  import tailf-ncs {
    prefix ncs;
  }

  revision 2020-11-04 {
    description
      "Added deviation for remote-meps";
  }
  revision 2020-05-18 {
    description
      "Added deviation for remote-mep-database  management-address";
  }
  revision 2016-02-04 {
    description
      "Initial revision.";
  }

  deviation "/ncs:devices/ncs:template/ncs:ned-id/ncs:config/mef-cfm:maintenance-domain/mef-cfm:md-level" {
    deviate add {
      // NCS drop default statement
    }
  }
  deviation "/ncs:devices/ncs:device/ncs:live-status/mef-cfm:maintenance-domain/mef-cfm:md-level" {
    deviate add {
      // NCS drop default statement
    }
  }
  deviation "/ncs:devices/ncs:device/ncs:config/mef-cfm:maintenance-domain/mef-cfm:md-level" {
    deviate add {
      default "3";
    }
  }
  deviation "/ncs:devices/ncs:template/ncs:ned-id/ncs:config/mef-cfm:default-md-levels/mef-cfm:default-md-level" {
    deviate not-supported;
  }
  deviation "/ncs:devices/ncs:device/ncs:live-status/mef-cfm:default-md-levels/mef-cfm:default-md-level" {
    deviate not-supported;
  }
  deviation "/ncs:devices/ncs:device/ncs:config/mef-cfm:default-md-levels/mef-cfm:default-md-level" {
    deviate not-supported;
  }
  deviation "/ncs:devices/ncs:device/ncs:live-status/mef-cfm:configuration-error-list" {
    deviate not-supported;
  }
  deviation "/ncs:devices/ncs:template/ncs:ned-id/ncs:config/mef-cfm:maintenance-domain/mef-cfm:name-type" {
    deviate replace {
      type string;
    }
  }
  deviation "/ncs:devices/ncs:device/ncs:live-status/mef-cfm:maintenance-domain/mef-cfm:name-type" {
    deviate replace {
      type enumeration {
        enum "none" {
          description
            "No format specified.";
        }
        enum "mac-address-and-uint" {
          description
            "MAC address + 2-octet (unsigned) integer.";
        }
        enum "character-string" {
          description
            "RFC2579 DisplayString, except that the character
             codes 0-31 (decimal) are not used.";
        }
      }
    }
  }
  deviation "/ncs:devices/ncs:device/ncs:config/mef-cfm:maintenance-domain/mef-cfm:name-type" {
    deviate replace {
      type enumeration {
        enum "none" {
          description
            "No format specified.";
        }
        enum "mac-address-and-uint" {
          description
            "MAC address + 2-octet (unsigned) integer.";
        }
        enum "character-string" {
          description
            "RFC2579 DisplayString, except that the character
             codes 0-31 (decimal) are not used.";
        }
      }
    }
  }
  deviation "/ncs:devices/ncs:template/ncs:ned-id/ncs:config/mef-cfm:maintenance-domain/mef-cfm:name" {
    deviate replace {
      type string;
    }
  }
  deviation "/ncs:devices/ncs:device/ncs:live-status/mef-cfm:maintenance-domain/mef-cfm:name" {
    deviate replace {
      type union {
        type string;
        type mef-cfm:live_ncs_mac-address-and-uint-type;
      }
    }
  }
  deviation "/ncs:devices/ncs:device/ncs:config/mef-cfm:maintenance-domain/mef-cfm:name" {
    deviate replace {
      type union {
        type string;
        type mef-cfm:mac-address-and-uint-type;
      }
    }
  }
  deviation "/ncs:devices/ncs:template/ncs:ned-id/ncs:config/mef-cfm:maintenance-domain/mef-cfm:maintenance-association/mef-cfm:component-list" {
    deviate add {
      // NCS drop min-elements statement
    }
  }
  deviation "/ncs:devices/ncs:device/ncs:live-status/mef-cfm:maintenance-domain/mef-cfm:maintenance-association/mef-cfm:component-list" {
    deviate add {
      // NCS drop min-elements statement
    }
  }
  deviation "/ncs:devices/ncs:device/ncs:config/mef-cfm:maintenance-domain/mef-cfm:maintenance-association/mef-cfm:component-list" {
    deviate add {
      min-elements 1;
    }
  }
  deviation "/ncs:devices/ncs:template/ncs:ned-id/ncs:config/mef-cfm:maintenance-domain/mef-cfm:maintenance-association/mef-cfm:component-list/mef-cfm:component-id" {
    deviate replace {
      type string;
    }
  }
  deviation "/ncs:devices/ncs:device/ncs:live-status/mef-cfm:maintenance-domain/mef-cfm:maintenance-association/mef-cfm:component-list/mef-cfm:component-id" {
    deviate replace {
      type uint32 {
        range "1";
      }
    }
  }
  deviation "/ncs:devices/ncs:device/ncs:config/mef-cfm:maintenance-domain/mef-cfm:maintenance-association/mef-cfm:component-list/mef-cfm:component-id" {
    deviate replace {
      type uint32 {
        range "1";
      }
    }
  }
  deviation "/ncs:devices/ncs:template/ncs:ned-id/ncs:config/mef-cfm:maintenance-domain/mef-cfm:maintenance-association/mef-cfm:remote-meps" {
    deviate not-supported;
  }
  deviation "/ncs:devices/ncs:device/ncs:live-status/mef-cfm:maintenance-domain/mef-cfm:maintenance-association/mef-cfm:remote-meps" {
    deviate not-supported;
  }
  deviation "/ncs:devices/ncs:device/ncs:config/mef-cfm:maintenance-domain/mef-cfm:maintenance-association/mef-cfm:remote-meps" {
    deviate not-supported;
  }
  deviation "/ncs:devices/ncs:template/ncs:ned-id/ncs:config/mef-cfm:maintenance-domain/mef-cfm:maintenance-association/mef-cfm:component-list/mef-cfm:vid" {
    deviate not-supported;
  }
  deviation "/ncs:devices/ncs:device/ncs:live-status/mef-cfm:maintenance-domain/mef-cfm:maintenance-association/mef-cfm:component-list/mef-cfm:vid" {
    deviate not-supported;
  }
  deviation "/ncs:devices/ncs:device/ncs:config/mef-cfm:maintenance-domain/mef-cfm:maintenance-association/mef-cfm:component-list/mef-cfm:vid" {
    deviate not-supported;
  }
  deviation "/ncs:devices/ncs:template/ncs:ned-id/ncs:config/mef-cfm:maintenance-domain/mef-cfm:maintenance-association/mef-cfm:name" {
    deviate replace {
      type string;
    }
  }
  deviation "/ncs:devices/ncs:device/ncs:live-status/mef-cfm:maintenance-domain/mef-cfm:maintenance-association/mef-cfm:name" {
    deviate replace {
      type union {
        type uint16;
        type binary {
          length "7";
        }
        type string;
      }
    }
  }
  deviation "/ncs:devices/ncs:device/ncs:config/mef-cfm:maintenance-domain/mef-cfm:maintenance-association/mef-cfm:name" {
    deviate replace {
      type union {
        type uint16;
        type binary {
          length "7";
        }
        type string;
      }
    }
  }
  deviation "/ncs:devices/ncs:template/ncs:ned-id/ncs:config/mef-cfm:maintenance-domain/mef-cfm:maintenance-association/mef-cfm:maintenance-association-end-point/mef-cfm:primary-vid" {
    deviate not-supported;
  }
  deviation "/ncs:devices/ncs:device/ncs:live-status/mef-cfm:maintenance-domain/mef-cfm:maintenance-association/mef-cfm:maintenance-association-end-point/mef-cfm:primary-vid" {
    deviate not-supported;
  }
  deviation "/ncs:devices/ncs:device/ncs:config/mef-cfm:maintenance-domain/mef-cfm:maintenance-association/mef-cfm:maintenance-association-end-point/mef-cfm:primary-vid" {
    deviate not-supported;
  }
  deviation "/ncs:devices/ncs:template/ncs:ned-id/ncs:config/mef-cfm:maintenance-domain/mef-cfm:maintenance-association/mef-cfm:maintenance-association-end-point/mef-cfm:interface" {
    deviate replace {
      type string;
    }
  }
  deviation "/ncs:devices/ncs:device/ncs:live-status/mef-cfm:maintenance-domain/mef-cfm:maintenance-association/mef-cfm:maintenance-association-end-point/mef-cfm:interface" {
    deviate replace {
      type leafref {
        path "/ncs:devices/ncs:device/ncs:live-status/ciena-mef-fp:fps/ciena-mef-fp:fp/ciena-mef-fp:name" {
          tailf:xpath-root 3;
        }
      }
    }
  }
  deviation "/ncs:devices/ncs:device/ncs:config/mef-cfm:maintenance-domain/mef-cfm:maintenance-association/mef-cfm:maintenance-association-end-point/mef-cfm:interface" {
    deviate replace {
      type leafref {
        path "/ncs:devices/ncs:device/ncs:config/ciena-mef-fp:fps/ciena-mef-fp:fp/ciena-mef-fp:name" {
          tailf:xpath-root 3;
        }
      }
    }
  }
  deviation "/ncs:devices/ncs:template/ncs:ned-id/ncs:config/mef-cfm:maintenance-domain/mef-cfm:maintenance-association/mef-cfm:maintenance-association-end-point/mef-cfm:continuity-check/mef-cfm:lowest-fault-priority-defect" {
    description
      "The lowest priority defect that is allowed to generate a Fault
       Alarm. If lowest-fault-priority-defect is not configured,
       defects of severity remote-invalid-ccm and higher are alarmed
       by default.";
    deviate add {
      // NCS drop default statement
    }
  }
  deviation "/ncs:devices/ncs:device/ncs:live-status/mef-cfm:maintenance-domain/mef-cfm:maintenance-association/mef-cfm:maintenance-association-end-point/mef-cfm:continuity-check/mef-cfm:lowest-fault-priority-defect" {
    description
      "The lowest priority defect that is allowed to generate a Fault
       Alarm. If lowest-fault-priority-defect is not configured,
       defects of severity remote-invalid-ccm and higher are alarmed
       by default.";
    deviate add {
      // NCS drop default statement
    }
  }
  deviation "/ncs:devices/ncs:device/ncs:config/mef-cfm:maintenance-domain/mef-cfm:maintenance-association/mef-cfm:maintenance-association-end-point/mef-cfm:continuity-check/mef-cfm:lowest-fault-priority-defect" {
    description
      "The lowest priority defect that is allowed to generate a Fault
       Alarm. If lowest-fault-priority-defect is not configured,
       defects of severity remote-invalid-ccm and higher are alarmed
       by default.";
    deviate add {
      default "remote-invalid-ccm";
    }
  }
  deviation "/ncs:devices/ncs:device/ncs:live-status/mef-cfm:maintenance-domain/mef-cfm:maintenance-association/mef-cfm:maintenance-association-end-point/mef-cfm:remote-mep-database/mef-cfm:remote-mep/mef-cfm:management-address" {
    deviate not-supported;
  }
}
