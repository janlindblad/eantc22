module ciena-sr {
  // Generated by yanger -t ncs
  tailf:mount-id "ciena107s3-nc-1.0:ciena107s3-nc-1.0";
  tailf:ncs-device-type "netconf";

  namespace "http://ciena.com/ns/yang/ciena-sr";
  prefix sr;

  import ietf-sr-cmn {
    prefix sr-cmn;
  }
  import ietf-inet-types {
    prefix inet;
  }
  import openconfig-interfaces {
    prefix oc-if;
  }
  import tailf-common {
    prefix tailf;
  }
  import tailf-ncs {
    prefix ncs;
  }

  organization
    "Ciena Corporation";
  contact
    "Web URL: http://www.ciena.com/
     E-mail:  yang@ciena.com
     Postal:  7035 Ridge Road
     Hanover, Maryland 21076
     U.S.A.
     Phone:   +1 800-921-1144
     Phone:   +1 408-904-2139
     Fax:     +1 410-694-5750";
  description
    "This YANG module defines Ciena's specific Segment Routing(SR) protocol

     Copyright (c) 2018  Ciena Corporation.  All rights
     reserved.

     All information contained herein is, and remains the
     property of Ciena Corporation. Dissemination of this
     information or reproduction of this material is strictly
     forbidden unless prior written permission is obtained
     from Ciena Corporation.";

  revision 2020-10-28 {
    description
      "Added support for Maximum SID Depth (MSD)
       Added SR Prefix SID flag grouping
       Global SRGB congifurations is obsolete";
    reference "IETF-DRAFT: YANG Data Model for Segment Routing.";
  }
  revision 2020-02-12 {
    description
      "Depreacted Global SRGB congifurations";
  }
  revision 2018-01-11 {
    description
      "Initial version";
    reference "RFC XXXX: YANG Data Model for Segment Routing.";
  }

  grouping ncs_template_sid-label-local-block {
    description
      "Grouping for SR Label Range configuration.";
    leaf lower-bound {
      status deprecated;
      type string;
      description
        "Lower value in the block.";
    }
    leaf upper-bound {
      status deprecated;
      type string;
      description
        "Upper value in the block.";
    }
  }

  grouping ncs_template_srgb-cfg {
    status obsolete;
    description
      "Grouping for SR Label Range configuration.";
    list srgb {
      // NCS patched for predictable order
      ordered-by user;
      status obsolete;
      key "lower-bound upper-bound";
      // NCS drop max-elements statement
      description
        "List of global blocks to be advertised.";
      uses ncs_template_sid-label-local-block;
    }
  }

  grouping ncs_template_max-sid-depth {
    description
      "Maximum SID Depth (MSD) configuration grouping.";
    leaf node-msd {
      type string;
      description
        "Node MSD is the lowest MSD supported by the node.";
    }
  }

  grouping ncs_template_prefix-sid-flags-cfg {
    description
      "Grouping of prefix SID Flags";
    leaf n-flag {
      type string;
      // NCS drop default statement
      description
        "Node SID flag settings";
    }
  }

  grouping ncs_rpc_notif_sid-label-local-block {
    description
      "Grouping for SR Label Range configuration.";
    leaf lower-bound {
      status deprecated;
      type uint32 {
        range "16000..23999";
      }
      description
        "Lower value in the block.";
    }
    leaf upper-bound {
      status deprecated;
      type uint32 {
        range "16000..23999";
      }
      description
        "Upper value in the block.";
    }
  }

  grouping ncs_rpc_notif_srgb-cfg {
    status obsolete;
    description
      "Grouping for SR Label Range configuration.";
    list srgb {
      status obsolete;
      key "lower-bound upper-bound";
      max-elements 1;
      description
        "List of global blocks to be advertised.";
      uses ncs_rpc_notif_sid-label-local-block;
    }
  }

  grouping ncs_rpc_notif_max-sid-depth {
    description
      "Maximum SID Depth (MSD) configuration grouping.";
    leaf node-msd {
      type uint8 {
        range "2..12";
      }
      description
        "Node MSD is the lowest MSD supported by the node.";
    }
  }

  grouping ncs_rpc_notif_prefix-sid-flags-cfg {
    description
      "Grouping of prefix SID Flags";
    leaf n-flag {
      type enumeration {
        enum "enable" {
          value 0;
          description
            "To set the N-flag value as 1";
        }
        enum "disable" {
          value 1;
          description
            "To set the N-flag value as 0";
        }
      }
      default "enable";
      description
        "Node SID flag settings";
    }
  }

  grouping live_ncs_sid-label-local-block {
    description
      "Grouping for SR Label Range configuration.";
    leaf lower-bound {
      status deprecated;
      type uint32 {
        range "16000..23999";
      }
      description
        "Lower value in the block.";
    }
    leaf upper-bound {
      status deprecated;
      type uint32 {
        range "16000..23999";
      }
      description
        "Upper value in the block.";
    }
  }

  grouping live_ncs_srgb-cfg {
    status obsolete;
    description
      "Grouping for SR Label Range configuration.";
    list srgb {
      status obsolete;
      key "lower-bound upper-bound";
      // NCS drop max-elements statement
      description
        "List of global blocks to be advertised.";
      uses live_ncs_sid-label-local-block;
    }
  }

  grouping live_ncs_max-sid-depth {
    description
      "Maximum SID Depth (MSD) configuration grouping.";
    leaf node-msd {
      type uint8 {
        range "2..12";
      }
      description
        "Node MSD is the lowest MSD supported by the node.";
    }
  }

  grouping live_ncs_prefix-sid-flags-cfg {
    description
      "Grouping of prefix SID Flags";
    leaf n-flag {
      type enumeration {
        enum "enable" {
          value 0;
          description
            "To set the N-flag value as 1";
        }
        enum "disable" {
          value 1;
          description
            "To set the N-flag value as 0";
        }
      }
      // NCS drop default statement
      description
        "Node SID flag settings";
    }
  }

  grouping sid-label-local-block {
    description
      "Grouping for SR Label Range configuration.";
    leaf lower-bound {
      status deprecated;
      type uint32 {
        range "16000..23999";
      }
      description
        "Lower value in the block.";
    }
    leaf upper-bound {
      status deprecated;
      type uint32 {
        range "16000..23999";
      }
      description
        "Upper value in the block.";
    }
  }

  grouping srgb-cfg {
    status obsolete;
    description
      "Grouping for SR Label Range configuration.";
    list srgb {
      status obsolete;
      key "lower-bound upper-bound";
      max-elements 1;
      description
        "List of global blocks to be advertised.";
      uses sid-label-local-block;
    }
  }

  grouping max-sid-depth {
    description
      "Maximum SID Depth (MSD) configuration grouping.";
    leaf node-msd {
      type uint8 {
        range "2..12";
      }
      description
        "Node MSD is the lowest MSD supported by the node.";
    }
  }

  grouping prefix-sid-flags-cfg {
    description
      "Grouping of prefix SID Flags";
    leaf n-flag {
      type enumeration {
        enum "enable" {
          value 0;
          description
            "To set the N-flag value as 1";
        }
        enum "disable" {
          value 1;
          description
            "To set the N-flag value as 0";
        }
      }
      default "enable";
      description
        "Node SID flag settings";
    }
  }

  augment "/ncs:devices/ncs:device/ncs:config" {
    container segment-routing {
      tailf:ncs-device-type "netconf";
      tailf:display-when "not(../../ncs:module) or ../../ncs:module[ncs:name='ciena-sr']";
      description
        "Segment routing global config";
      container msd {
        tailf:display-when "not(../../ncs:module) or boolean(/ncs:devices/ncs:device[ncs:name=current()/../../ncs:name]/capability/feature='max-sid-depth')";
        description
          "MSD configuration.";
        uses max-sid-depth;
      }
      container bindings {
        description
          "List of bindings.";
        container mapping-server {
          tailf:display-when "not(../../../ncs:module) or boolean(/ncs:devices/ncs:device[ncs:name=current()/../../../ncs:name]/capability/feature='mapping-server')";
          description
            "Configuration of mapping-server local entries.";
          list policy {
            key "name";
            max-elements 1;
            description
              "List mapping-server policies.";
            leaf name {
              type string;
              description
                "Name of the mapping policy.";
            }
            leaf preference {
              type uint32 {
                range "1..255";
              }
              default "128";
              description
                "SRMS Preference sub-tlv is used in order to
                 associate a preference with SRMS advertisements from a
                 particular source.";
            }
            container entries {
              description
                "IPv4/IPv6 mapping entries.";
              list mapping-entry {
                key "prefix algorithm";
                description
                  "Mapping entries.";
                uses sr-cmn:prefix-sid;
                leaf attached {
                  type boolean;
                  default "false";
                  description
                    "Indicates that the prefixes and SID configured in the mapping entry
                     and as a result advertised in the SID/Label Binding TLV are directly
                     connected to their originators.";
                }
              }
            }
          }
        }
      }
      list connected-prefix-sid-map {
        key "prefix";
        description
          "List of prefix SID mapped to IPv4 local prefixes.";
        leaf interface {
          type leafref {
            path "/ncs:devices/ncs:device/ncs:config/oc-if:interfaces/oc-if:interface/oc-if:name" {
              tailf:xpath-root 3;
            }
          }
          description
            "Interface in which prefix-sid is configured ";
        }
        uses sr-cmn:ipv4-sid-cfg;
        uses sr-cmn:last-hop-behavior;
        uses prefix-sid-flags-cfg;
      }
      uses srgb-cfg {
        status obsolete;
      }
    }
    // NCS drop config false container 'segment-routing-state'
  }
  augment "/ncs:devices/ncs:device/ncs:live-status" {
    container segment-routing {
      tailf:ncs-device-type "netconf";
      tailf:display-when "not(../../ncs:module) or ../../ncs:module[ncs:name='ciena-sr'] or (../../ncs:live-status-protocol[not(ncs:capability)]) or (../../ncs:live-status-protocol/ncs:capability/ncs:module[.='ciena-sr'])";
      description
        "Segment routing global config";
      container msd {
        // NCS drop if-feature statement
        description
          "MSD configuration.";
        uses live_ncs_max-sid-depth;
      }
      container bindings {
        description
          "List of bindings.";
        container mapping-server {
          // NCS drop if-feature statement
          description
            "Configuration of mapping-server local entries.";
          list policy {
            key "name";
            // NCS drop max-elements statement
            description
              "List mapping-server policies.";
            leaf name {
              type string;
              description
                "Name of the mapping policy.";
            }
            leaf preference {
              type uint32 {
                range "1..255";
              }
              // NCS drop default statement
              description
                "SRMS Preference sub-tlv is used in order to
                 associate a preference with SRMS advertisements from a
                 particular source.";
            }
            container entries {
              description
                "IPv4/IPv6 mapping entries.";
              list mapping-entry {
                key "prefix algorithm";
                description
                  "Mapping entries.";
                uses sr-cmn:live_ncs_prefix-sid;
                leaf attached {
                  type boolean;
                  // NCS drop default statement
                  description
                    "Indicates that the prefixes and SID configured in the mapping entry
                     and as a result advertised in the SID/Label Binding TLV are directly
                     connected to their originators.";
                }
              }
            }
          }
        }
      }
      list connected-prefix-sid-map {
        key "prefix";
        description
          "List of prefix SID mapped to IPv4 local prefixes.";
        leaf interface {
          type leafref {
            path "/ncs:devices/ncs:device/ncs:live-status/oc-if:interfaces/oc-if:interface/oc-if:name" {
              tailf:xpath-root 3;
            }
          }
          description
            "Interface in which prefix-sid is configured ";
        }
        uses sr-cmn:live_ncs_ipv4-sid-cfg;
        uses sr-cmn:live_ncs_last-hop-behavior;
        uses live_ncs_prefix-sid-flags-cfg;
      }
      uses live_ncs_srgb-cfg {
        status obsolete;
      }
    }
    container segment-routing-state {
      tailf:ncs-device-type "netconf";
      tailf:display-when "not(../../ncs:module) or ../../ncs:module[ncs:name='ciena-sr'] or (../../ncs:live-status-protocol[not(ncs:capability)]) or (../../ncs:live-status-protocol/ncs:capability/ncs:module[.='ciena-sr'])";
      description
        "segment routing oper config.";
      list label-blocks {
        key "lower-bound upper-bound";
        description
          "List of labels blocks currently in use.";
        leaf lower-bound {
          status deprecated;
          type uint32;
          description
            "Lower bound of the label block.";
        }
        leaf upper-bound {
          status deprecated;
          type uint32;
          description
            "Upper bound of the label block.";
        }
        leaf scope {
          status deprecated;
          type enumeration {
            enum "global" {
              value 0;
              description
                "Global sid.";
            }
            enum "local" {
              value 1;
              description
                "Local sid.";
            }
          }
          description
            "Scope of this label block.";
        }
      }
      list connected-prefix-sid-map {
        key "prefix";
        description
          "List of prefix SID mapped to IPv4 local prefixes.";
        uses sr-cmn:live_ncs_ipv4-sid-cfg;
        uses sr-cmn:live_ncs_last-hop-behavior;
        leaf interface {
          type string;
          description
            "Interface in which prefix-sid is configured ";
        }
        uses live_ncs_prefix-sid-flags-cfg;
      }
      list mapping-server-policy {
        key "name";
        description
          "List mapping-server policies.";
        leaf name {
          type string;
          description
            "Name of the mapping policy.";
        }
        leaf preference {
          type uint32;
          description
            "Segment Routing Mapping Server Preference";
        }
        list mapping-entry {
          key "prefix";
          description
            "List of supported transport planes.";
          leaf prefix {
            type inet:ip-prefix;
            description
              "SRMS Start Prefix ";
          }
          leaf start-sid-index {
            type uint32;
            description
              "SRMS Start SID Index";
          }
          leaf srms-range {
            type uint32;
            description
              "SRMS Range";
          }
          leaf last-prefix {
            type inet:ip-prefix;
            description
              "Prefix";
          }
          leaf last-sid-index {
            type uint32;
            description
              "SRMS Last SID Index";
          }
          leaf attached {
            type boolean;
            description
              "Indicates that the prefixes and SID configured in the mapping entry
               and as a result advertised in the SID/Label Binding TLV are directly
               connected to their originators.";
          }
        }
      }
    }
  }
  augment "/ncs:devices/ncs:template/ncs:ned-id/ncs:config" {
    container segment-routing {
      description
        "Segment routing global config";
      container msd {
        // NCS drop if-feature statement
        description
          "MSD configuration.";
        uses ncs_template_max-sid-depth;
      }
      container bindings {
        description
          "List of bindings.";
        container mapping-server {
          // NCS drop if-feature statement
          description
            "Configuration of mapping-server local entries.";
          list policy {
            // NCS patched for predictable order
            ordered-by user;
            key "name";
            // NCS drop max-elements statement
            description
              "List mapping-server policies.";
            leaf name {
              type string;
              description
                "Name of the mapping policy.";
            }
            leaf preference {
              type string;
              // NCS drop default statement
              description
                "SRMS Preference sub-tlv is used in order to
                 associate a preference with SRMS advertisements from a
                 particular source.";
            }
            container entries {
              description
                "IPv4/IPv6 mapping entries.";
              list mapping-entry {
                // NCS patched for predictable order
                ordered-by user;
                key "prefix algorithm";
                description
                  "Mapping entries.";
                uses sr-cmn:ncs_template_prefix-sid;
                leaf attached {
                  type string;
                  // NCS drop default statement
                  description
                    "Indicates that the prefixes and SID configured in the mapping entry
                     and as a result advertised in the SID/Label Binding TLV are directly
                     connected to their originators.";
                }
              }
            }
          }
        }
      }
      list connected-prefix-sid-map {
        // NCS patched for predictable order
        ordered-by user;
        key "prefix";
        description
          "List of prefix SID mapped to IPv4 local prefixes.";
        leaf interface {
          type string;
          description
            "Interface in which prefix-sid is configured ";
        }
        uses sr-cmn:ncs_template_ipv4-sid-cfg;
        uses sr-cmn:ncs_template_last-hop-behavior;
        uses ncs_template_prefix-sid-flags-cfg;
      }
      uses ncs_template_srgb-cfg {
        status obsolete;
      }
    }
    // NCS drop config false container 'segment-routing-state'
  }

  feature max-sid-depth {
    description
      "Support for signaling MSD (Maximum SID Depth) in IGP.";
    reference
      "RFC 8476: Signaling Maximum SID Depth (MSD)
       Using OSPF
       RFC 8491: Signaling Maximum SID Depth (MSD)
       Using IS-IS";
  }

  feature mapping-server {
    description
      "Support for Segment Routing Mapping Server (SRMS).";
  }
}
