module openconfig-platform {
  // Generated by yanger -t ncs
  tailf:mount-id "ciena107s3-nc-1.0:ciena107s3-nc-1.0";
  tailf:ncs-device-type "netconf";

  yang-version 1;
  namespace "http://openconfig.net/yang/platform";
  prefix oc-platform;

  import openconfig-platform-types {
    prefix oc-platform-types;
  }
  import openconfig-interfaces {
    prefix oc-if;
  }
  import openconfig-extensions {
    prefix oc-ext;
  }
  import tailf-common {
    prefix tailf;
  }
  import tailf-ncs {
    prefix ncs;
  }

  organization
    "OpenConfig working group";
  contact
    "OpenConfig working group
     www.openconfig.net";
  description
    "This module defines a data model for representing a system
     component inventory, which can include hardware or software
     elements arranged in an arbitrary structure. The primary
     relationship supported by the model is containment, e.g.,
     components containing subcomponents.

     It is expected that this model reflects every field replacable
     unit on the device at a minimum (i.e., additional information
     may be supplied about non-replacable components).

     Every element in the inventory is termed a 'component' with each
     component expected to have a unique name and type, and optionally
     a unique system-assigned identifier and FRU number.  The
     uniqueness is guaranteed by the system within the device.

     Components may have properties defined by the system that are
     modeled as a list of key-value pairs. These may or may not be
     user-configurable.  The model provides a flag for the system
     to optionally indicate which properties are user configurable.

     Each component also has a list of 'subcomponents' which are
     references to other components. Appearance in a list of
     subcomponents indicates a containment relationship as described
     above.  For example, a linecard component may have a list of
     references to port components that reside on the linecard.

     This schema is generic to allow devices to express their own
     platform-specific structure.  It may be augmented by additional
     component type-specific schemas that provide a common structure
     for well-known component types.  In these cases, the system is
     expected to populate the common component schema, and may
     optionally also represent the component and its properties in the
     generic structure.

     The properties for each component may include dynamic values,
     e.g., in the 'state' part of the schema.  For example, a CPU
     component may report its utilization, temperature, or other
     physical properties.  The intent is to capture all platform-
     specific physical data in one location, including inventory
     (presence or absence of a component) and state (physical
     attributes or status).";
  oc-ext:openconfig-version "0.5.0";

  revision 2016-12-22 {
    description
      "Added temperature state variable to component";
    reference "0.5.0";
  }

  grouping ncs_template_platform-component-properties-config {
    description
      "System-defined configuration data for component properties";
    leaf name {
      type string;
      description
        "System-supplied name of the property -- this is typically
         non-configurable";
    }
    leaf value {
      type string;
      description
        "Property values can take on a variety of types.  Signed and
         unsigned integer types may be provided in smaller sizes,
         e.g., int8, uint16, etc.";
    }
  }

  grouping ncs_template_platform-component-properties-state {
    description
      "Operational state data for component properties";
    leaf configurable {
      type string;
      description
        "Indication whether the property is user-configurable";
    }
  }

  grouping ncs_template_platform-component-properties-top {
    description
      "Top-level grouping ";
    container properties {
      description
        "Enclosing container ";
      list property {
        // NCS patched for predictable order
        ordered-by user;
        key "name";
        description
          "List of system properties for the component";
        leaf name {
          type string;
          description
            "Reference to the property name.";
        }
        container config {
          description
            "Configuration data for each property";
          uses ncs_template_platform-component-properties-config;
        }
        // NCS drop config false container state
      }
    }
  }

  grouping ncs_template_platform-subcomponent-ref-config {
    description
      "Configuration data for subcomponent references";
    leaf name {
      type string;
      description
        "Reference to the name of the subcomponent";
    }
  }

  grouping ncs_template_platform-subcomponent-ref-state {
    description
      "Operational state data for subcomponent references";
  }

  grouping ncs_template_platform-subcomponent-ref-top {
    description
      "Top-level grouping for list of subcomponent references";
    container subcomponents {
      description
        "Enclosing container for subcomponent references";
      list subcomponent {
        // NCS patched for predictable order
        ordered-by user;
        key "name";
        description
          "List of subcomponent references";
        leaf name {
          type string;
          description
            "Reference to the name list key";
        }
        container config {
          description
            "Configuration data ";
          uses ncs_template_platform-subcomponent-ref-config;
        }
        // NCS drop config false container state
      }
    }
  }

  grouping ncs_template_platform-component-config {
    description
      "Configuration data for components";
    leaf name {
      type string;
      description
        "Device name for the component -- this will not be a
         configurable parameter on many implementations";
    }
  }

  grouping ncs_template_platform-component-state {
    description
      "Operational state data for device components.";
    leaf type {
      type string;
      description
        "Type of component as identified by the system";
    }
    leaf id {
      type string;
      description
        "Unique identifier assigned by the system for the
         component";
    }
    leaf description {
      type string;
      description
        "System-supplied description of the component";
    }
    leaf mfg-name {
      type string;
      description
        "System-supplied identifier for the manufacturer of the
         component.  This data is particularly useful when a
         component manufacturer is different than the overall
         device vendor.";
    }
    leaf version {
      type string;
      description
        "System-defined version string for a hardware, firmware,
         or software component.";
    }
    leaf serial-no {
      type string;
      description
        "System-assigned serial number of the component.";
    }
    leaf part-no {
      type string;
      description
        "System-assigned part number for the component.  This should
         be present in particular if the component is also an FRU
         (field replacable unit)";
    }
  }

  grouping ncs_template_platform-component-temp-state {
    description
      "Temperature state data for device components";
    container temperature {
      description
        "Temperature in degrees Celsius of the component. Values include
         the instantaneous, average, minimum, and maximum statistics. If
         avg/min/max statistics are not supported, the target is expected
         to just supply the instant value";
      uses oc-platform-types:ncs_template_avg-min-max-instant-stats-precision1-celsius;
    }
  }

  grouping ncs_template_platform-component-top {
    description
      "Top-level grouping for components in the device inventory";
    container components {
      description
        "Enclosing container for the components in the system.";
      list component {
        // NCS patched for predictable order
        ordered-by user;
        key "name";
        description
          "List of components, keyed by component name.";
        leaf name {
          type string;
          description
            "References the component name";
        }
        container config {
          description
            "Configuration data for each component";
          uses ncs_template_platform-component-config;
        }
        // NCS drop config false container state
        uses ncs_template_platform-component-properties-top;
        uses ncs_template_platform-subcomponent-ref-top;
      }
    }
  }

  grouping ncs_rpc_notif_platform-component-properties-config {
    description
      "System-defined configuration data for component properties";
    leaf name {
      type string;
      description
        "System-supplied name of the property -- this is typically
         non-configurable";
    }
    leaf value {
      type union {
        type string;
        type boolean;
        type int64;
        type uint64;
        type decimal64 {
          fraction-digits 2;
        }
      }
      description
        "Property values can take on a variety of types.  Signed and
         unsigned integer types may be provided in smaller sizes,
         e.g., int8, uint16, etc.";
    }
  }

  grouping ncs_rpc_notif_platform-component-properties-state {
    description
      "Operational state data for component properties";
    leaf configurable {
      type boolean;
      description
        "Indication whether the property is user-configurable";
    }
  }

  grouping ncs_rpc_notif_platform-component-properties-top {
    description
      "Top-level grouping ";
    container properties {
      description
        "Enclosing container ";
      list property {
        key "name";
        description
          "List of system properties for the component";
        leaf name {
          type leafref {
            path "../config/name";
          }
          description
            "Reference to the property name.";
        }
        container config {
          description
            "Configuration data for each property";
          uses ncs_rpc_notif_platform-component-properties-config;
        }
        container state {
          config false;
          description
            "Operational state data for each property";
          uses ncs_rpc_notif_platform-component-properties-config;
          uses ncs_rpc_notif_platform-component-properties-state;
        }
      }
    }
  }

  grouping ncs_rpc_notif_platform-subcomponent-ref-config {
    description
      "Configuration data for subcomponent references";
    leaf name {
      type leafref {
        path "../../../../../component/config/name";
      }
      description
        "Reference to the name of the subcomponent";
    }
  }

  grouping ncs_rpc_notif_platform-subcomponent-ref-state {
    description
      "Operational state data for subcomponent references";
  }

  grouping ncs_rpc_notif_platform-subcomponent-ref-top {
    description
      "Top-level grouping for list of subcomponent references";
    container subcomponents {
      description
        "Enclosing container for subcomponent references";
      list subcomponent {
        key "name";
        description
          "List of subcomponent references";
        leaf name {
          type leafref {
            path "../config/name";
          }
          description
            "Reference to the name list key";
        }
        container config {
          description
            "Configuration data ";
          uses ncs_rpc_notif_platform-subcomponent-ref-config;
        }
        container state {
          config false;
          description
            "Operational state data ";
          uses ncs_rpc_notif_platform-subcomponent-ref-config;
          uses ncs_rpc_notif_platform-subcomponent-ref-state;
        }
      }
    }
  }

  grouping ncs_rpc_notif_platform-component-config {
    description
      "Configuration data for components";
    leaf name {
      type string;
      description
        "Device name for the component -- this will not be a
         configurable parameter on many implementations";
    }
  }

  grouping ncs_rpc_notif_platform-component-state {
    description
      "Operational state data for device components.";
    leaf type {
      type union {
        type identityref {
          base oc-platform-types:OPENCONFIG_HARDWARE_COMPONENT;
        }
        type identityref {
          base oc-platform-types:OPENCONFIG_SOFTWARE_COMPONENT;
        }
      }
      description
        "Type of component as identified by the system";
    }
    leaf id {
      type string;
      description
        "Unique identifier assigned by the system for the
         component";
    }
    leaf description {
      type string;
      description
        "System-supplied description of the component";
    }
    leaf mfg-name {
      type string;
      description
        "System-supplied identifier for the manufacturer of the
         component.  This data is particularly useful when a
         component manufacturer is different than the overall
         device vendor.";
    }
    leaf version {
      type string;
      description
        "System-defined version string for a hardware, firmware,
         or software component.";
    }
    leaf serial-no {
      type string;
      description
        "System-assigned serial number of the component.";
    }
    leaf part-no {
      type string;
      description
        "System-assigned part number for the component.  This should
         be present in particular if the component is also an FRU
         (field replacable unit)";
    }
  }

  grouping ncs_rpc_notif_platform-component-temp-state {
    description
      "Temperature state data for device components";
    container temperature {
      description
        "Temperature in degrees Celsius of the component. Values include
         the instantaneous, average, minimum, and maximum statistics. If
         avg/min/max statistics are not supported, the target is expected
         to just supply the instant value";
      uses oc-platform-types:ncs_rpc_notif_avg-min-max-instant-stats-precision1-celsius;
    }
  }

  grouping ncs_rpc_notif_platform-component-top {
    description
      "Top-level grouping for components in the device inventory";
    container components {
      description
        "Enclosing container for the components in the system.";
      list component {
        key "name";
        description
          "List of components, keyed by component name.";
        leaf name {
          type leafref {
            path "../config/name";
          }
          description
            "References the component name";
        }
        container config {
          description
            "Configuration data for each component";
          uses ncs_rpc_notif_platform-component-config;
        }
        container state {
          config false;
          description
            "Operational state data for each component";
          uses ncs_rpc_notif_platform-component-config;
          uses ncs_rpc_notif_platform-component-state;
          uses ncs_rpc_notif_platform-component-temp-state;
        }
        uses ncs_rpc_notif_platform-component-properties-top;
        uses ncs_rpc_notif_platform-subcomponent-ref-top;
      }
    }
  }

  grouping live_ncs_platform-component-properties-config {
    description
      "System-defined configuration data for component properties";
    leaf name {
      type string;
      description
        "System-supplied name of the property -- this is typically
         non-configurable";
    }
    leaf value {
      type union {
        type string;
        type boolean;
        type int64;
        type uint64;
        type decimal64 {
          fraction-digits 2;
        }
      }
      description
        "Property values can take on a variety of types.  Signed and
         unsigned integer types may be provided in smaller sizes,
         e.g., int8, uint16, etc.";
    }
  }

  grouping live_ncs_platform-component-properties-state {
    description
      "Operational state data for component properties";
    leaf configurable {
      type boolean;
      description
        "Indication whether the property is user-configurable";
    }
  }

  grouping live_ncs_platform-component-properties-top {
    description
      "Top-level grouping ";
    container properties {
      description
        "Enclosing container ";
      list property {
        key "name";
        description
          "List of system properties for the component";
        leaf name {
          type leafref {
            path "../config/name";
          }
          description
            "Reference to the property name.";
        }
        container config {
          description
            "Configuration data for each property";
          uses live_ncs_platform-component-properties-config;
        }
        container state {
          description
            "Operational state data for each property";
          uses live_ncs_platform-component-properties-config;
          uses live_ncs_platform-component-properties-state;
        }
      }
    }
  }

  grouping live_ncs_platform-subcomponent-ref-config {
    description
      "Configuration data for subcomponent references";
    leaf name {
      type leafref {
        path "../../../../../component/config/name";
      }
      description
        "Reference to the name of the subcomponent";
    }
  }

  grouping live_ncs_platform-subcomponent-ref-state {
    description
      "Operational state data for subcomponent references";
  }

  grouping live_ncs_platform-subcomponent-ref-top {
    description
      "Top-level grouping for list of subcomponent references";
    container subcomponents {
      description
        "Enclosing container for subcomponent references";
      list subcomponent {
        key "name";
        description
          "List of subcomponent references";
        leaf name {
          type leafref {
            path "../config/name";
          }
          description
            "Reference to the name list key";
        }
        container config {
          description
            "Configuration data ";
          uses live_ncs_platform-subcomponent-ref-config;
        }
        container state {
          description
            "Operational state data ";
          uses live_ncs_platform-subcomponent-ref-config;
          uses live_ncs_platform-subcomponent-ref-state;
        }
      }
    }
  }

  grouping live_ncs_platform-component-config {
    description
      "Configuration data for components";
    leaf name {
      type string;
      description
        "Device name for the component -- this will not be a
         configurable parameter on many implementations";
    }
  }

  grouping live_ncs_platform-component-state {
    description
      "Operational state data for device components.";
    leaf type {
      type union {
        type identityref {
          base oc-platform-types:OPENCONFIG_HARDWARE_COMPONENT;
        }
        type identityref {
          base oc-platform-types:OPENCONFIG_SOFTWARE_COMPONENT;
        }
      }
      description
        "Type of component as identified by the system";
    }
    leaf id {
      type string;
      description
        "Unique identifier assigned by the system for the
         component";
    }
    leaf description {
      type string;
      description
        "System-supplied description of the component";
    }
    leaf mfg-name {
      type string;
      description
        "System-supplied identifier for the manufacturer of the
         component.  This data is particularly useful when a
         component manufacturer is different than the overall
         device vendor.";
    }
    leaf version {
      type string;
      description
        "System-defined version string for a hardware, firmware,
         or software component.";
    }
    leaf serial-no {
      type string;
      description
        "System-assigned serial number of the component.";
    }
    leaf part-no {
      type string;
      description
        "System-assigned part number for the component.  This should
         be present in particular if the component is also an FRU
         (field replacable unit)";
    }
  }

  grouping live_ncs_platform-component-temp-state {
    description
      "Temperature state data for device components";
    container temperature {
      description
        "Temperature in degrees Celsius of the component. Values include
         the instantaneous, average, minimum, and maximum statistics. If
         avg/min/max statistics are not supported, the target is expected
         to just supply the instant value";
      uses oc-platform-types:live_ncs_avg-min-max-instant-stats-precision1-celsius;
    }
  }

  grouping live_ncs_platform-component-top {
    description
      "Top-level grouping for components in the device inventory";
    container components {
      description
        "Enclosing container for the components in the system.";
      list component {
        key "name";
        description
          "List of components, keyed by component name.";
        leaf name {
          type leafref {
            path "../config/name";
          }
          description
            "References the component name";
        }
        container config {
          description
            "Configuration data for each component";
          uses live_ncs_platform-component-config;
        }
        container state {
          description
            "Operational state data for each component";
          uses live_ncs_platform-component-config;
          uses live_ncs_platform-component-state;
          uses live_ncs_platform-component-temp-state;
        }
        uses live_ncs_platform-component-properties-top;
        uses live_ncs_platform-subcomponent-ref-top;
      }
    }
  }

  grouping platform-component-properties-config {
    description
      "System-defined configuration data for component properties";
    leaf name {
      type string;
      description
        "System-supplied name of the property -- this is typically
         non-configurable";
    }
    leaf value {
      type union {
        type string;
        type boolean;
        type int64;
        type uint64;
        type decimal64 {
          fraction-digits 2;
        }
      }
      description
        "Property values can take on a variety of types.  Signed and
         unsigned integer types may be provided in smaller sizes,
         e.g., int8, uint16, etc.";
    }
  }

  grouping platform-component-properties-state {
    description
      "Operational state data for component properties";
    leaf configurable {
      type boolean;
      description
        "Indication whether the property is user-configurable";
    }
  }

  grouping platform-component-properties-top {
    description
      "Top-level grouping ";
    container properties {
      description
        "Enclosing container ";
      list property {
        key "name";
        description
          "List of system properties for the component";
        leaf name {
          type leafref {
            path "../config/name";
          }
          description
            "Reference to the property name.";
        }
        container config {
          description
            "Configuration data for each property";
          uses platform-component-properties-config;
        }
        // NCS drop config false container state
      }
    }
  }

  grouping platform-subcomponent-ref-config {
    description
      "Configuration data for subcomponent references";
    leaf name {
      type leafref {
        path "../../../../../component/config/name";
      }
      description
        "Reference to the name of the subcomponent";
    }
  }

  grouping platform-subcomponent-ref-state {
    description
      "Operational state data for subcomponent references";
  }

  grouping platform-subcomponent-ref-top {
    description
      "Top-level grouping for list of subcomponent references";
    container subcomponents {
      description
        "Enclosing container for subcomponent references";
      list subcomponent {
        key "name";
        description
          "List of subcomponent references";
        leaf name {
          type leafref {
            path "../config/name";
          }
          description
            "Reference to the name list key";
        }
        container config {
          description
            "Configuration data ";
          uses platform-subcomponent-ref-config;
        }
        // NCS drop config false container state
      }
    }
  }

  grouping platform-component-config {
    description
      "Configuration data for components";
    leaf name {
      type string;
      description
        "Device name for the component -- this will not be a
         configurable parameter on many implementations";
    }
  }

  grouping platform-component-state {
    description
      "Operational state data for device components.";
    leaf type {
      type union {
        type identityref {
          base oc-platform-types:OPENCONFIG_HARDWARE_COMPONENT;
        }
        type identityref {
          base oc-platform-types:OPENCONFIG_SOFTWARE_COMPONENT;
        }
      }
      description
        "Type of component as identified by the system";
    }
    leaf id {
      type string;
      description
        "Unique identifier assigned by the system for the
         component";
    }
    leaf description {
      type string;
      description
        "System-supplied description of the component";
    }
    leaf mfg-name {
      type string;
      description
        "System-supplied identifier for the manufacturer of the
         component.  This data is particularly useful when a
         component manufacturer is different than the overall
         device vendor.";
    }
    leaf version {
      type string;
      description
        "System-defined version string for a hardware, firmware,
         or software component.";
    }
    leaf serial-no {
      type string;
      description
        "System-assigned serial number of the component.";
    }
    leaf part-no {
      type string;
      description
        "System-assigned part number for the component.  This should
         be present in particular if the component is also an FRU
         (field replacable unit)";
    }
  }

  grouping platform-component-temp-state {
    description
      "Temperature state data for device components";
    container temperature {
      description
        "Temperature in degrees Celsius of the component. Values include
         the instantaneous, average, minimum, and maximum statistics. If
         avg/min/max statistics are not supported, the target is expected
         to just supply the instant value";
      uses oc-platform-types:avg-min-max-instant-stats-precision1-celsius;
    }
  }

  grouping platform-component-top {
    description
      "Top-level grouping for components in the device inventory";
    container components {
      description
        "Enclosing container for the components in the system.";
      list component {
        key "name";
        description
          "List of components, keyed by component name.";
        leaf name {
          type leafref {
            path "../config/name";
          }
          description
            "References the component name";
        }
        container config {
          description
            "Configuration data for each component";
          uses platform-component-config;
        }
        // NCS drop config false container state
        uses platform-component-properties-top;
        uses platform-subcomponent-ref-top;
      }
    }
  }

  augment "/ncs:devices/ncs:device/ncs:config" {
    uses platform-component-top {
      refine components {
        tailf:ncs-device-type "netconf";
        tailf:display-when "not(../../ncs:module) or ../../ncs:module[ncs:name='openconfig-platform']";
      }
    }
  }
  augment "/ncs:devices/ncs:device/ncs:live-status" {
    uses live_ncs_platform-component-top {
      refine components {
        tailf:ncs-device-type "netconf";
        tailf:display-when "not(../../ncs:module) or ../../ncs:module[ncs:name='openconfig-platform'] or (../../ncs:live-status-protocol[not(ncs:capability)]) or (../../ncs:live-status-protocol/ncs:capability/ncs:module[.='openconfig-platform'])";
      }
    }
  }
  augment "/ncs:devices/ncs:template/ncs:ned-id/ncs:config" {
    uses ncs_template_platform-component-top;
  }
}
