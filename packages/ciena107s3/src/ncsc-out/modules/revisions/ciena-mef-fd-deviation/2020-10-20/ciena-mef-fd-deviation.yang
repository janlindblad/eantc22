module ciena-mef-fd-deviation {
  // Generated by yanger -t ncs
  tailf:mount-id "ciena107s3-nc-1.0:ciena107s3-nc-1.0";
  tailf:ncs-device-type "netconf";

  namespace "http://ciena.com/ns/yang/ciena-mef-fd-deviation";
  prefix mef-fd-deviation;

  import ciena-mef-fd {
    prefix mef-fd;
  }
  import tailf-common {
    prefix tailf;
  }
  import tailf-ncs {
    prefix ncs;
  }

  organization
    "Ciena Corporation";
  contact
    "Web URL: http://www.ciena.com/
     E-mail:  yang@ciena.com
     Postal:  7035 Ridge Road
              Hanover, Maryland 21076
              U.S.A.
     Phone:   +1 800-921-1144
     Fax:     +1 410-694-5750";
  description
    "This YANG module defines the deviations for Ciena's configuration of
     the Forwarding Domain.";

  revision 2020-10-20 {
    description
      "Initial version";
  }

  deviation "/ncs:devices/ncs:template/ncs:ned-id/ncs:config/mef-fd:fds/mef-fd:fd/mef-fd:mode" {
    deviate replace {
      type string;
    }
    description
      "forwarding mode of the forwarding-domain";
  }
  deviation "/ncs:devices/ncs:device/ncs:live-status/mef-fd:fds/mef-fd:fd/mef-fd:mode" {
    deviate replace {
      type enumeration {
        enum "vlan" {
          status obsolete;
        }
        enum "vpls" {
          description
            "forwarding mode is based on l2 mac-lookups involving 2 or more endpoints";
        }
        enum "vpws" {
          description
            "forwarding mode is based on exactly 2 endpoints";
        }
        enum "fxc" {
          description
            "forwarding mode is based on flexible cross-connects for evpn-fxc within an evpn-instance";
        }
        enum "tdm-vpws" {
          description
            "forwarding mode is based on exactly 2 endpoints where some of the endpoints are over TDM ports";
        }
        enum "evpn-vpws" {
          description
            "forwarding mode is based on exactly 2 endpoints within an evpn-instance";
        }
        enum "evpn-vpls" {
          description
            "forwarding mode is based on l2 mac-lookups involving 2 or more endpoints within an evpn-instance";
        }
      }
    }
    description
      "forwarding mode of the forwarding-domain";
  }
  deviation "/ncs:devices/ncs:device/ncs:config/mef-fd:fds/mef-fd:fd/mef-fd:mode" {
    deviate replace {
      type enumeration {
        enum "vlan" {
          status obsolete;
        }
        enum "vpls" {
          description
            "forwarding mode is based on l2 mac-lookups involving 2 or more endpoints";
        }
        enum "vpws" {
          description
            "forwarding mode is based on exactly 2 endpoints";
        }
        enum "fxc" {
          description
            "forwarding mode is based on flexible cross-connects for evpn-fxc within an evpn-instance";
        }
        enum "tdm-vpws" {
          description
            "forwarding mode is based on exactly 2 endpoints where some of the endpoints are over TDM ports";
        }
        enum "evpn-vpws" {
          description
            "forwarding mode is based on exactly 2 endpoints within an evpn-instance";
        }
        enum "evpn-vpls" {
          description
            "forwarding mode is based on l2 mac-lookups involving 2 or more endpoints within an evpn-instance";
        }
      }
    }
    description
      "forwarding mode of the forwarding-domain";
  }
}
