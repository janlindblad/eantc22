module ciena-ip-oam-deviation {
  // Generated by yanger -t ncs
  tailf:mount-id "ciena107s3-nc-1.0:ciena107s3-nc-1.0";
  tailf:ncs-device-type "netconf";

  namespace "http://ciena.com/ns/yang/ciena-ip-oam-deviation";
  prefix ip-oam-deviation;

  import ciena-ip-oam {
    prefix ip-oam;
  }
  import tailf-common {
    prefix tailf;
  }
  import tailf-ncs {
    prefix ncs;
  }

  organization
    "Ciena Corporation";
  contact
    "Web URL: http://www.ciena.com/
     E-mail:  yang@ciena.com
     Postal:  7035 Ridge Road
              Hanover, Maryland 21076
                  U.S.A.
     Phone:   +1 800-921-1144
     Fax:     +1 410-694-5750";
  description
    "This YANG module defines Ciena proprietary YANG deviations
     of the IP ping and traceroute module.

     Copyright (c) 2018  Ciena Corporation.  All rights
     reserved.

     All information contained herein is, and remains the
     property of Ciena Corporation. Dissemination of this
     information or reproduction of this material is strictly
     forbidden unless prior written permission is obtained
     from Ciena Corporation.";

  revision 2018-11-27 {
    description
      "Initial version";
  }

  deviation "/ncs:devices/ncs:device/ncs:rpc/ip-oam:rpc-ping/ip-oam:ping/ip-oam:input/ip-oam:repeat-count" {
    deviate not-supported;
  }
  deviation "/ncs:devices/ncs:device/ncs:rpc/ip-oam:rpc-ping/ip-oam:ping/ip-oam:input/ip-oam:interval" {
    deviate not-supported;
  }
}
