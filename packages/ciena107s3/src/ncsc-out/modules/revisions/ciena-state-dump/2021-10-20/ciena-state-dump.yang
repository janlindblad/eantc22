module ciena-state-dump {
  // Generated by yanger -t ncs
  tailf:mount-id "ciena107s3-nc-1.0:ciena107s3-nc-1.0";
  tailf:ncs-device-type "netconf";

  namespace "http://www.ciena.com/ns/yang/ciena-state-dump";
  prefix ciena-state-dump;

  import ciena-file-transfer-types {
    prefix ciena-ftt;
  }
  import tailf-common {
    prefix tailf;
  }
  import tailf-ncs {
    prefix ncs;
  }

  organization
    "Ciena Corporation";
  contact
    "Web URL: http://www.ciena.com/
     E-mail:  yang@ciena.com
     Postal:  7035 Ridge Road
              Hanover, Maryland 21076
              U.S.A.
     Phone:   +1 800-921-1144
     Fax:     +1 410-694-5750";
  description
    "This YANG module defines Ciena's state dump rpc.

     Copyright (c) 2020 Ciena Corporation.  All rights
     reserved.

     All information contained herein is, and remains
     the property of Ciena Corporation. Dissemination of this
     information or reproduction of this material is strictly
     forbidden unless prior written permission is obtained from
     Ciena Corporation.";

  revision 2021-10-20 {
    description
      "Adding operating mode (sequential or parallel) for statedump";
  }
  revision 2020-02-03 {
    description
      "Initial version";
  }

  typedef ncs_template_state-dump-status-enum {
    type string;
  }

  typedef ncs_rpc_notif_state-dump-status-enum {
    type enumeration {
      enum "idle" {
        description
          "state-dump operation is not initiated";
      }
      enum "state-dump-started" {
        description
          "state-dump operation is initiated";
      }
      enum "state-dump-failed" {
        description
          "state-dump operation failed";
      }
      enum "state-dump-in-progress" {
        description
          "state-dump operation in progress";
      }
      enum "state-dump-complete" {
        description
          "state-dump operation completed successfully";
      }
    }
  }

  typedef live_ncs_state-dump-status-enum {
    type enumeration {
      enum "idle" {
        description
          "state-dump operation is not initiated";
      }
      enum "state-dump-started" {
        description
          "state-dump operation is initiated";
      }
      enum "state-dump-failed" {
        description
          "state-dump operation failed";
      }
      enum "state-dump-in-progress" {
        description
          "state-dump operation in progress";
      }
      enum "state-dump-complete" {
        description
          "state-dump operation completed successfully";
      }
    }
  }

  typedef state-dump-status-enum {
    type enumeration {
      enum "idle" {
        description
          "state-dump operation is not initiated";
      }
      enum "state-dump-started" {
        description
          "state-dump operation is initiated";
      }
      enum "state-dump-failed" {
        description
          "state-dump operation failed";
      }
      enum "state-dump-in-progress" {
        description
          "state-dump operation in progress";
      }
      enum "state-dump-complete" {
        description
          "state-dump operation completed successfully";
      }
    }
  }

  augment "/ncs:devices/ncs:device/ncs:rpc" {
    container rpc-state-dump {
      tailf:ncs-device-type "netconf";
      tailf:display-when "not(../../ncs:module) or ../../ncs:module[ncs:name='ciena-state-dump']";
      tailf:action state-dump {
        tailf:actionpoint ncsproxy {
          tailf:internal;
        }
        description
          "Initiates a system state dump.  The status of the state dump
           can be checked in state-dump-status";
        input {
          uses ciena-ftt:ncs_rpc_notif_file-transfer-parameters;
          leaf target-path {
            type string;
            description
              "The destination path";
          }
          leaf timeout {
            type uint64;
            units "seconds";
            description
              "How long should statedump wait in seconds before timing out";
          }
          leaf mode {
            type enumeration {
              enum "sequential" {
                description
                  "Running statedump operation on each container one by one";
              }
              enum "parallel" {
                description
                  "Running statedump operation on all containers at the same time";
              }
            }
            description
              "Statedump operating in sequential mode or parallel mode";
          }
        }
      }
    }
  }
  augment "/ncs:devices/ncs:device-group/ncs:ned-id/ncs:rpc" {
    container rpc-state-dump {
      tailf:ncs-device-type "netconf";
      tailf:display-when "/ncs:devices/ncs:device[ncs:name=current()/../../../ncs:member]/ncs:module[ncs:name='ciena-state-dump']";
      tailf:action state-dump {
        tailf:actionpoint ncsproxy {
          tailf:internal;
        }
        description
          "Initiates a system state dump.  The status of the state dump
           can be checked in state-dump-status";
        input {
          uses ciena-ftt:ncs_rpc_notif_file-transfer-parameters;
          leaf target-path {
            type string;
            description
              "The destination path";
          }
          leaf timeout {
            type uint64;
            units "seconds";
            description
              "How long should statedump wait in seconds before timing out";
          }
          leaf mode {
            type enumeration {
              enum "sequential" {
                description
                  "Running statedump operation on each container one by one";
              }
              enum "parallel" {
                description
                  "Running statedump operation on all containers at the same time";
              }
            }
            description
              "Statedump operating in sequential mode or parallel mode";
          }
        }
      }
    }
  }
  augment "/ncs:devices/ncs:device/ncs:config" {
    // NCS drop config false container 'state-dump-status'
  }
  augment "/ncs:devices/ncs:device/ncs:live-status" {
    container state-dump-status {
      tailf:ncs-device-type "netconf";
      tailf:display-when "not(../../ncs:module) or ../../ncs:module[ncs:name='ciena-state-dump'] or (../../ncs:live-status-protocol[not(ncs:capability)]) or (../../ncs:live-status-protocol/ncs:capability/ncs:module[.='ciena-state-dump'])";
      leaf status {
        type live_ncs_state-dump-status-enum;
        description
          "Status of state-dump operation";
      }
    }
  }
  augment "/ncs:devices/ncs:template/ncs:ned-id/ncs:config" {
    // NCS drop config false container 'state-dump-status'
  }
}
