module ciena-of-controller-data-packets {
  // Generated by yanger -t ncs
  tailf:mount-id "ciena107s3-nc-1.0:ciena107s3-nc-1.0";
  tailf:ncs-device-type "netconf";

  namespace "http://www.ciena.com/ns/yang/ciena-pn/ciena-of-controller-data-packets";
  prefix of-controller-data-packets;

  import ciena-of-types {
    prefix of-types;
  }
  import ciena-of-vfsi {
    prefix of-vfsi;
  }
  import ciena-of-flow-tables {
    prefix of-flow-tables;
  }
  import ciena-of-group-tables {
    prefix of-group-tables;
  }
  import tailf-common {
    prefix tailf;
  }
  import tailf-ncs {
    prefix ncs;
  }

  organization
    "Ciena Corporation";
  contact
    "Web URL: http://www.ciena.com/
     E-mail:  yang@ciena.com
     Postal:  7035 Ridge Road
              Hanover, Maryland 21076
                  U.S.A.
     Phone:   +1 800-921-1144
     Fax:     +1 410-694-5750";
  description
    "This YANG module defines Ciena's management data definition for the definition of
     Open Flow controller data packets for use by Ciena Open Flow packet handling.";

  revision 2018-09-20 {
    description
      "Initial Version.";
  }

  augment "/ncs:devices/ncs:device/ncs:rpc" {
    container rpc-of-packet-out {
      tailf:ncs-device-type "netconf";
      tailf:display-when "not(../../ncs:module) or ../../ncs:module[ncs:name='ciena-of-controller-data-packets']";
      tailf:action of-packet-out {
        tailf:actionpoint ncsproxy {
          tailf:internal;
        }
        description
          "Send the provided packet out the specified port.";
        input {
          leaf vfsi {
            type of-vfsi:ncs_rpc_notif_vfsi-id-ref;
            description
              "Identifier of the Virtual FlowSwitch Instance for the packet-out.";
          }
          container action-set {
            description
              "Action set. Although OpenFlow supports a list of actions, this is
               limited to an action set, which contains at most one action of
               each type. An empty set drops the packet.";
            uses of-types:ncs_rpc_notif_action-set;
            leaf group-id {
              type of-group-tables:ncs_rpc_notif_group-table-entry-ref;
              description
                "Action to send the packet to a particular group table.";
            }
          }
          uses of-types:ncs_rpc_notif_packet-data;
        }
        output {
          leaf status {
            type string;
            description
              "Status indicating if the operation has succeeded or not.";
          }
        }
      }
    }
  }
  augment "/ncs:devices/ncs:device-group/ncs:ned-id/ncs:rpc" {
    container rpc-of-packet-out {
      tailf:ncs-device-type "netconf";
      tailf:display-when "/ncs:devices/ncs:device[ncs:name=current()/../../../ncs:member]/ncs:module[ncs:name='ciena-of-controller-data-packets']";
      tailf:action of-packet-out {
        tailf:actionpoint ncsproxy {
          tailf:internal;
        }
        description
          "Send the provided packet out the specified port.";
        input {
          leaf vfsi {
            type of-vfsi:ncs_rpc_notif_vfsi-id-ref;
            description
              "Identifier of the Virtual FlowSwitch Instance for the packet-out.";
          }
          container action-set {
            description
              "Action set. Although OpenFlow supports a list of actions, this is
               limited to an action set, which contains at most one action of
               each type. An empty set drops the packet.";
            uses of-types:ncs_rpc_notif_action-set;
            leaf group-id {
              type of-group-tables:ncs_rpc_notif_group-table-entry-ref;
              description
                "Action to send the packet to a particular group table.";
            }
          }
          uses of-types:ncs_rpc_notif_packet-data;
        }
        output {
          container "device" {
            leaf "name" {
              type string;
            }
            leaf "info" {
              type string;
            }
            container "result" {
              leaf status {
                type string;
                description
                  "Status indicating if the operation has succeeded or not.";
              }
            }
          }
        }
      }
    }
  }
  augment "/ncs:devices/ncs:device/ncs:notifications/ncs:received-notifications/ncs:notification/ncs:data" {
    container of-packet-in {
      presence "";
      config false;
      description
        "Send a packet to the controller.";
      leaf vfsi {
        type of-vfsi:ncs_rpc_notif_vfsi-id-ref;
        description
          "Identifier of the Virtual FlowSwitch Instance that generated
           this packet-in.";
      }
      uses of-types:ncs_rpc_notif_of-logical-port;
      leaf table-id {
        type of-flow-tables:ncs_rpc_notif_flow-table-number-ref;
        description
          "ID of the flow table that was looked up";
      }
      leaf entry-id {
        type of-flow-tables:ncs_rpc_notif_flow-table-entry-ref;
        description
          "ID of the flow table entry that was looked up.";
      }
      leaf cookie {
        type of-types:ncs_rpc_notif_cookie;
        description
          "Cookie of the flow table entry that was looked up.";
      }
      leaf reason {
        type of-types:ncs_rpc_notif_packet-in-reason;
        description
          "Reason that resulted in this packet-in.";
      }
      uses of-types:ncs_rpc_notif_packet-data;
    }
  }
  augment "/ncs:devices/ncs:device/ncs:netconf-notifications/ncs:received-notifications/ncs:notification/ncs:data" {
    container of-packet-in {
      presence "";
      config false;
      description
        "Send a packet to the controller.";
      leaf vfsi {
        type of-vfsi:ncs_rpc_notif_vfsi-id-ref;
        description
          "Identifier of the Virtual FlowSwitch Instance that generated
           this packet-in.";
      }
      uses of-types:ncs_rpc_notif_of-logical-port;
      leaf table-id {
        type of-flow-tables:ncs_rpc_notif_flow-table-number-ref;
        description
          "ID of the flow table that was looked up";
      }
      leaf entry-id {
        type of-flow-tables:ncs_rpc_notif_flow-table-entry-ref;
        description
          "ID of the flow table entry that was looked up.";
      }
      leaf cookie {
        type of-types:ncs_rpc_notif_cookie;
        description
          "Cookie of the flow table entry that was looked up.";
      }
      leaf reason {
        type of-types:ncs_rpc_notif_packet-in-reason;
        description
          "Reason that resulted in this packet-in.";
      }
      uses of-types:ncs_rpc_notif_packet-data;
    }
  }
}
