module ciena-packet-ptp-deviation {
  // Generated by yanger -t ncs
  tailf:mount-id "ciena107s3-nc-1.0:ciena107s3-nc-1.0";
  tailf:ncs-device-type "netconf";

  namespace "http://www.ciena.com/ns/yang/ciena-packet-ptp-deviation";
  prefix ciena-ptp-deviation;

  import ciena-packet-ptp {
    prefix ciena-ptp;
  }
  import tailf-common {
    prefix tailf;
  }
  import tailf-ncs {
    prefix ncs;
  }

  organization
    "Ciena Corporation";
  contact
    "Web URL: http://www.ciena.com/
     Postal:  7035 Ridge Road
             Hanover, Maryland 21076
             U.S.A.
     Phone:   +1 800-921-1144
     Fax:     +1 410-694-5750";

  revision 2019-10-14 {
    description
      "Remove the deviation of admin-state";
  }
  revision 2018-05-17 {
    description
      "Initial revision";
  }

  deviation "/ncs:devices/ncs:template/ncs:ned-id/ncs:config/ciena-ptp:ptps/ciena-ptp:ptp/ciena-ptp:state/ciena-ptp:spli-management" {
    deviate not-supported;
  }
  deviation "/ncs:devices/ncs:device/ncs:live-status/ciena-ptp:ptps/ciena-ptp:ptp/ciena-ptp:state/ciena-ptp:spli-management" {
    deviate not-supported;
  }
  deviation "/ncs:devices/ncs:device/ncs:config/ciena-ptp:ptps/ciena-ptp:ptp/ciena-ptp:state/ciena-ptp:spli-management" {
    deviate not-supported;
  }
  deviation "/ncs:devices/ncs:device/ncs:live-status/ciena-ptp:ptps/ciena-ptp:ptp/ciena-ptp:state/ciena-ptp:spli-management-status" {
    deviate not-supported;
  }
}
