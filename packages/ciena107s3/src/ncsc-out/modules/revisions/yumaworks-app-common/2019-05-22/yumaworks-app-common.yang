module yumaworks-app-common {
  // Generated by yanger -t ncs
  tailf:mount-id "ciena107s3-nc-1.0:ciena107s3-nc-1.0";
  tailf:ncs-device-type "netconf";

  yang-version 1;
  namespace "http://yumaworks.com/ns/yumaworks-app-common";
  prefix ywapp;

  import yuma-ncx {
    prefix ncx;
  }
  import yumaworks-types {
    prefix ywt;
  }
  import yuma-types {
    prefix yt;
  }
  import tailf-common {
    prefix tailf;
  }
  import tailf-ncs {
    prefix ncs;
  }

  organization
    "YumaWorks, Inc.";
  contact
    "Support <support at yumaworks.com>";
  description
    "Common CLI parameters used in all yumapro applications.

     Copyright (c) 2012 - 2019 YumaWorks, Inc. All rights reserved.

     Redistribution and use in source and binary forms, with or
     without modification, is permitted pursuant to, and subject
     to the license terms contained in, the BSD 3-Clause License
     http://opensource.org/licenses/BSD-3-Clause";

  revision 2019-05-22 {
    description
      "Add WithTermMsgParm grouping.
       Add MaxStrlenParm grouping.";
  }
  revision 2019-03-30 {
    description
      "Add binary-display-maxlen parameter in
       BinaryDisplayMaxlenParm grouping";
  }
  revision 2018-06-26 {
    description
      "Move SshKeyParms and SslKeyParms to this module
       so they can be shared by yumaworks-sesmgr";
  }
  revision 2018-03-26 {
    description
      "Add ErrMsgParm and ErrMsgLangParm groupings.
       Add ModuleTagParm grouping";
  }
  revision 2018-03-08 {
    description
      "Add InsecureOkParm grouping";
  }
  revision 2018-01-07 {
    description
      "Add LoadPathParm grouping";
  }
  revision 2017-04-27 {
    description
      "Add OcPatternParm grouping";
  }
  revision 2016-04-11 {
    description
      "Add AnnotationParm grouping";
  }
  revision 2014-02-14 {
    description
      "Add UseSesssionVars CLI variable grouping.
       Add SaveSesssionVars CLI variable grouping.
       Add DataTemplateParms grouping.";
  }
  revision 2013-08-13 {
    description
      "Split log-vendor and log-vendor-level parameters into
       their own grouping.";
  }
  revision 2013-05-25 {
    description
      "Add log-console param as user friendly synonym
       for log-mirroring.";
  }
  revision 2013-02-11 {
    description
      "Move common yangcli-pro grouping to this module";
  }
  revision 2012-11-30 {
    description
      "Add message-indent parameter.";
  }
  revision 2012-10-23 {
    description
      "Remove log-custom and log-localtime empty leafs and convert
                 to \"bits\" entity: log-header=\"custom localtime\".";
  }
  revision 2012-10-10 {
    description
      "Change log-backtrace-level to and add log-backtrace-stream
       parameters as 'bits' type entities. Eliminate
       log-backtrace-xxx 'type empty' leafs.";
  }
  revision 2012-08-16 {
    description
      "Split from yuma-app-common; Add new logging parameters.";
  }

  grouping ncs_template_LoggingCommonParms {
    leaf log-backtrace {
      description
        "If present, log output will include traceback
         detail for each log message, subject to further
         filtering by --log-backtrace-level and/or
         log-backtrace-stream qualifiers";
      type string;
    }
    leaf log-backtrace-detail {
      description
        "If present in conjunction with --log-backtrace
         log messages will include 'detailed' backtrace
         information (if supported by the compiler).";
      type empty;
    }
    leaf log-backtrace-level {
      description
        "Indicates for which debug level(s) backtrace
                      info will be generated. Param string is an XSD
                      list: a double quoted series of whitespace
                      separated (level) strings like \"error warn debug\"";
      type string;
    }
    leaf log-backtrace-stream {
      description
        "Indicates in which log stream(s) backtrace info
                      will be included. Param string is an XSD list:
                      a double quoted series of whitespace separated
                      (log stream) strings like \"logfile syslog\"";
      type string;
    }
    leaf log-header {
      description
        "Indicates what header elements to include in
                      header output. Param string is an XSD list:
                      a double quoted series of whitespace separated
                      (element) strings like \"custom localtime\"";
      type string;
    }
    leaf log-mirroring {
      description
        "If present in conjunction with --log, --log-syslog,
         and/or --log-vendor, log output will be directed to
         the normal stdout/stderr/logfile as well as
         to the syslog or vendor log stream";
      type empty;
    }
    leaf log-console {
      description
        "User friendly synonym for --log-mirroring.";
      type empty;
    }
    leaf log-stderr {
      description
        "If present, error level output be directed to stderr
         instead of stdout (as well as log file, if specified)";
      type empty;
    }
    leaf log-suppress-ctrl {
      ncx:hidden;
      description
        "If present, strip certain control characters from
         output in order to modify log formatting.";
      type empty;
    }
    leaf log-syslog {
      description
        "If present, log output will be directed to the
         standard syslog interface. Yuma log priorities
         will be translated into the appropriate syslog
         equivalents.";
      type empty;
    }
    leaf log-syslog-level {
      description
        "Sets the syslog debug logging level filter for output to
         the syslog file for the program.";
      type yt:ncs_template_NcDebugType;
    }
  }

  grouping ncs_template_LoggingVendorParms {
    leaf log-vendor {
      description
        "If present, log messages will be directed to a
         customer-written and registered callback function.
         This functionality is defined by an API specified in
         the YumaWorks API Reference Manual. In the absence of
         a registered callback, this parameter will direct
         logging messages to syslog in order to facilitate
         standalone testing.";
      type empty;
    }
    leaf log-vendor-level {
      description
        "Sets the vendor debug logging level filter for output to
         the vendor-specific log output file stream for the program.";
      type yt:ncs_template_NcDebugType;
    }
  }

  grouping ncs_template_MessageIndentParm {
    leaf message-indent {
      type string;
      // NCS drop default statement
      description
        "The number of spaces to indent for each level of
         output in a protocol message, e.g. NETCONF request.
         The value zero means no indent, just line feeds.
         The value -1 means no indent and no line feeds either.";
    }
  }

  grouping ncs_template_YumaproHomeParm {
    leaf yumapro-home {
      description
        "Directory for the yumapro project root to use.
         If present, this directory location will
         override the 'YUMAPRO_HOME' environment variable,
         if it is present.  If a zero-length string is
         entered, then the YUMAPRO_HOME environment variable
         will be ignored.";
      type string;
    }
  }

  grouping ncs_template_MatchParms {
    leaf match-names {
      type ywt:ncs_template_NameMatchMode;
      description
        "Match mode to use for UrlPath name searches.";
    }
    leaf alt-names {
      type ywt:ncs_template_AltNameMode;
      description
        "Match mode to use for UrlPath name searches.";
    }
    leaf wildcard-keys {
      type string;
      description
        "Enable wildcards on key leaf values.
         Set to 'true' if UrlPath targets for GET operations
         are allowed to replace key values with the dash '-'
         character to indicate that all instances of that key
         are requested.

         Set to false to treat the '-' character as a plain
         character if entered as a key value in a UrlPath string.";
    }
  }

  grouping ncs_template_UseSessionVarsParm {
    leaf use-session-vars {
      description
        "Specifies how global variables will be handled when
         set from the context of a named session.  If 'true',
         then an assignment (e.g., $$foo = 'bar') will only
         affect the session-specific instance of the variable,
         and only be visible within the scope of the named
         session.

         If 'false', then assignment statements for global
         variables will affect the global instance of the
         variable, and be visible to all sessions.

         If the current session is the default session,
         and not a named session, then the value of this
         variable is ignored, and all global variable
         assignments will affect the global instance of
         the variable, and be visible to all sessions.";
      type string;
      // NCS drop default statement
    }
  }

  grouping ncs_template_SaveSessionVarsParm {
    leaf save-session-vars {
      description
        "Specifies if session variables will be saved
         when the program exits. If use-session-vars
         is 'false' then this variable is ignored.

         If 'false', then session variables will not be
         saved when the program exits.

         If 'true', then session variables will be
         saved when the program exits, but only if user
         variables are being saved.";
      type string;
      // NCS drop default statement
    }
  }

  grouping ncs_template_DataTemplateParms {
    leaf use-data-templates {
      description
        "Specifies if variable expressions are enabled for
         data in XML, JSON or .conf instance documents.

         If 'false', then text matching the pattern for
         variable expressions in these instance documents
         will be treated as plain strings.

         If 'true', then text matching the pattern for
         variable expressions in these instance documents
         will be processed as variable expressions.";
      type string;
      // NCS drop default statement
    }
    leaf ignore-missing-vars {
      description
        "Specifies how missing variable errors in data
         templates are handled. This parameter has no
         affect unless the 'use-data-templates' parameter
         is 'true'.

         If 'false', then variable expressions that contain
         references to missing variables will cause a parsing
         error.

         If 'true', then variable expressions that contain
         references to missing variables will not cause a
         parsing error. Instead, an empty string will be used
         for the value of a missing variable.";
      type string;
      // NCS drop default statement
    }
  }

  grouping ncs_template_AnnotationParm {
    leaf-list annotation {
      // NCS patched for predictable order
      ordered-by user;
      description
        "YANG deviation file representing model annotations.
         Processed the same as a deviation parameter except
         the module is not advertised to any client sessions.

         Only the deviation 'deviate add' operation can be
         used to transfer extension statements to another
         model.

         The annotations will be applied to a data definition
         statement, as if they were defined as sub-statements
         of the deviation target.

            --annotation=acme-dev1

         Example object annotations (contents of acme-dev1)

           deviation /if:interfaces {
             deviate add {
               ncx:sil-delete-chilren-first;
             }
           }

           deviation /if:interfaces/if:interface {
             deviate add {
               ncx:sil-delete-chilren-first;
               acme:my-deviation1 'the deviation parm';
             }
           }
        ";
      type yt:ncs_template_NcModuleSpec;
    }
  }

  grouping ncs_template_OcPatternParm {
    leaf with-ocpattern {
      description
        "If true, then OpenConfig patterns with be checked.
         If the module name starts with the string 'openconfig-'
         then all pattern statements within that module
         are treated as POSIX patterns, not YANG patterns.

         If false, then the pattern statements in all modules
         will be checked as YANG patterns.
        ";
      type string;
      // NCS drop default statement
    }
  }

  grouping ncs_template_LoadPathParm {
    leaf loadpath {
      description
        "Directory load path for YANG or YIN modules.
         This will be checked before the modpath setting
         if present when finding modules. After all module
         and bundle parameters have been processed, this
         load path will be checked and the server will
         attempt to load any modules not already loaded.
         Overrides the YUMA_LOADPATH environment variable.";
      type yt:ncs_template_NcPathList;
    }
  }

  grouping ncs_template_InsecureOkParm {
    leaf insecure-ok {
      type string;
      // NCS drop default statement
      description
        "Specifies if insecure NETCONF over TLS should be allowed.
         If true then X.509 certificates will be accepted even
         if they cannot be verified. Used for debugging only!
         This parameter is only available if the image was built
         with the DEBUG=1 parameter.";
    }
  }

  grouping ncs_template_ErrMsgParm {
    leaf-list errmsg {
      // NCS patched for predictable order
      ordered-by user;
      type string;
      description
        "Specifies a replacement string for a specific error number.
         Can specify error message for 1 specific language.

         The 'num' component must match the <error-number>
         found in status_enum.h. New error enums are always added
         at the end of the list, so the numbers will not change.

         The 'lang' component should use the ISO-639-1 code
         Max length is 7 characters.

         The string has the format: '<num>:<lang>:error string'
         where:
             <num> = error number to use for error message
             <lang> = language code (en for English)
             error string = error string text

         Example:

           Replace error 117 (ERR_WB_WRITE_FAILED) 'db write failed'

           errmsg='117:en:The database could not be written'
        ";
    }
  }

  grouping ncs_template_ErrMsgLangParm {
    leaf errmsg-lang {
      type string;
      // NCS drop default statement
      description
        "Specifies the language code for the error-message
         language. This is only relevant if there are errmsg
         parameters for multiple languages loaded in the program.
         This value should use the ISO-639-1 code.
        ";
    }
  }

  grouping ncs_template_ModuleTagParm {
    leaf-list module-tag {
      // NCS patched for predictable order
      ordered-by user;
      type string;
      description
        "Include only data nodes that match the module-tag.

         Multiple module-tag parameters are combined as a
         logical OR expression. Matching any tag value will
         cause the data node to be included.

         It is not an error to include an unknown module-tag.
         Such tag values will simply be treated as a 'false'
         match result, when evaluating the filter.

         If any module-tag parameters are provided at all,
         and there are no matches found, then no data will be
         returned in the response.";
    }
  }

  grouping ncs_template_SshKeyParms {
    leaf public-key {
      type string;
      description
        "Contains the file path specification
         for the file containing the client-side public key.
         If both 'public-key' and 'private-key' files are
         present, the client will attempt to connect
         to the server using these keys.  If this fails,
         or not done, then password authentication will
         be attempted.";
      // NCS drop default statement
    }
    leaf private-key {
      type string;
      description
        "Contains the file path specification
         for the file containing the client-side private key.
         If both 'public-key' and 'private-key' files are
         present, the client will attempt to connect
         to the server using these keys.  If this fails,
         or not done, then password authentication will
         be attempted.";
      // NCS drop default statement
    }
  }

  grouping ncs_template_SslKeyParms {
    leaf ssl-fallback-ok {
      type string;
      // NCS drop default statement
      description
        "If true then an attempt to establish a plain TCP
         connection will be made if an SSL connection cannot
         be made. This parameter only applies of the
         'transport' is 'ssl'";
    }
    leaf ssl-certificate {
      type string;
      description
        "Contains the file path specification
         for the file containing the client-side ssl certificate.
         If both 'certificate' and 'key' files are
         present, the client will attempt to setup a secure
         connection with the server using the certificate and
         SSL key.

         If this fails, and the 'ssl-fallback-ok' leaf is
         set to true, the client will attempt to setup
         a raw TCP connection with the server.";
      // NCS drop default statement
    }
    leaf ssl-key {
      type string;
      description
        "Contains the file path specification
         for the file containing the client-side ssl key.
         If both 'certificate' and 'key' files are
         present, the client will attempt to setup a secure
         connection with the server using the certificate and
         SSL key.  If this fails, client will attempt to setup
         a raw TCP connection with the server.";
      // NCS drop default statement
    }
    leaf ssl-trust-store {
      type string;
      description
        "Contains the file path specification
         for the file containing the client-side ssl trust-store,
         or the path specification for the directory to use
         for finding trusted certificates. If the default value
         is used and the file is not found, then the default
         directory location '/etc/ssl/certs' will be used.";
      // NCS drop default statement
    }
  }

  grouping ncs_template_BinaryDisplayMaxlenParm {
    leaf binary-display-maxlen {
      type string;
      // NCS drop default statement
      description
        "The maximum number of bytes to display when dumping
         the contents of a binary value. Normally a message
         will be displayed showing the name and length.

         If this parameter is set to a value greater than zero
         then a standard 8-byte per line hex dump of the
         binary type will also be displayed for a maximum number
         of bytes set by this parameter.";
    }
  }

  grouping ncs_template_WithTermMsgParm {
    leaf with-term-msg {
      description
        "If set to 'true', then the yumaworks-term-msg module
         will be loaded and enabled. Otherwise, this module will
         not be loaded. The <term-msg> notification is used by
         yp-shell for displaying terminal diagnostic messages.";
      type string;
      // NCS drop default statement
    }
  }

  grouping ncs_rpc_notif_LoggingCommonParms {
    leaf log-backtrace {
      description
        "If present, log output will include traceback
         detail for each log message, subject to further
         filtering by --log-backtrace-level and/or
         log-backtrace-stream qualifiers";
      type uint32 {
        range "0 .. 100";
      }
    }
    leaf log-backtrace-detail {
      description
        "If present in conjunction with --log-backtrace
         log messages will include 'detailed' backtrace
         information (if supported by the compiler).";
      type empty;
    }
    leaf log-backtrace-level {
      description
        "Indicates for which debug level(s) backtrace
                      info will be generated. Param string is an XSD
                      list: a double quoted series of whitespace
                      separated (level) strings like \"error warn debug\"";
      type bits {
        bit write {
          description
            "Include backtrace info in write messages.";
        }
        bit dev0 {
          description
            "Include backtrace info in developer
             level 0 messages.";
        }
        bit error {
          description
            "Include backtrace info in error messages.";
        }
        bit warn {
          description
            "Include backtrace info in warning messages.";
        }
        bit info {
          description
            "Include backtrace info in info messages.";
        }
        bit dev1 {
          description
            "Include backtrace info in developer
             level 1 messages.";
        }
        bit debug {
          description
            "Include backtrace info in debug messages.";
        }
        bit debug2 {
          description
            "Include backtrace info in debug2 messages.";
        }
        bit debug3 {
          description
            "Include backtrace info in debug3 messages.";
        }
        bit debug4 {
          description
            "Include backtrace info in debug4 messages.";
        }
      }
    }
    leaf log-backtrace-stream {
      description
        "Indicates in which log stream(s) backtrace info
                      will be included. Param string is an XSD list:
                      a double quoted series of whitespace separated
                      (log stream) strings like \"logfile syslog\"";
      type bits {
        bit logfile {
          description
            "Include backtrace in logfile stream.";
        }
        bit stderr {
          description
            "Include backtrace in stderr stream.";
        }
        bit stdout {
          description
            "Include backtrace in stdout stream.";
        }
        bit syslog {
          description
            "Include backtrace in syslog stream.";
        }
        bit vendor {
          description
            "Include backtrace in vendor stream.";
        }
      }
    }
    leaf log-header {
      description
        "Indicates what header elements to include in
                      header output. Param string is an XSD list:
                      a double quoted series of whitespace separated
                      (element) strings like \"custom localtime\"";
      type bits {
        bit custom {
          description
            "Include date, time, and level.";
        }
        bit localtime {
          description
            "Include localtime instead of Yang canonical format.";
        }
      }
    }
    leaf log-mirroring {
      description
        "If present in conjunction with --log, --log-syslog,
         and/or --log-vendor, log output will be directed to
         the normal stdout/stderr/logfile as well as
         to the syslog or vendor log stream";
      type empty;
    }
    leaf log-console {
      description
        "User friendly synonym for --log-mirroring.";
      type empty;
    }
    leaf log-stderr {
      description
        "If present, error level output be directed to stderr
         instead of stdout (as well as log file, if specified)";
      type empty;
    }
    leaf log-suppress-ctrl {
      ncx:hidden;
      description
        "If present, strip certain control characters from
         output in order to modify log formatting.";
      type empty;
    }
    leaf log-syslog {
      description
        "If present, log output will be directed to the
         standard syslog interface. Yuma log priorities
         will be translated into the appropriate syslog
         equivalents.";
      type empty;
    }
    leaf log-syslog-level {
      description
        "Sets the syslog debug logging level filter for output to
         the syslog file for the program.";
      type yt:ncs_rpc_notif_NcDebugType;
    }
  }

  grouping ncs_rpc_notif_LoggingVendorParms {
    leaf log-vendor {
      description
        "If present, log messages will be directed to a
         customer-written and registered callback function.
         This functionality is defined by an API specified in
         the YumaWorks API Reference Manual. In the absence of
         a registered callback, this parameter will direct
         logging messages to syslog in order to facilitate
         standalone testing.";
      type empty;
    }
    leaf log-vendor-level {
      description
        "Sets the vendor debug logging level filter for output to
         the vendor-specific log output file stream for the program.";
      type yt:ncs_rpc_notif_NcDebugType;
    }
  }

  grouping ncs_rpc_notif_MessageIndentParm {
    leaf message-indent {
      type int8 {
        range "-1 .. 9";
      }
      default "-1";
      description
        "The number of spaces to indent for each level of
         output in a protocol message, e.g. NETCONF request.
         The value zero means no indent, just line feeds.
         The value -1 means no indent and no line feeds either.";
    }
  }

  grouping ncs_rpc_notif_YumaproHomeParm {
    leaf yumapro-home {
      description
        "Directory for the yumapro project root to use.
         If present, this directory location will
         override the 'YUMAPRO_HOME' environment variable,
         if it is present.  If a zero-length string is
         entered, then the YUMAPRO_HOME environment variable
         will be ignored.";
      type string;
    }
  }

  grouping ncs_rpc_notif_MatchParms {
    leaf match-names {
      type ywt:ncs_rpc_notif_NameMatchMode;
      description
        "Match mode to use for UrlPath name searches.";
    }
    leaf alt-names {
      type ywt:ncs_rpc_notif_AltNameMode;
      description
        "Match mode to use for UrlPath name searches.";
    }
    leaf wildcard-keys {
      type boolean;
      description
        "Enable wildcards on key leaf values.
         Set to 'true' if UrlPath targets for GET operations
         are allowed to replace key values with the dash '-'
         character to indicate that all instances of that key
         are requested.

         Set to false to treat the '-' character as a plain
         character if entered as a key value in a UrlPath string.";
    }
  }

  grouping ncs_rpc_notif_UseSessionVarsParm {
    leaf use-session-vars {
      description
        "Specifies how global variables will be handled when
         set from the context of a named session.  If 'true',
         then an assignment (e.g., $$foo = 'bar') will only
         affect the session-specific instance of the variable,
         and only be visible within the scope of the named
         session.

         If 'false', then assignment statements for global
         variables will affect the global instance of the
         variable, and be visible to all sessions.

         If the current session is the default session,
         and not a named session, then the value of this
         variable is ignored, and all global variable
         assignments will affect the global instance of
         the variable, and be visible to all sessions.";
      type boolean;
      default "true";
    }
  }

  grouping ncs_rpc_notif_SaveSessionVarsParm {
    leaf save-session-vars {
      description
        "Specifies if session variables will be saved
         when the program exits. If use-session-vars
         is 'false' then this variable is ignored.

         If 'false', then session variables will not be
         saved when the program exits.

         If 'true', then session variables will be
         saved when the program exits, but only if user
         variables are being saved.";
      type boolean;
      default "true";
    }
  }

  grouping ncs_rpc_notif_DataTemplateParms {
    leaf use-data-templates {
      description
        "Specifies if variable expressions are enabled for
         data in XML, JSON or .conf instance documents.

         If 'false', then text matching the pattern for
         variable expressions in these instance documents
         will be treated as plain strings.

         If 'true', then text matching the pattern for
         variable expressions in these instance documents
         will be processed as variable expressions.";
      type boolean;
      default "true";
    }
    leaf ignore-missing-vars {
      description
        "Specifies how missing variable errors in data
         templates are handled. This parameter has no
         affect unless the 'use-data-templates' parameter
         is 'true'.

         If 'false', then variable expressions that contain
         references to missing variables will cause a parsing
         error.

         If 'true', then variable expressions that contain
         references to missing variables will not cause a
         parsing error. Instead, an empty string will be used
         for the value of a missing variable.";
      type boolean;
      default "false";
    }
  }

  grouping ncs_rpc_notif_AnnotationParm {
    leaf-list annotation {
      description
        "YANG deviation file representing model annotations.
         Processed the same as a deviation parameter except
         the module is not advertised to any client sessions.

         Only the deviation 'deviate add' operation can be
         used to transfer extension statements to another
         model.

         The annotations will be applied to a data definition
         statement, as if they were defined as sub-statements
         of the deviation target.

            --annotation=acme-dev1

         Example object annotations (contents of acme-dev1)

           deviation /if:interfaces {
             deviate add {
               ncx:sil-delete-chilren-first;
             }
           }

           deviation /if:interfaces/if:interface {
             deviate add {
               ncx:sil-delete-chilren-first;
               acme:my-deviation1 'the deviation parm';
             }
           }
        ";
      type yt:ncs_rpc_notif_NcModuleSpec;
    }
  }

  grouping ncs_rpc_notif_OcPatternParm {
    leaf with-ocpattern {
      description
        "If true, then OpenConfig patterns with be checked.
         If the module name starts with the string 'openconfig-'
         then all pattern statements within that module
         are treated as POSIX patterns, not YANG patterns.

         If false, then the pattern statements in all modules
         will be checked as YANG patterns.
        ";
      type boolean;
      default "false";
    }
  }

  grouping ncs_rpc_notif_LoadPathParm {
    leaf loadpath {
      description
        "Directory load path for YANG or YIN modules.
         This will be checked before the modpath setting
         if present when finding modules. After all module
         and bundle parameters have been processed, this
         load path will be checked and the server will
         attempt to load any modules not already loaded.
         Overrides the YUMA_LOADPATH environment variable.";
      type yt:ncs_rpc_notif_NcPathList;
    }
  }

  grouping ncs_rpc_notif_InsecureOkParm {
    leaf insecure-ok {
      type boolean;
      default "false";
      description
        "Specifies if insecure NETCONF over TLS should be allowed.
         If true then X.509 certificates will be accepted even
         if they cannot be verified. Used for debugging only!
         This parameter is only available if the image was built
         with the DEBUG=1 parameter.";
    }
  }

  grouping ncs_rpc_notif_ErrMsgParm {
    leaf-list errmsg {
      type string;
      description
        "Specifies a replacement string for a specific error number.
         Can specify error message for 1 specific language.

         The 'num' component must match the <error-number>
         found in status_enum.h. New error enums are always added
         at the end of the list, so the numbers will not change.

         The 'lang' component should use the ISO-639-1 code
         Max length is 7 characters.

         The string has the format: '<num>:<lang>:error string'
         where:
             <num> = error number to use for error message
             <lang> = language code (en for English)
             error string = error string text

         Example:

           Replace error 117 (ERR_WB_WRITE_FAILED) 'db write failed'

           errmsg='117:en:The database could not be written'
        ";
    }
  }

  grouping ncs_rpc_notif_ErrMsgLangParm {
    leaf errmsg-lang {
      type string {
        length "1 .. 7";
      }
      default "en";
      description
        "Specifies the language code for the error-message
         language. This is only relevant if there are errmsg
         parameters for multiple languages loaded in the program.
         This value should use the ISO-639-1 code.
        ";
    }
  }

  grouping ncs_rpc_notif_ModuleTagParm {
    leaf-list module-tag {
      type string {
        length "1 .. 1023";
      }
      description
        "Include only data nodes that match the module-tag.

         Multiple module-tag parameters are combined as a
         logical OR expression. Matching any tag value will
         cause the data node to be included.

         It is not an error to include an unknown module-tag.
         Such tag values will simply be treated as a 'false'
         match result, when evaluating the filter.

         If any module-tag parameters are provided at all,
         and there are no matches found, then no data will be
         returned in the response.";
    }
  }

  grouping ncs_rpc_notif_SshKeyParms {
    leaf public-key {
      type string {
        length "1 .. max";
      }
      description
        "Contains the file path specification
         for the file containing the client-side public key.
         If both 'public-key' and 'private-key' files are
         present, the client will attempt to connect
         to the server using these keys.  If this fails,
         or not done, then password authentication will
         be attempted.";
      default "$HOME/.ssh/id_rsa.pub";
    }
    leaf private-key {
      type string {
        length "1 .. max";
      }
      description
        "Contains the file path specification
         for the file containing the client-side private key.
         If both 'public-key' and 'private-key' files are
         present, the client will attempt to connect
         to the server using these keys.  If this fails,
         or not done, then password authentication will
         be attempted.";
      default "$HOME/.ssh/id_rsa";
    }
  }

  grouping ncs_rpc_notif_SslKeyParms {
    leaf ssl-fallback-ok {
      type boolean;
      default "true";
      description
        "If true then an attempt to establish a plain TCP
         connection will be made if an SSL connection cannot
         be made. This parameter only applies of the
         'transport' is 'ssl'";
    }
    leaf ssl-certificate {
      type string {
        length "1 .. max";
      }
      description
        "Contains the file path specification
         for the file containing the client-side ssl certificate.
         If both 'certificate' and 'key' files are
         present, the client will attempt to setup a secure
         connection with the server using the certificate and
         SSL key.

         If this fails, and the 'ssl-fallback-ok' leaf is
         set to true, the client will attempt to setup
         a raw TCP connection with the server.";
      default "$HOME/.ssl/yangapi-client.crt";
    }
    leaf ssl-key {
      type string {
        length "1 .. max";
      }
      description
        "Contains the file path specification
         for the file containing the client-side ssl key.
         If both 'certificate' and 'key' files are
         present, the client will attempt to setup a secure
         connection with the server using the certificate and
         SSL key.  If this fails, client will attempt to setup
         a raw TCP connection with the server.";
      default "$HOME/.ssl/yangapi-client.key";
    }
    leaf ssl-trust-store {
      type string {
        length "1 .. max";
      }
      description
        "Contains the file path specification
         for the file containing the client-side ssl trust-store,
         or the path specification for the directory to use
         for finding trusted certificates. If the default value
         is used and the file is not found, then the default
         directory location '/etc/ssl/certs' will be used.";
      default "$HOME/.ssl/trust-store.pem";
    }
  }

  grouping ncs_rpc_notif_BinaryDisplayMaxlenParm {
    leaf binary-display-maxlen {
      type uint32;
      default "0";
      description
        "The maximum number of bytes to display when dumping
         the contents of a binary value. Normally a message
         will be displayed showing the name and length.

         If this parameter is set to a value greater than zero
         then a standard 8-byte per line hex dump of the
         binary type will also be displayed for a maximum number
         of bytes set by this parameter.";
    }
  }

  grouping ncs_rpc_notif_WithTermMsgParm {
    leaf with-term-msg {
      description
        "If set to 'true', then the yumaworks-term-msg module
         will be loaded and enabled. Otherwise, this module will
         not be loaded. The <term-msg> notification is used by
         yp-shell for displaying terminal diagnostic messages.";
      type boolean;
      default "true";
    }
  }

  grouping live_ncs_LoggingCommonParms {
    leaf log-backtrace {
      description
        "If present, log output will include traceback
         detail for each log message, subject to further
         filtering by --log-backtrace-level and/or
         log-backtrace-stream qualifiers";
      type uint32 {
        range "0 .. 100";
      }
    }
    leaf log-backtrace-detail {
      description
        "If present in conjunction with --log-backtrace
         log messages will include 'detailed' backtrace
         information (if supported by the compiler).";
      type empty;
    }
    leaf log-backtrace-level {
      description
        "Indicates for which debug level(s) backtrace
                      info will be generated. Param string is an XSD
                      list: a double quoted series of whitespace
                      separated (level) strings like \"error warn debug\"";
      type bits {
        bit write {
          description
            "Include backtrace info in write messages.";
        }
        bit dev0 {
          description
            "Include backtrace info in developer
             level 0 messages.";
        }
        bit error {
          description
            "Include backtrace info in error messages.";
        }
        bit warn {
          description
            "Include backtrace info in warning messages.";
        }
        bit info {
          description
            "Include backtrace info in info messages.";
        }
        bit dev1 {
          description
            "Include backtrace info in developer
             level 1 messages.";
        }
        bit debug {
          description
            "Include backtrace info in debug messages.";
        }
        bit debug2 {
          description
            "Include backtrace info in debug2 messages.";
        }
        bit debug3 {
          description
            "Include backtrace info in debug3 messages.";
        }
        bit debug4 {
          description
            "Include backtrace info in debug4 messages.";
        }
      }
    }
    leaf log-backtrace-stream {
      description
        "Indicates in which log stream(s) backtrace info
                      will be included. Param string is an XSD list:
                      a double quoted series of whitespace separated
                      (log stream) strings like \"logfile syslog\"";
      type bits {
        bit logfile {
          description
            "Include backtrace in logfile stream.";
        }
        bit stderr {
          description
            "Include backtrace in stderr stream.";
        }
        bit stdout {
          description
            "Include backtrace in stdout stream.";
        }
        bit syslog {
          description
            "Include backtrace in syslog stream.";
        }
        bit vendor {
          description
            "Include backtrace in vendor stream.";
        }
      }
    }
    leaf log-header {
      description
        "Indicates what header elements to include in
                      header output. Param string is an XSD list:
                      a double quoted series of whitespace separated
                      (element) strings like \"custom localtime\"";
      type bits {
        bit custom {
          description
            "Include date, time, and level.";
        }
        bit localtime {
          description
            "Include localtime instead of Yang canonical format.";
        }
      }
    }
    leaf log-mirroring {
      description
        "If present in conjunction with --log, --log-syslog,
         and/or --log-vendor, log output will be directed to
         the normal stdout/stderr/logfile as well as
         to the syslog or vendor log stream";
      type empty;
    }
    leaf log-console {
      description
        "User friendly synonym for --log-mirroring.";
      type empty;
    }
    leaf log-stderr {
      description
        "If present, error level output be directed to stderr
         instead of stdout (as well as log file, if specified)";
      type empty;
    }
    leaf log-suppress-ctrl {
      ncx:hidden;
      description
        "If present, strip certain control characters from
         output in order to modify log formatting.";
      type empty;
    }
    leaf log-syslog {
      description
        "If present, log output will be directed to the
         standard syslog interface. Yuma log priorities
         will be translated into the appropriate syslog
         equivalents.";
      type empty;
    }
    leaf log-syslog-level {
      description
        "Sets the syslog debug logging level filter for output to
         the syslog file for the program.";
      type yt:live_ncs_NcDebugType;
    }
  }

  grouping live_ncs_LoggingVendorParms {
    leaf log-vendor {
      description
        "If present, log messages will be directed to a
         customer-written and registered callback function.
         This functionality is defined by an API specified in
         the YumaWorks API Reference Manual. In the absence of
         a registered callback, this parameter will direct
         logging messages to syslog in order to facilitate
         standalone testing.";
      type empty;
    }
    leaf log-vendor-level {
      description
        "Sets the vendor debug logging level filter for output to
         the vendor-specific log output file stream for the program.";
      type yt:live_ncs_NcDebugType;
    }
  }

  grouping live_ncs_MessageIndentParm {
    leaf message-indent {
      type int8 {
        range "-1 .. 9";
      }
      // NCS drop default statement
      description
        "The number of spaces to indent for each level of
         output in a protocol message, e.g. NETCONF request.
         The value zero means no indent, just line feeds.
         The value -1 means no indent and no line feeds either.";
    }
  }

  grouping live_ncs_YumaproHomeParm {
    leaf yumapro-home {
      description
        "Directory for the yumapro project root to use.
         If present, this directory location will
         override the 'YUMAPRO_HOME' environment variable,
         if it is present.  If a zero-length string is
         entered, then the YUMAPRO_HOME environment variable
         will be ignored.";
      type string;
    }
  }

  grouping live_ncs_MatchParms {
    leaf match-names {
      type ywt:live_ncs_NameMatchMode;
      description
        "Match mode to use for UrlPath name searches.";
    }
    leaf alt-names {
      type ywt:live_ncs_AltNameMode;
      description
        "Match mode to use for UrlPath name searches.";
    }
    leaf wildcard-keys {
      type boolean;
      description
        "Enable wildcards on key leaf values.
         Set to 'true' if UrlPath targets for GET operations
         are allowed to replace key values with the dash '-'
         character to indicate that all instances of that key
         are requested.

         Set to false to treat the '-' character as a plain
         character if entered as a key value in a UrlPath string.";
    }
  }

  grouping live_ncs_UseSessionVarsParm {
    leaf use-session-vars {
      description
        "Specifies how global variables will be handled when
         set from the context of a named session.  If 'true',
         then an assignment (e.g., $$foo = 'bar') will only
         affect the session-specific instance of the variable,
         and only be visible within the scope of the named
         session.

         If 'false', then assignment statements for global
         variables will affect the global instance of the
         variable, and be visible to all sessions.

         If the current session is the default session,
         and not a named session, then the value of this
         variable is ignored, and all global variable
         assignments will affect the global instance of
         the variable, and be visible to all sessions.";
      type boolean;
      // NCS drop default statement
    }
  }

  grouping live_ncs_SaveSessionVarsParm {
    leaf save-session-vars {
      description
        "Specifies if session variables will be saved
         when the program exits. If use-session-vars
         is 'false' then this variable is ignored.

         If 'false', then session variables will not be
         saved when the program exits.

         If 'true', then session variables will be
         saved when the program exits, but only if user
         variables are being saved.";
      type boolean;
      // NCS drop default statement
    }
  }

  grouping live_ncs_DataTemplateParms {
    leaf use-data-templates {
      description
        "Specifies if variable expressions are enabled for
         data in XML, JSON or .conf instance documents.

         If 'false', then text matching the pattern for
         variable expressions in these instance documents
         will be treated as plain strings.

         If 'true', then text matching the pattern for
         variable expressions in these instance documents
         will be processed as variable expressions.";
      type boolean;
      // NCS drop default statement
    }
    leaf ignore-missing-vars {
      description
        "Specifies how missing variable errors in data
         templates are handled. This parameter has no
         affect unless the 'use-data-templates' parameter
         is 'true'.

         If 'false', then variable expressions that contain
         references to missing variables will cause a parsing
         error.

         If 'true', then variable expressions that contain
         references to missing variables will not cause a
         parsing error. Instead, an empty string will be used
         for the value of a missing variable.";
      type boolean;
      // NCS drop default statement
    }
  }

  grouping live_ncs_AnnotationParm {
    leaf-list annotation {
      description
        "YANG deviation file representing model annotations.
         Processed the same as a deviation parameter except
         the module is not advertised to any client sessions.

         Only the deviation 'deviate add' operation can be
         used to transfer extension statements to another
         model.

         The annotations will be applied to a data definition
         statement, as if they were defined as sub-statements
         of the deviation target.

            --annotation=acme-dev1

         Example object annotations (contents of acme-dev1)

           deviation /if:interfaces {
             deviate add {
               ncx:sil-delete-chilren-first;
             }
           }

           deviation /if:interfaces/if:interface {
             deviate add {
               ncx:sil-delete-chilren-first;
               acme:my-deviation1 'the deviation parm';
             }
           }
        ";
      type yt:live_ncs_NcModuleSpec;
    }
  }

  grouping live_ncs_OcPatternParm {
    leaf with-ocpattern {
      description
        "If true, then OpenConfig patterns with be checked.
         If the module name starts with the string 'openconfig-'
         then all pattern statements within that module
         are treated as POSIX patterns, not YANG patterns.

         If false, then the pattern statements in all modules
         will be checked as YANG patterns.
        ";
      type boolean;
      // NCS drop default statement
    }
  }

  grouping live_ncs_LoadPathParm {
    leaf loadpath {
      description
        "Directory load path for YANG or YIN modules.
         This will be checked before the modpath setting
         if present when finding modules. After all module
         and bundle parameters have been processed, this
         load path will be checked and the server will
         attempt to load any modules not already loaded.
         Overrides the YUMA_LOADPATH environment variable.";
      type yt:live_ncs_NcPathList;
    }
  }

  grouping live_ncs_InsecureOkParm {
    leaf insecure-ok {
      type boolean;
      // NCS drop default statement
      description
        "Specifies if insecure NETCONF over TLS should be allowed.
         If true then X.509 certificates will be accepted even
         if they cannot be verified. Used for debugging only!
         This parameter is only available if the image was built
         with the DEBUG=1 parameter.";
    }
  }

  grouping live_ncs_ErrMsgParm {
    leaf-list errmsg {
      type string;
      description
        "Specifies a replacement string for a specific error number.
         Can specify error message for 1 specific language.

         The 'num' component must match the <error-number>
         found in status_enum.h. New error enums are always added
         at the end of the list, so the numbers will not change.

         The 'lang' component should use the ISO-639-1 code
         Max length is 7 characters.

         The string has the format: '<num>:<lang>:error string'
         where:
             <num> = error number to use for error message
             <lang> = language code (en for English)
             error string = error string text

         Example:

           Replace error 117 (ERR_WB_WRITE_FAILED) 'db write failed'

           errmsg='117:en:The database could not be written'
        ";
    }
  }

  grouping live_ncs_ErrMsgLangParm {
    leaf errmsg-lang {
      type string {
        length "1 .. 7";
      }
      // NCS drop default statement
      description
        "Specifies the language code for the error-message
         language. This is only relevant if there are errmsg
         parameters for multiple languages loaded in the program.
         This value should use the ISO-639-1 code.
        ";
    }
  }

  grouping live_ncs_ModuleTagParm {
    leaf-list module-tag {
      type string {
        length "1 .. 1023";
      }
      description
        "Include only data nodes that match the module-tag.

         Multiple module-tag parameters are combined as a
         logical OR expression. Matching any tag value will
         cause the data node to be included.

         It is not an error to include an unknown module-tag.
         Such tag values will simply be treated as a 'false'
         match result, when evaluating the filter.

         If any module-tag parameters are provided at all,
         and there are no matches found, then no data will be
         returned in the response.";
    }
  }

  grouping live_ncs_SshKeyParms {
    leaf public-key {
      type string {
        length "1 .. max";
      }
      description
        "Contains the file path specification
         for the file containing the client-side public key.
         If both 'public-key' and 'private-key' files are
         present, the client will attempt to connect
         to the server using these keys.  If this fails,
         or not done, then password authentication will
         be attempted.";
      // NCS drop default statement
    }
    leaf private-key {
      type string {
        length "1 .. max";
      }
      description
        "Contains the file path specification
         for the file containing the client-side private key.
         If both 'public-key' and 'private-key' files are
         present, the client will attempt to connect
         to the server using these keys.  If this fails,
         or not done, then password authentication will
         be attempted.";
      // NCS drop default statement
    }
  }

  grouping live_ncs_SslKeyParms {
    leaf ssl-fallback-ok {
      type boolean;
      // NCS drop default statement
      description
        "If true then an attempt to establish a plain TCP
         connection will be made if an SSL connection cannot
         be made. This parameter only applies of the
         'transport' is 'ssl'";
    }
    leaf ssl-certificate {
      type string {
        length "1 .. max";
      }
      description
        "Contains the file path specification
         for the file containing the client-side ssl certificate.
         If both 'certificate' and 'key' files are
         present, the client will attempt to setup a secure
         connection with the server using the certificate and
         SSL key.

         If this fails, and the 'ssl-fallback-ok' leaf is
         set to true, the client will attempt to setup
         a raw TCP connection with the server.";
      // NCS drop default statement
    }
    leaf ssl-key {
      type string {
        length "1 .. max";
      }
      description
        "Contains the file path specification
         for the file containing the client-side ssl key.
         If both 'certificate' and 'key' files are
         present, the client will attempt to setup a secure
         connection with the server using the certificate and
         SSL key.  If this fails, client will attempt to setup
         a raw TCP connection with the server.";
      // NCS drop default statement
    }
    leaf ssl-trust-store {
      type string {
        length "1 .. max";
      }
      description
        "Contains the file path specification
         for the file containing the client-side ssl trust-store,
         or the path specification for the directory to use
         for finding trusted certificates. If the default value
         is used and the file is not found, then the default
         directory location '/etc/ssl/certs' will be used.";
      // NCS drop default statement
    }
  }

  grouping live_ncs_BinaryDisplayMaxlenParm {
    leaf binary-display-maxlen {
      type uint32;
      // NCS drop default statement
      description
        "The maximum number of bytes to display when dumping
         the contents of a binary value. Normally a message
         will be displayed showing the name and length.

         If this parameter is set to a value greater than zero
         then a standard 8-byte per line hex dump of the
         binary type will also be displayed for a maximum number
         of bytes set by this parameter.";
    }
  }

  grouping live_ncs_WithTermMsgParm {
    leaf with-term-msg {
      description
        "If set to 'true', then the yumaworks-term-msg module
         will be loaded and enabled. Otherwise, this module will
         not be loaded. The <term-msg> notification is used by
         yp-shell for displaying terminal diagnostic messages.";
      type boolean;
      // NCS drop default statement
    }
  }

  grouping LoggingCommonParms {
    leaf log-backtrace {
      description
        "If present, log output will include traceback
         detail for each log message, subject to further
         filtering by --log-backtrace-level and/or
         log-backtrace-stream qualifiers";
      type uint32 {
        range "0 .. 100";
      }
    }
    leaf log-backtrace-detail {
      description
        "If present in conjunction with --log-backtrace
         log messages will include 'detailed' backtrace
         information (if supported by the compiler).";
      type empty;
    }
    leaf log-backtrace-level {
      description
        "Indicates for which debug level(s) backtrace
                      info will be generated. Param string is an XSD
                      list: a double quoted series of whitespace
                      separated (level) strings like \"error warn debug\"";
      type bits {
        bit write {
          description
            "Include backtrace info in write messages.";
        }
        bit dev0 {
          description
            "Include backtrace info in developer
             level 0 messages.";
        }
        bit error {
          description
            "Include backtrace info in error messages.";
        }
        bit warn {
          description
            "Include backtrace info in warning messages.";
        }
        bit info {
          description
            "Include backtrace info in info messages.";
        }
        bit dev1 {
          description
            "Include backtrace info in developer
             level 1 messages.";
        }
        bit debug {
          description
            "Include backtrace info in debug messages.";
        }
        bit debug2 {
          description
            "Include backtrace info in debug2 messages.";
        }
        bit debug3 {
          description
            "Include backtrace info in debug3 messages.";
        }
        bit debug4 {
          description
            "Include backtrace info in debug4 messages.";
        }
      }
    }
    leaf log-backtrace-stream {
      description
        "Indicates in which log stream(s) backtrace info
                      will be included. Param string is an XSD list:
                      a double quoted series of whitespace separated
                      (log stream) strings like \"logfile syslog\"";
      type bits {
        bit logfile {
          description
            "Include backtrace in logfile stream.";
        }
        bit stderr {
          description
            "Include backtrace in stderr stream.";
        }
        bit stdout {
          description
            "Include backtrace in stdout stream.";
        }
        bit syslog {
          description
            "Include backtrace in syslog stream.";
        }
        bit vendor {
          description
            "Include backtrace in vendor stream.";
        }
      }
    }
    leaf log-header {
      description
        "Indicates what header elements to include in
                      header output. Param string is an XSD list:
                      a double quoted series of whitespace separated
                      (element) strings like \"custom localtime\"";
      type bits {
        bit custom {
          description
            "Include date, time, and level.";
        }
        bit localtime {
          description
            "Include localtime instead of Yang canonical format.";
        }
      }
    }
    leaf log-mirroring {
      description
        "If present in conjunction with --log, --log-syslog,
         and/or --log-vendor, log output will be directed to
         the normal stdout/stderr/logfile as well as
         to the syslog or vendor log stream";
      type empty;
    }
    leaf log-console {
      description
        "User friendly synonym for --log-mirroring.";
      type empty;
    }
    leaf log-stderr {
      description
        "If present, error level output be directed to stderr
         instead of stdout (as well as log file, if specified)";
      type empty;
    }
    leaf log-suppress-ctrl {
      ncx:hidden;
      description
        "If present, strip certain control characters from
         output in order to modify log formatting.";
      type empty;
    }
    leaf log-syslog {
      description
        "If present, log output will be directed to the
         standard syslog interface. Yuma log priorities
         will be translated into the appropriate syslog
         equivalents.";
      type empty;
    }
    leaf log-syslog-level {
      description
        "Sets the syslog debug logging level filter for output to
         the syslog file for the program.";
      type yt:NcDebugType;
    }
  }

  grouping LoggingVendorParms {
    leaf log-vendor {
      description
        "If present, log messages will be directed to a
         customer-written and registered callback function.
         This functionality is defined by an API specified in
         the YumaWorks API Reference Manual. In the absence of
         a registered callback, this parameter will direct
         logging messages to syslog in order to facilitate
         standalone testing.";
      type empty;
    }
    leaf log-vendor-level {
      description
        "Sets the vendor debug logging level filter for output to
         the vendor-specific log output file stream for the program.";
      type yt:NcDebugType;
    }
  }

  grouping MessageIndentParm {
    leaf message-indent {
      type int8 {
        range "-1 .. 9";
      }
      default "-1";
      description
        "The number of spaces to indent for each level of
         output in a protocol message, e.g. NETCONF request.
         The value zero means no indent, just line feeds.
         The value -1 means no indent and no line feeds either.";
    }
  }

  grouping YumaproHomeParm {
    leaf yumapro-home {
      description
        "Directory for the yumapro project root to use.
         If present, this directory location will
         override the 'YUMAPRO_HOME' environment variable,
         if it is present.  If a zero-length string is
         entered, then the YUMAPRO_HOME environment variable
         will be ignored.";
      type string;
    }
  }

  grouping MatchParms {
    leaf match-names {
      type ywt:NameMatchMode;
      description
        "Match mode to use for UrlPath name searches.";
    }
    leaf alt-names {
      type ywt:AltNameMode;
      description
        "Match mode to use for UrlPath name searches.";
    }
    leaf wildcard-keys {
      type boolean;
      description
        "Enable wildcards on key leaf values.
         Set to 'true' if UrlPath targets for GET operations
         are allowed to replace key values with the dash '-'
         character to indicate that all instances of that key
         are requested.

         Set to false to treat the '-' character as a plain
         character if entered as a key value in a UrlPath string.";
    }
  }

  grouping UseSessionVarsParm {
    leaf use-session-vars {
      description
        "Specifies how global variables will be handled when
         set from the context of a named session.  If 'true',
         then an assignment (e.g., $$foo = 'bar') will only
         affect the session-specific instance of the variable,
         and only be visible within the scope of the named
         session.

         If 'false', then assignment statements for global
         variables will affect the global instance of the
         variable, and be visible to all sessions.

         If the current session is the default session,
         and not a named session, then the value of this
         variable is ignored, and all global variable
         assignments will affect the global instance of
         the variable, and be visible to all sessions.";
      type boolean;
      default "true";
    }
  }

  grouping SaveSessionVarsParm {
    leaf save-session-vars {
      description
        "Specifies if session variables will be saved
         when the program exits. If use-session-vars
         is 'false' then this variable is ignored.

         If 'false', then session variables will not be
         saved when the program exits.

         If 'true', then session variables will be
         saved when the program exits, but only if user
         variables are being saved.";
      type boolean;
      default "true";
    }
  }

  grouping DataTemplateParms {
    leaf use-data-templates {
      description
        "Specifies if variable expressions are enabled for
         data in XML, JSON or .conf instance documents.

         If 'false', then text matching the pattern for
         variable expressions in these instance documents
         will be treated as plain strings.

         If 'true', then text matching the pattern for
         variable expressions in these instance documents
         will be processed as variable expressions.";
      type boolean;
      default "true";
    }
    leaf ignore-missing-vars {
      description
        "Specifies how missing variable errors in data
         templates are handled. This parameter has no
         affect unless the 'use-data-templates' parameter
         is 'true'.

         If 'false', then variable expressions that contain
         references to missing variables will cause a parsing
         error.

         If 'true', then variable expressions that contain
         references to missing variables will not cause a
         parsing error. Instead, an empty string will be used
         for the value of a missing variable.";
      type boolean;
      default "false";
    }
  }

  grouping AnnotationParm {
    leaf-list annotation {
      description
        "YANG deviation file representing model annotations.
         Processed the same as a deviation parameter except
         the module is not advertised to any client sessions.

         Only the deviation 'deviate add' operation can be
         used to transfer extension statements to another
         model.

         The annotations will be applied to a data definition
         statement, as if they were defined as sub-statements
         of the deviation target.

            --annotation=acme-dev1

         Example object annotations (contents of acme-dev1)

           deviation /if:interfaces {
             deviate add {
               ncx:sil-delete-chilren-first;
             }
           }

           deviation /if:interfaces/if:interface {
             deviate add {
               ncx:sil-delete-chilren-first;
               acme:my-deviation1 'the deviation parm';
             }
           }
        ";
      type yt:NcModuleSpec;
    }
  }

  grouping OcPatternParm {
    leaf with-ocpattern {
      description
        "If true, then OpenConfig patterns with be checked.
         If the module name starts with the string 'openconfig-'
         then all pattern statements within that module
         are treated as POSIX patterns, not YANG patterns.

         If false, then the pattern statements in all modules
         will be checked as YANG patterns.
        ";
      type boolean;
      default "false";
    }
  }

  grouping LoadPathParm {
    leaf loadpath {
      description
        "Directory load path for YANG or YIN modules.
         This will be checked before the modpath setting
         if present when finding modules. After all module
         and bundle parameters have been processed, this
         load path will be checked and the server will
         attempt to load any modules not already loaded.
         Overrides the YUMA_LOADPATH environment variable.";
      type yt:NcPathList;
    }
  }

  grouping InsecureOkParm {
    leaf insecure-ok {
      type boolean;
      default "false";
      description
        "Specifies if insecure NETCONF over TLS should be allowed.
         If true then X.509 certificates will be accepted even
         if they cannot be verified. Used for debugging only!
         This parameter is only available if the image was built
         with the DEBUG=1 parameter.";
    }
  }

  grouping ErrMsgParm {
    leaf-list errmsg {
      type string;
      description
        "Specifies a replacement string for a specific error number.
         Can specify error message for 1 specific language.

         The 'num' component must match the <error-number>
         found in status_enum.h. New error enums are always added
         at the end of the list, so the numbers will not change.

         The 'lang' component should use the ISO-639-1 code
         Max length is 7 characters.

         The string has the format: '<num>:<lang>:error string'
         where:
             <num> = error number to use for error message
             <lang> = language code (en for English)
             error string = error string text

         Example:

           Replace error 117 (ERR_WB_WRITE_FAILED) 'db write failed'

           errmsg='117:en:The database could not be written'
        ";
    }
  }

  grouping ErrMsgLangParm {
    leaf errmsg-lang {
      type string {
        length "1 .. 7";
      }
      default "en";
      description
        "Specifies the language code for the error-message
         language. This is only relevant if there are errmsg
         parameters for multiple languages loaded in the program.
         This value should use the ISO-639-1 code.
        ";
    }
  }

  grouping ModuleTagParm {
    leaf-list module-tag {
      type string {
        length "1 .. 1023";
      }
      description
        "Include only data nodes that match the module-tag.

         Multiple module-tag parameters are combined as a
         logical OR expression. Matching any tag value will
         cause the data node to be included.

         It is not an error to include an unknown module-tag.
         Such tag values will simply be treated as a 'false'
         match result, when evaluating the filter.

         If any module-tag parameters are provided at all,
         and there are no matches found, then no data will be
         returned in the response.";
    }
  }

  grouping SshKeyParms {
    leaf public-key {
      type string {
        length "1 .. max";
      }
      description
        "Contains the file path specification
         for the file containing the client-side public key.
         If both 'public-key' and 'private-key' files are
         present, the client will attempt to connect
         to the server using these keys.  If this fails,
         or not done, then password authentication will
         be attempted.";
      default "$HOME/.ssh/id_rsa.pub";
    }
    leaf private-key {
      type string {
        length "1 .. max";
      }
      description
        "Contains the file path specification
         for the file containing the client-side private key.
         If both 'public-key' and 'private-key' files are
         present, the client will attempt to connect
         to the server using these keys.  If this fails,
         or not done, then password authentication will
         be attempted.";
      default "$HOME/.ssh/id_rsa";
    }
  }

  grouping SslKeyParms {
    leaf ssl-fallback-ok {
      type boolean;
      default "true";
      description
        "If true then an attempt to establish a plain TCP
         connection will be made if an SSL connection cannot
         be made. This parameter only applies of the
         'transport' is 'ssl'";
    }
    leaf ssl-certificate {
      type string {
        length "1 .. max";
      }
      description
        "Contains the file path specification
         for the file containing the client-side ssl certificate.
         If both 'certificate' and 'key' files are
         present, the client will attempt to setup a secure
         connection with the server using the certificate and
         SSL key.

         If this fails, and the 'ssl-fallback-ok' leaf is
         set to true, the client will attempt to setup
         a raw TCP connection with the server.";
      default "$HOME/.ssl/yangapi-client.crt";
    }
    leaf ssl-key {
      type string {
        length "1 .. max";
      }
      description
        "Contains the file path specification
         for the file containing the client-side ssl key.
         If both 'certificate' and 'key' files are
         present, the client will attempt to setup a secure
         connection with the server using the certificate and
         SSL key.  If this fails, client will attempt to setup
         a raw TCP connection with the server.";
      default "$HOME/.ssl/yangapi-client.key";
    }
    leaf ssl-trust-store {
      type string {
        length "1 .. max";
      }
      description
        "Contains the file path specification
         for the file containing the client-side ssl trust-store,
         or the path specification for the directory to use
         for finding trusted certificates. If the default value
         is used and the file is not found, then the default
         directory location '/etc/ssl/certs' will be used.";
      default "$HOME/.ssl/trust-store.pem";
    }
  }

  grouping BinaryDisplayMaxlenParm {
    leaf binary-display-maxlen {
      type uint32;
      default "0";
      description
        "The maximum number of bytes to display when dumping
         the contents of a binary value. Normally a message
         will be displayed showing the name and length.

         If this parameter is set to a value greater than zero
         then a standard 8-byte per line hex dump of the
         binary type will also be displayed for a maximum number
         of bytes set by this parameter.";
    }
  }

  grouping WithTermMsgParm {
    leaf with-term-msg {
      description
        "If set to 'true', then the yumaworks-term-msg module
         will be loaded and enabled. Otherwise, this module will
         not be loaded. The <term-msg> notification is used by
         yp-shell for displaying terminal diagnostic messages.";
      type boolean;
      default "true";
    }
  }
}
