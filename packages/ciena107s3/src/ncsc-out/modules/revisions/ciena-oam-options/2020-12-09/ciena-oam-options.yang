module ciena-oam-options {
  // Generated by yanger -t ncs
  tailf:mount-id "ciena107s3-nc-1.0:ciena107s3-nc-1.0";
  tailf:ncs-device-type "netconf";

  namespace "http://ciena.com/ns/yang/ciena-oam-options";
  prefix oam-options;

  import ietf-inet-types {
    prefix inet;
  }
  import tailf-common {
    prefix tailf;
  }
  import tailf-ncs {
    prefix ncs;
  }

  organization
    "Ciena Corporation";
  contact
    "Web URL: http://www.ciena.com/
     E-mail:  yang@ciena.com
     Postal:  7035 Ridge Road
              Hanover, Maryland 21076
                 U.S.A.
     Phone:   +1 800-921-1144
     Fax:     +1 410-694-5750";
  description
    "Common parameters for OAM Ping and Traceroute";

  revision 2020-12-09 {
    description
      "Updated oam-target-fec-type for SR policy.";
  }
  revision 2020-01-31 {
    description
      "Updated mpls-oam-return-code with standard MPLS ping return
       code values. Added common parameters for ping/traceroute
       configuration. Marked older ip/mpls ping groupings
       (ping-base-input-options and ping-base-output) deprecated.";
  }
  revision 2018-08-30 {
    description
      "Initial version of ciena oam options.";
  }

  typedef ncs_template_oam-response-type {
    type string;
    description
      "Response of RPC, Failure/Success";
  }

  typedef ncs_template_oam-target-fec-type {
    type string;
    description
      "FEC type for IP/MPLS ping";
  }

  typedef ncs_template_oam-return-code {
    type string;
    description
      "Return codes in MPLS OAM response";
  }

  typedef ncs_template_mpls-oam-return-code {
    type string;
    description
      "Return codes in MPLS OAM response";
  }

  typedef ncs_template_mpls-fec-type {
    type string;
    description
      "FEC type for MPLS ping";
  }

  typedef ncs_template_reply-mode {
    type string;
    description
      "The channel throught which reply is expected";
  }

  typedef ncs_template_operational-state {
    type string;
    description
      "Current state of the operation";
  }

  typedef ncs_template_fec-verification-state {
    type string;
    description
      "Is FEC verification required.";
  }

  typedef ncs_template_oam-result-type {
    type string;
    description
      "Probe Result type";
  }

  typedef ncs_template_encap-ip-udp {
    type string;
    description
      "Does IP/UDP needs to be encapsulated";
  }

  typedef ncs_rpc_notif_oam-response-type {
    type enumeration {
      enum "success" {
        value 0;
        description
          "Response of RPC is success";
      }
      enum "failure" {
        value 1;
        description
          "Response of RPC is failure";
      }
    }
    description
      "Response of RPC, Failure/Success";
  }

  typedef ncs_rpc_notif_oam-target-fec-type {
    type enumeration {
      enum "vrf-fec" {
        value 0;
        description
          "Ping type VPN";
      }
      enum "ip-fec" {
        value 1;
        description
          "Ping type IP";
      }
      enum "ldp-fec" {
        value 2;
        description
          "FEC type LDP";
      }
      enum "bgp-lu-fec" {
        value 3;
        description
          "FEC type BGP-LU";
      }
      enum "sr-isis-fec" {
        value 4;
        description
          "FEC type SR ISIS";
      }
      enum "sr-ospf-fec" {
        value 5;
        description
          "FEC type SR OSPF";
      }
      enum "scrt-fec" {
        value 6;
        description
          "FEC type SCRT";
      }
      enum "pseudowire-fec" {
        value 7;
        description
          "FEC type pseudowire";
      }
      enum "evpn-fec" {
        value 8;
        description
          "FEC type EVPN";
      }
      enum "sr-policy-fec" {
        value 9;
        description
          "FEC type SR policy";
      }
    }
    description
      "FEC type for IP/MPLS ping";
  }

  typedef ncs_rpc_notif_oam-return-code {
    type enumeration {
      enum "none" {
        value 0;
        description
          "No return code";
      }
      enum "malformed-request" {
        value 1;
        description
          "Malformed echo request received";
      }
      enum "errored-tlv" {
        value 2;
        description
          "One or more of the TLVs was not understood";
      }
      enum "peer-router-is-egress" {
        value 3;
        description
          "Replying router is an egress for the FEC";
      }
      enum "peer-router-has-no-fec" {
        value 4;
        description
          "Replying router has no mapping for the FEC";
      }
      enum "dsmap-mismatch" {
        value 5;
        description
          "Downstream mapping mismatch";
      }
      enum "upstream-interface-not-found" {
        value 6;
        description
          "Upstream interface index unknown";
      }
      enum "reserved" {
        value 7;
        description
          "Reserved";
      }
      enum "label-switched" {
        value 8;
        description
          "Label Switched";
      }
      enum "label-switched-no-forwarding" {
        value 9;
        description
          "Label switched but no MPLS Forwarding";
      }
      enum "no-fec-label-mapping" {
        value 10;
        description
          "Mapping for this FEC is not the given label";
      }
      enum "no-label-entry" {
        value 11;
        description
          "No label entry";
      }
      enum "protocol-to-fec-mismatch" {
        value 12;
        description
          "Protocol not associated with interface at FEC";
      }
      enum "termination" {
        value 13;
        description
          "Premature termination of ping due to label
           stack shrinking to a single label";
      }
      enum "dd-map-tlv" {
        value 14;
        description
          "DDMAP Tlv";
      }
      enum "label-switch-fec" {
        value 15;
        description
          "Label switched with fec change";
      }
      enum "ping-not-authorized" {
        value 16;
        description
          "Proxy Ping not authorized";
      }
      enum "ping-params-modify" {
        value 17;
        description
          "Proxy Ping parameters need to be modified";
      }
      enum "request-not-send" {
        value 18;
        description
          "MPLS Echo Request could not be sent";
      }
      enum "fec-map-top-fec" {
        value 19;
        description
          "Replying router has FEC mapping for topmost FEC";
      }
      enum "tlv-fail-mtu" {
        value 20;
        description
          "One or more TLVs not returned due to MTU size";
      }
      enum "unsupported-bfd-ver" {
        value 21;
        description
          "OAM Problem/Unsupported BFD Version";
      }
      enum "unsupported-bfd-encap" {
        value 22;
        description
          "OAM Problem/Unsupported BFD Encapsulation format";
      }
      enum "unsupported-bfd-auth" {
        value 23;
        description
          "OAM Problem/Unsupported BFD Authentication Type";
      }
      enum "unsupported-bfd-auth-key-id" {
        value 24;
        description
          "OAM Problem/Mismatch of BFD Authentication Key ID";
      }
      enum "unsupported-time-stamp" {
        value 25;
        description
          "OAM Problem/Unsupported Timestamp Format";
      }
      enum "unsupported-delay-mode" {
        value 26;
        description
          "OAM Problem/Unsupported Delay Mode";
      }
      enum "unsupported-loss-mode" {
        value 27;
        description
          "OAM Problem/Unsupported Loss Mode";
      }
      enum "unsupported-delay-variation" {
        value 28;
        description
          "OAM Problem/Delay variation unsupported";
      }
      enum "unsupported-dyadic-mode" {
        value 29;
        description
          "OAM Problem/Dyadic mode unsupported";
      }
      enum "unsupported-lbk-mode" {
        value 30;
        description
          "OAM Problem/Loopback mode unsupported";
      }
      enum "unsupported-combined-mode" {
        value 31;
        description
          "OAM Problem/Combined mode unsupported";
      }
      enum "unsupported-fault-mgmt-sig" {
        value 32;
        description
          "OAM Problem/Fault management signaling unsupported";
      }
      enum "create-fail-fault-mgmt-asoc" {
        value 33;
        description
          "OAM Problem/Unable to create fault management association";
      }
      enum "pm-config-error" {
        value 34;
        description
          "OAM Problem/PM Configuration error";
      }
      enum "fec-intf-map-error" {
        value 35;
        description
          "Mapping for this FEC is not associated with the incoming interfac";
      }
      enum "fec-non-df" {
        value 36;
        description
          "The FEC exists on the PE and the behavior is
           to drop the packet because of not DF";
      }
      enum "fec-split-horizon" {
        value 37;
        description
          "The FEC exists on the PE and the behavior is
           to drop the packet because of Split Horizon Filtering";
      }
    }
    description
      "Return codes in MPLS OAM response";
  }

  typedef ncs_rpc_notif_mpls-oam-return-code {
    type enumeration {
      enum "success" {
        description
          "Successful OAM response";
      }
      enum "malformed-request" {
        description
          "Malformed OAM request";
      }
      enum "errored-tlv" {
        description
          "Errored TLV";
      }
      enum "label-mapping-error" {
        description
          "Label mapping error at egress";
      }
      enum "dsmap-mismatch" {
        description
          "Downstream mapping mismatch";
      }
      enum "upstream-interface-not-found" {
        description
          "Upstream interface not found";
      }
      enum "fec-mismatch" {
        description
          "Forwarding equivalence class mismatch";
      }
      enum "fec-not-found" {
        description
          "Forwarding equivalence class not found";
      }
      enum "echo-timeout" {
        description
          "Echo request timed out";
      }
      enum "ftn-not-found" {
        description
          "FTN not found";
      }
      enum "unknown-error" {
        description
          "Unknown MPLS OAM error";
      }
      enum "pw-not-found" {
        description
          "Pseudowire not found";
      }
    }
    description
      "Return codes in MPLS OAM response";
  }

  typedef ncs_rpc_notif_mpls-fec-type {
    type enumeration {
      enum "ldp" {
        value 0;
        description
          "FEC type LDP";
      }
      enum "bgp-lu" {
        value 1;
        description
          "FEC type BGP-LU";
      }
      enum "sr-isis" {
        value 2;
        description
          "FEC type SR ISIS";
      }
      enum "sr-ospf" {
        value 3;
        description
          "FEC type SR OSPF";
      }
      enum "scrt" {
        value 4;
        description
          "FEC type SCRT";
      }
      enum "evpn" {
        value 5;
        description
          "FEC type EVPN";
      }
    }
    description
      "FEC type for MPLS ping";
  }

  typedef ncs_rpc_notif_reply-mode {
    type enumeration {
      enum "do-not-reply" {
        value 1;
        description
          "Do not reply";
      }
      enum "reply-via-udp" {
        value 2;
        description
          "Reply via an IPv4/IPv6 UDP packet";
      }
      enum "reply-via-udp-router-alert" {
        value 3;
        description
          "Reply via an IPv4/IPv6 UDP packet with Router
           Alert. It is used when return path is unreliable";
      }
      enum "reply-via-control-channel" {
        value 4;
        description
          "Reply via application level control channel";
      }
    }
    description
      "The channel throught which reply is expected";
  }

  typedef ncs_rpc_notif_operational-state {
    type enumeration {
      enum "not-started" {
        value 0;
        description
          "The Ping Test not started.";
      }
      enum "in-progress" {
        value 1;
        description
          "The Ping Test is in progress.";
      }
      enum "cancelled" {
        value 2;
        description
          "The Ping Test is cancelled.";
      }
      enum "completed" {
        value 3;
        description
          "The Ping Test is completed.";
      }
    }
    description
      "Current state of the operation";
  }

  typedef ncs_rpc_notif_fec-verification-state {
    type enumeration {
      enum "off" {
        value 0;
        description
          "Do not verify FEC Stack.";
      }
      enum "on" {
        value 1;
        description
          "Verify FEC Stack.";
      }
    }
    description
      "Is FEC verification required.";
  }

  typedef ncs_rpc_notif_oam-result-type {
    type enumeration {
      enum "success" {
        value 0;
        description
          "The probe result is successful.";
      }
      enum "fail" {
        value 1;
        description
          "The probe result is failed.";
      }
      enum "timeout" {
        value 2;
        description
          "The probe result is timeout.";
      }
      enum "unknown-error" {
        value 3;
        description
          "Unknown MPLS OAM error.";
      }
      enum "ftn-not-found" {
        value 4;
        description
          "FTN not found.";
      }
      enum "pw-not-found" {
        value 5;
        description
          "Pseudowire not found.";
      }
      enum "evpn-instance-not-found" {
        value 6;
        description
          "Evpn instance not found.";
      }
      enum "evpn-multiple-fec-found" {
        value 7;
        description
          "Evpn multiple FEC found.";
      }
      enum "tunnel-not-found" {
        value 8;
        description
          "Tunnel not found";
      }
      enum "tunnel-admin-down" {
        value 9;
        description
          "Tunnel admin down.";
      }
    }
    description
      "Probe Result type";
  }

  typedef ncs_rpc_notif_encap-ip-udp {
    type enumeration {
      enum "non-ip/udp" {
        value 0;
        description
          "Don't need to encapsulate ip/udp in frame.";
      }
      enum "ip/udp" {
        value 1;
        description
          "Need to encapsulate ip/udp in frame.";
      }
    }
    description
      "Does IP/UDP needs to be encapsulated";
  }

  typedef live_ncs_oam-response-type {
    type enumeration {
      enum "success" {
        value 0;
        description
          "Response of RPC is success";
      }
      enum "failure" {
        value 1;
        description
          "Response of RPC is failure";
      }
    }
    description
      "Response of RPC, Failure/Success";
  }

  typedef live_ncs_oam-target-fec-type {
    type enumeration {
      enum "vrf-fec" {
        value 0;
        description
          "Ping type VPN";
      }
      enum "ip-fec" {
        value 1;
        description
          "Ping type IP";
      }
      enum "ldp-fec" {
        value 2;
        description
          "FEC type LDP";
      }
      enum "bgp-lu-fec" {
        value 3;
        description
          "FEC type BGP-LU";
      }
      enum "sr-isis-fec" {
        value 4;
        description
          "FEC type SR ISIS";
      }
      enum "sr-ospf-fec" {
        value 5;
        description
          "FEC type SR OSPF";
      }
      enum "scrt-fec" {
        value 6;
        description
          "FEC type SCRT";
      }
      enum "pseudowire-fec" {
        value 7;
        description
          "FEC type pseudowire";
      }
      enum "evpn-fec" {
        value 8;
        description
          "FEC type EVPN";
      }
      enum "sr-policy-fec" {
        value 9;
        description
          "FEC type SR policy";
      }
    }
    description
      "FEC type for IP/MPLS ping";
  }

  typedef live_ncs_oam-return-code {
    type enumeration {
      enum "none" {
        value 0;
        description
          "No return code";
      }
      enum "malformed-request" {
        value 1;
        description
          "Malformed echo request received";
      }
      enum "errored-tlv" {
        value 2;
        description
          "One or more of the TLVs was not understood";
      }
      enum "peer-router-is-egress" {
        value 3;
        description
          "Replying router is an egress for the FEC";
      }
      enum "peer-router-has-no-fec" {
        value 4;
        description
          "Replying router has no mapping for the FEC";
      }
      enum "dsmap-mismatch" {
        value 5;
        description
          "Downstream mapping mismatch";
      }
      enum "upstream-interface-not-found" {
        value 6;
        description
          "Upstream interface index unknown";
      }
      enum "reserved" {
        value 7;
        description
          "Reserved";
      }
      enum "label-switched" {
        value 8;
        description
          "Label Switched";
      }
      enum "label-switched-no-forwarding" {
        value 9;
        description
          "Label switched but no MPLS Forwarding";
      }
      enum "no-fec-label-mapping" {
        value 10;
        description
          "Mapping for this FEC is not the given label";
      }
      enum "no-label-entry" {
        value 11;
        description
          "No label entry";
      }
      enum "protocol-to-fec-mismatch" {
        value 12;
        description
          "Protocol not associated with interface at FEC";
      }
      enum "termination" {
        value 13;
        description
          "Premature termination of ping due to label
           stack shrinking to a single label";
      }
      enum "dd-map-tlv" {
        value 14;
        description
          "DDMAP Tlv";
      }
      enum "label-switch-fec" {
        value 15;
        description
          "Label switched with fec change";
      }
      enum "ping-not-authorized" {
        value 16;
        description
          "Proxy Ping not authorized";
      }
      enum "ping-params-modify" {
        value 17;
        description
          "Proxy Ping parameters need to be modified";
      }
      enum "request-not-send" {
        value 18;
        description
          "MPLS Echo Request could not be sent";
      }
      enum "fec-map-top-fec" {
        value 19;
        description
          "Replying router has FEC mapping for topmost FEC";
      }
      enum "tlv-fail-mtu" {
        value 20;
        description
          "One or more TLVs not returned due to MTU size";
      }
      enum "unsupported-bfd-ver" {
        value 21;
        description
          "OAM Problem/Unsupported BFD Version";
      }
      enum "unsupported-bfd-encap" {
        value 22;
        description
          "OAM Problem/Unsupported BFD Encapsulation format";
      }
      enum "unsupported-bfd-auth" {
        value 23;
        description
          "OAM Problem/Unsupported BFD Authentication Type";
      }
      enum "unsupported-bfd-auth-key-id" {
        value 24;
        description
          "OAM Problem/Mismatch of BFD Authentication Key ID";
      }
      enum "unsupported-time-stamp" {
        value 25;
        description
          "OAM Problem/Unsupported Timestamp Format";
      }
      enum "unsupported-delay-mode" {
        value 26;
        description
          "OAM Problem/Unsupported Delay Mode";
      }
      enum "unsupported-loss-mode" {
        value 27;
        description
          "OAM Problem/Unsupported Loss Mode";
      }
      enum "unsupported-delay-variation" {
        value 28;
        description
          "OAM Problem/Delay variation unsupported";
      }
      enum "unsupported-dyadic-mode" {
        value 29;
        description
          "OAM Problem/Dyadic mode unsupported";
      }
      enum "unsupported-lbk-mode" {
        value 30;
        description
          "OAM Problem/Loopback mode unsupported";
      }
      enum "unsupported-combined-mode" {
        value 31;
        description
          "OAM Problem/Combined mode unsupported";
      }
      enum "unsupported-fault-mgmt-sig" {
        value 32;
        description
          "OAM Problem/Fault management signaling unsupported";
      }
      enum "create-fail-fault-mgmt-asoc" {
        value 33;
        description
          "OAM Problem/Unable to create fault management association";
      }
      enum "pm-config-error" {
        value 34;
        description
          "OAM Problem/PM Configuration error";
      }
      enum "fec-intf-map-error" {
        value 35;
        description
          "Mapping for this FEC is not associated with the incoming interfac";
      }
      enum "fec-non-df" {
        value 36;
        description
          "The FEC exists on the PE and the behavior is
           to drop the packet because of not DF";
      }
      enum "fec-split-horizon" {
        value 37;
        description
          "The FEC exists on the PE and the behavior is
           to drop the packet because of Split Horizon Filtering";
      }
    }
    description
      "Return codes in MPLS OAM response";
  }

  typedef live_ncs_mpls-oam-return-code {
    type enumeration {
      enum "success" {
        description
          "Successful OAM response";
      }
      enum "malformed-request" {
        description
          "Malformed OAM request";
      }
      enum "errored-tlv" {
        description
          "Errored TLV";
      }
      enum "label-mapping-error" {
        description
          "Label mapping error at egress";
      }
      enum "dsmap-mismatch" {
        description
          "Downstream mapping mismatch";
      }
      enum "upstream-interface-not-found" {
        description
          "Upstream interface not found";
      }
      enum "fec-mismatch" {
        description
          "Forwarding equivalence class mismatch";
      }
      enum "fec-not-found" {
        description
          "Forwarding equivalence class not found";
      }
      enum "echo-timeout" {
        description
          "Echo request timed out";
      }
      enum "ftn-not-found" {
        description
          "FTN not found";
      }
      enum "unknown-error" {
        description
          "Unknown MPLS OAM error";
      }
      enum "pw-not-found" {
        description
          "Pseudowire not found";
      }
    }
    description
      "Return codes in MPLS OAM response";
  }

  typedef live_ncs_mpls-fec-type {
    type enumeration {
      enum "ldp" {
        value 0;
        description
          "FEC type LDP";
      }
      enum "bgp-lu" {
        value 1;
        description
          "FEC type BGP-LU";
      }
      enum "sr-isis" {
        value 2;
        description
          "FEC type SR ISIS";
      }
      enum "sr-ospf" {
        value 3;
        description
          "FEC type SR OSPF";
      }
      enum "scrt" {
        value 4;
        description
          "FEC type SCRT";
      }
      enum "evpn" {
        value 5;
        description
          "FEC type EVPN";
      }
    }
    description
      "FEC type for MPLS ping";
  }

  typedef live_ncs_reply-mode {
    type enumeration {
      enum "do-not-reply" {
        value 1;
        description
          "Do not reply";
      }
      enum "reply-via-udp" {
        value 2;
        description
          "Reply via an IPv4/IPv6 UDP packet";
      }
      enum "reply-via-udp-router-alert" {
        value 3;
        description
          "Reply via an IPv4/IPv6 UDP packet with Router
           Alert. It is used when return path is unreliable";
      }
      enum "reply-via-control-channel" {
        value 4;
        description
          "Reply via application level control channel";
      }
    }
    description
      "The channel throught which reply is expected";
  }

  typedef live_ncs_operational-state {
    type enumeration {
      enum "not-started" {
        value 0;
        description
          "The Ping Test not started.";
      }
      enum "in-progress" {
        value 1;
        description
          "The Ping Test is in progress.";
      }
      enum "cancelled" {
        value 2;
        description
          "The Ping Test is cancelled.";
      }
      enum "completed" {
        value 3;
        description
          "The Ping Test is completed.";
      }
    }
    description
      "Current state of the operation";
  }

  typedef live_ncs_fec-verification-state {
    type enumeration {
      enum "off" {
        value 0;
        description
          "Do not verify FEC Stack.";
      }
      enum "on" {
        value 1;
        description
          "Verify FEC Stack.";
      }
    }
    description
      "Is FEC verification required.";
  }

  typedef live_ncs_oam-result-type {
    type enumeration {
      enum "success" {
        value 0;
        description
          "The probe result is successful.";
      }
      enum "fail" {
        value 1;
        description
          "The probe result is failed.";
      }
      enum "timeout" {
        value 2;
        description
          "The probe result is timeout.";
      }
      enum "unknown-error" {
        value 3;
        description
          "Unknown MPLS OAM error.";
      }
      enum "ftn-not-found" {
        value 4;
        description
          "FTN not found.";
      }
      enum "pw-not-found" {
        value 5;
        description
          "Pseudowire not found.";
      }
      enum "evpn-instance-not-found" {
        value 6;
        description
          "Evpn instance not found.";
      }
      enum "evpn-multiple-fec-found" {
        value 7;
        description
          "Evpn multiple FEC found.";
      }
      enum "tunnel-not-found" {
        value 8;
        description
          "Tunnel not found";
      }
      enum "tunnel-admin-down" {
        value 9;
        description
          "Tunnel admin down.";
      }
    }
    description
      "Probe Result type";
  }

  typedef live_ncs_encap-ip-udp {
    type enumeration {
      enum "non-ip/udp" {
        value 0;
        description
          "Don't need to encapsulate ip/udp in frame.";
      }
      enum "ip/udp" {
        value 1;
        description
          "Need to encapsulate ip/udp in frame.";
      }
    }
    description
      "Does IP/UDP needs to be encapsulated";
  }

  typedef oam-response-type {
    type enumeration {
      enum "success" {
        value 0;
        description
          "Response of RPC is success";
      }
      enum "failure" {
        value 1;
        description
          "Response of RPC is failure";
      }
    }
    description
      "Response of RPC, Failure/Success";
  }

  typedef oam-target-fec-type {
    type enumeration {
      enum "vrf-fec" {
        value 0;
        description
          "Ping type VPN";
      }
      enum "ip-fec" {
        value 1;
        description
          "Ping type IP";
      }
      enum "ldp-fec" {
        value 2;
        description
          "FEC type LDP";
      }
      enum "bgp-lu-fec" {
        value 3;
        description
          "FEC type BGP-LU";
      }
      enum "sr-isis-fec" {
        value 4;
        description
          "FEC type SR ISIS";
      }
      enum "sr-ospf-fec" {
        value 5;
        description
          "FEC type SR OSPF";
      }
      enum "scrt-fec" {
        value 6;
        description
          "FEC type SCRT";
      }
      enum "pseudowire-fec" {
        value 7;
        description
          "FEC type pseudowire";
      }
      enum "evpn-fec" {
        value 8;
        description
          "FEC type EVPN";
      }
      enum "sr-policy-fec" {
        value 9;
        description
          "FEC type SR policy";
      }
    }
    description
      "FEC type for IP/MPLS ping";
  }

  typedef oam-return-code {
    type enumeration {
      enum "none" {
        value 0;
        description
          "No return code";
      }
      enum "malformed-request" {
        value 1;
        description
          "Malformed echo request received";
      }
      enum "errored-tlv" {
        value 2;
        description
          "One or more of the TLVs was not understood";
      }
      enum "peer-router-is-egress" {
        value 3;
        description
          "Replying router is an egress for the FEC";
      }
      enum "peer-router-has-no-fec" {
        value 4;
        description
          "Replying router has no mapping for the FEC";
      }
      enum "dsmap-mismatch" {
        value 5;
        description
          "Downstream mapping mismatch";
      }
      enum "upstream-interface-not-found" {
        value 6;
        description
          "Upstream interface index unknown";
      }
      enum "reserved" {
        value 7;
        description
          "Reserved";
      }
      enum "label-switched" {
        value 8;
        description
          "Label Switched";
      }
      enum "label-switched-no-forwarding" {
        value 9;
        description
          "Label switched but no MPLS Forwarding";
      }
      enum "no-fec-label-mapping" {
        value 10;
        description
          "Mapping for this FEC is not the given label";
      }
      enum "no-label-entry" {
        value 11;
        description
          "No label entry";
      }
      enum "protocol-to-fec-mismatch" {
        value 12;
        description
          "Protocol not associated with interface at FEC";
      }
      enum "termination" {
        value 13;
        description
          "Premature termination of ping due to label
           stack shrinking to a single label";
      }
      enum "dd-map-tlv" {
        value 14;
        description
          "DDMAP Tlv";
      }
      enum "label-switch-fec" {
        value 15;
        description
          "Label switched with fec change";
      }
      enum "ping-not-authorized" {
        value 16;
        description
          "Proxy Ping not authorized";
      }
      enum "ping-params-modify" {
        value 17;
        description
          "Proxy Ping parameters need to be modified";
      }
      enum "request-not-send" {
        value 18;
        description
          "MPLS Echo Request could not be sent";
      }
      enum "fec-map-top-fec" {
        value 19;
        description
          "Replying router has FEC mapping for topmost FEC";
      }
      enum "tlv-fail-mtu" {
        value 20;
        description
          "One or more TLVs not returned due to MTU size";
      }
      enum "unsupported-bfd-ver" {
        value 21;
        description
          "OAM Problem/Unsupported BFD Version";
      }
      enum "unsupported-bfd-encap" {
        value 22;
        description
          "OAM Problem/Unsupported BFD Encapsulation format";
      }
      enum "unsupported-bfd-auth" {
        value 23;
        description
          "OAM Problem/Unsupported BFD Authentication Type";
      }
      enum "unsupported-bfd-auth-key-id" {
        value 24;
        description
          "OAM Problem/Mismatch of BFD Authentication Key ID";
      }
      enum "unsupported-time-stamp" {
        value 25;
        description
          "OAM Problem/Unsupported Timestamp Format";
      }
      enum "unsupported-delay-mode" {
        value 26;
        description
          "OAM Problem/Unsupported Delay Mode";
      }
      enum "unsupported-loss-mode" {
        value 27;
        description
          "OAM Problem/Unsupported Loss Mode";
      }
      enum "unsupported-delay-variation" {
        value 28;
        description
          "OAM Problem/Delay variation unsupported";
      }
      enum "unsupported-dyadic-mode" {
        value 29;
        description
          "OAM Problem/Dyadic mode unsupported";
      }
      enum "unsupported-lbk-mode" {
        value 30;
        description
          "OAM Problem/Loopback mode unsupported";
      }
      enum "unsupported-combined-mode" {
        value 31;
        description
          "OAM Problem/Combined mode unsupported";
      }
      enum "unsupported-fault-mgmt-sig" {
        value 32;
        description
          "OAM Problem/Fault management signaling unsupported";
      }
      enum "create-fail-fault-mgmt-asoc" {
        value 33;
        description
          "OAM Problem/Unable to create fault management association";
      }
      enum "pm-config-error" {
        value 34;
        description
          "OAM Problem/PM Configuration error";
      }
      enum "fec-intf-map-error" {
        value 35;
        description
          "Mapping for this FEC is not associated with the incoming interfac";
      }
      enum "fec-non-df" {
        value 36;
        description
          "The FEC exists on the PE and the behavior is
           to drop the packet because of not DF";
      }
      enum "fec-split-horizon" {
        value 37;
        description
          "The FEC exists on the PE and the behavior is
           to drop the packet because of Split Horizon Filtering";
      }
    }
    description
      "Return codes in MPLS OAM response";
  }

  typedef mpls-oam-return-code {
    type enumeration {
      enum "success" {
        description
          "Successful OAM response";
      }
      enum "malformed-request" {
        description
          "Malformed OAM request";
      }
      enum "errored-tlv" {
        description
          "Errored TLV";
      }
      enum "label-mapping-error" {
        description
          "Label mapping error at egress";
      }
      enum "dsmap-mismatch" {
        description
          "Downstream mapping mismatch";
      }
      enum "upstream-interface-not-found" {
        description
          "Upstream interface not found";
      }
      enum "fec-mismatch" {
        description
          "Forwarding equivalence class mismatch";
      }
      enum "fec-not-found" {
        description
          "Forwarding equivalence class not found";
      }
      enum "echo-timeout" {
        description
          "Echo request timed out";
      }
      enum "ftn-not-found" {
        description
          "FTN not found";
      }
      enum "unknown-error" {
        description
          "Unknown MPLS OAM error";
      }
      enum "pw-not-found" {
        description
          "Pseudowire not found";
      }
    }
    description
      "Return codes in MPLS OAM response";
  }

  typedef mpls-fec-type {
    type enumeration {
      enum "ldp" {
        value 0;
        description
          "FEC type LDP";
      }
      enum "bgp-lu" {
        value 1;
        description
          "FEC type BGP-LU";
      }
      enum "sr-isis" {
        value 2;
        description
          "FEC type SR ISIS";
      }
      enum "sr-ospf" {
        value 3;
        description
          "FEC type SR OSPF";
      }
      enum "scrt" {
        value 4;
        description
          "FEC type SCRT";
      }
      enum "evpn" {
        value 5;
        description
          "FEC type EVPN";
      }
    }
    description
      "FEC type for MPLS ping";
  }

  typedef reply-mode {
    type enumeration {
      enum "do-not-reply" {
        value 1;
        description
          "Do not reply";
      }
      enum "reply-via-udp" {
        value 2;
        description
          "Reply via an IPv4/IPv6 UDP packet";
      }
      enum "reply-via-udp-router-alert" {
        value 3;
        description
          "Reply via an IPv4/IPv6 UDP packet with Router
           Alert. It is used when return path is unreliable";
      }
      enum "reply-via-control-channel" {
        value 4;
        description
          "Reply via application level control channel";
      }
    }
    description
      "The channel throught which reply is expected";
  }

  typedef operational-state {
    type enumeration {
      enum "not-started" {
        value 0;
        description
          "The Ping Test not started.";
      }
      enum "in-progress" {
        value 1;
        description
          "The Ping Test is in progress.";
      }
      enum "cancelled" {
        value 2;
        description
          "The Ping Test is cancelled.";
      }
      enum "completed" {
        value 3;
        description
          "The Ping Test is completed.";
      }
    }
    description
      "Current state of the operation";
  }

  typedef fec-verification-state {
    type enumeration {
      enum "off" {
        value 0;
        description
          "Do not verify FEC Stack.";
      }
      enum "on" {
        value 1;
        description
          "Verify FEC Stack.";
      }
    }
    description
      "Is FEC verification required.";
  }

  typedef oam-result-type {
    type enumeration {
      enum "success" {
        value 0;
        description
          "The probe result is successful.";
      }
      enum "fail" {
        value 1;
        description
          "The probe result is failed.";
      }
      enum "timeout" {
        value 2;
        description
          "The probe result is timeout.";
      }
      enum "unknown-error" {
        value 3;
        description
          "Unknown MPLS OAM error.";
      }
      enum "ftn-not-found" {
        value 4;
        description
          "FTN not found.";
      }
      enum "pw-not-found" {
        value 5;
        description
          "Pseudowire not found.";
      }
      enum "evpn-instance-not-found" {
        value 6;
        description
          "Evpn instance not found.";
      }
      enum "evpn-multiple-fec-found" {
        value 7;
        description
          "Evpn multiple FEC found.";
      }
      enum "tunnel-not-found" {
        value 8;
        description
          "Tunnel not found";
      }
      enum "tunnel-admin-down" {
        value 9;
        description
          "Tunnel admin down.";
      }
    }
    description
      "Probe Result type";
  }

  typedef encap-ip-udp {
    type enumeration {
      enum "non-ip/udp" {
        value 0;
        description
          "Don't need to encapsulate ip/udp in frame.";
      }
      enum "ip/udp" {
        value 1;
        description
          "Need to encapsulate ip/udp in frame.";
      }
    }
    description
      "Does IP/UDP needs to be encapsulated";
  }

  grouping ncs_template_oam-base-config-params {
    description
      "Configurable parameters for the Ping test.";
    leaf traffic-class {
      type string;
      // NCS drop default statement
      description
        "Specifies the Traffic Class.";
    }
    leaf reply-mode {
      type ncs_template_reply-mode;
      // NCS drop default statement
      description
        "Specifies the reply mode requested.";
    }
    leaf timeout {
      type string;
      units "seconds";
      // NCS drop default statement
      description
        "Specifies the timeout value in seconds for
         a Ping request.";
    }
    leaf interval {
      type string;
      units "seconds";
      // NCS drop default statement
      description
        "Specifies the interval in seconds to send a ping echo
         request packet(probe) as part of one Ping test.";
    }
    leaf repeat-count {
      type string;
      // NCS drop default statement
      description
        "Specifies the number of echo requests sent for
         one Ping test.";
    }
    leaf ttl {
      type string;
      // NCS drop default statement
      description
        "Time to live.";
    }
    leaf data-size {
      type string;
      units "bytes";
      description
        "Specifies the size of the data bytes to be
         transmitted in each Ping request.";
    }
    leaf source-ip {
      type string;
      description
        "Source IP to start ping.";
    }
  }

  grouping ncs_template_ping-base-input-options {
    status deprecated;
    leaf interval {
      type string;
      units "milliseconds";
      // NCS drop default statement
      description
        "Send delay between requests in milliseconds";
    }
    leaf repeat-count {
      type string;
      // NCS drop default statement
      description
        "Number of packets to be sent out";
    }
    leaf timeout {
      type string;
      units "seconds";
      // NCS drop default statement
      description
        "Timeout value in seconds";
    }
    leaf ttl {
      type string;
      // NCS drop default statement
      description
        "Time-to-live value";
    }
    description
      "Input options for ciena-ip-oam.yang and ciena-mpls-ping.yang";
  }

  grouping ncs_template_ping-base-output {
    status deprecated;
    leaf rtt {
      type string;
      units "milliseconds";
      description
        "Round trip time for an echo request in milliseconds";
    }
    description
      "Output options for ciena-ip-oam.yang and ciena-mpls-ping.yang";
  }

  grouping ncs_rpc_notif_oam-base-config-params {
    description
      "Configurable parameters for the Ping test.";
    leaf traffic-class {
      type uint8 {
        range "0..7";
      }
      default "0";
      description
        "Specifies the Traffic Class.";
    }
    leaf reply-mode {
      type ncs_rpc_notif_reply-mode;
      default "reply-via-udp";
      description
        "Specifies the reply mode requested.";
    }
    leaf timeout {
      type uint8 {
        range "1..60";
      }
      units "seconds";
      default "1";
      description
        "Specifies the timeout value in seconds for
         a Ping request.";
    }
    leaf interval {
      type uint8 {
        range "1..20";
      }
      units "seconds";
      default "1";
      description
        "Specifies the interval in seconds to send a ping echo
         request packet(probe) as part of one Ping test.";
    }
    leaf repeat-count {
      type uint8 {
        range "1..100";
      }
      default "5";
      description
        "Specifies the number of echo requests sent for
         one Ping test.";
    }
    leaf ttl {
      type uint8 {
        range "1..255";
      }
      default "255";
      description
        "Time to live.";
    }
    leaf data-size {
      type uint16 {
        range "36..18000";
      }
      units "bytes";
      description
        "Specifies the size of the data bytes to be
         transmitted in each Ping request.";
    }
    leaf source-ip {
      type inet:ip-address;
      description
        "Source IP to start ping.";
    }
  }

  grouping ncs_rpc_notif_ping-base-input-options {
    status deprecated;
    leaf interval {
      type uint16 {
        range "1000..20000";
      }
      units "milliseconds";
      default "1000";
      description
        "Send delay between requests in milliseconds";
    }
    leaf repeat-count {
      type uint16 {
        range "5..200";
      }
      default "5";
      description
        "Number of packets to be sent out";
    }
    leaf timeout {
      type uint16 {
        range "1..60";
      }
      units "seconds";
      default "2";
      description
        "Timeout value in seconds";
    }
    leaf ttl {
      type uint8 {
        range "1..255";
      }
      default "255";
      description
        "Time-to-live value";
    }
    description
      "Input options for ciena-ip-oam.yang and ciena-mpls-ping.yang";
  }

  grouping ncs_rpc_notif_ping-base-output {
    status deprecated;
    leaf rtt {
      type decimal64 {
        fraction-digits 2;
      }
      units "milliseconds";
      description
        "Round trip time for an echo request in milliseconds";
    }
    description
      "Output options for ciena-ip-oam.yang and ciena-mpls-ping.yang";
  }

  grouping live_ncs_oam-base-config-params {
    description
      "Configurable parameters for the Ping test.";
    leaf traffic-class {
      type uint8 {
        range "0..7";
      }
      // NCS drop default statement
      description
        "Specifies the Traffic Class.";
    }
    leaf reply-mode {
      type live_ncs_reply-mode;
      // NCS drop default statement
      description
        "Specifies the reply mode requested.";
    }
    leaf timeout {
      type uint8 {
        range "1..60";
      }
      units "seconds";
      // NCS drop default statement
      description
        "Specifies the timeout value in seconds for
         a Ping request.";
    }
    leaf interval {
      type uint8 {
        range "1..20";
      }
      units "seconds";
      // NCS drop default statement
      description
        "Specifies the interval in seconds to send a ping echo
         request packet(probe) as part of one Ping test.";
    }
    leaf repeat-count {
      type uint8 {
        range "1..100";
      }
      // NCS drop default statement
      description
        "Specifies the number of echo requests sent for
         one Ping test.";
    }
    leaf ttl {
      type uint8 {
        range "1..255";
      }
      // NCS drop default statement
      description
        "Time to live.";
    }
    leaf data-size {
      type uint16 {
        range "36..18000";
      }
      units "bytes";
      description
        "Specifies the size of the data bytes to be
         transmitted in each Ping request.";
    }
    leaf source-ip {
      type inet:ip-address;
      description
        "Source IP to start ping.";
    }
  }

  grouping live_ncs_ping-base-input-options {
    status deprecated;
    leaf interval {
      type uint16 {
        range "1000..20000";
      }
      units "milliseconds";
      // NCS drop default statement
      description
        "Send delay between requests in milliseconds";
    }
    leaf repeat-count {
      type uint16 {
        range "5..200";
      }
      // NCS drop default statement
      description
        "Number of packets to be sent out";
    }
    leaf timeout {
      type uint16 {
        range "1..60";
      }
      units "seconds";
      // NCS drop default statement
      description
        "Timeout value in seconds";
    }
    leaf ttl {
      type uint8 {
        range "1..255";
      }
      // NCS drop default statement
      description
        "Time-to-live value";
    }
    description
      "Input options for ciena-ip-oam.yang and ciena-mpls-ping.yang";
  }

  grouping live_ncs_ping-base-output {
    status deprecated;
    leaf rtt {
      type decimal64 {
        fraction-digits 2;
      }
      units "milliseconds";
      description
        "Round trip time for an echo request in milliseconds";
    }
    description
      "Output options for ciena-ip-oam.yang and ciena-mpls-ping.yang";
  }

  grouping oam-base-config-params {
    description
      "Configurable parameters for the Ping test.";
    leaf traffic-class {
      type uint8 {
        range "0..7";
      }
      default "0";
      description
        "Specifies the Traffic Class.";
    }
    leaf reply-mode {
      type reply-mode;
      default "reply-via-udp";
      description
        "Specifies the reply mode requested.";
    }
    leaf timeout {
      type uint8 {
        range "1..60";
      }
      units "seconds";
      default "1";
      description
        "Specifies the timeout value in seconds for
         a Ping request.";
    }
    leaf interval {
      type uint8 {
        range "1..20";
      }
      units "seconds";
      default "1";
      description
        "Specifies the interval in seconds to send a ping echo
         request packet(probe) as part of one Ping test.";
    }
    leaf repeat-count {
      type uint8 {
        range "1..100";
      }
      default "5";
      description
        "Specifies the number of echo requests sent for
         one Ping test.";
    }
    leaf ttl {
      type uint8 {
        range "1..255";
      }
      default "255";
      description
        "Time to live.";
    }
    leaf data-size {
      type uint16 {
        range "36..18000";
      }
      units "bytes";
      description
        "Specifies the size of the data bytes to be
         transmitted in each Ping request.";
    }
    leaf source-ip {
      type inet:ip-address;
      description
        "Source IP to start ping.";
    }
  }

  grouping ping-base-input-options {
    status deprecated;
    leaf interval {
      type uint16 {
        range "1000..20000";
      }
      units "milliseconds";
      default "1000";
      description
        "Send delay between requests in milliseconds";
    }
    leaf repeat-count {
      type uint16 {
        range "5..200";
      }
      default "5";
      description
        "Number of packets to be sent out";
    }
    leaf timeout {
      type uint16 {
        range "1..60";
      }
      units "seconds";
      default "2";
      description
        "Timeout value in seconds";
    }
    leaf ttl {
      type uint8 {
        range "1..255";
      }
      default "255";
      description
        "Time-to-live value";
    }
    description
      "Input options for ciena-ip-oam.yang and ciena-mpls-ping.yang";
  }

  grouping ping-base-output {
    status deprecated;
    leaf rtt {
      type decimal64 {
        fraction-digits 2;
      }
      units "milliseconds";
      description
        "Round trip time for an echo request in milliseconds";
    }
    description
      "Output options for ciena-ip-oam.yang and ciena-mpls-ping.yang";
  }
}
