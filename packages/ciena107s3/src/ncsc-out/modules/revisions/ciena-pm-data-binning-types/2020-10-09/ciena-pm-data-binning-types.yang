module ciena-pm-data-binning-types {
  // Generated by yanger -t ncs
  tailf:mount-id "ciena107s3-nc-1.0:ciena107s3-nc-1.0";
  tailf:ncs-device-type "netconf";

  namespace "http://www.ciena.com/ns/yang/ciena-pm-data-binning-types";
  prefix ciena-pm-data-binning-types;

  import tailf-common {
    prefix tailf;
  }
  import tailf-ncs {
    prefix ncs;
  }

  organization
    "Ciena Corporation";
  contact
    "Web URL: http://www.ciena.com/
     E-mail:  yang@ciena.com
     Postal:  7035 Ridge Road
              Hanover, Maryland 21076
              U.S.A.
     Phone:   +1 800-921-1144
     Fax:     +1 410-694-5750";
  description
    "This YANG module defines typing for Ciena's global
     configuration for network device health and performance monitoring
     and data binning ability and provides a view into such
     operational stats being collected across the network device functional
     modules.

     Copyright (c) 2020 Ciena Corporation. All rights
     reserved.

     All information contained herein is, and remains
     the property of Ciena Corporation. Dissemination of this
     information or reproduction of this material is strictly
     forbidden unless prior written permission is obtained from
     Ciena Corporation.";

  revision 2020-10-09 {
    description
      "Initial version for proposing network device health
       monitoring and performance monitoring data binning ability";
    reference "No Specific Reference. Standard not available";
  }

  typedef ncs_template_cn-pmdb-oper-state {
    description
      "Operational state of corresponding node.";
    type string;
  }

  typedef ncs_template_cn-pmdb-bin-state {
    description
      "Final collection state of the bin.";
    type string;
  }

  typedef ncs_rpc_notif_cn-pmdb-oper-state {
    description
      "Operational state of corresponding node.";
    type enumeration {
      enum "enabled" {
        description
          "Node is operationally enabled.";
      }
      enum "disabled" {
        description
          "Node is operationally disabled.";
      }
      enum "invalid" {
        description
          "Node is operationally disabled due
           to invalid configuration.";
      }
    }
  }

  typedef ncs_rpc_notif_cn-pmdb-bin-state {
    description
      "Final collection state of the bin.";
    type enumeration {
      enum "partial" {
        description
          "Stats have not been collected over the full bin duration.";
      }
      enum "complete" {
        description
          "Stats have been collected over the full bin duration.";
      }
    }
  }

  typedef live_ncs_cn-pmdb-oper-state {
    description
      "Operational state of corresponding node.";
    type enumeration {
      enum "enabled" {
        description
          "Node is operationally enabled.";
      }
      enum "disabled" {
        description
          "Node is operationally disabled.";
      }
      enum "invalid" {
        description
          "Node is operationally disabled due
           to invalid configuration.";
      }
    }
  }

  typedef live_ncs_cn-pmdb-bin-state {
    description
      "Final collection state of the bin.";
    type enumeration {
      enum "partial" {
        description
          "Stats have not been collected over the full bin duration.";
      }
      enum "complete" {
        description
          "Stats have been collected over the full bin duration.";
      }
    }
  }

  typedef cn-pmdb-oper-state {
    description
      "Operational state of corresponding node.";
    type enumeration {
      enum "enabled" {
        description
          "Node is operationally enabled.";
      }
      enum "disabled" {
        description
          "Node is operationally disabled.";
      }
      enum "invalid" {
        description
          "Node is operationally disabled due
           to invalid configuration.";
      }
    }
  }

  typedef cn-pmdb-bin-state {
    description
      "Final collection state of the bin.";
    type enumeration {
      enum "partial" {
        description
          "Stats have not been collected over the full bin duration.";
      }
      enum "complete" {
        description
          "Stats have been collected over the full bin duration.";
      }
    }
  }
}
