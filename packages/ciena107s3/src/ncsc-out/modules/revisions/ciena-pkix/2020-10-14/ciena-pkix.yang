module ciena-pkix {
  // Generated by yanger -t ncs
  tailf:mount-id "ciena107s3-nc-1.0:ciena107s3-nc-1.0";
  tailf:ncs-device-type "netconf";

  namespace "http://www.ciena.com/ns/yang/ciena-pkix";
  prefix pkix;

  import ciena-pkix-types {
    prefix pkix-types;
  }
  import ciena-packet-typedefs {
    prefix cntypes;
  }
  import tailf-common {
    prefix tailf;
  }
  import tailf-ncs {
    prefix ncs;
  }

  organization
    "Ciena Corporation";
  contact
    "Web URL: http://www.ciena.com/
     E-mail:  yang@ciena.com
     Postal:  7035 Ridge Road
              Hanover, Maryland 21076
              U.S.A.
     Phone:   +1 800-921-1144
     Fax:     +1 410-694-5750";
  description
    "This YANG module defines the nodes for Public Key Infrastructure
     (PKI) Security Certificates CA (Certificate Authority) and CRL
     (Certificate Revocation List) for the NETCONF protocol.

     Copyright (c) 2016-2017 Ciena Corporation.  All rights reserved.

     All information contained herein is, and remains the property of
     Ciena Corporation. Dissemination of this information or
     reproduction of this material is strictly forbidden unless prior
     written permission is obtained from Ciena Corporation.";

  revision 2020-10-14 {
    description
      "Adding csr generate event, user to install/uninstall events, and range for cert name lengths
       Adding default for check-expiry, check-fingerprint, check-ip-host";
    reference "No specific reference; standard not available.";
  }
  revision 2020-08-04 {
    description
      "Adding uninstalled certificates";
    reference "No specific reference; standard not available.";
  }
  revision 2020-01-20 {
    description
      "Adding list of acceptable fingerprints.
       Adding next-update in crl";
    reference "No specific reference; standard not available.";
  }
  revision 2019-12-20 {
    description
      "Adding list of acceptable ips/hostnames and updating the
       description text for container pkix";
    reference "No specific reference; standard not available.";
  }
  revision 2018-05-01 {
    description
      "Update to reflect requirements for the 10.1 release";
    reference "No specific reference; standard not available.";
  }
  revision 2017-10-18 {
    description
      "Initial version";
    reference
      "RFC 6020: YANG - A Data Modeling Language for
       the Network Configuration Protocol (NETCONF).
       No specific reference; standard not available.";
  }

  augment "/ncs:devices/ncs:device/ncs:notifications/ncs:received-notifications/ncs:notification/ncs:data" {
    container certificate-expiry {
      presence "";
      config false;
      description
        "Certificate expiry notification";
      leaf cert-name {
        description
          "Cert Name";
        type string;
      }
      leaf days-until {
        type uint32;
        description
          "Days until expiration";
      }
      leaf expired {
        type boolean;
        description
          "Whether cert is expired";
      }
    }
  }
  augment "/ncs:devices/ncs:device/ncs:notifications/ncs:received-notifications/ncs:notification/ncs:data" {
    container csr-generate {
      presence "";
      config false;
      description
        "Csr generation notification";
      leaf key-name {
        description
          "Unique Key Name";
        type string;
      }
      leaf user {
        type string;
        description
          "The user of the operation";
      }
      leaf operation {
        type string;
        description
          "The operation done on the csr";
      }
      leaf result {
        type string;
        description
          "The result of the operation";
      }
    }
  }
  augment "/ncs:devices/ncs:device/ncs:notifications/ncs:received-notifications/ncs:notification/ncs:data" {
    container device-certificate-change {
      presence "";
      config false;
      description
        "Device certificate change notification";
      leaf device-certificate {
        type string;
        description
          "Device certificate that changed";
      }
      leaf operation {
        type string;
        description
          "The operation done on the device certificate";
      }
      leaf result {
        type string;
        description
          "The result of the operation";
      }
      leaf user {
        type string;
        description
          "The user of the operation";
      }
    }
  }
  augment "/ncs:devices/ncs:device/ncs:notifications/ncs:received-notifications/ncs:notification/ncs:data" {
    container crl-change {
      presence "";
      config false;
      description
        "CRL change notification";
      leaf crl {
        type string;
        description
          "CRL that changed";
      }
      leaf operation {
        type string;
        description
          "The operation done on the CRL";
      }
      leaf result {
        type string;
        description
          "The result of the operation";
      }
      leaf user {
        type string;
        description
          "The user of the operation";
      }
    }
  }
  augment "/ncs:devices/ncs:device/ncs:notifications/ncs:received-notifications/ncs:notification/ncs:data" {
    container ca-certificate-change {
      presence "";
      config false;
      description
        "CA certificate change notification";
      leaf ca-certificate {
        type string;
        description
          "CA certificate that changed";
      }
      leaf operation {
        type string;
        description
          "The operation done on the CA certificate";
      }
      leaf result {
        type string;
        description
          "The result of the operation";
      }
      leaf user {
        type string;
        description
          "The user of the operation";
      }
    }
  }
  augment "/ncs:devices/ncs:device/ncs:netconf-notifications/ncs:received-notifications/ncs:notification/ncs:data" {
    container certificate-expiry {
      presence "";
      config false;
      description
        "Certificate expiry notification";
      leaf cert-name {
        description
          "Cert Name";
        type string;
      }
      leaf days-until {
        type uint32;
        description
          "Days until expiration";
      }
      leaf expired {
        type boolean;
        description
          "Whether cert is expired";
      }
    }
  }
  augment "/ncs:devices/ncs:device/ncs:netconf-notifications/ncs:received-notifications/ncs:notification/ncs:data" {
    container csr-generate {
      presence "";
      config false;
      description
        "Csr generation notification";
      leaf key-name {
        description
          "Unique Key Name";
        type string;
      }
      leaf user {
        type string;
        description
          "The user of the operation";
      }
      leaf operation {
        type string;
        description
          "The operation done on the csr";
      }
      leaf result {
        type string;
        description
          "The result of the operation";
      }
    }
  }
  augment "/ncs:devices/ncs:device/ncs:netconf-notifications/ncs:received-notifications/ncs:notification/ncs:data" {
    container device-certificate-change {
      presence "";
      config false;
      description
        "Device certificate change notification";
      leaf device-certificate {
        type string;
        description
          "Device certificate that changed";
      }
      leaf operation {
        type string;
        description
          "The operation done on the device certificate";
      }
      leaf result {
        type string;
        description
          "The result of the operation";
      }
      leaf user {
        type string;
        description
          "The user of the operation";
      }
    }
  }
  augment "/ncs:devices/ncs:device/ncs:netconf-notifications/ncs:received-notifications/ncs:notification/ncs:data" {
    container crl-change {
      presence "";
      config false;
      description
        "CRL change notification";
      leaf crl {
        type string;
        description
          "CRL that changed";
      }
      leaf operation {
        type string;
        description
          "The operation done on the CRL";
      }
      leaf result {
        type string;
        description
          "The result of the operation";
      }
      leaf user {
        type string;
        description
          "The user of the operation";
      }
    }
  }
  augment "/ncs:devices/ncs:device/ncs:netconf-notifications/ncs:received-notifications/ncs:notification/ncs:data" {
    container ca-certificate-change {
      presence "";
      config false;
      description
        "CA certificate change notification";
      leaf ca-certificate {
        type string;
        description
          "CA certificate that changed";
      }
      leaf operation {
        type string;
        description
          "The operation done on the CA certificate";
      }
      leaf result {
        type string;
        description
          "The result of the operation";
      }
      leaf user {
        type string;
        description
          "The user of the operation";
      }
    }
  }
  augment "/ncs:devices/ncs:device/ncs:config" {
    container pkix {
      tailf:ncs-device-type "netconf";
      tailf:display-when "not(../../ncs:module) or ../../ncs:module[ncs:name='ciena-pkix']";
      description
        "PKIX management configuration data for peer authentication";
      container peer-auth-profiles {
        description
          "Controls how a peer certificate is validated";
        list peer-auth-profile {
          key "peer-auth-profile-name";
          description
            "The peer-auth-profile list.";
          leaf peer-auth-profile-name {
            type string;
            description
              "The user defined peer-auth-profile name.";
          }
          leaf check-cert-expiry {
            type boolean;
            default "false";
            description
              "Enforces the expiry dates provided in the certificates.";
          }
          leaf check-ip-host {
            type boolean;
            default "false";
            description
              "Validates the peer hostname or ip against the certificate subject name";
          }
          leaf check-fingerprint {
            type boolean;
            default "false";
            description
              "Verifies the peer certificate fingerprint against locally configured value";
          }
          leaf periodic-reauthorization-max-interval {
            type uint32 {
              range "600..86400";
            }
            units "seconds";
            description
              "The maximum amount of time to wait before
               reauthorizing the connection.";
          }
          leaf-list ip-host-list {
            type string;
            description
              "List of acceptable server connections. Can be IP or it can be hostname";
          }
          leaf-list fingerprint-list {
            type cntypes:fingerprint;
            description
              "List of acceptable certificate fingerprints";
          }
        }
      }
    }
    // NCS drop config false container 'pkix-state'
  }
  augment "/ncs:devices/ncs:device/ncs:live-status" {
    container pkix {
      tailf:ncs-device-type "netconf";
      tailf:display-when "not(../../ncs:module) or ../../ncs:module[ncs:name='ciena-pkix'] or (../../ncs:live-status-protocol[not(ncs:capability)]) or (../../ncs:live-status-protocol/ncs:capability/ncs:module[.='ciena-pkix'])";
      description
        "PKIX management configuration data for peer authentication";
      container peer-auth-profiles {
        description
          "Controls how a peer certificate is validated";
        list peer-auth-profile {
          key "peer-auth-profile-name";
          description
            "The peer-auth-profile list.";
          leaf peer-auth-profile-name {
            type string;
            description
              "The user defined peer-auth-profile name.";
          }
          leaf check-cert-expiry {
            type boolean;
            // NCS drop default statement
            description
              "Enforces the expiry dates provided in the certificates.";
          }
          leaf check-ip-host {
            type boolean;
            // NCS drop default statement
            description
              "Validates the peer hostname or ip against the certificate subject name";
          }
          leaf check-fingerprint {
            type boolean;
            // NCS drop default statement
            description
              "Verifies the peer certificate fingerprint against locally configured value";
          }
          leaf periodic-reauthorization-max-interval {
            type uint32 {
              range "600..86400";
            }
            units "seconds";
            description
              "The maximum amount of time to wait before
               reauthorizing the connection.";
          }
          leaf-list ip-host-list {
            type string;
            description
              "List of acceptable server connections. Can be IP or it can be hostname";
          }
          leaf-list fingerprint-list {
            type cntypes:live_ncs_fingerprint;
            description
              "List of acceptable certificate fingerprints";
          }
        }
      }
    }
    container pkix-state {
      tailf:ncs-device-type "netconf";
      tailf:display-when "not(../../ncs:module) or ../../ncs:module[ncs:name='ciena-pkix'] or (../../ncs:live-status-protocol[not(ncs:capability)]) or (../../ncs:live-status-protocol/ncs:capability/ncs:module[.='ciena-pkix'])";
      description
        "Device Certificates, CA certificates and CRL state.";
      container ca-certificates {
        description
          "CA certificates.";
        list ca-certificate {
          key "ca-name";
          description
            "The CA certificate list.";
          leaf ca-name {
            type string {
              length "1..255";
            }
            description
              "The user defined CA  name.";
          }
          uses pkix-types:live_ncs_pkix-certificate-fields;
        }
      }
      container crls {
        description
          "Certificate Revocation Lists.";
        list crl {
          key "crl-name";
          leaf crl-name {
            type string {
              length "1..255";
            }
            description
              "The user defined crl name";
          }
          leaf issuer-common-name {
            type string;
            description
              "The CRL issuer common name.";
          }
          leaf last-update {
            type string;
            description
              "The CRL last update.";
          }
          leaf next-update {
            type string;
            description
              "The CRL next update.";
          }
          leaf revoked-cert-count {
            type int32;
            description
              "The CRL revoked certificate count.";
          }
          description
            "The CRL Certificate List.";
        }
      }
      container device-certificates {
        description
          "device certificates.";
        list device-certificate {
          key "certificate-name";
          description
            "The device certificate list.";
          leaf certificate-name {
            type string {
              length "1..255";
            }
            description
              "The device certificate name";
          }
          leaf algorithm-identifier {
            type identityref {
              base pkix-types:key-algorithm;
            }
            description
              "Identifies which algorithm was used to generate the key.
               Also referred to within SAOS as key-type.";
          }
          leaf private-key {
            type enumeration {
              enum "present" {
                description
                  "key is present";
              }
              enum "not-present" {
                description
                  "key is not present";
              }
            }
            description
              "The state of the d certificate name";
          }
          uses pkix-types:live_ncs_pkix-certificate-fields;
        }
      }
      container uninstalled-certificates {
        leaf-list uninstalled-certificate-name {
          type string {
            length "1..255";
          }
        }
      }
    }
  }
  augment "/ncs:devices/ncs:template/ncs:ned-id/ncs:config" {
    container pkix {
      description
        "PKIX management configuration data for peer authentication";
      container peer-auth-profiles {
        description
          "Controls how a peer certificate is validated";
        list peer-auth-profile {
          // NCS patched for predictable order
          ordered-by user;
          key "peer-auth-profile-name";
          description
            "The peer-auth-profile list.";
          leaf peer-auth-profile-name {
            type string;
            description
              "The user defined peer-auth-profile name.";
          }
          leaf check-cert-expiry {
            type string;
            // NCS drop default statement
            description
              "Enforces the expiry dates provided in the certificates.";
          }
          leaf check-ip-host {
            type string;
            // NCS drop default statement
            description
              "Validates the peer hostname or ip against the certificate subject name";
          }
          leaf check-fingerprint {
            type string;
            // NCS drop default statement
            description
              "Verifies the peer certificate fingerprint against locally configured value";
          }
          leaf periodic-reauthorization-max-interval {
            type string;
            units "seconds";
            description
              "The maximum amount of time to wait before
               reauthorizing the connection.";
          }
          leaf-list ip-host-list {
            // NCS patched for predictable order
            ordered-by user;
            type string;
            description
              "List of acceptable server connections. Can be IP or it can be hostname";
          }
          leaf-list fingerprint-list {
            // NCS patched for predictable order
            ordered-by user;
            type cntypes:ncs_template_fingerprint;
            description
              "List of acceptable certificate fingerprints";
          }
        }
      }
    }
    // NCS drop config false container 'pkix-state'
  }
}
