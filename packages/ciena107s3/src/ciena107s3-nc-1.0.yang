module ciena107s3-nc-1.0 {
  yang-version 1.1;
  namespace "http://tail-f.com/ns/ned-id/ciena107s3-nc-1.0";
  prefix ciena107s3-nc-1.0;

  import ciena107s3-nc {
    prefix family;
  }

  identity ciena107s3-nc-1.0 {
    base family:ciena107s3-nc;
  }
}
