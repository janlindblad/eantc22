module huawei-nc-1.0 {
  yang-version 1.1;
  namespace "http://tail-f.com/ns/ned-id/huawei-nc-1.0";
  prefix huawei-nc-1.0;

  import huawei-nc {
    prefix family;
  }

  identity huawei-nc-1.0 {
    base family:huawei-nc;
  }
}
