module huawei-port-group {
  // Generated by yanger -t ncs
  tailf:mount-id "huawei-nc-1.0:huawei-nc-1.0";
  tailf:ncs-device-type "netconf";

  namespace "urn:huawei:yang:huawei-port-group";
  prefix port-group;

  import huawei-ifm {
    prefix ifm;
  }
  import huawei-extension {
    prefix ext;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Display permanent port group information.";

  revision 2019-04-17 {
    description
      "Initial revision.";
    reference "Huawei private.";
  }
  ext:task-name "interface-mgr";

  augment "/ncs:devices/ncs:device/ncs:rpc" {
    container rpc-port-group-shutdown {
      tailf:ncs-device-type "netconf";
      tailf:display-when "not(../../ncs:module) or ../../ncs:module[ncs:name='huawei-port-group']";
      tailf:action port-group-shutdown {
        tailf:actionpoint ncsproxy {
          tailf:internal;
        }
        description
          "Configure the administrative status of permanent port group member interfaces.";
        input {
          leaf name {
            type string;
            mandatory true;
            description
              "Specify the name of a permanent port group.";
          }
          leaf shutdown {
            type boolean;
            default "false";
            description
              "Shutdown member interfaces of the permanent port group.";
          }
        }
      }
    }
  }
  augment "/ncs:devices/ncs:device-group/ncs:ned-id/ncs:rpc" {
    container rpc-port-group-shutdown {
      tailf:ncs-device-type "netconf";
      tailf:display-when "/ncs:devices/ncs:device[ncs:name=current()/../../../ncs:member]/ncs:module[ncs:name='huawei-port-group']";
      tailf:action port-group-shutdown {
        tailf:actionpoint ncsproxy {
          tailf:internal;
        }
        description
          "Configure the administrative status of permanent port group member interfaces.";
        input {
          leaf name {
            type string;
            mandatory true;
            description
              "Specify the name of a permanent port group.";
          }
          leaf shutdown {
            type boolean;
            default "false";
            description
              "Shutdown member interfaces of the permanent port group.";
          }
        }
      }
    }
  }
  augment "/ncs:devices/ncs:device/ncs:config" {
    container port-group {
      tailf:ncs-device-type "netconf";
      tailf:display-when "not(../../ncs:module) or ../../ncs:module[ncs:name='huawei-port-group']";
      description
        "Display permanent port group information.";
      container groups {
        description
          "List of permanent port groups.";
        list group {
          key "name";
          description
            "Configure a permanent port group.";
          leaf name {
            type string {
              length "1..32";
            }
            ext:case-sensitivity "lower-or-upper";
            description
              "Specify the name of a permanent port group.";
          }
          container members {
            description
              "List of permanent port group member interfaces.";
            list member {
              key "if-name";
              description
                "Configure permanent port group member interfaces.";
              leaf if-name {
                type leafref {
                  path "/ncs:devices/ncs:device/ncs:config/ifm:ifm/ifm:interfaces/ifm:interface/ifm:name" {
                    tailf:xpath-root 3;
                  }
                }
                description
                  "Configure the name of a permanent port group member interface.";
              }
            }
          }
        }
      }
    }
  }
  augment "/ncs:devices/ncs:device/ncs:live-status" {
    container port-group {
      tailf:ncs-device-type "netconf";
      tailf:display-when "not(../../ncs:module) or ../../ncs:module[ncs:name='huawei-port-group'] or (../../ncs:live-status-protocol[not(ncs:capability)]) or (../../ncs:live-status-protocol/ncs:capability/ncs:module[.='huawei-port-group'])";
      description
        "Display permanent port group information.";
      container groups {
        description
          "List of permanent port groups.";
        list group {
          key "name";
          description
            "Configure a permanent port group.";
          leaf name {
            type string {
              length "1..32";
            }
            ext:case-sensitivity "lower-or-upper";
            description
              "Specify the name of a permanent port group.";
          }
          container members {
            description
              "List of permanent port group member interfaces.";
            list member {
              key "if-name";
              description
                "Configure permanent port group member interfaces.";
              leaf if-name {
                type leafref {
                  path "/ncs:devices/ncs:device/ncs:live-status/ifm:ifm/ifm:interfaces/ifm:interface/ifm:name" {
                    tailf:xpath-root 3;
                  }
                }
                description
                  "Configure the name of a permanent port group member interface.";
              }
            }
          }
        }
      }
    }
  }
  augment "/ncs:devices/ncs:template/ncs:ned-id/ncs:config" {
    container port-group {
      description
        "Display permanent port group information.";
      container groups {
        description
          "List of permanent port groups.";
        list group {
          // NCS patched for predictable order
          ordered-by user;
          key "name";
          description
            "Configure a permanent port group.";
          leaf name {
            type string;
            ext:case-sensitivity "lower-or-upper";
            description
              "Specify the name of a permanent port group.";
          }
          container members {
            description
              "List of permanent port group member interfaces.";
            list member {
              // NCS patched for predictable order
              ordered-by user;
              key "if-name";
              description
                "Configure permanent port group member interfaces.";
              leaf if-name {
                type string;
                description
                  "Configure the name of a permanent port group member interface.";
              }
            }
          }
        }
      }
    }
  }
}
