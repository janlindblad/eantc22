module huawei-driver {
  // Generated by yanger -t ncs
  tailf:mount-id "huawei-nc-1.0:huawei-nc-1.0";
  tailf:ncs-device-type "netconf";

  yang-version 1;
  namespace "urn:huawei:yang:huawei-driver";
  prefix driver;

  import huawei-pub-type {
    prefix pub-type;
  }
  import huawei-extension {
    prefix ext;
  }
  import huawei-devm {
    prefix devm;
  }
  import huawei-hardware-type {
    prefix hardware-type;
  }
  import huawei-ifm {
    prefix ifm;
  }
  import huawei-license {
    prefix lcs;
  }
  include huawei-driver-type;
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Configuration of the driver file.";

  revision 2020-04-02 {
    description
      "Init revision.";
    reference "Huawei private.";
  }
  ext:task-name "device-mgr";

  grouping ncs_template_led-flash-time {
    description
      "Indicator blinking periods.";
    leaf flash-time {
      type string;
      units "s";
      // NCS drop default statement
      description
        "Set the duration in which an indicator blinks.";
    }
    leaf alarm-status-time {
      type string;
      units "s";
      // NCS drop default statement
      description
        "Set the duration in which an indicator does not blink temporarily.";
    }
    leaf cancel-time {
      type string;
      units "min";
      // NCS drop default statement
      description
        "Set the total duration after which an indicator stops blinking.";
    }
  }

  grouping ncs_rpc_notif_led-flash-time {
    description
      "Indicator blinking periods.";
    leaf flash-time {
      type uint32 {
        range "1..5";
      }
      units "s";
      default "3";
      description
        "Set the duration in which an indicator blinks.";
    }
    leaf alarm-status-time {
      type uint32 {
        range "1..5";
      }
      units "s";
      default "3";
      description
        "Set the duration in which an indicator does not blink temporarily.";
    }
    leaf cancel-time {
      type uint32 {
        range "5..60";
      }
      units "min";
      default "10";
      description
        "Set the total duration after which an indicator stops blinking.";
    }
  }

  grouping live_ncs_led-flash-time {
    description
      "Indicator blinking periods.";
    leaf flash-time {
      type uint32 {
        range "1..5";
      }
      units "s";
      // NCS drop default statement
      description
        "Set the duration in which an indicator blinks.";
    }
    leaf alarm-status-time {
      type uint32 {
        range "1..5";
      }
      units "s";
      // NCS drop default statement
      description
        "Set the duration in which an indicator does not blink temporarily.";
    }
    leaf cancel-time {
      type uint32 {
        range "5..60";
      }
      units "min";
      // NCS drop default statement
      description
        "Set the total duration after which an indicator stops blinking.";
    }
  }

  grouping led-flash-time {
    description
      "Indicator blinking periods.";
    leaf flash-time {
      type uint32 {
        range "1..5";
      }
      units "s";
      default "3";
      description
        "Set the duration in which an indicator blinks.";
    }
    leaf alarm-status-time {
      type uint32 {
        range "1..5";
      }
      units "s";
      default "3";
      description
        "Set the duration in which an indicator does not blink temporarily.";
    }
    leaf cancel-time {
      type uint32 {
        range "5..60";
      }
      units "min";
      default "10";
      description
        "Set the total duration after which an indicator stops blinking.";
    }
  }

  augment "/ncs:devices/ncs:device/ncs:rpc" {
    container rpc-set-dcn-management-plane-lock {
      tailf:ncs-device-type "netconf";
      tailf:display-when "not(../../ncs:module) or ../../ncs:module[ncs:name='huawei-driver']";
      tailf:action set-dcn-management-plane-lock {
        tailf:actionpoint ncsproxy {
          tailf:internal;
        }
        description
          "Set dcn-management-plane locked status.";
        input {
          leaf lock-status {
            type ncs_rpc_notif_driver-lock-state-type;
            mandatory true;
            description
              "Locked status.";
          }
        }
      }
    }
  }
  augment "/ncs:devices/ncs:device-group/ncs:ned-id/ncs:rpc" {
    container rpc-set-dcn-management-plane-lock {
      tailf:ncs-device-type "netconf";
      tailf:display-when "/ncs:devices/ncs:device[ncs:name=current()/../../../ncs:member]/ncs:module[ncs:name='huawei-driver']";
      tailf:action set-dcn-management-plane-lock {
        tailf:actionpoint ncsproxy {
          tailf:internal;
        }
        description
          "Set dcn-management-plane locked status.";
        input {
          leaf lock-status {
            type ncs_rpc_notif_driver-lock-state-type;
            mandatory true;
            description
              "Locked status.";
          }
        }
      }
    }
  }
  augment "/ncs:devices/ncs:device/ncs:rpc" {
    container rpc-set-next-chassis-id {
      tailf:ncs-device-type "netconf";
      tailf:display-when "not(../../ncs:module) or ../../ncs:module[ncs:name='huawei-driver']";
      tailf:action set-next-chassis-id {
        tailf:actionpoint ncsproxy {
          tailf:internal;
        }
        description
          "Set next chassis ID, set a chassis ID to be used at the next startup (warning:system will restart after success, and then take effect).";
        input {
          leaf chassis-id {
            type string {
              length "1..31";
            }
            description
              "Chassis ID.";
          }
          leaf next-chassis-id {
            type uint32 {
              range "1..8";
            }
            description
              "Next chassis ID.";
          }
        }
      }
    }
  }
  augment "/ncs:devices/ncs:device-group/ncs:ned-id/ncs:rpc" {
    container rpc-set-next-chassis-id {
      tailf:ncs-device-type "netconf";
      tailf:display-when "/ncs:devices/ncs:device[ncs:name=current()/../../../ncs:member]/ncs:module[ncs:name='huawei-driver']";
      tailf:action set-next-chassis-id {
        tailf:actionpoint ncsproxy {
          tailf:internal;
        }
        description
          "Set next chassis ID, set a chassis ID to be used at the next startup (warning:system will restart after success, and then take effect).";
        input {
          leaf chassis-id {
            type string {
              length "1..31";
            }
            description
              "Chassis ID.";
          }
          leaf next-chassis-id {
            type uint32 {
              range "1..8";
            }
            description
              "Next chassis ID.";
          }
        }
      }
    }
  }
  augment "/ncs:devices/ncs:device/ncs:rpc" {
    container rpc-set-next-run-mode {
      tailf:ncs-device-type "netconf";
      tailf:display-when "not(../../ncs:module) or ../../ncs:module[ncs:name='huawei-driver']";
      tailf:action set-next-run-mode {
        tailf:actionpoint ncsproxy {
          tailf:internal;
        }
        description
          "Set chassis run mode, set a chassis operating mode to be used at the next startup (warning:system will restart after success, and then take effect).";
        input {
          leaf chassis-id {
            type string {
              length "1..31";
            }
            description
              "Chassis ID.";
          }
          leaf next-run-mode {
            type ncs_rpc_notif_driver-run-mode-type;
            description
              "Next run mode.";
          }
        }
      }
    }
  }
  augment "/ncs:devices/ncs:device-group/ncs:ned-id/ncs:rpc" {
    container rpc-set-next-run-mode {
      tailf:ncs-device-type "netconf";
      tailf:display-when "/ncs:devices/ncs:device[ncs:name=current()/../../../ncs:member]/ncs:module[ncs:name='huawei-driver']";
      tailf:action set-next-run-mode {
        tailf:actionpoint ncsproxy {
          tailf:internal;
        }
        description
          "Set chassis run mode, set a chassis operating mode to be used at the next startup (warning:system will restart after success, and then take effect).";
        input {
          leaf chassis-id {
            type string {
              length "1..31";
            }
            description
              "Chassis ID.";
          }
          leaf next-run-mode {
            type ncs_rpc_notif_driver-run-mode-type;
            description
              "Next run mode.";
          }
        }
      }
    }
  }
  augment "/ncs:devices/ncs:device/ncs:rpc" {
    container rpc-set-next-system-mode {
      tailf:ncs-device-type "netconf";
      tailf:display-when "not(../../ncs:module) or ../../ncs:module[ncs:name='huawei-driver']";
      tailf:action set-next-system-mode {
        tailf:actionpoint ncsproxy {
          tailf:internal;
        }
        description
          "Set next system mode.";
        input {
          leaf next-system-mode {
            type ncs_rpc_notif_driver-system-mode-type;
            description
              "Set next system mode.";
          }
        }
      }
    }
  }
  augment "/ncs:devices/ncs:device-group/ncs:ned-id/ncs:rpc" {
    container rpc-set-next-system-mode {
      tailf:ncs-device-type "netconf";
      tailf:display-when "/ncs:devices/ncs:device[ncs:name=current()/../../../ncs:member]/ncs:module[ncs:name='huawei-driver']";
      tailf:action set-next-system-mode {
        tailf:actionpoint ncsproxy {
          tailf:internal;
        }
        description
          "Set next system mode.";
        input {
          leaf next-system-mode {
            type ncs_rpc_notif_driver-system-mode-type;
            description
              "Set next system mode.";
          }
        }
      }
    }
  }
  augment "/ncs:devices/ncs:device/ncs:rpc" {
    container rpc-sysmac-load {
      tailf:ncs-device-type "netconf";
      tailf:display-when "not(../../ncs:module) or ../../ncs:module[ncs:name='huawei-driver']";
      tailf:action sysmac-load {
        tailf:actionpoint ncsproxy {
          tailf:internal;
        }
        description
          "Loads MAC addresses assigned to multiple VSs.";
        input {
          leaf sysmac-file {
            type string {
              length "1..32";
            }
            mandatory true;
            description
              "The MAC address file for loading. For example, sysmac.txt.";
          }
          leaf slot-id {
            type string {
              length "1..32";
            }
            mandatory true;
            description
              "Slot ID. The slot ID is expressed in the format of slot ID. For example, 1. Here 1 is an example. The value may vary with devices.";
          }
          leaf chassis-id {
            type uint32 {
              range "1..2";
            }
            description
              "Chassis ID. The chassis ID is expressed in the format of chassis ID. For example, 1. Here 1 is an example. The value may vary with devices.";
          }
        }
      }
    }
  }
  augment "/ncs:devices/ncs:device-group/ncs:ned-id/ncs:rpc" {
    container rpc-sysmac-load {
      tailf:ncs-device-type "netconf";
      tailf:display-when "/ncs:devices/ncs:device[ncs:name=current()/../../../ncs:member]/ncs:module[ncs:name='huawei-driver']";
      tailf:action sysmac-load {
        tailf:actionpoint ncsproxy {
          tailf:internal;
        }
        description
          "Loads MAC addresses assigned to multiple VSs.";
        input {
          leaf sysmac-file {
            type string {
              length "1..32";
            }
            mandatory true;
            description
              "The MAC address file for loading. For example, sysmac.txt.";
          }
          leaf slot-id {
            type string {
              length "1..32";
            }
            mandatory true;
            description
              "Slot ID. The slot ID is expressed in the format of slot ID. For example, 1. Here 1 is an example. The value may vary with devices.";
          }
          leaf chassis-id {
            type uint32 {
              range "1..2";
            }
            description
              "Chassis ID. The chassis ID is expressed in the format of chassis ID. For example, 1. Here 1 is an example. The value may vary with devices.";
          }
        }
      }
    }
  }
  augment "/ncs:devices/ncs:device/ncs:rpc" {
    container rpc-multi-level-alarm-boolean {
      tailf:ncs-device-type "netconf";
      tailf:display-when "not(../../ncs:module) or ../../ncs:module[ncs:name='huawei-driver']";
      tailf:action multi-level-alarm-boolean {
        tailf:actionpoint ncsproxy {
          tailf:internal;
        }
        description
          "Multi level alarm boolean output.";
        input {
          leaf operation-flag {
            type ncs_rpc_notif_driver-operation-flag;
            mandatory true;
            description
              "Operation flag (which includes disable, enable).";
          }
          leaf slot {
            type string {
              length "1..31";
            }
            mandatory true;
            description
              "The available slot. The slot is expressed in the format of slotID. For example, 1. Here 1 is an example. The value may vary with devices.";
          }
          leaf index {
            type string {
              length "1..31";
            }
            mandatory true;
            description
              "Index id. The index is expressed in the format of a number. For example, 1. Here 1 is an example. The value may vary with devices.";
          }
          leaf relation {
            type ncs_rpc_notif_driver-relation-type;
            must "(../operation-flag='enable' and ../relation) or (../operation-flag='disable' and not(../relation))" {
              tailf:xpath-root 3;
            }
            description
              "Relation.";
          }
          leaf alarm-level {
            type ncs_rpc_notif_driver-alarm-level-type;
            must "(../operation-flag='enable' and ../alarm-level) or (../operation-flag='disable' and not(../alarm-level))" {
              tailf:xpath-root 3;
            }
            description
              "Alarm level.";
          }
        }
      }
    }
  }
  augment "/ncs:devices/ncs:device-group/ncs:ned-id/ncs:rpc" {
    container rpc-multi-level-alarm-boolean {
      tailf:ncs-device-type "netconf";
      tailf:display-when "/ncs:devices/ncs:device[ncs:name=current()/../../../ncs:member]/ncs:module[ncs:name='huawei-driver']";
      tailf:action multi-level-alarm-boolean {
        tailf:actionpoint ncsproxy {
          tailf:internal;
        }
        description
          "Multi level alarm boolean output.";
        input {
          leaf operation-flag {
            type ncs_rpc_notif_driver-operation-flag;
            mandatory true;
            description
              "Operation flag (which includes disable, enable).";
          }
          leaf slot {
            type string {
              length "1..31";
            }
            mandatory true;
            description
              "The available slot. The slot is expressed in the format of slotID. For example, 1. Here 1 is an example. The value may vary with devices.";
          }
          leaf index {
            type string {
              length "1..31";
            }
            mandatory true;
            description
              "Index id. The index is expressed in the format of a number. For example, 1. Here 1 is an example. The value may vary with devices.";
          }
          leaf relation {
            type ncs_rpc_notif_driver-relation-type;
            must "(../operation-flag='enable' and ../relation) or (../operation-flag='disable' and not(../relation))" {
              tailf:xpath-root 4;
            }
            description
              "Relation.";
          }
          leaf alarm-level {
            type ncs_rpc_notif_driver-alarm-level-type;
            must "(../operation-flag='enable' and ../alarm-level) or (../operation-flag='disable' and not(../alarm-level))" {
              tailf:xpath-root 4;
            }
            description
              "Alarm level.";
          }
        }
      }
    }
  }
  augment "/ncs:devices/ncs:device/ncs:rpc" {
    container rpc-check-lcm-channel {
      tailf:ncs-device-type "netconf";
      tailf:display-when "not(../../ncs:module) or ../../ncs:module[ncs:name='huawei-driver']";
      tailf:action check-lcm-channel {
        tailf:actionpoint ncsproxy {
          tailf:internal;
        }
        description
          "Check lcm channel.";
        output {
          container check-lcm-channel-slots {
            description
              "List of checking results of channels on slots.";
            list check-lcm-channel-slot {
              key "slot interface-name link-slot link-interface-name";
              description
                "The checking result of channels on slot.";
              leaf slot {
                type string {
                  length "1..31";
                }
                description
                  "Slot.";
              }
              leaf interface-name {
                type string {
                  length "1..31";
                }
                description
                  "Interface name.";
              }
              leaf link-slot {
                type string {
                  length "1..31";
                }
                description
                  "Link slot.";
              }
              leaf link-interface-name {
                type string {
                  length "1..31";
                }
                description
                  "Link interface name.";
              }
              leaf product-type {
                type string {
                  length "1..31";
                }
                description
                  "Product type.";
              }
              leaf channel-status {
                type string {
                  length "1..31";
                }
                description
                  "Channel status.";
              }
            }
          }
        }
      }
    }
  }
  augment "/ncs:devices/ncs:device-group/ncs:ned-id/ncs:rpc" {
    container rpc-check-lcm-channel {
      tailf:ncs-device-type "netconf";
      tailf:display-when "/ncs:devices/ncs:device[ncs:name=current()/../../../ncs:member]/ncs:module[ncs:name='huawei-driver']";
      tailf:action check-lcm-channel {
        tailf:actionpoint ncsproxy {
          tailf:internal;
        }
        description
          "Check lcm channel.";
        output {
          container "device" {
            leaf "name" {
              type string;
            }
            leaf "info" {
              type string;
            }
            container "result" {
              container check-lcm-channel-slots {
                description
                  "List of checking results of channels on slots.";
                list check-lcm-channel-slot {
                  key "slot interface-name link-slot link-interface-name";
                  description
                    "The checking result of channels on slot.";
                  leaf slot {
                    type string {
                      length "1..31";
                    }
                    description
                      "Slot.";
                  }
                  leaf interface-name {
                    type string {
                      length "1..31";
                    }
                    description
                      "Interface name.";
                  }
                  leaf link-slot {
                    type string {
                      length "1..31";
                    }
                    description
                      "Link slot.";
                  }
                  leaf link-interface-name {
                    type string {
                      length "1..31";
                    }
                    description
                      "Link interface name.";
                  }
                  leaf product-type {
                    type string {
                      length "1..31";
                    }
                    description
                      "Product type.";
                  }
                  leaf channel-status {
                    type string {
                      length "1..31";
                    }
                    description
                      "Channel status.";
                  }
                }
              }
            }
          }
        }
      }
    }
  }
  augment "/ncs:devices/ncs:device/ncs:rpc" {
    container rpc-set-nv-laser-turn {
      tailf:ncs-device-type "netconf";
      tailf:display-when "not(../../ncs:module) or ../../ncs:module[ncs:name='huawei-driver']";
      tailf:action set-nv-laser-turn {
        tailf:actionpoint ncsproxy {
          tailf:internal;
        }
        ext:node-ref "/devm/ports/port";
        description
          "Set port nv laser.";
        input {
          leaf if-name {
            type string;
            default "0";
            description
              "Remote port index.";
          }
          leaf laser-shutdown {
            type enumeration {
              enum "on" {
                value 0;
                description
                  "Laser open.";
              }
              enum "off" {
                value 1;
                description
                  "Laser close.";
              }
            }
            default "on";
            description
              "Laser open or shut.";
          }
          leaf laser-test-time {
            type uint32 {
              range "200..30000";
            }
            description
              "Laser open time(10ms).";
          }
        }
      }
    }
  }
  augment "/ncs:devices/ncs:device-group/ncs:ned-id/ncs:rpc" {
    container rpc-set-nv-laser-turn {
      tailf:ncs-device-type "netconf";
      tailf:display-when "/ncs:devices/ncs:device[ncs:name=current()/../../../ncs:member]/ncs:module[ncs:name='huawei-driver']";
      tailf:action set-nv-laser-turn {
        tailf:actionpoint ncsproxy {
          tailf:internal;
        }
        ext:node-ref "/devm/ports/port";
        description
          "Set port nv laser.";
        input {
          leaf if-name {
            type string;
            default "0";
            description
              "Remote port index.";
          }
          leaf laser-shutdown {
            type enumeration {
              enum "on" {
                value 0;
                description
                  "Laser open.";
              }
              enum "off" {
                value 1;
                description
                  "Laser close.";
              }
            }
            default "on";
            description
              "Laser open or shut.";
          }
          leaf laser-test-time {
            type uint32 {
              range "200..30000";
            }
            description
              "Laser open time(10ms).";
          }
        }
      }
    }
  }
  augment "/ncs:devices/ncs:device/ncs:rpc" {
    container rpc-clear-port-tx-pause-err-alarm {
      tailf:ncs-device-type "netconf";
      tailf:display-when "not(../../ncs:module) or ../../ncs:module[ncs:name='huawei-driver']";
      tailf:action clear-port-tx-pause-err-alarm {
        tailf:actionpoint ncsproxy {
          tailf:internal;
        }
        ext:node-ref "/devm/ports/port";
        description
          "Clear txPause error alarm.";
        input {
          leaf port-position {
            type string;
            description
              "Port position.";
          }
        }
      }
    }
  }
  augment "/ncs:devices/ncs:device-group/ncs:ned-id/ncs:rpc" {
    container rpc-clear-port-tx-pause-err-alarm {
      tailf:ncs-device-type "netconf";
      tailf:display-when "/ncs:devices/ncs:device[ncs:name=current()/../../../ncs:member]/ncs:module[ncs:name='huawei-driver']";
      tailf:action clear-port-tx-pause-err-alarm {
        tailf:actionpoint ncsproxy {
          tailf:internal;
        }
        ext:node-ref "/devm/ports/port";
        description
          "Clear txPause error alarm.";
        input {
          leaf port-position {
            type string;
            description
              "Port position.";
          }
        }
      }
    }
  }
  augment "/ncs:devices/ncs:device/ncs:rpc" {
    container rpc-clear-port-bip8-err-alarm {
      tailf:ncs-device-type "netconf";
      tailf:display-when "not(../../ncs:module) or ../../ncs:module[ncs:name='huawei-driver']";
      tailf:action clear-port-bip8-err-alarm {
        tailf:actionpoint ncsproxy {
          tailf:internal;
        }
        ext:node-ref "/devm/ports/port";
        description
          "Clear bip error alarm.";
        input {
          leaf port-position {
            type string;
            description
              "Port position.";
          }
        }
      }
    }
  }
  augment "/ncs:devices/ncs:device-group/ncs:ned-id/ncs:rpc" {
    container rpc-clear-port-bip8-err-alarm {
      tailf:ncs-device-type "netconf";
      tailf:display-when "/ncs:devices/ncs:device[ncs:name=current()/../../../ncs:member]/ncs:module[ncs:name='huawei-driver']";
      tailf:action clear-port-bip8-err-alarm {
        tailf:actionpoint ncsproxy {
          tailf:internal;
        }
        ext:node-ref "/devm/ports/port";
        description
          "Clear bip error alarm.";
        input {
          leaf port-position {
            type string;
            description
              "Port position.";
          }
        }
      }
    }
  }
  augment "/ncs:devices/ncs:device/ncs:rpc" {
    container rpc-clear-nv-port-tx-pause-err-alarm {
      tailf:ncs-device-type "netconf";
      tailf:display-when "not(../../ncs:module) or ../../ncs:module[ncs:name='huawei-driver']";
      tailf:action clear-nv-port-tx-pause-err-alarm {
        tailf:actionpoint ncsproxy {
          tailf:internal;
        }
        ext:node-ref "/devm/ports/port";
        description
          "Clear nv txpause error alarm.";
        input {
          leaf if-name {
            type string;
            description
              "Remote port index.";
          }
        }
      }
    }
  }
  augment "/ncs:devices/ncs:device-group/ncs:ned-id/ncs:rpc" {
    container rpc-clear-nv-port-tx-pause-err-alarm {
      tailf:ncs-device-type "netconf";
      tailf:display-when "/ncs:devices/ncs:device[ncs:name=current()/../../../ncs:member]/ncs:module[ncs:name='huawei-driver']";
      tailf:action clear-nv-port-tx-pause-err-alarm {
        tailf:actionpoint ncsproxy {
          tailf:internal;
        }
        ext:node-ref "/devm/ports/port";
        description
          "Clear nv txpause error alarm.";
        input {
          leaf if-name {
            type string;
            description
              "Remote port index.";
          }
        }
      }
    }
  }
  augment "/ncs:devices/ncs:device/ncs:rpc" {
    container rpc-clear-nv-port-trans-alarm {
      tailf:ncs-device-type "netconf";
      tailf:display-when "not(../../ncs:module) or ../../ncs:module[ncs:name='huawei-driver']";
      tailf:action clear-nv-port-trans-alarm {
        tailf:actionpoint ncsproxy {
          tailf:internal;
        }
        ext:node-ref "/devm/ports/port";
        description
          "Clear remote port tad alarm information.";
        input {
          leaf if-name {
            type string;
            description
              "Remote port index.";
          }
        }
      }
    }
  }
  augment "/ncs:devices/ncs:device-group/ncs:ned-id/ncs:rpc" {
    container rpc-clear-nv-port-trans-alarm {
      tailf:ncs-device-type "netconf";
      tailf:display-when "/ncs:devices/ncs:device[ncs:name=current()/../../../ncs:member]/ncs:module[ncs:name='huawei-driver']";
      tailf:action clear-nv-port-trans-alarm {
        tailf:actionpoint ncsproxy {
          tailf:internal;
        }
        ext:node-ref "/devm/ports/port";
        description
          "Clear remote port tad alarm information.";
        input {
          leaf if-name {
            type string;
            description
              "Remote port index.";
          }
        }
      }
    }
  }
  augment "/ncs:devices/ncs:device/ncs:rpc" {
    container rpc-clear-nv-port-symbol-err-alarm {
      tailf:ncs-device-type "netconf";
      tailf:display-when "not(../../ncs:module) or ../../ncs:module[ncs:name='huawei-driver']";
      tailf:action clear-nv-port-symbol-err-alarm {
        tailf:actionpoint ncsproxy {
          tailf:internal;
        }
        ext:node-ref "/devm/ports/port";
        description
          "Clear nv symbol error alarm.";
        input {
          leaf if-name {
            type string;
            description
              "Remote port index.";
          }
        }
      }
    }
  }
  augment "/ncs:devices/ncs:device-group/ncs:ned-id/ncs:rpc" {
    container rpc-clear-nv-port-symbol-err-alarm {
      tailf:ncs-device-type "netconf";
      tailf:display-when "/ncs:devices/ncs:device[ncs:name=current()/../../../ncs:member]/ncs:module[ncs:name='huawei-driver']";
      tailf:action clear-nv-port-symbol-err-alarm {
        tailf:actionpoint ncsproxy {
          tailf:internal;
        }
        ext:node-ref "/devm/ports/port";
        description
          "Clear nv symbol error alarm.";
        input {
          leaf if-name {
            type string;
            description
              "Remote port index.";
          }
        }
      }
    }
  }
  augment "/ncs:devices/ncs:device/ncs:rpc" {
    container rpc-clear-nv-port-sdh-err-alarm {
      tailf:ncs-device-type "netconf";
      tailf:display-when "not(../../ncs:module) or ../../ncs:module[ncs:name='huawei-driver']";
      tailf:action clear-nv-port-sdh-err-alarm {
        tailf:actionpoint ncsproxy {
          tailf:internal;
        }
        ext:node-ref "/devm/ports/port";
        description
          "Clear nv sdh error alarm.";
        input {
          leaf if-name {
            type string;
            description
              "Remote port index.";
          }
        }
      }
    }
  }
  augment "/ncs:devices/ncs:device-group/ncs:ned-id/ncs:rpc" {
    container rpc-clear-nv-port-sdh-err-alarm {
      tailf:ncs-device-type "netconf";
      tailf:display-when "/ncs:devices/ncs:device[ncs:name=current()/../../../ncs:member]/ncs:module[ncs:name='huawei-driver']";
      tailf:action clear-nv-port-sdh-err-alarm {
        tailf:actionpoint ncsproxy {
          tailf:internal;
        }
        ext:node-ref "/devm/ports/port";
        description
          "Clear nv sdh error alarm.";
        input {
          leaf if-name {
            type string;
            description
              "Remote port index.";
          }
        }
      }
    }
  }
  augment "/ncs:devices/ncs:device/ncs:rpc" {
    container rpc-clear-nv-port-output-err-alarm {
      tailf:ncs-device-type "netconf";
      tailf:display-when "not(../../ncs:module) or ../../ncs:module[ncs:name='huawei-driver']";
      tailf:action clear-nv-port-output-err-alarm {
        tailf:actionpoint ncsproxy {
          tailf:internal;
        }
        ext:node-ref "/devm/ports/port";
        description
          "Clear nv output error alarm.";
        input {
          leaf if-name {
            type string;
            description
              "Remote port index.";
          }
        }
      }
    }
  }
  augment "/ncs:devices/ncs:device-group/ncs:ned-id/ncs:rpc" {
    container rpc-clear-nv-port-output-err-alarm {
      tailf:ncs-device-type "netconf";
      tailf:display-when "/ncs:devices/ncs:device[ncs:name=current()/../../../ncs:member]/ncs:module[ncs:name='huawei-driver']";
      tailf:action clear-nv-port-output-err-alarm {
        tailf:actionpoint ncsproxy {
          tailf:internal;
        }
        ext:node-ref "/devm/ports/port";
        description
          "Clear nv output error alarm.";
        input {
          leaf if-name {
            type string;
            description
              "Remote port index.";
          }
        }
      }
    }
  }
  augment "/ncs:devices/ncs:device/ncs:rpc" {
    container rpc-clear-nv-port-input-err-alarm {
      tailf:ncs-device-type "netconf";
      tailf:display-when "not(../../ncs:module) or ../../ncs:module[ncs:name='huawei-driver']";
      tailf:action clear-nv-port-input-err-alarm {
        tailf:actionpoint ncsproxy {
          tailf:internal;
        }
        ext:node-ref "/devm/ports/port";
        description
          "Clear nv input error alarm.";
        input {
          leaf if-name {
            type string;
            description
              "Remote port index.";
          }
        }
      }
    }
  }
  augment "/ncs:devices/ncs:device-group/ncs:ned-id/ncs:rpc" {
    container rpc-clear-nv-port-input-err-alarm {
      tailf:ncs-device-type "netconf";
      tailf:display-when "/ncs:devices/ncs:device[ncs:name=current()/../../../ncs:member]/ncs:module[ncs:name='huawei-driver']";
      tailf:action clear-nv-port-input-err-alarm {
        tailf:actionpoint ncsproxy {
          tailf:internal;
        }
        ext:node-ref "/devm/ports/port";
        description
          "Clear nv input error alarm.";
        input {
          leaf if-name {
            type string;
            description
              "Remote port index.";
          }
        }
      }
    }
  }
  augment "/ncs:devices/ncs:device/ncs:rpc" {
    container rpc-clear-nv-port-crc-err-alarm {
      tailf:ncs-device-type "netconf";
      tailf:display-when "not(../../ncs:module) or ../../ncs:module[ncs:name='huawei-driver']";
      tailf:action clear-nv-port-crc-err-alarm {
        tailf:actionpoint ncsproxy {
          tailf:internal;
        }
        ext:node-ref "/devm/ports/port";
        description
          "Clear nv crc error alarm.";
        input {
          leaf if-name {
            type string;
            description
              "Remote port index.";
          }
        }
      }
    }
  }
  augment "/ncs:devices/ncs:device-group/ncs:ned-id/ncs:rpc" {
    container rpc-clear-nv-port-crc-err-alarm {
      tailf:ncs-device-type "netconf";
      tailf:display-when "/ncs:devices/ncs:device[ncs:name=current()/../../../ncs:member]/ncs:module[ncs:name='huawei-driver']";
      tailf:action clear-nv-port-crc-err-alarm {
        tailf:actionpoint ncsproxy {
          tailf:internal;
        }
        ext:node-ref "/devm/ports/port";
        description
          "Clear nv crc error alarm.";
        input {
          leaf if-name {
            type string;
            description
              "Remote port index.";
          }
        }
      }
    }
  }
  augment "/ncs:devices/ncs:device/ncs:rpc" {
    container rpc-clear-nv-port-bip8-err-alarm {
      tailf:ncs-device-type "netconf";
      tailf:display-when "not(../../ncs:module) or ../../ncs:module[ncs:name='huawei-driver']";
      tailf:action clear-nv-port-bip8-err-alarm {
        tailf:actionpoint ncsproxy {
          tailf:internal;
        }
        ext:node-ref "/devm/ports/port";
        description
          "Clear nv bip error alarm.";
        input {
          leaf if-name {
            type string;
            description
              "Remote port index.";
          }
        }
      }
    }
  }
  augment "/ncs:devices/ncs:device-group/ncs:ned-id/ncs:rpc" {
    container rpc-clear-nv-port-bip8-err-alarm {
      tailf:ncs-device-type "netconf";
      tailf:display-when "/ncs:devices/ncs:device[ncs:name=current()/../../../ncs:member]/ncs:module[ncs:name='huawei-driver']";
      tailf:action clear-nv-port-bip8-err-alarm {
        tailf:actionpoint ncsproxy {
          tailf:internal;
        }
        ext:node-ref "/devm/ports/port";
        description
          "Clear nv bip error alarm.";
        input {
          leaf if-name {
            type string;
            description
              "Remote port index.";
          }
        }
      }
    }
  }
  augment "/ncs:devices/ncs:device/ncs:rpc" {
    container rpc-check-hardware-version {
      tailf:ncs-device-type "netconf";
      tailf:display-when "not(../../ncs:module) or ../../ncs:module[ncs:name='huawei-driver']";
      tailf:action check-hardware-version {
        tailf:actionpoint ncsproxy {
          tailf:internal;
        }
        description
          "Check whether the system software package version matches the software versions, such as the EPLD and CANBUS version, running on the hardware.";
        input {
          leaf chassis-id {
            type string {
              length "1..32";
            }
            description
              "Chassis ID of device.";
          }
          choice check-type {
            mandatory true;
            description
              "Choose startup or file.";
            case startup-package {
              description
                "Startup.";
              leaf startup {
                type empty;
                description
                  "The startup file.";
              }
            }
            case package-file {
              description
                "Packet file name.";
              leaf file-name {
                type string {
                  length "4..127";
                }
                description
                  "Packet file name in master MPU.";
              }
            }
          }
        }
        output {
          leaf signature-result {
            type ncs_rpc_notif_driver-check-result-type;
            description
              "Result of system software signature check.";
          }
          leaf match-result {
            type ncs_rpc_notif_driver-check-result-type;
            description
              "Result of system software version check.";
          }
          container version-infos {
            description
              "List of version information.";
            list version-info {
              key "slot";
              description
                "Information of version.";
              leaf slot {
                type string {
                  length "1..32";
                }
                description
                  "Slot ID of device.";
              }
              leaf hardware-type {
                type ncs_rpc_notif_driver-slot-infos-type;
                description
                  "Hardware type.";
              }
              leaf content {
                type ncs_rpc_notif_driver-hardware-version-type;
                description
                  "Content of system software.";
              }
              leaf current-version {
                type uint32;
                description
                  "Current version.";
              }
              leaf package-version {
                type uint32;
                description
                  "Package version.";
              }
              leaf compatibility-state {
                type ncs_rpc_notif_driver-compatibility-state-type;
                description
                  "Compatibility state of system software.";
              }
              leaf upgrade-suggestion {
                type ncs_rpc_notif_driver-upgrade-suggestion-type;
                description
                  "Upgrade suggestion.";
              }
            }
          }
        }
      }
    }
  }
  augment "/ncs:devices/ncs:device-group/ncs:ned-id/ncs:rpc" {
    container rpc-check-hardware-version {
      tailf:ncs-device-type "netconf";
      tailf:display-when "/ncs:devices/ncs:device[ncs:name=current()/../../../ncs:member]/ncs:module[ncs:name='huawei-driver']";
      tailf:action check-hardware-version {
        tailf:actionpoint ncsproxy {
          tailf:internal;
        }
        description
          "Check whether the system software package version matches the software versions, such as the EPLD and CANBUS version, running on the hardware.";
        input {
          leaf chassis-id {
            type string {
              length "1..32";
            }
            description
              "Chassis ID of device.";
          }
          choice check-type {
            mandatory true;
            description
              "Choose startup or file.";
            case startup-package {
              description
                "Startup.";
              leaf startup {
                type empty;
                description
                  "The startup file.";
              }
            }
            case package-file {
              description
                "Packet file name.";
              leaf file-name {
                type string {
                  length "4..127";
                }
                description
                  "Packet file name in master MPU.";
              }
            }
          }
        }
        output {
          container "device" {
            leaf "name" {
              type string;
            }
            leaf "info" {
              type string;
            }
            container "result" {
              leaf signature-result {
                type ncs_rpc_notif_driver-check-result-type;
                description
                  "Result of system software signature check.";
              }
              leaf match-result {
                type ncs_rpc_notif_driver-check-result-type;
                description
                  "Result of system software version check.";
              }
              container version-infos {
                description
                  "List of version information.";
                list version-info {
                  key "slot";
                  description
                    "Information of version.";
                  leaf slot {
                    type string {
                      length "1..32";
                    }
                    description
                      "Slot ID of device.";
                  }
                  leaf hardware-type {
                    type ncs_rpc_notif_driver-slot-infos-type;
                    description
                      "Hardware type.";
                  }
                  leaf content {
                    type ncs_rpc_notif_driver-hardware-version-type;
                    description
                      "Content of system software.";
                  }
                  leaf current-version {
                    type uint32;
                    description
                      "Current version.";
                  }
                  leaf package-version {
                    type uint32;
                    description
                      "Package version.";
                  }
                  leaf compatibility-state {
                    type ncs_rpc_notif_driver-compatibility-state-type;
                    description
                      "Compatibility state of system software.";
                  }
                  leaf upgrade-suggestion {
                    type ncs_rpc_notif_driver-upgrade-suggestion-type;
                    description
                      "Upgrade suggestion.";
                  }
                }
              }
            }
          }
        }
      }
    }
  }
  augment "/ncs:devices/ncs:device/ncs:rpc" {
    container rpc-check-system-software {
      tailf:ncs-device-type "netconf";
      tailf:display-when "not(../../ncs:module) or ../../ncs:module[ncs:name='huawei-driver']";
      tailf:action check-system-software {
        tailf:actionpoint ncsproxy {
          tailf:internal;
        }
        description
          "Check system software.";
        input {
          choice startup-file {
            mandatory true;
            description
              "Choose startup or file.";
            case startup {
              description
                "Startup file.";
              leaf startup {
                type empty;
                description
                  "The startup file.";
              }
            }
            case file {
              description
                "Packet file.";
              leaf file-name {
                type string {
                  length "4..127";
                }
                description
                  "Packet file name in master MPU cfcard, for example:cfcard:/B02D.cc.";
              }
            }
          }
        }
        output {
          leaf sha256-hash-value {
            type string {
              length "1..255";
            }
            description
              "SHA256 hash value of the system software.";
          }
          leaf signature-result {
            type ncs_rpc_notif_driver-check-result-type;
            description
              "Result of system software signature check.";
          }
          leaf crc-result {
            type ncs_rpc_notif_driver-check-result-type;
            description
              "Result of system software CRC check.";
          }
          leaf match-result {
            type ncs_rpc_notif_driver-check-result-type;
            description
              "Result of system software match check.";
          }
        }
      }
    }
  }
  augment "/ncs:devices/ncs:device-group/ncs:ned-id/ncs:rpc" {
    container rpc-check-system-software {
      tailf:ncs-device-type "netconf";
      tailf:display-when "/ncs:devices/ncs:device[ncs:name=current()/../../../ncs:member]/ncs:module[ncs:name='huawei-driver']";
      tailf:action check-system-software {
        tailf:actionpoint ncsproxy {
          tailf:internal;
        }
        description
          "Check system software.";
        input {
          choice startup-file {
            mandatory true;
            description
              "Choose startup or file.";
            case startup {
              description
                "Startup file.";
              leaf startup {
                type empty;
                description
                  "The startup file.";
              }
            }
            case file {
              description
                "Packet file.";
              leaf file-name {
                type string {
                  length "4..127";
                }
                description
                  "Packet file name in master MPU cfcard, for example:cfcard:/B02D.cc.";
              }
            }
          }
        }
        output {
          container "device" {
            leaf "name" {
              type string;
            }
            leaf "info" {
              type string;
            }
            container "result" {
              leaf sha256-hash-value {
                type string {
                  length "1..255";
                }
                description
                  "SHA256 hash value of the system software.";
              }
              leaf signature-result {
                type ncs_rpc_notif_driver-check-result-type;
                description
                  "Result of system software signature check.";
              }
              leaf crc-result {
                type ncs_rpc_notif_driver-check-result-type;
                description
                  "Result of system software CRC check.";
              }
              leaf match-result {
                type ncs_rpc_notif_driver-check-result-type;
                description
                  "Result of system software match check.";
              }
            }
          }
        }
      }
    }
  }
  augment "/ncs:devices/ncs:device/ncs:rpc" {
    container rpc-check-hardware-compatibility {
      tailf:ncs-device-type "netconf";
      tailf:display-when "not(../../ncs:module) or ../../ncs:module[ncs:name='huawei-driver']";
      tailf:action check-hardware-compatibility {
        tailf:actionpoint ncsproxy {
          tailf:internal;
        }
        description
          "Check hardware compatibility.";
        input {
          choice check-type {
            mandatory true;
            description
              "Check type.";
            case startup {
              description
                "Startup.";
              leaf startup {
                type empty;
                description
                  "The startup file.";
              }
            }
            case file {
              description
                "File.";
              leaf file-name {
                type string {
                  length "4..127";
                }
                description
                  "Packet file name in master MPU cfcard, for example:cfcard:/B02D.CC.";
              }
            }
          }
        }
        output {
          container hardware-compatibility-infos {
            description
              "List of hardware compatibility information.";
            list hardware-compatibility-info {
              key "slot";
              description
                "Information of hardware compatibility.";
              leaf slot {
                type string {
                  length "1..32";
                }
                description
                  "Slot.";
              }
              leaf board-type {
                type string {
                  length "1..32";
                }
                description
                  "Board type.";
              }
              leaf result {
                type string {
                  length "1..32";
                }
                description
                  "Result.";
              }
              leaf detail {
                type string {
                  length "1..64";
                }
                description
                  "Detail.";
              }
            }
          }
        }
      }
    }
  }
  augment "/ncs:devices/ncs:device-group/ncs:ned-id/ncs:rpc" {
    container rpc-check-hardware-compatibility {
      tailf:ncs-device-type "netconf";
      tailf:display-when "/ncs:devices/ncs:device[ncs:name=current()/../../../ncs:member]/ncs:module[ncs:name='huawei-driver']";
      tailf:action check-hardware-compatibility {
        tailf:actionpoint ncsproxy {
          tailf:internal;
        }
        description
          "Check hardware compatibility.";
        input {
          choice check-type {
            mandatory true;
            description
              "Check type.";
            case startup {
              description
                "Startup.";
              leaf startup {
                type empty;
                description
                  "The startup file.";
              }
            }
            case file {
              description
                "File.";
              leaf file-name {
                type string {
                  length "4..127";
                }
                description
                  "Packet file name in master MPU cfcard, for example:cfcard:/B02D.CC.";
              }
            }
          }
        }
        output {
          container "device" {
            leaf "name" {
              type string;
            }
            leaf "info" {
              type string;
            }
            container "result" {
              container hardware-compatibility-infos {
                description
                  "List of hardware compatibility information.";
                list hardware-compatibility-info {
                  key "slot";
                  description
                    "Information of hardware compatibility.";
                  leaf slot {
                    type string {
                      length "1..32";
                    }
                    description
                      "Slot.";
                  }
                  leaf board-type {
                    type string {
                      length "1..32";
                    }
                    description
                      "Board type.";
                  }
                  leaf result {
                    type string {
                      length "1..32";
                    }
                    description
                      "Result.";
                  }
                  leaf detail {
                    type string {
                      length "1..64";
                    }
                    description
                      "Detail.";
                  }
                }
              }
            }
          }
        }
      }
    }
  }
  augment "/ncs:devices/ncs:device/ncs:rpc" {
    container rpc-set-vsu-service-type {
      tailf:ncs-device-type "netconf";
      tailf:display-when "not(../../ncs:module) or ../../ncs:module[ncs:name='huawei-driver']";
      tailf:action set-vsu-service-type {
        tailf:actionpoint ncsproxy {
          tailf:internal;
        }
        description
          "Set VSU service type.";
        input {
          leaf position {
            type string {
              length "1..32";
            }
            mandatory true;
            description
              "VSU position. The position is expressed in the format of slotID. For example, 1. Here 1 is an example. The value may vary with devices.";
          }
          leaf service-type {
            type ncs_rpc_notif_driver-vsu-service-type;
            mandatory true;
            description
              "VSU service type.";
          }
        }
      }
    }
  }
  augment "/ncs:devices/ncs:device-group/ncs:ned-id/ncs:rpc" {
    container rpc-set-vsu-service-type {
      tailf:ncs-device-type "netconf";
      tailf:display-when "/ncs:devices/ncs:device[ncs:name=current()/../../../ncs:member]/ncs:module[ncs:name='huawei-driver']";
      tailf:action set-vsu-service-type {
        tailf:actionpoint ncsproxy {
          tailf:internal;
        }
        description
          "Set VSU service type.";
        input {
          leaf position {
            type string {
              length "1..32";
            }
            mandatory true;
            description
              "VSU position. The position is expressed in the format of slotID. For example, 1. Here 1 is an example. The value may vary with devices.";
          }
          leaf service-type {
            type ncs_rpc_notif_driver-vsu-service-type;
            mandatory true;
            description
              "VSU service type.";
          }
        }
      }
    }
  }
  augment "/ncs:devices/ncs:device/ncs:rpc" {
    container rpc-board-channel-check {
      tailf:ncs-device-type "netconf";
      tailf:display-when "not(../../ncs:module) or ../../ncs:module[ncs:name='huawei-driver']";
      tailf:action board-channel-check {
        tailf:actionpoint ncsproxy {
          tailf:internal;
        }
        description
          "Board channel check.";
        input {
          leaf enable {
            type ncs_rpc_notif_board-channel-check-type;
            mandatory true;
            description
              "Enable or disable board channel check.";
          }
        }
      }
    }
  }
  augment "/ncs:devices/ncs:device-group/ncs:ned-id/ncs:rpc" {
    container rpc-board-channel-check {
      tailf:ncs-device-type "netconf";
      tailf:display-when "/ncs:devices/ncs:device[ncs:name=current()/../../../ncs:member]/ncs:module[ncs:name='huawei-driver']";
      tailf:action board-channel-check {
        tailf:actionpoint ncsproxy {
          tailf:internal;
        }
        description
          "Board channel check.";
        input {
          leaf enable {
            type ncs_rpc_notif_board-channel-check-type;
            mandatory true;
            description
              "Enable or disable board channel check.";
          }
        }
      }
    }
  }
  augment "/ncs:devices/ncs:device/ncs:rpc" {
    container rpc-set-npu-led-flash {
      tailf:ncs-device-type "netconf";
      tailf:display-when "not(../../ncs:module) or ../../ncs:module[ncs:name='huawei-driver']";
      tailf:action set-npu-led-flash {
        tailf:actionpoint ncsproxy {
          tailf:internal;
        }
        description
          "Set the board indicator blinking periods.";
        input {
          leaf board-position {
            type string;
            mandatory true;
            description
              "Board position.";
          }
          uses ncs_rpc_notif_led-flash-time;
        }
      }
    }
  }
  augment "/ncs:devices/ncs:device-group/ncs:ned-id/ncs:rpc" {
    container rpc-set-npu-led-flash {
      tailf:ncs-device-type "netconf";
      tailf:display-when "/ncs:devices/ncs:device[ncs:name=current()/../../../ncs:member]/ncs:module[ncs:name='huawei-driver']";
      tailf:action set-npu-led-flash {
        tailf:actionpoint ncsproxy {
          tailf:internal;
        }
        description
          "Set the board indicator blinking periods.";
        input {
          leaf board-position {
            type string;
            mandatory true;
            description
              "Board position.";
          }
          uses ncs_rpc_notif_led-flash-time;
        }
      }
    }
  }
  augment "/ncs:devices/ncs:device/ncs:rpc" {
    container rpc-set-slot-led-flash {
      tailf:ncs-device-type "netconf";
      tailf:display-when "not(../../ncs:module) or ../../ncs:module[ncs:name='huawei-driver']";
      tailf:action set-slot-led-flash {
        tailf:actionpoint ncsproxy {
          tailf:internal;
        }
        description
          "Set the board indicator blinking periods.";
        input {
          leaf board-position {
            type string;
            mandatory true;
            description
              "Board position.";
          }
          uses ncs_rpc_notif_led-flash-time;
        }
      }
    }
  }
  augment "/ncs:devices/ncs:device-group/ncs:ned-id/ncs:rpc" {
    container rpc-set-slot-led-flash {
      tailf:ncs-device-type "netconf";
      tailf:display-when "/ncs:devices/ncs:device[ncs:name=current()/../../../ncs:member]/ncs:module[ncs:name='huawei-driver']";
      tailf:action set-slot-led-flash {
        tailf:actionpoint ncsproxy {
          tailf:internal;
        }
        description
          "Set the board indicator blinking periods.";
        input {
          leaf board-position {
            type string;
            mandatory true;
            description
              "Board position.";
          }
          uses ncs_rpc_notif_led-flash-time;
        }
      }
    }
  }
  augment "/ncs:devices/ncs:device/ncs:rpc" {
    container rpc-set-led-flash {
      tailf:ncs-device-type "netconf";
      tailf:display-when "not(../../ncs:module) or ../../ncs:module[ncs:name='huawei-driver']";
      tailf:action set-led-flash {
        tailf:actionpoint ncsproxy {
          tailf:internal;
        }
        description
          "Set the indicator blinking periods.";
        input {
          uses ncs_rpc_notif_led-flash-time;
        }
      }
    }
  }
  augment "/ncs:devices/ncs:device-group/ncs:ned-id/ncs:rpc" {
    container rpc-set-led-flash {
      tailf:ncs-device-type "netconf";
      tailf:display-when "/ncs:devices/ncs:device[ncs:name=current()/../../../ncs:member]/ncs:module[ncs:name='huawei-driver']";
      tailf:action set-led-flash {
        tailf:actionpoint ncsproxy {
          tailf:internal;
        }
        description
          "Set the indicator blinking periods.";
        input {
          uses ncs_rpc_notif_led-flash-time;
        }
      }
    }
  }
  augment "/ncs:devices/ncs:device/ncs:rpc" {
    container rpc-set-split-resume {
      tailf:ncs-device-type "netconf";
      tailf:display-when "not(../../ncs:module) or ../../ncs:module[ncs:name='huawei-driver']";
      tailf:action set-split-resume {
        tailf:actionpoint ncsproxy {
          tailf:internal;
        }
        description
          "Slave chassis reset mode. It will take effect only both the inter-chassis control link and data link fail in virtual cluster scenarios.";
        input {
          leaf split-resume {
            type ncs_rpc_notif_driver-split-resume-mode-type;
            mandatory true;
            description
              "Slave chassis reset mode.";
          }
        }
      }
    }
  }
  augment "/ncs:devices/ncs:device-group/ncs:ned-id/ncs:rpc" {
    container rpc-set-split-resume {
      tailf:ncs-device-type "netconf";
      tailf:display-when "/ncs:devices/ncs:device[ncs:name=current()/../../../ncs:member]/ncs:module[ncs:name='huawei-driver']";
      tailf:action set-split-resume {
        tailf:actionpoint ncsproxy {
          tailf:internal;
        }
        description
          "Slave chassis reset mode. It will take effect only both the inter-chassis control link and data link fail in virtual cluster scenarios.";
        input {
          leaf split-resume {
            type ncs_rpc_notif_driver-split-resume-mode-type;
            mandatory true;
            description
              "Slave chassis reset mode.";
          }
        }
      }
    }
  }
  augment "/ncs:devices/ncs:device/ncs:rpc" {
    container rpc-set-next-work-mode {
      tailf:ncs-device-type "netconf";
      tailf:display-when "not(../../ncs:module) or ../../ncs:module[ncs:name='huawei-driver']";
      tailf:action set-next-work-mode {
        tailf:actionpoint ncsproxy {
          tailf:internal;
        }
        description
          "Set next work mode, 1+1 or 1:1. The work mode cannot be switched on specific device models or in specific scenarios (warning:system will restart after success, and then take effect).";
        input {
          leaf next-work-mode {
            type ncs_rpc_notif_driver-system-mode;
            mandatory true;
            description
              "Next work mode, 1+1 or 1:1.";
          }
        }
      }
    }
  }
  augment "/ncs:devices/ncs:device-group/ncs:ned-id/ncs:rpc" {
    container rpc-set-next-work-mode {
      tailf:ncs-device-type "netconf";
      tailf:display-when "/ncs:devices/ncs:device[ncs:name=current()/../../../ncs:member]/ncs:module[ncs:name='huawei-driver']";
      tailf:action set-next-work-mode {
        tailf:actionpoint ncsproxy {
          tailf:internal;
        }
        description
          "Set next work mode, 1+1 or 1:1. The work mode cannot be switched on specific device models or in specific scenarios (warning:system will restart after success, and then take effect).";
        input {
          leaf next-work-mode {
            type ncs_rpc_notif_driver-system-mode;
            mandatory true;
            description
              "Next work mode, 1+1 or 1:1.";
          }
        }
      }
    }
  }
  augment "/ncs:devices/ncs:device/ncs:rpc" {
    container rpc-set-chassis-run-mode {
      tailf:ncs-device-type "netconf";
      tailf:display-when "not(../../ncs:module) or ../../ncs:module[ncs:name='huawei-driver']";
      tailf:action set-chassis-run-mode {
        tailf:actionpoint ncsproxy {
          tailf:internal;
        }
        description
          "Set chassis run mode.";
        input {
          leaf chassis-id {
            type string {
              length "1..31";
            }
            description
              "Chassis id. The chassis-id is expressed in the format of chassisID. For example, 1. Here 1 is an example. The value may vary with devices.";
          }
          leaf next-run-mode {
            type ncs_rpc_notif_driver-next-run-mode;
            mandatory true;
            description
              "Next run mode.";
          }
          leaf next-run-cluster {
            when "../next-run-mode='virtual-cluster-chassis'" {
              tailf:xpath-root 3;
            }
            type string {
              length "1..3";
            }
            description
              "Next cluster id.";
          }
        }
      }
    }
  }
  augment "/ncs:devices/ncs:device-group/ncs:ned-id/ncs:rpc" {
    container rpc-set-chassis-run-mode {
      tailf:ncs-device-type "netconf";
      tailf:display-when "/ncs:devices/ncs:device[ncs:name=current()/../../../ncs:member]/ncs:module[ncs:name='huawei-driver']";
      tailf:action set-chassis-run-mode {
        tailf:actionpoint ncsproxy {
          tailf:internal;
        }
        description
          "Set chassis run mode.";
        input {
          leaf chassis-id {
            type string {
              length "1..31";
            }
            description
              "Chassis id. The chassis-id is expressed in the format of chassisID. For example, 1. Here 1 is an example. The value may vary with devices.";
          }
          leaf next-run-mode {
            type ncs_rpc_notif_driver-next-run-mode;
            mandatory true;
            description
              "Next run mode.";
          }
          leaf next-run-cluster {
            when "../next-run-mode='virtual-cluster-chassis'" {
              tailf:xpath-root 4;
            }
            type string {
              length "1..3";
            }
            description
              "Next cluster id.";
          }
        }
      }
    }
  }
  augment "/ncs:devices/ncs:device/ncs:rpc" {
    container rpc-set-multi-chassis-id {
      tailf:ncs-device-type "netconf";
      tailf:display-when "not(../../ncs:module) or ../../ncs:module[ncs:name='huawei-driver']";
      tailf:action set-multi-chassis-id {
        tailf:actionpoint ncsproxy {
          tailf:internal;
        }
        description
          "Set multi chassis id.";
        input {
          leaf current-chassis-id {
            type uint32 {
              range "1..2";
            }
            description
              "Current chassis id.";
          }
          leaf next-chassis-id {
            type uint32 {
              range "1..2";
            }
            description
              "Next chassis id.";
          }
        }
      }
    }
  }
  augment "/ncs:devices/ncs:device-group/ncs:ned-id/ncs:rpc" {
    container rpc-set-multi-chassis-id {
      tailf:ncs-device-type "netconf";
      tailf:display-when "/ncs:devices/ncs:device[ncs:name=current()/../../../ncs:member]/ncs:module[ncs:name='huawei-driver']";
      tailf:action set-multi-chassis-id {
        tailf:actionpoint ncsproxy {
          tailf:internal;
        }
        description
          "Set multi chassis id.";
        input {
          leaf current-chassis-id {
            type uint32 {
              range "1..2";
            }
            description
              "Current chassis id.";
          }
          leaf next-chassis-id {
            type uint32 {
              range "1..2";
            }
            description
              "Next chassis id.";
          }
        }
      }
    }
  }
  augment "/ncs:devices/ncs:device/ncs:rpc" {
    container rpc-rollback {
      tailf:ncs-device-type "netconf";
      tailf:display-when "not(../../ncs:module) or ../../ncs:module[ncs:name='huawei-driver']";
      tailf:action rollback {
        tailf:actionpoint ncsproxy {
          tailf:internal;
        }
        description
          "The system will rollback to the previous version, the current configuration will be lost.";
        input {
          leaf rollback-choice {
            type ncs_rpc_notif_rollback-choice-type;
            description
              "Used to rollback to the previous version.";
          }
        }
      }
    }
  }
  augment "/ncs:devices/ncs:device-group/ncs:ned-id/ncs:rpc" {
    container rpc-rollback {
      tailf:ncs-device-type "netconf";
      tailf:display-when "/ncs:devices/ncs:device[ncs:name=current()/../../../ncs:member]/ncs:module[ncs:name='huawei-driver']";
      tailf:action rollback {
        tailf:actionpoint ncsproxy {
          tailf:internal;
        }
        description
          "The system will rollback to the previous version, the current configuration will be lost.";
        input {
          leaf rollback-choice {
            type ncs_rpc_notif_rollback-choice-type;
            description
              "Used to rollback to the previous version.";
          }
        }
      }
    }
  }
  augment "/ncs:devices/ncs:device/ncs:rpc" {
    container rpc-interface-match-check-recovery {
      tailf:ncs-device-type "netconf";
      tailf:display-when "not(../../ncs:module) or ../../ncs:module[ncs:name='huawei-driver']";
      tailf:action interface-match-check-recovery {
        tailf:actionpoint ncsproxy {
          tailf:internal;
        }
        description
          "Used to enable the configuration restoration function.";
        input {
          leaf position {
            type string {
              length "1..30";
            }
            description
              "Enabling position of configuration restoration function. The position is expressed in the format of slotID. For example, 1. Here 1 is an example. The value may vary with devices.";
          }
        }
      }
    }
  }
  augment "/ncs:devices/ncs:device-group/ncs:ned-id/ncs:rpc" {
    container rpc-interface-match-check-recovery {
      tailf:ncs-device-type "netconf";
      tailf:display-when "/ncs:devices/ncs:device[ncs:name=current()/../../../ncs:member]/ncs:module[ncs:name='huawei-driver']";
      tailf:action interface-match-check-recovery {
        tailf:actionpoint ncsproxy {
          tailf:internal;
        }
        description
          "Used to enable the configuration restoration function.";
        input {
          leaf position {
            type string {
              length "1..30";
            }
            description
              "Enabling position of configuration restoration function. The position is expressed in the format of slotID. For example, 1. Here 1 is an example. The value may vary with devices.";
          }
        }
      }
    }
  }
  augment "/ncs:devices/ncs:device/ncs:rpc" {
    container rpc-auto-upgrade-models {
      tailf:ncs-device-type "netconf";
      tailf:display-when "not(../../ncs:module) or ../../ncs:module[ncs:name='huawei-driver']";
      tailf:action auto-upgrade-models {
        tailf:actionpoint ncsproxy {
          tailf:internal;
        }
        description
          "Set auto upgrade model.";
        input {
          leaf auto-upgrade-model {
            type ncs_rpc_notif_driver-auto-upgrade-mode;
            description
              "Auto upgrade model.";
          }
        }
      }
    }
  }
  augment "/ncs:devices/ncs:device-group/ncs:ned-id/ncs:rpc" {
    container rpc-auto-upgrade-models {
      tailf:ncs-device-type "netconf";
      tailf:display-when "/ncs:devices/ncs:device[ncs:name=current()/../../../ncs:member]/ncs:module[ncs:name='huawei-driver']";
      tailf:action auto-upgrade-models {
        tailf:actionpoint ncsproxy {
          tailf:internal;
        }
        description
          "Set auto upgrade model.";
        input {
          leaf auto-upgrade-model {
            type ncs_rpc_notif_driver-auto-upgrade-mode;
            description
              "Auto upgrade model.";
          }
        }
      }
    }
  }
  augment "/ncs:devices/ncs:device/ncs:rpc" {
    container rpc-set-boot-password {
      tailf:ncs-device-type "netconf";
      tailf:display-when "not(../../ncs:module) or ../../ncs:module[ncs:name='huawei-driver']";
      tailf:action set-boot-password {
        tailf:actionpoint ncsproxy {
          tailf:internal;
        }
        description
          "Set-boot-password.";
        input {
          leaf slot-id {
            type string {
              length "1..31";
            }
            mandatory true;
            description
              "Slot ID. The slot-id is expressed in the format of slotID. For example, 1. Here 1 is an example. The value may vary with devices.";
          }
          leaf old-password {
            type pub-type:ncs_rpc_notif_one-input-password-extend;
            description
              "OldPassword.";
          }
          leaf new-password {
            type pub-type:ncs_rpc_notif_password-extend;
            mandatory true;
            description
              "NewPassword.";
          }
        }
      }
    }
  }
  augment "/ncs:devices/ncs:device-group/ncs:ned-id/ncs:rpc" {
    container rpc-set-boot-password {
      tailf:ncs-device-type "netconf";
      tailf:display-when "/ncs:devices/ncs:device[ncs:name=current()/../../../ncs:member]/ncs:module[ncs:name='huawei-driver']";
      tailf:action set-boot-password {
        tailf:actionpoint ncsproxy {
          tailf:internal;
        }
        description
          "Set-boot-password.";
        input {
          leaf slot-id {
            type string {
              length "1..31";
            }
            mandatory true;
            description
              "Slot ID. The slot-id is expressed in the format of slotID. For example, 1. Here 1 is an example. The value may vary with devices.";
          }
          leaf old-password {
            type pub-type:ncs_rpc_notif_one-input-password-extend;
            description
              "OldPassword.";
          }
          leaf new-password {
            type pub-type:ncs_rpc_notif_password-extend;
            mandatory true;
            description
              "NewPassword.";
          }
        }
      }
    }
  }
  augment "/ncs:devices/ncs:device/ncs:rpc" {
    container rpc-power-off-card {
      tailf:ncs-device-type "netconf";
      tailf:display-when "not(../../ncs:module) or ../../ncs:module[ncs:name='huawei-driver']";
      tailf:action power-off-card {
        tailf:actionpoint ncsproxy {
          tailf:internal;
        }
        description
          "Power-off-card.";
        input {
          leaf card-position {
            type string;
            mandatory true;
            description
              "Card Position. The card-position is expressed in the format of slotID/cardID. For example, 1/0. Here 1/0 is an example. The value may vary with devices.";
          }
          leaf auto-power-on {
            type empty;
            description
              "Auto power on.";
          }
        }
      }
    }
  }
  augment "/ncs:devices/ncs:device-group/ncs:ned-id/ncs:rpc" {
    container rpc-power-off-card {
      tailf:ncs-device-type "netconf";
      tailf:display-when "/ncs:devices/ncs:device[ncs:name=current()/../../../ncs:member]/ncs:module[ncs:name='huawei-driver']";
      tailf:action power-off-card {
        tailf:actionpoint ncsproxy {
          tailf:internal;
        }
        description
          "Power-off-card.";
        input {
          leaf card-position {
            type string;
            mandatory true;
            description
              "Card Position. The card-position is expressed in the format of slotID/cardID. For example, 1/0. Here 1/0 is an example. The value may vary with devices.";
          }
          leaf auto-power-on {
            type empty;
            description
              "Auto power on.";
          }
        }
      }
    }
  }
  augment "/ncs:devices/ncs:device/ncs:rpc" {
    container rpc-power-on-card {
      tailf:ncs-device-type "netconf";
      tailf:display-when "not(../../ncs:module) or ../../ncs:module[ncs:name='huawei-driver']";
      tailf:action power-on-card {
        tailf:actionpoint ncsproxy {
          tailf:internal;
        }
        description
          "Power-on-card.";
        input {
          leaf card-position {
            type string;
            mandatory true;
            description
              "Card Position. The card-position is expressed in the format of slotID/cardID. For example, 1/0. Here 1/0 is an example. The value may vary with devices.";
          }
        }
      }
    }
  }
  augment "/ncs:devices/ncs:device-group/ncs:ned-id/ncs:rpc" {
    container rpc-power-on-card {
      tailf:ncs-device-type "netconf";
      tailf:display-when "/ncs:devices/ncs:device[ncs:name=current()/../../../ncs:member]/ncs:module[ncs:name='huawei-driver']";
      tailf:action power-on-card {
        tailf:actionpoint ncsproxy {
          tailf:internal;
        }
        description
          "Power-on-card.";
        input {
          leaf card-position {
            type string;
            mandatory true;
            description
              "Card Position. The card-position is expressed in the format of slotID/cardID. For example, 1/0. Here 1/0 is an example. The value may vary with devices.";
          }
        }
      }
    }
  }
  augment "/ncs:devices/ncs:device/ncs:rpc" {
    container rpc-set-flash-lock {
      tailf:ncs-device-type "netconf";
      tailf:display-when "not(../../ncs:module) or ../../ncs:module[ncs:name='huawei-driver']";
      tailf:action set-flash-lock {
        tailf:actionpoint ncsproxy {
          tailf:internal;
        }
        description
          "Set-flash-lock.";
        input {
          leaf flash-lock {
            type ncs_rpc_notif_driver-flash-lock;
            default "immediately";
            description
              "Flash lock.";
          }
          leaf days {
            when "../flash-lock = 'delay' " {
              tailf:xpath-root 3;
            }
            type uint32 {
              range "1..90";
            }
            description
              "Days.";
          }
        }
      }
    }
  }
  augment "/ncs:devices/ncs:device-group/ncs:ned-id/ncs:rpc" {
    container rpc-set-flash-lock {
      tailf:ncs-device-type "netconf";
      tailf:display-when "/ncs:devices/ncs:device[ncs:name=current()/../../../ncs:member]/ncs:module[ncs:name='huawei-driver']";
      tailf:action set-flash-lock {
        tailf:actionpoint ncsproxy {
          tailf:internal;
        }
        description
          "Set-flash-lock.";
        input {
          leaf flash-lock {
            type ncs_rpc_notif_driver-flash-lock;
            default "immediately";
            description
              "Flash lock.";
          }
          leaf days {
            when "../flash-lock = 'delay' " {
              tailf:xpath-root 4;
            }
            type uint32 {
              range "1..90";
            }
            description
              "Days.";
          }
        }
      }
    }
  }
  augment "/ncs:devices/ncs:device/ncs:rpc" {
    container rpc-set-slave-default {
      tailf:ncs-device-type "netconf";
      tailf:display-when "not(../../ncs:module) or ../../ncs:module[ncs:name='huawei-driver']";
      tailf:action set-slave-default {
        tailf:actionpoint ncsproxy {
          tailf:internal;
        }
        description
          "Set slave default.";
        input {
          leaf chassis-id {
            type string {
              length "1..32";
            }
            description
              "Chassis ID. The chassis-id is expressed in the format of chassisID. For example, 1. Here 1 is an example. The value may vary with devices.";
          }
          choice set-slave-board {
            mandatory true;
            description
              "Set the default slave board.";
            case slave-default {
              description
                "Set the default slave board.";
              leaf slave-default {
                type string {
                  length "1..64";
                }
                description
                  "Slave Default. The slave-default is expressed in the format of slotID. For example, 1. Here 1 is an example. The value may vary with devices.";
              }
            }
            case clear-slave-default {
              description
                "Clear the configuration of the default slave board.";
              leaf clear-slave-board {
                type empty;
                description
                  "Clear the configuration of the default slave board.";
              }
            }
          }
        }
      }
    }
  }
  augment "/ncs:devices/ncs:device-group/ncs:ned-id/ncs:rpc" {
    container rpc-set-slave-default {
      tailf:ncs-device-type "netconf";
      tailf:display-when "/ncs:devices/ncs:device[ncs:name=current()/../../../ncs:member]/ncs:module[ncs:name='huawei-driver']";
      tailf:action set-slave-default {
        tailf:actionpoint ncsproxy {
          tailf:internal;
        }
        description
          "Set slave default.";
        input {
          leaf chassis-id {
            type string {
              length "1..32";
            }
            description
              "Chassis ID. The chassis-id is expressed in the format of chassisID. For example, 1. Here 1 is an example. The value may vary with devices.";
          }
          choice set-slave-board {
            mandatory true;
            description
              "Set the default slave board.";
            case slave-default {
              description
                "Set the default slave board.";
              leaf slave-default {
                type string {
                  length "1..64";
                }
                description
                  "Slave Default. The slave-default is expressed in the format of slotID. For example, 1. Here 1 is an example. The value may vary with devices.";
              }
            }
            case clear-slave-default {
              description
                "Clear the configuration of the default slave board.";
              leaf clear-slave-board {
                type empty;
                description
                  "Clear the configuration of the default slave board.";
              }
            }
          }
        }
      }
    }
  }
  augment "/ncs:devices/ncs:device/ncs:rpc" {
    container rpc-reset-chassis {
      tailf:ncs-device-type "netconf";
      tailf:display-when "not(../../ncs:module) or ../../ncs:module[ncs:name='huawei-driver']";
      tailf:action reset-chassis {
        tailf:actionpoint ncsproxy {
          tailf:internal;
        }
        description
          "Reset chassis.";
        input {
          leaf chassis-position {
            type string;
            description
              "Chassis position. The chassis-position is expressed in the format of chassisID. For example, 1. Here 1 is an example. The value may vary with devices.";
          }
        }
      }
    }
  }
  augment "/ncs:devices/ncs:device-group/ncs:ned-id/ncs:rpc" {
    container rpc-reset-chassis {
      tailf:ncs-device-type "netconf";
      tailf:display-when "/ncs:devices/ncs:device[ncs:name=current()/../../../ncs:member]/ncs:module[ncs:name='huawei-driver']";
      tailf:action reset-chassis {
        tailf:actionpoint ncsproxy {
          tailf:internal;
        }
        description
          "Reset chassis.";
        input {
          leaf chassis-position {
            type string;
            description
              "Chassis position. The chassis-position is expressed in the format of chassisID. For example, 1. Here 1 is an example. The value may vary with devices.";
          }
        }
      }
    }
  }
  augment "/ncs:devices/ncs:device/ncs:rpc" {
    container rpc-reset-mbus-node {
      tailf:ncs-device-type "netconf";
      tailf:display-when "not(../../ncs:module) or ../../ncs:module[ncs:name='huawei-driver']";
      tailf:action reset-mbus-node {
        tailf:actionpoint ncsproxy {
          tailf:internal;
        }
        description
          "Reset mbus node.";
        input {
          leaf board-position {
            type string;
            description
              "Board Position. The board-position is expressed in the format of slotID. For example, 1. Here 1 is an example. The value may vary with devices.";
          }
        }
      }
    }
  }
  augment "/ncs:devices/ncs:device-group/ncs:ned-id/ncs:rpc" {
    container rpc-reset-mbus-node {
      tailf:ncs-device-type "netconf";
      tailf:display-when "/ncs:devices/ncs:device[ncs:name=current()/../../../ncs:member]/ncs:module[ncs:name='huawei-driver']";
      tailf:action reset-mbus-node {
        tailf:actionpoint ncsproxy {
          tailf:internal;
        }
        description
          "Reset mbus node.";
        input {
          leaf board-position {
            type string;
            description
              "Board Position. The board-position is expressed in the format of slotID. For example, 1. Here 1 is an example. The value may vary with devices.";
          }
        }
      }
    }
  }
  augment "/ncs:devices/ncs:device/ncs:rpc" {
    container rpc-reset-dustproof-net {
      tailf:ncs-device-type "netconf";
      tailf:display-when "not(../../ncs:module) or ../../ncs:module[ncs:name='huawei-driver']";
      tailf:action reset-dustproof-net {
        tailf:actionpoint ncsproxy {
          tailf:internal;
        }
        description
          "Clear the running time of the air filter in a specified chassis.";
        input {
          leaf chassis-position {
            type string;
            description
              "Chassis position. The chassis-position is expressed in the format of chassisID. For example, 1. Here 1 is an example. The value may vary with devices.";
          }
        }
      }
    }
  }
  augment "/ncs:devices/ncs:device-group/ncs:ned-id/ncs:rpc" {
    container rpc-reset-dustproof-net {
      tailf:ncs-device-type "netconf";
      tailf:display-when "/ncs:devices/ncs:device[ncs:name=current()/../../../ncs:member]/ncs:module[ncs:name='huawei-driver']";
      tailf:action reset-dustproof-net {
        tailf:actionpoint ncsproxy {
          tailf:internal;
        }
        description
          "Clear the running time of the air filter in a specified chassis.";
        input {
          leaf chassis-position {
            type string;
            description
              "Chassis position. The chassis-position is expressed in the format of chassisID. For example, 1. Here 1 is an example. The value may vary with devices.";
          }
        }
      }
    }
  }
  augment "/ncs:devices/ncs:device/ncs:rpc" {
    container rpc-reset-fan-board {
      tailf:ncs-device-type "netconf";
      tailf:display-when "not(../../ncs:module) or ../../ncs:module[ncs:name='huawei-driver']";
      tailf:action reset-fan-board {
        tailf:actionpoint ncsproxy {
          tailf:internal;
        }
        description
          "Reset Fan.";
        input {
          leaf board-position {
            type string;
            description
              "Board Position. The board-position is expressed in the format of slotID. For example, 1. Here 1 is an example. The value may vary with devices.";
          }
        }
      }
    }
  }
  augment "/ncs:devices/ncs:device-group/ncs:ned-id/ncs:rpc" {
    container rpc-reset-fan-board {
      tailf:ncs-device-type "netconf";
      tailf:display-when "/ncs:devices/ncs:device[ncs:name=current()/../../../ncs:member]/ncs:module[ncs:name='huawei-driver']";
      tailf:action reset-fan-board {
        tailf:actionpoint ncsproxy {
          tailf:internal;
        }
        description
          "Reset Fan.";
        input {
          leaf board-position {
            type string;
            description
              "Board Position. The board-position is expressed in the format of slotID. For example, 1. Here 1 is an example. The value may vary with devices.";
          }
        }
      }
    }
  }
  augment "/ncs:devices/ncs:device/ncs:rpc" {
    container rpc-reset-cmu-board {
      tailf:ncs-device-type "netconf";
      tailf:display-when "not(../../ncs:module) or ../../ncs:module[ncs:name='huawei-driver']";
      tailf:action reset-cmu-board {
        tailf:actionpoint ncsproxy {
          tailf:internal;
        }
        description
          "Reset CMU Board.";
        input {
          leaf board-position {
            type string;
            description
              "Board Position. The board-position is expressed in the format of slotID. For example, 1. Here 1 is an example. The value may vary with devices.";
          }
        }
      }
    }
  }
  augment "/ncs:devices/ncs:device-group/ncs:ned-id/ncs:rpc" {
    container rpc-reset-cmu-board {
      tailf:ncs-device-type "netconf";
      tailf:display-when "/ncs:devices/ncs:device[ncs:name=current()/../../../ncs:member]/ncs:module[ncs:name='huawei-driver']";
      tailf:action reset-cmu-board {
        tailf:actionpoint ncsproxy {
          tailf:internal;
        }
        description
          "Reset CMU Board.";
        input {
          leaf board-position {
            type string;
            description
              "Board Position. The board-position is expressed in the format of slotID. For example, 1. Here 1 is an example. The value may vary with devices.";
          }
        }
      }
    }
  }
  augment "/ncs:devices/ncs:device/ncs:rpc" {
    container rpc-reset-icu-board {
      tailf:ncs-device-type "netconf";
      tailf:display-when "not(../../ncs:module) or ../../ncs:module[ncs:name='huawei-driver']";
      tailf:action reset-icu-board {
        tailf:actionpoint ncsproxy {
          tailf:internal;
        }
        description
          "Reset ICU Board.";
        input {
          leaf board-position {
            type string;
            description
              "Board Position. The board-position is expressed in the format of slotID. For example, 1. Here 1 is an example. The value may vary with devices.";
          }
        }
      }
    }
  }
  augment "/ncs:devices/ncs:device-group/ncs:ned-id/ncs:rpc" {
    container rpc-reset-icu-board {
      tailf:ncs-device-type "netconf";
      tailf:display-when "/ncs:devices/ncs:device[ncs:name=current()/../../../ncs:member]/ncs:module[ncs:name='huawei-driver']";
      tailf:action reset-icu-board {
        tailf:actionpoint ncsproxy {
          tailf:internal;
        }
        description
          "Reset ICU Board.";
        input {
          leaf board-position {
            type string;
            description
              "Board Position. The board-position is expressed in the format of slotID. For example, 1. Here 1 is an example. The value may vary with devices.";
          }
        }
      }
    }
  }
  augment "/ncs:devices/ncs:device/ncs:rpc" {
    container rpc-power-off-icu {
      tailf:ncs-device-type "netconf";
      tailf:display-when "not(../../ncs:module) or ../../ncs:module[ncs:name='huawei-driver']";
      tailf:action power-off-icu {
        tailf:actionpoint ncsproxy {
          tailf:internal;
        }
        description
          "Power Off Icu.";
        input {
          leaf board-position {
            type string;
            mandatory true;
            description
              "Board Position. The board-position is expressed in the format of slotID. For example, 1. Here 1 is an example. The value may vary with devices.";
          }
          leaf auto-power-on {
            type empty;
            description
              "Auto power on.";
          }
        }
      }
    }
  }
  augment "/ncs:devices/ncs:device-group/ncs:ned-id/ncs:rpc" {
    container rpc-power-off-icu {
      tailf:ncs-device-type "netconf";
      tailf:display-when "/ncs:devices/ncs:device[ncs:name=current()/../../../ncs:member]/ncs:module[ncs:name='huawei-driver']";
      tailf:action power-off-icu {
        tailf:actionpoint ncsproxy {
          tailf:internal;
        }
        description
          "Power Off Icu.";
        input {
          leaf board-position {
            type string;
            mandatory true;
            description
              "Board Position. The board-position is expressed in the format of slotID. For example, 1. Here 1 is an example. The value may vary with devices.";
          }
          leaf auto-power-on {
            type empty;
            description
              "Auto power on.";
          }
        }
      }
    }
  }
  augment "/ncs:devices/ncs:device/ncs:rpc" {
    container rpc-power-on-icu {
      tailf:ncs-device-type "netconf";
      tailf:display-when "not(../../ncs:module) or ../../ncs:module[ncs:name='huawei-driver']";
      tailf:action power-on-icu {
        tailf:actionpoint ncsproxy {
          tailf:internal;
        }
        description
          "Power On Icu.";
        input {
          leaf board-position {
            type string;
            mandatory true;
            description
              "Board Position. The board-position is expressed in the format of slotID. For example, 1. Here 1 is an example. The value may vary with devices.";
          }
        }
      }
    }
  }
  augment "/ncs:devices/ncs:device-group/ncs:ned-id/ncs:rpc" {
    container rpc-power-on-icu {
      tailf:ncs-device-type "netconf";
      tailf:display-when "/ncs:devices/ncs:device[ncs:name=current()/../../../ncs:member]/ncs:module[ncs:name='huawei-driver']";
      tailf:action power-on-icu {
        tailf:actionpoint ncsproxy {
          tailf:internal;
        }
        description
          "Power On Icu.";
        input {
          leaf board-position {
            type string;
            mandatory true;
            description
              "Board Position. The board-position is expressed in the format of slotID. For example, 1. Here 1 is an example. The value may vary with devices.";
          }
        }
      }
    }
  }
  augment "/ncs:devices/ncs:device/ncs:rpc" {
    container rpc-power-off-sfu {
      tailf:ncs-device-type "netconf";
      tailf:display-when "not(../../ncs:module) or ../../ncs:module[ncs:name='huawei-driver']";
      tailf:action power-off-sfu {
        tailf:actionpoint ncsproxy {
          tailf:internal;
        }
        description
          "Power Off Sfu.";
        input {
          leaf board-position {
            type string;
            mandatory true;
            description
              "Board Position. The board-position is expressed in the format of slotID. For example, 1. Here 1 is an example. The value may vary with devices.";
          }
          leaf auto-power-on {
            type empty;
            description
              "Auto power on.";
          }
        }
      }
    }
  }
  augment "/ncs:devices/ncs:device-group/ncs:ned-id/ncs:rpc" {
    container rpc-power-off-sfu {
      tailf:ncs-device-type "netconf";
      tailf:display-when "/ncs:devices/ncs:device[ncs:name=current()/../../../ncs:member]/ncs:module[ncs:name='huawei-driver']";
      tailf:action power-off-sfu {
        tailf:actionpoint ncsproxy {
          tailf:internal;
        }
        description
          "Power Off Sfu.";
        input {
          leaf board-position {
            type string;
            mandatory true;
            description
              "Board Position. The board-position is expressed in the format of slotID. For example, 1. Here 1 is an example. The value may vary with devices.";
          }
          leaf auto-power-on {
            type empty;
            description
              "Auto power on.";
          }
        }
      }
    }
  }
  augment "/ncs:devices/ncs:device/ncs:rpc" {
    container rpc-power-on-sfu {
      tailf:ncs-device-type "netconf";
      tailf:display-when "not(../../ncs:module) or ../../ncs:module[ncs:name='huawei-driver']";
      tailf:action power-on-sfu {
        tailf:actionpoint ncsproxy {
          tailf:internal;
        }
        description
          "Power On Sfu.";
        input {
          leaf board-position {
            type string;
            mandatory true;
            description
              "Board Position. The board-position is expressed in the format of slotID. For example, 1. Here 1 is an example. The value may vary with devices.";
          }
        }
      }
    }
  }
  augment "/ncs:devices/ncs:device-group/ncs:ned-id/ncs:rpc" {
    container rpc-power-on-sfu {
      tailf:ncs-device-type "netconf";
      tailf:display-when "/ncs:devices/ncs:device[ncs:name=current()/../../../ncs:member]/ncs:module[ncs:name='huawei-driver']";
      tailf:action power-on-sfu {
        tailf:actionpoint ncsproxy {
          tailf:internal;
        }
        description
          "Power On Sfu.";
        input {
          leaf board-position {
            type string;
            mandatory true;
            description
              "Board Position. The board-position is expressed in the format of slotID. For example, 1. Here 1 is an example. The value may vary with devices.";
          }
        }
      }
    }
  }
  augment "/ncs:devices/ncs:device/ncs:rpc" {
    container rpc-power-off-lpu {
      tailf:ncs-device-type "netconf";
      tailf:display-when "not(../../ncs:module) or ../../ncs:module[ncs:name='huawei-driver']";
      tailf:action power-off-lpu {
        tailf:actionpoint ncsproxy {
          tailf:internal;
        }
        description
          "Power Off Lpu.";
        input {
          leaf board-position {
            type string;
            mandatory true;
            description
              "Board Position. The board-position is expressed in the format of slotID. For example, 1. Here 1 is an example. The value may vary with devices.";
          }
          leaf auto-power-on {
            type empty;
            description
              "Auto power on.";
          }
        }
      }
    }
  }
  augment "/ncs:devices/ncs:device-group/ncs:ned-id/ncs:rpc" {
    container rpc-power-off-lpu {
      tailf:ncs-device-type "netconf";
      tailf:display-when "/ncs:devices/ncs:device[ncs:name=current()/../../../ncs:member]/ncs:module[ncs:name='huawei-driver']";
      tailf:action power-off-lpu {
        tailf:actionpoint ncsproxy {
          tailf:internal;
        }
        description
          "Power Off Lpu.";
        input {
          leaf board-position {
            type string;
            mandatory true;
            description
              "Board Position. The board-position is expressed in the format of slotID. For example, 1. Here 1 is an example. The value may vary with devices.";
          }
          leaf auto-power-on {
            type empty;
            description
              "Auto power on.";
          }
        }
      }
    }
  }
  augment "/ncs:devices/ncs:device/ncs:rpc" {
    container rpc-power-on-lpu {
      tailf:ncs-device-type "netconf";
      tailf:display-when "not(../../ncs:module) or ../../ncs:module[ncs:name='huawei-driver']";
      tailf:action power-on-lpu {
        tailf:actionpoint ncsproxy {
          tailf:internal;
        }
        description
          "Power On Lpu.";
        input {
          leaf board-position {
            type string;
            mandatory true;
            description
              "Board Position. The board-position is expressed in the format of slotID. For example, 1. Here 1 is an example. The value may vary with devices.";
          }
        }
      }
    }
  }
  augment "/ncs:devices/ncs:device-group/ncs:ned-id/ncs:rpc" {
    container rpc-power-on-lpu {
      tailf:ncs-device-type "netconf";
      tailf:display-when "/ncs:devices/ncs:device[ncs:name=current()/../../../ncs:member]/ncs:module[ncs:name='huawei-driver']";
      tailf:action power-on-lpu {
        tailf:actionpoint ncsproxy {
          tailf:internal;
        }
        description
          "Power On Lpu.";
        input {
          leaf board-position {
            type string;
            mandatory true;
            description
              "Board Position. The board-position is expressed in the format of slotID. For example, 1. Here 1 is an example. The value may vary with devices.";
          }
        }
      }
    }
  }
  augment "/ncs:devices/ncs:device/ncs:rpc" {
    container rpc-power-off-mpu {
      tailf:ncs-device-type "netconf";
      tailf:display-when "not(../../ncs:module) or ../../ncs:module[ncs:name='huawei-driver']";
      tailf:action power-off-mpu {
        tailf:actionpoint ncsproxy {
          tailf:internal;
        }
        description
          "Power Off Mpu.";
        input {
          leaf board-position {
            type string;
            mandatory true;
            description
              "Board Position. The board-position is expressed in the format of slotID. For example, 1. Here 1 is an example. The value may vary with devices.";
          }
          leaf auto-power-on {
            type empty;
            description
              "Auto power on.";
          }
        }
      }
    }
  }
  augment "/ncs:devices/ncs:device-group/ncs:ned-id/ncs:rpc" {
    container rpc-power-off-mpu {
      tailf:ncs-device-type "netconf";
      tailf:display-when "/ncs:devices/ncs:device[ncs:name=current()/../../../ncs:member]/ncs:module[ncs:name='huawei-driver']";
      tailf:action power-off-mpu {
        tailf:actionpoint ncsproxy {
          tailf:internal;
        }
        description
          "Power Off Mpu.";
        input {
          leaf board-position {
            type string;
            mandatory true;
            description
              "Board Position. The board-position is expressed in the format of slotID. For example, 1. Here 1 is an example. The value may vary with devices.";
          }
          leaf auto-power-on {
            type empty;
            description
              "Auto power on.";
          }
        }
      }
    }
  }
  augment "/ncs:devices/ncs:device/ncs:rpc" {
    container rpc-power-on-mpu {
      tailf:ncs-device-type "netconf";
      tailf:display-when "not(../../ncs:module) or ../../ncs:module[ncs:name='huawei-driver']";
      tailf:action power-on-mpu {
        tailf:actionpoint ncsproxy {
          tailf:internal;
        }
        description
          "Power On Mpu.";
        input {
          leaf board-position {
            type string;
            mandatory true;
            description
              "Board Position. The board-position is expressed in the format of slotID. For example, 1. Here 1 is an example. The value may vary with devices.";
          }
        }
      }
    }
  }
  augment "/ncs:devices/ncs:device-group/ncs:ned-id/ncs:rpc" {
    container rpc-power-on-mpu {
      tailf:ncs-device-type "netconf";
      tailf:display-when "/ncs:devices/ncs:device[ncs:name=current()/../../../ncs:member]/ncs:module[ncs:name='huawei-driver']";
      tailf:action power-on-mpu {
        tailf:actionpoint ncsproxy {
          tailf:internal;
        }
        description
          "Power On Mpu.";
        input {
          leaf board-position {
            type string;
            mandatory true;
            description
              "Board Position. The board-position is expressed in the format of slotID. For example, 1. Here 1 is an example. The value may vary with devices.";
          }
        }
      }
    }
  }
  augment "/ncs:devices/ncs:device/ncs:rpc" {
    container rpc-set-usb-uart-stat {
      tailf:ncs-device-type "netconf";
      tailf:display-when "not(../../ncs:module) or ../../ncs:module[ncs:name='huawei-driver']";
      tailf:action set-usb-uart-stat {
        tailf:actionpoint ncsproxy {
          tailf:internal;
        }
        description
          "Set usb uart status.";
        input {
          leaf usb-uart-status {
            type ncs_rpc_notif_driver-usb-uart;
            description
              "Usb uart status, open or close.";
          }
        }
      }
    }
  }
  augment "/ncs:devices/ncs:device-group/ncs:ned-id/ncs:rpc" {
    container rpc-set-usb-uart-stat {
      tailf:ncs-device-type "netconf";
      tailf:display-when "/ncs:devices/ncs:device[ncs:name=current()/../../../ncs:member]/ncs:module[ncs:name='huawei-driver']";
      tailf:action set-usb-uart-stat {
        tailf:actionpoint ncsproxy {
          tailf:internal;
        }
        description
          "Set usb uart status.";
        input {
          leaf usb-uart-status {
            type ncs_rpc_notif_driver-usb-uart;
            description
              "Usb uart status, open or close.";
          }
        }
      }
    }
  }
  augment "/ncs:devices/ncs:device/ncs:config" {
    container driver {
      tailf:ncs-device-type "netconf";
      tailf:display-when "not(../../ncs:module) or ../../ncs:module[ncs:name='huawei-driver']";
      description
        "Configuration of the driver.";
      container global-attribute {
        description
          "Configure global attribute.";
        leaf board-power-on-delay {
          type uint32 {
            range "0..65535";
          }
          units "min";
          default "0";
          description
            "Board Power-on-delay (0 stands for cancel operation).";
        }
        leaf card-power-on-delay {
          type uint32 {
            range "0..65535";
          }
          units "min";
          default "0";
          description
            "Pic Power-on-delay (0 stands for cancel operation).";
        }
        leaf dustproof-check {
          type driver-bool;
          default "yes";
          description
            "Dustproof Gate Check.";
        }
        leaf energy-mode {
          type energy-mode-type;
          default "basic";
          description
            "Energy saving mode.";
        }
        leaf energy-saving-pm {
          ext:dynamic-default;
          type energy-saving-pm-type;
          must "not(../energy-mode='standard' and ../energy-saving-pm='enable')" {
            tailf:xpath-root 3;
          }
          description
            "PM Energy-saving Mode (which includes disable, enable. The default value is disable).";
        }
        leaf entity-fault-board-isolate {
          type driver-entity-bool;
          default "enable";
          description
            "Enable Board Abnormal Reset Detection.";
        }
        leaf entity-fault-card-isolate {
          type driver-entity-bool;
          default "enable";
          description
            "Enable Card Abnormal Reset Detection.";
        }
        leaf fault-strategy {
          type global-card-fault-process-mode;
          default "reset";
          description
            "Global Card-Fault Process-Mode.";
        }
        leaf high-temp-switch {
          type driver-bool;
          default "yes";
          description
            "High Temperature Switch.";
        }
        leaf interface-match-check {
          type driver-interface-match-check-flag;
          default "disable";
          description
            "Used to configure interface matching check functionality.";
        }
        leaf least-sfu-number {
          type uint32 {
            range "1..8";
          }
          default "3";
          description
            "Least number of sfu (Dynamic parameter range, which may be smaller).";
        }
        leaf offline-function {
          type offline-function-type;
          default "enable";
          description
            "Offline function mask (which includes disable, enable. The default value is enable).";
        }
        leaf optional-entity-fault-isolate {
          type entity-fault-isolate-type;
          default "enable";
          description
            "EntFaultIso mode.";
        }
        leaf pic-reload-cycle {
          type reload-time;
          default "60min";
          description
            "Set the pic reload cycle after the pic failed to register 10 times.";
        }
        leaf sampling-period {
          type sampling-period-type;
          default "one-hour";
          description
            "Power sampling period.";
        }
        leaf sfu-switch-mode {
          type sfu-switch-mode-type;
          default "disable";
          description
            "SfuSwitchMode.";
        }
        leaf system-mac-address {
          type pub-type:mac-address {
            pattern '[0-9a-f][02468ace][0-9a-f]{2}(-[0-9a-f]{4}){2}';
          }
          description
            "The system MAC address, with the value being a unicast MAC address that is not composed of all 0s. It will take effect only after the system is rebooted.";
        }
        leaf system-mac-number {
          when '../system-mac-address' {
            tailf:xpath-root 3;
          }
          type uint32 {
            range "1..32";
          }
          default "8";
          description
            "The number of system MAC address.";
        }
        leaf system-trap {
          type trap-type;
          default "base-trap";
          description
            "Switch trap type.";
        }
        leaf temp-query-mode {
          type mib-query-mode-type;
          default "default";
          description
            "MIB Temperatue Brief Query Mode.";
        }
        leaf vlt-query-mode {
          type mib-query-mode-type;
          default "default";
          description
            "MIB Voltage Brief Query Mode.";
        }
        // NCS drop config false leaf 'cur-forward-mode'
        leaf next-forward-mode {
          type forwarding-mode;
          ext:dynamic-default;
          description
            "Next forward mode, compatible or enhance, which some boards can not support. The default value varies with the forward mode of a device. Generally, the default value is compatible. However, it changes to enhance if the device supports only enhance (warning:system will restart after success, and then take effect).";
        }
        // NCS drop config false leaf 'cur-work-mode'
        // NCS drop config false leaf 'next-work-mode'
        // NCS drop config false leaf 'warm-backup-states'
        leaf warm-backup-mode {
          type warm-backup-mode;
          must "not((../energy-mode='deep' or ../energy-mode='optimal') and (../warm-backup-mode='enable'))" {
            tailf:xpath-root 3;
          }
          default "disable";
          description
            "Cur warm-backup mode.";
        }
        // NCS drop config false leaf 'cur-device-work-mode'
        // NCS drop config false leaf 'next-device-work-mode'
        // NCS drop config false leaf 'dcn-management-plane-lock-status'
        // NCS drop config false leaf 'cur-dcn-plane-mode'
        // NCS drop config false leaf 'next-dcn-plane-mode'
        // NCS drop config false leaf 'cur-system-mode'
        // NCS drop config false leaf 'next-system-mode'
        // NCS drop config false leaf 'auto-upgrade-model'
        // NCS drop config false leaf 'chassis-last-change-time'
        // NCS drop config false leaf 'cur-chassis-number'
        // NCS drop config false leaf 'max-chassis-number'
        // NCS drop config false leaf 'power-consumption'
        // NCS drop config false leaf 'split-resume'
        // NCS drop config false leaf 'switch-port-mode'
        // NCS drop config false leaf 'system-service-type'
        // NCS drop config false leaf 'usb-uart-status'
        // NCS drop config false leaf 'cur-system-mac-address'
        // NCS drop config false leaf 'board-channel-check-status'
        // NCS drop config false leaf 'energy-saving-pm-status'
      }
      // NCS drop config false container 'io-inspect-states'
      container io-inspect-attributes {
        description
          "List of IO inspect attributes.";
        list io-inspect-attribute {
          key "position index";
          description
            "Configure IO inspect attribute.";
          leaf position {
            type string {
              length "1..32";
            }
            description
              "Position. The position is expressed in the format of slotID. For example, 1. Here 1 is an example. The value may vary with devices.";
          }
          leaf index {
            type uint32;
            description
              "Index.";
          }
          leaf default-states {
            type driver-default-states;
            mandatory true;
            description
              "Default status.";
          }
          leaf alarm-name {
            ext:operation-exclude "update|delete";
            type string {
              length "1..16";
            }
            description
              "Alarm name.";
          }
        }
      }
      container temperatures {
        ext:operation-exclude "create";
        description
          "List of temperature information about a board.";
        list temperature {
          ext:generated-by "system";
          ext:operation-exclude "create";
          key "position i2c address channel";
          description
            "Configure temperature information about a board.";
          leaf position {
            type string {
              length "1..50";
            }
            description
              "Location of a board. The position is expressed in the format of slotID. For example, 1. Here 1 is an example. The value may vary with devices.";
          }
          leaf i2c {
            type uint32;
            description
              "I2C bus number of a board.";
          }
          leaf address {
            type string {
              length "1..50";
            }
            description
              "Sensor address of a board. The address is expressed in the format of a number. For example, 0. Here 0 is an example. The value may vary with devices.";
          }
          leaf channel {
            type uint32;
            description
              "ID of the sensor channel of a board.";
          }
          leaf minor {
            type uint32 {
              range "80..120";
            }
            description
              "Minor high temperature alarm threshold of a board. The relationships between temperature alarm threshold percentages are as follows: 1. The minor high-temperature alarm threshold percentage multiplying the default minor high-temperature alarm threshold must be less than the major high-temperature alarm threshold percentage multiplying the default major high-temperature alarm threshold. 2. The major high-temperature alarm threshold percentage multiplying the default major high-temperature alarm threshold must be less than the critical high-temperature alarm threshold percentage multiplying the default critical high-temperature alarm threshold.";
          }
          leaf major {
            type uint32 {
              range "80..120";
            }
            description
              "Major high temperature alarm threshold of a board. The relationships between temperature alarm threshold percentages are as follows: 1. The minor high-temperature alarm threshold percentage multiplying the default minor high-temperature alarm threshold must be less than the major high-temperature alarm threshold percentage multiplying the default major high-temperature alarm threshold. 2. The major high-temperature alarm threshold percentage multiplying the default major high-temperature alarm threshold must be less than the critical high-temperature alarm threshold percentage multiplying the default critical high-temperature alarm threshold.";
          }
          leaf fatal {
            type uint32 {
              range "80..120";
            }
            description
              "Fatal high temperature alarm threshold of a board. The relationships between temperature alarm threshold percentages are as follows: 1. The minor high-temperature alarm threshold percentage multiplying the default minor high-temperature alarm threshold must be less than the major high-temperature alarm threshold percentage multiplying the default major high-temperature alarm threshold. 2. The major high-temperature alarm threshold percentage multiplying the default major high-temperature alarm threshold must be less than the critical high-temperature alarm threshold percentage multiplying the default critical high-temperature alarm threshold.";
          }
          leaf fan-tmax {
            ext:dynamic-default;
            when '../minor and ../major and ../fatal' {
              tailf:xpath-root 3;
            }
            type int32 {
              range "-50..127";
            }
            must '(../fan-tmax>=../fan-tmin)' {
              tailf:xpath-root 3;
            }
            description
              "Fan Speed Adjust High Threshold.[-50,127]for get operation,[-50,127]for edit operation. Each board has a different default fan-tmax value.";
          }
          leaf fan-tmin {
            ext:dynamic-default;
            when '../minor and ../major and ../fatal' {
              tailf:xpath-root 3;
            }
            type int32 {
              range "-50..127";
            }
            must '(../fan-tmin<=../fan-tmax)' {
              tailf:xpath-root 3;
            }
            description
              "Fan Speed Adjust Low Threshold.[-50,127]for get operation,[-50,127]for edit operation. Each board has a different default fan-tmin value.";
          }
          // NCS drop config false leaf 'pcb-name'
          // NCS drop config false leaf 'entity-index'
          // NCS drop config false leaf state
          // NCS drop config false leaf 'current-temperature'
          // NCS drop config false leaf 'minor-alarm-threshold'
          // NCS drop config false leaf 'major-alarm-threshold'
          // NCS drop config false leaf 'fatal-alarm-threshold'
          // NCS drop config false leaf 'fan-tmax-states'
          // NCS drop config false leaf 'fan-tmin-states'
        }
      }
      container voltageinfos {
        ext:operation-exclude "create";
        description
          "List of voltage information about a board.";
        list voltageinfo {
          ext:generated-by "system";
          ext:operation-exclude "create";
          key "position i2c address channel";
          description
            "Configure voltage information about a board.";
          leaf position {
            type string {
              length "1..50";
            }
            description
              "Location of a board. The position is expressed in the format of slotID. For example, 1. Here 1 is an example. The value may vary with devices.";
          }
          leaf i2c {
            type uint32;
            description
              "I2C bus number of a board.";
          }
          leaf address {
            type string {
              length "1..50";
            }
            description
              "Sensor address of a board. The address is expressed in the format of a number. For example, 0. Here 0 is an example. The value may vary with devices.";
          }
          leaf channel {
            type uint32;
            description
              "ID of the sensor channel of a board.";
          }
          leaf major-voltage-threshold-low {
            type uint32 {
              range "80..120";
            }
            description
              "The percentage of the major voltage threshold below the default voltage. The relationships between voltage alarm threshold percentages are as follows: 1. The fatal undervoltage alarm threshold percentage multiplying the default fatal undervoltage alarm threshold must be less than the major undervoltage alarm threshold percentage multiplying the default major undervoltage alarm threshold. 2. The major undervoltage alarm threshold percentage multiplying the default major undervoltage alarm threshold must be less than the major overvoltage alarm threshold percentage multiplying the default major overvoltage alarm threshold. 3. The major overvoltage alarm threshold percentage multiplying the default major overvoltage alarm threshold must be less than the fatal overvoltage alarm threshold percentage multiplying the default fatal overvoltage alarm threshold.";
          }
          leaf major-voltage-threshold-high {
            type uint32 {
              range "80..120";
            }
            description
              "The percentage of the major voltage threshold above the default voltage. The relationships between voltage alarm threshold percentages are as follows: 1. The fatal undervoltage alarm threshold percentage multiplying the default fatal undervoltage alarm threshold must be less than the major undervoltage alarm threshold percentage multiplying the default major undervoltage alarm threshold. 2. The major undervoltage alarm threshold percentage multiplying the default major undervoltage alarm threshold must be less than the major overvoltage alarm threshold percentage multiplying the default major overvoltage alarm threshold. 3. The major overvoltage alarm threshold percentage multiplying the default major overvoltage alarm threshold must be less than the fatal overvoltage alarm threshold percentage multiplying the default fatal overvoltage alarm threshold.";
          }
          leaf fatal-voltage-threshold-low {
            type uint32 {
              range "80..120";
            }
            description
              "The percentage of the fatal voltage threshold below the default voltage. The relationships between voltage alarm threshold percentages are as follows: 1. The fatal undervoltage alarm threshold percentage multiplying the default fatal undervoltage alarm threshold must be less than the major undervoltage alarm threshold percentage multiplying the default major undervoltage alarm threshold. 2. The major undervoltage alarm threshold percentage multiplying the default major undervoltage alarm threshold must be less than the major overvoltage alarm threshold percentage multiplying the default major overvoltage alarm threshold. 3. The major overvoltage alarm threshold percentage multiplying the default major overvoltage alarm threshold must be less than the fatal overvoltage alarm threshold percentage multiplying the default fatal overvoltage alarm threshold.";
          }
          leaf fatal-voltage-threshold-high {
            type uint32 {
              range "80..120";
            }
            description
              "The percentage of the fatal voltage threshold above the default voltage. The relationships between voltage alarm threshold percentages are as follows: 1. The fatal undervoltage alarm threshold percentage multiplying the default fatal undervoltage alarm threshold must be less than the major undervoltage alarm threshold percentage multiplying the default major undervoltage alarm threshold. 2. The major undervoltage alarm threshold percentage multiplying the default major undervoltage alarm threshold must be less than the major overvoltage alarm threshold percentage multiplying the default major overvoltage alarm threshold. 3. The major overvoltage alarm threshold percentage multiplying the default major overvoltage alarm threshold must be less than the fatal overvoltage alarm threshold percentage multiplying the default fatal overvoltage alarm threshold.";
          }
          // NCS drop config false leaf 'pcb-name'
          // NCS drop config false leaf 'entity-index'
          // NCS drop config false leaf state
          // NCS drop config false leaf 'current-voltage'
          // NCS drop config false leaf 'required-voltage'
          // NCS drop config false leaf 'major-low-threshold'
          // NCS drop config false leaf 'low-threshold'
          // NCS drop config false leaf 'major-high-threshold'
          // NCS drop config false leaf 'high-threshold'
          // NCS drop config false leaf 'voltage-ratio'
        }
      }
      // NCS drop config false container 'electric-current-infos'
      // NCS drop config false container 'interface-match-check-states'
      // NCS drop config false container 'area-energyinfos'
      // NCS drop config false container 'board-powers'
      // NCS drop config false container 'electronic-labels'
      // NCS drop config false container mbusnodes
      // NCS drop config false container 'check-running-software-safes'
      // NCS drop config false container bootinfos
      // NCS drop config false container 'multi-chassis-attributes'
      // NCS drop config false container 'chassis-run-modes'
      // NCS drop config false container 'stratum-3-clocks'
      // NCS drop config false container 'system-sync-clocks'
      // NCS drop config false container 'rollback-attribute'
      // NCS drop config false container 'slave-defaults'
      // NCS drop config false container 'inner-links'
      // NCS drop config false container 'slot-statistics'
    }
  }
  augment "/ncs:devices/ncs:device/ncs:live-status" {
    container driver {
      tailf:ncs-device-type "netconf";
      tailf:display-when "not(../../ncs:module) or ../../ncs:module[ncs:name='huawei-driver'] or (../../ncs:live-status-protocol[not(ncs:capability)]) or (../../ncs:live-status-protocol/ncs:capability/ncs:module[.='huawei-driver'])";
      description
        "Configuration of the driver.";
      container global-attribute {
        description
          "Configure global attribute.";
        leaf board-power-on-delay {
          type uint32 {
            range "0..65535";
          }
          units "min";
          // NCS drop default statement
          description
            "Board Power-on-delay (0 stands for cancel operation).";
        }
        leaf card-power-on-delay {
          type uint32 {
            range "0..65535";
          }
          units "min";
          // NCS drop default statement
          description
            "Pic Power-on-delay (0 stands for cancel operation).";
        }
        leaf dustproof-check {
          type live_ncs_driver-bool;
          // NCS drop default statement
          description
            "Dustproof Gate Check.";
        }
        leaf energy-mode {
          type live_ncs_energy-mode-type;
          // NCS drop default statement
          description
            "Energy saving mode.";
        }
        leaf energy-saving-pm {
          ext:dynamic-default;
          type live_ncs_energy-saving-pm-type;
          // NCS drop must statement
          description
            "PM Energy-saving Mode (which includes disable, enable. The default value is disable).";
        }
        leaf entity-fault-board-isolate {
          type live_ncs_driver-entity-bool;
          // NCS drop default statement
          description
            "Enable Board Abnormal Reset Detection.";
        }
        leaf entity-fault-card-isolate {
          type live_ncs_driver-entity-bool;
          // NCS drop default statement
          description
            "Enable Card Abnormal Reset Detection.";
        }
        leaf fault-strategy {
          type live_ncs_global-card-fault-process-mode;
          // NCS drop default statement
          description
            "Global Card-Fault Process-Mode.";
        }
        leaf high-temp-switch {
          type live_ncs_driver-bool;
          // NCS drop default statement
          description
            "High Temperature Switch.";
        }
        leaf interface-match-check {
          type live_ncs_driver-interface-match-check-flag;
          // NCS drop default statement
          description
            "Used to configure interface matching check functionality.";
        }
        leaf least-sfu-number {
          type uint32 {
            range "1..8";
          }
          // NCS drop default statement
          description
            "Least number of sfu (Dynamic parameter range, which may be smaller).";
        }
        leaf offline-function {
          type live_ncs_offline-function-type;
          // NCS drop default statement
          description
            "Offline function mask (which includes disable, enable. The default value is enable).";
        }
        leaf optional-entity-fault-isolate {
          type live_ncs_entity-fault-isolate-type;
          // NCS drop default statement
          description
            "EntFaultIso mode.";
        }
        leaf pic-reload-cycle {
          type live_ncs_reload-time;
          // NCS drop default statement
          description
            "Set the pic reload cycle after the pic failed to register 10 times.";
        }
        leaf sampling-period {
          type live_ncs_sampling-period-type;
          // NCS drop default statement
          description
            "Power sampling period.";
        }
        leaf sfu-switch-mode {
          type live_ncs_sfu-switch-mode-type;
          // NCS drop default statement
          description
            "SfuSwitchMode.";
        }
        leaf system-mac-address {
          type pub-type:live_ncs_mac-address;
          description
            "The system MAC address, with the value being a unicast MAC address that is not composed of all 0s. It will take effect only after the system is rebooted.";
        }
        leaf system-mac-number {
          // NCS drop when statement
          type uint32 {
            range "1..32";
          }
          // NCS drop default statement
          description
            "The number of system MAC address.";
        }
        leaf system-trap {
          type live_ncs_trap-type;
          // NCS drop default statement
          description
            "Switch trap type.";
        }
        leaf temp-query-mode {
          type live_ncs_mib-query-mode-type;
          // NCS drop default statement
          description
            "MIB Temperatue Brief Query Mode.";
        }
        leaf vlt-query-mode {
          type live_ncs_mib-query-mode-type;
          // NCS drop default statement
          description
            "MIB Voltage Brief Query Mode.";
        }
        leaf cur-forward-mode {
          type live_ncs_forwarding-mode;
          // NCS drop default statement
          description
            "Current forward mode, compatible or enhance.";
        }
        leaf next-forward-mode {
          type live_ncs_forwarding-mode;
          ext:dynamic-default;
          description
            "Next forward mode, compatible or enhance, which some boards can not support. The default value varies with the forward mode of a device. Generally, the default value is compatible. However, it changes to enhance if the device supports only enhance (warning:system will restart after success, and then take effect).";
        }
        leaf cur-work-mode {
          type live_ncs_driver-system-mode;
          description
            "Cur work mode, 1+1 or 1:1.";
        }
        leaf next-work-mode {
          type live_ncs_driver-system-mode;
          description
            "Next work mode,1+1 or 1:1. The work mode cannot be switched on specific device models or in specific scenarios (warning:system will restart after success, and then take effect).";
        }
        leaf warm-backup-states {
          type live_ncs_warm-backup-status;
          // NCS drop default statement
          description
            "Cur warm-backup status.";
        }
        leaf warm-backup-mode {
          type live_ncs_warm-backup-mode;
          // NCS drop must statement
          // NCS drop default statement
          description
            "Cur warm-backup mode.";
        }
        leaf cur-device-work-mode {
          type live_ncs_driver-work-mode;
          description
            "Cur device work mode, base or ptn-iot.";
        }
        leaf next-device-work-mode {
          type live_ncs_driver-work-mode;
          description
            "Next device work mode, base or ptn-iot.";
        }
        leaf dcn-management-plane-lock-status {
          type live_ncs_driver-lock-state-type;
          description
            "Dcn-management-plane locked status.";
        }
        leaf cur-dcn-plane-mode {
          type live_ncs_driver-dcn-plane-mode-type;
          description
            "Current DCN plane mode.";
        }
        leaf next-dcn-plane-mode {
          type live_ncs_driver-dcn-plane-mode-type;
          description
            "Next DCN plane mode.";
        }
        leaf cur-system-mode {
          type live_ncs_driver-system-mode-type;
          // NCS drop default statement
          description
            "Cur System mode, classic or ls.";
        }
        leaf next-system-mode {
          type live_ncs_driver-system-mode-type;
          // NCS drop default statement
          description
            "Next System mode, classic or ls (warning:system will restart after success, and then take effect).";
        }
        leaf auto-upgrade-model {
          type live_ncs_driver-upgrade-mode-type;
          // NCS drop default statement
          description
            "Auto Upgrade Model.";
        }
        leaf chassis-last-change-time {
          type pub-type:live_ncs_time-tick;
          description
            "Time when a chassis or an entity is last added or removed, or time when chassis status (administration status, running status, or active/standby status) is last changed. The time is in UTC time.";
        }
        leaf cur-chassis-number {
          type uint32;
          description
            "Current number of chassis.";
        }
        leaf max-chassis-number {
          type uint32 {
            range "1..255";
          }
          description
            "Maximum number of chassis.";
        }
        leaf power-consumption {
          type string {
            length "1..255";
          }
          description
            "Power Consumption.";
        }
        leaf split-resume {
          type live_ncs_driver-split-resume-mode-type;
          description
            "Slave chassis reset mode.";
        }
        leaf switch-port-mode {
          type string {
            length "1..128";
          }
          description
            "Switch-port Work-mode.";
        }
        leaf system-service-type {
          type string {
            length "1..128";
          }
          description
            "System Service Type.";
        }
        leaf usb-uart-status {
          type live_ncs_usb-uart-status;
          description
            "Usb uart status, open or closed.";
        }
        leaf cur-system-mac-address {
          type pub-type:live_ncs_mac-address;
          description
            "Current system MAC address.";
        }
        leaf board-channel-check-status {
          type live_ncs_board-channel-check-type;
          description
            "The board-channel-check status.";
        }
        leaf energy-saving-pm-status {
          type live_ncs_energy-saving-pm-type;
          description
            "PM energy-saving mode status.";
        }
      }
      container io-inspect-states {
        description
          "List of IO inspect state.";
        list io-inspect-state {
          key "position index";
          description
            "IO inspect state.";
          leaf position {
            type string {
              length "1..32";
            }
            description
              "Position. The position is expressed in the format of slotID. For example, 1. Here 1 is an example. The value may vary with devices.";
          }
          leaf index {
            type uint32;
            description
              "Index.";
          }
          leaf states {
            type live_ncs_driver-inspect-state;
            description
              "Input status.";
          }
          leaf default-states {
            type live_ncs_driver-inspect-state;
            description
              "Default status.";
          }
          leaf alarm-name {
            type string {
              length "1..16";
            }
            description
              "Alarm name.";
          }
          leaf alarm-status {
            type live_ncs_driver-inspect-alarm-state;
            description
              "Alarm status.";
          }
        }
      }
      container io-inspect-attributes {
        description
          "List of IO inspect attributes.";
        list io-inspect-attribute {
          key "position index";
          description
            "Configure IO inspect attribute.";
          leaf position {
            type string {
              length "1..32";
            }
            description
              "Position. The position is expressed in the format of slotID. For example, 1. Here 1 is an example. The value may vary with devices.";
          }
          leaf index {
            type uint32;
            description
              "Index.";
          }
          leaf default-states {
            type live_ncs_driver-default-states;
            // NCS drop mandatory statement
            description
              "Default status.";
          }
          leaf alarm-name {
            ext:operation-exclude "update|delete";
            type string {
              length "1..16";
            }
            description
              "Alarm name.";
          }
        }
      }
      container temperatures {
        ext:operation-exclude "create";
        description
          "List of temperature information about a board.";
        list temperature {
          ext:generated-by "system";
          ext:operation-exclude "create";
          key "position i2c address channel";
          description
            "Configure temperature information about a board.";
          leaf position {
            type string {
              length "1..50";
            }
            description
              "Location of a board. The position is expressed in the format of slotID. For example, 1. Here 1 is an example. The value may vary with devices.";
          }
          leaf i2c {
            type uint32;
            description
              "I2C bus number of a board.";
          }
          leaf address {
            type string {
              length "1..50";
            }
            description
              "Sensor address of a board. The address is expressed in the format of a number. For example, 0. Here 0 is an example. The value may vary with devices.";
          }
          leaf channel {
            type uint32;
            description
              "ID of the sensor channel of a board.";
          }
          leaf minor {
            type uint32 {
              range "80..120";
            }
            description
              "Minor high temperature alarm threshold of a board. The relationships between temperature alarm threshold percentages are as follows: 1. The minor high-temperature alarm threshold percentage multiplying the default minor high-temperature alarm threshold must be less than the major high-temperature alarm threshold percentage multiplying the default major high-temperature alarm threshold. 2. The major high-temperature alarm threshold percentage multiplying the default major high-temperature alarm threshold must be less than the critical high-temperature alarm threshold percentage multiplying the default critical high-temperature alarm threshold.";
          }
          leaf major {
            type uint32 {
              range "80..120";
            }
            description
              "Major high temperature alarm threshold of a board. The relationships between temperature alarm threshold percentages are as follows: 1. The minor high-temperature alarm threshold percentage multiplying the default minor high-temperature alarm threshold must be less than the major high-temperature alarm threshold percentage multiplying the default major high-temperature alarm threshold. 2. The major high-temperature alarm threshold percentage multiplying the default major high-temperature alarm threshold must be less than the critical high-temperature alarm threshold percentage multiplying the default critical high-temperature alarm threshold.";
          }
          leaf fatal {
            type uint32 {
              range "80..120";
            }
            description
              "Fatal high temperature alarm threshold of a board. The relationships between temperature alarm threshold percentages are as follows: 1. The minor high-temperature alarm threshold percentage multiplying the default minor high-temperature alarm threshold must be less than the major high-temperature alarm threshold percentage multiplying the default major high-temperature alarm threshold. 2. The major high-temperature alarm threshold percentage multiplying the default major high-temperature alarm threshold must be less than the critical high-temperature alarm threshold percentage multiplying the default critical high-temperature alarm threshold.";
          }
          leaf fan-tmax {
            ext:dynamic-default;
            // NCS drop when statement
            type int32 {
              range "-50..127";
            }
            // NCS drop must statement
            description
              "Fan Speed Adjust High Threshold.[-50,127]for get operation,[-50,127]for edit operation. Each board has a different default fan-tmax value.";
          }
          leaf fan-tmin {
            ext:dynamic-default;
            // NCS drop when statement
            type int32 {
              range "-50..127";
            }
            // NCS drop must statement
            description
              "Fan Speed Adjust Low Threshold.[-50,127]for get operation,[-50,127]for edit operation. Each board has a different default fan-tmin value.";
          }
          leaf pcb-name {
            type string {
              length "1..50";
            }
            description
              "Type of a board.";
          }
          leaf entity-index {
            type uint32;
            description
              "Index of a board.";
          }
          leaf state {
            type live_ncs_driver-sensor-state;
            description
              "Sensor status of a board.";
          }
          leaf current-temperature {
            type int32;
            description
              "Current temperature of a board.";
          }
          leaf minor-alarm-threshold {
            type int32;
            description
              "Lower temperature threshold of a board.";
          }
          leaf major-alarm-threshold {
            type int32;
            description
              "Upper temperature threshold of a board.";
          }
          leaf fatal-alarm-threshold {
            type int32;
            description
              "Upper limit of the temperature of a board.";
          }
          leaf fan-tmax-states {
            type int32 {
              range "-50..127";
            }
            description
              "Fan Speed Adjust High Threshold.";
          }
          leaf fan-tmin-states {
            type int32 {
              range "-50..127";
            }
            description
              "Fan Speed Adjust Low Threshold.";
          }
        }
      }
      container voltageinfos {
        ext:operation-exclude "create";
        description
          "List of voltage information about a board.";
        list voltageinfo {
          ext:generated-by "system";
          ext:operation-exclude "create";
          key "position i2c address channel";
          description
            "Configure voltage information about a board.";
          leaf position {
            type string {
              length "1..50";
            }
            description
              "Location of a board. The position is expressed in the format of slotID. For example, 1. Here 1 is an example. The value may vary with devices.";
          }
          leaf i2c {
            type uint32;
            description
              "I2C bus number of a board.";
          }
          leaf address {
            type string {
              length "1..50";
            }
            description
              "Sensor address of a board. The address is expressed in the format of a number. For example, 0. Here 0 is an example. The value may vary with devices.";
          }
          leaf channel {
            type uint32;
            description
              "ID of the sensor channel of a board.";
          }
          leaf major-voltage-threshold-low {
            type uint32 {
              range "80..120";
            }
            description
              "The percentage of the major voltage threshold below the default voltage. The relationships between voltage alarm threshold percentages are as follows: 1. The fatal undervoltage alarm threshold percentage multiplying the default fatal undervoltage alarm threshold must be less than the major undervoltage alarm threshold percentage multiplying the default major undervoltage alarm threshold. 2. The major undervoltage alarm threshold percentage multiplying the default major undervoltage alarm threshold must be less than the major overvoltage alarm threshold percentage multiplying the default major overvoltage alarm threshold. 3. The major overvoltage alarm threshold percentage multiplying the default major overvoltage alarm threshold must be less than the fatal overvoltage alarm threshold percentage multiplying the default fatal overvoltage alarm threshold.";
          }
          leaf major-voltage-threshold-high {
            type uint32 {
              range "80..120";
            }
            description
              "The percentage of the major voltage threshold above the default voltage. The relationships between voltage alarm threshold percentages are as follows: 1. The fatal undervoltage alarm threshold percentage multiplying the default fatal undervoltage alarm threshold must be less than the major undervoltage alarm threshold percentage multiplying the default major undervoltage alarm threshold. 2. The major undervoltage alarm threshold percentage multiplying the default major undervoltage alarm threshold must be less than the major overvoltage alarm threshold percentage multiplying the default major overvoltage alarm threshold. 3. The major overvoltage alarm threshold percentage multiplying the default major overvoltage alarm threshold must be less than the fatal overvoltage alarm threshold percentage multiplying the default fatal overvoltage alarm threshold.";
          }
          leaf fatal-voltage-threshold-low {
            type uint32 {
              range "80..120";
            }
            description
              "The percentage of the fatal voltage threshold below the default voltage. The relationships between voltage alarm threshold percentages are as follows: 1. The fatal undervoltage alarm threshold percentage multiplying the default fatal undervoltage alarm threshold must be less than the major undervoltage alarm threshold percentage multiplying the default major undervoltage alarm threshold. 2. The major undervoltage alarm threshold percentage multiplying the default major undervoltage alarm threshold must be less than the major overvoltage alarm threshold percentage multiplying the default major overvoltage alarm threshold. 3. The major overvoltage alarm threshold percentage multiplying the default major overvoltage alarm threshold must be less than the fatal overvoltage alarm threshold percentage multiplying the default fatal overvoltage alarm threshold.";
          }
          leaf fatal-voltage-threshold-high {
            type uint32 {
              range "80..120";
            }
            description
              "The percentage of the fatal voltage threshold above the default voltage. The relationships between voltage alarm threshold percentages are as follows: 1. The fatal undervoltage alarm threshold percentage multiplying the default fatal undervoltage alarm threshold must be less than the major undervoltage alarm threshold percentage multiplying the default major undervoltage alarm threshold. 2. The major undervoltage alarm threshold percentage multiplying the default major undervoltage alarm threshold must be less than the major overvoltage alarm threshold percentage multiplying the default major overvoltage alarm threshold. 3. The major overvoltage alarm threshold percentage multiplying the default major overvoltage alarm threshold must be less than the fatal overvoltage alarm threshold percentage multiplying the default fatal overvoltage alarm threshold.";
          }
          leaf pcb-name {
            type string {
              length "1..50";
            }
            description
              "Type of a board.";
          }
          leaf entity-index {
            type uint32;
            description
              "Index of a board.";
          }
          leaf state {
            type live_ncs_driver-sensor-state;
            description
              "Voltage sensor status of a board.";
          }
          leaf current-voltage {
            type string {
              length "1..50";
            }
            description
              "Current voltage of a board.";
          }
          leaf required-voltage {
            type string {
              length "1..50";
            }
            description
              "Basic voltage required by the board.";
          }
          leaf major-low-threshold {
            type string {
              length "1..50";
            }
            description
              "Lower or lower threshold of the voltage of a board.";
          }
          leaf low-threshold {
            type string {
              length "1..50";
            }
            description
              "Lower threshold of the board voltage.";
          }
          leaf major-high-threshold {
            type string {
              length "1..50";
            }
            description
              "High upper threshold of the voltage of a board.";
          }
          leaf high-threshold {
            type string {
              length "1..50";
            }
            description
              "Fatal upper threshold of the board voltage.";
          }
          leaf voltage-ratio {
            type string {
              length "1..50";
            }
            description
              "Voltage division ratio of a board.";
          }
        }
      }
      container electric-current-infos {
        description
          "List of current information about a board.";
        list electric-current-info {
          key "position i2c address channel";
          description
            "Statistics of current information about a board.";
          leaf position {
            type string {
              length "1..32";
            }
            description
              "Board position. The position is expressed in the format of slot ID. For example, 1. Here 1 is an example. The value may vary with devices.";
          }
          leaf i2c {
            type uint32;
            description
              "I2C bus number of a board.";
          }
          leaf address {
            type string {
              length "1..50";
            }
            description
              "Sensor address of a board. The address is expressed in the format of a number. For example, 0. Here 0 is an example. The value may vary with devices.";
          }
          leaf channel {
            type uint32;
            description
              "ID of the sensor channel of a board.";
          }
          leaf pcb-name {
            type string {
              length "1..50";
            }
            description
              "Type of a board.";
          }
          leaf state {
            type live_ncs_driver-sensor-state;
            description
              "Sensor status of a board.";
          }
          leaf current {
            type string {
              length "1..50";
            }
            units "A";
            description
              "Current value of the sensor.";
          }
          leaf required-current {
            type string {
              length "1..50";
            }
            units "A";
            description
              "Basic current required for the sensor.";
          }
          leaf fatal-low-threshold {
            type string {
              length "1..50";
            }
            units "A";
            description
              "Lower threshold of a critical current alarm.";
          }
          leaf fatal-high-threshold {
            type string {
              length "1..50";
            }
            units "A";
            description
              "Upper threshold of a critical current alarm.";
          }
          leaf major-low-threshold {
            type string {
              length "1..50";
            }
            units "A";
            description
              "Lower threshold of a major current alarm.";
          }
          leaf major-high-threshold {
            type string {
              length "1..50";
            }
            units "A";
            description
              "Upper threshold of a major current alarm.";
          }
        }
      }
      container interface-match-check-states {
        description
          "List of matching detection information about interfaces.";
        list interface-match-check-state {
          key "position";
          description
            "Statistics of matching detection information about an interface.";
          leaf position {
            type string {
              length "1..30";
            }
            description
              "Enabling position of interface match detection. The position is expressed in the format of slotID. For example, 1. Here 1 is an example. The value may vary with devices.";
          }
          leaf object {
            type live_ncs_driver-interface-match-check-object;
            description
              "Enabling object of interface match detection.";
          }
        }
      }
      container area-energyinfos {
        description
          "List of Area Energy.";
        list area-energyinfo {
          key "chassis-position area-id";
          description
            "Statistics of Area Energy.";
          leaf chassis-position {
            type string {
              length "1..32";
            }
            description
              "Chassis position. The chassis-position is expressed in the format of chassisID. For example, 1. Here 1 is an example. The value may vary with devices.";
          }
          leaf area-id {
            type uint32;
            description
              "Area ID.";
          }
          leaf area-rated-power {
            type string {
              length "1..255";
            }
            description
              "Area Rated Power.";
          }
          leaf area-assigned-power {
            type string {
              length "1..255";
            }
            description
              "Area assigned Power.";
          }
          leaf area-used-power {
            type string {
              length "1..255";
            }
            description
              "Area Used Power.";
          }
          leaf area-left-power {
            type string {
              length "1..255";
            }
            description
              "Area Left Power.";
          }
          container board-energys {
            description
              "List of energy information about a board.";
            list board-energy {
              key "position";
              description
                "Statistics of energy information about a board.";
              leaf position {
                type string {
                  length "1..32";
                }
                description
                  "Board position. The position is expressed in the format of slotID. For example, 1. Here 1 is an example. The value may vary with devices.";
              }
              leaf entity-index {
                type uint32;
                description
                  "Board index.";
              }
              leaf pcb-name {
                type string {
                  length "1..32";
                }
                description
                  "Board type.";
              }
              leaf voltage-value {
                type string {
                  length "1..255";
                }
                description
                  "Current voltage value.";
              }
              leaf electrical-value {
                type string {
                  length "1..255";
                }
                description
                  "Current electrical value.";
              }
              leaf current-power {
                type string {
                  length "1..255";
                }
                description
                  "Current power value.";
              }
              leaf rated-power {
                type string {
                  length "1..255";
                }
                description
                  "Rated power value.";
              }
              leaf power-threshold {
                type string {
                  length "1..255";
                }
                description
                  "Power threshold value.";
              }
              leaf efficiency {
                type string {
                  length "1..255";
                }
                description
                  "Efficiency value.";
              }
            }
          }
        }
      }
      container board-powers {
        description
          "List of power information about a board.";
        list board-power {
          key "position";
          description
            "Statistics of power information about a board.";
          leaf position {
            type string {
              length "1..32";
            }
            description
              "Board position. The position is expressed in the format of slotID. For example, 1. Here 1 is an example. The value may vary with devices.";
          }
          leaf entity-index {
            type uint32;
            description
              "Board index.";
          }
          leaf pcb-name {
            type string {
              length "1..32";
            }
            description
              "Board type.";
          }
          leaf voltage-value {
            type string {
              length "1..255";
            }
            description
              "Current voltage value.";
          }
          leaf electrical-value {
            type string {
              length "1..255";
            }
            description
              "Current electrical value.";
          }
          leaf current-power {
            type string {
              length "1..255";
            }
            description
              "Current power value.";
          }
          leaf rated-power {
            type string {
              length "1..255";
            }
            description
              "Rated power value.";
          }
          leaf power-threshold {
            type string {
              length "1..255";
            }
            description
              "Power threshold value.";
          }
          leaf efficiency {
            type string {
              length "1..255";
            }
            description
              "Efficiency value.";
          }
        }
      }
      container electronic-labels {
        description
          "List of electronic labels.";
        list electronic-label {
          key "entity-class position entity-serial-number";
          description
            "Statistics of electronic label.";
          leaf entity-class {
            type hardware-type:live_ncs_hardware-entityclass-type;
            description
              "Entity Class.";
          }
          leaf position {
            type string {
              length "1..32";
            }
            description
              "Position. The position is expressed in the format of slotID. For example, 1. Here 1 is an example. The value may vary with devices.";
          }
          leaf entity-serial-number {
            type uint32;
            description
              "Physical Number.";
          }
          leaf entity-index {
            type uint32;
            description
              "Entity Index.";
          }
          leaf entity-bomid {
            type string {
              length "1..128";
            }
            description
              "BOM ID.";
          }
          leaf barcode {
            type string {
              length "1..128";
            }
            description
              "Barcode.";
          }
          leaf bom-english-desc {
            type string {
              length "1..256";
            }
            description
              "English description of a BOM.";
          }
          leaf bom-local-desc {
            type string {
              length "1..256";
            }
            description
              "Local description of a BOM.";
          }
          leaf manufacturer-name {
            type string {
              length "1..128";
            }
            description
              "Manufacturer name.";
          }
          leaf manufacturer-date {
            type string {
              length "1..128";
            }
            description
              "Manufacture date.";
          }
          leaf manufacturer-code {
            type string {
              length "1..128";
            }
            description
              "Manufacture code.";
          }
          leaf board-type {
            type string {
              length "1..128";
            }
            description
              "Board type.";
          }
          leaf entity-asset-id {
            type string {
              length "1..128";
            }
            description
              "Asset ID.";
          }
          leaf entity-clei-code {
            type string {
              length "1..128";
            }
            description
              "CLEI code.";
          }
          leaf entity-update-log {
            type string {
              length "1..128";
            }
            description
              "Update log.";
          }
          leaf archives-info-version {
            type string {
              length "1..128";
            }
            description
              "Archives information version.";
          }
          leaf entity-open-bomid {
            type string {
              length "1..128";
            }
            description
              "The BomId for distribution.";
          }
          leaf entity-issue-number {
            type string {
              length "1..128";
            }
            description
              "Issue number.";
          }
          leaf entity-model {
            type string {
              length "1..128";
            }
            description
              "External model of an entity.";
          }
          leaf entity-elabel-version {
            type string {
              length "1..128";
            }
            description
              "Elabel version.";
          }
          leaf entity-elabel-extend {
            type string {
              length "1..270";
            }
            description
              "Extend information.";
          }
          leaf silk-screen {
            type string {
              length "1..256";
            }
            description
              "Silk screen information.";
          }
        }
      }
      container mbusnodes {
        description
          "List of information about all monitoring nodes of the host.";
        list mbusnode {
          key "slot-id";
          description
            "Statistics of information about a monitoring node.";
          leaf slot-id {
            type string {
              length "1..30";
            }
            description
              "Position. The slot-id is expressed in the format of slotID. For example, 1. Here 1 is an example. The value may vary with devices.";
          }
          leaf register {
            type string {
              length "1..63";
            }
            description
              "Registration status of the board.";
          }
          leaf board-type {
            type string {
              length "1..63";
            }
            description
              "Type of the board.";
          }
          leaf eeprom-number {
            type uint32 {
              range "0..24";
            }
            description
              "Number of EEPROMS on the board.";
          }
          leaf temperature-monitor-number {
            type uint32 {
              range "0..128";
            }
            description
              "Number of temperature sensors on the board.";
          }
          leaf voltage-monitor-number {
            type uint32 {
              range "0..128";
            }
            description
              "Number of voltage sensors on the board.";
          }
        }
      }
      container check-running-software-safes {
        description
          "List of checking running software safety.";
        list check-running-software-safe {
          key "position item";
          description
            "Statistics of checking running software safety.";
          leaf position {
            type string {
              length "1..32";
            }
            description
              "Board position. The position is expressed in the format of slotID. For example, 1. Here 1 is an example. The value may vary with devices.";
          }
          leaf item {
            type live_ncs_driver-item-type;
            description
              "System Item.";
          }
          leaf board-type {
            type string {
              length "1..32";
            }
            description
              "Board type.";
          }
          leaf pkgsha256hash {
            type string {
              length "1..255";
            }
            description
              "The HASH value in the system.";
          }
          leaf runsha256hash {
            type string {
              length "1..255";
            }
            description
              "The HASH value in the board.";
          }
          leaf result {
            type live_ncs_driver-result-type;
            description
              "Check Result.";
          }
        }
      }
      container bootinfos {
        description
          "List of boot information.";
        list bootinfo {
          key "position";
          description
            "Statistics of boot status information.";
          leaf position {
            type string {
              length "1..32";
            }
            description
              "Board position. The position is expressed in the format of slotID. For example, 1. Here 1 is an example. The value may vary with devices.";
          }
          leaf board-type {
            type string {
              length "1..32";
            }
            description
              "Board type.";
          }
          leaf rot {
            type string {
              length "1..64";
            }
            description
              "Boot Status.";
          }
        }
      }
      container multi-chassis-attributes {
        description
          "List of multiple chassis attributes.";
        list multi-chassis-attribute {
          key "current-chassis-id";
          description
            "Statistics of multiple chassis attribute.";
          leaf current-chassis-id {
            type uint32 {
              range "1..2";
            }
            description
              "Current chassis id.";
          }
          leaf next-chassis-id {
            type uint32 {
              range "1..2";
            }
            description
              "Next chassis id.";
          }
          leaf chassis-type {
            type live_ncs_driver-multi-chassis-type;
            description
              "Multi chassis type.";
          }
        }
      }
      container chassis-run-modes {
        description
          "List of chassis running modes.";
        list chassis-run-mode {
          key "chassis-id";
          description
            "Statistics of chassis running mode.";
          leaf chassis-id {
            type string {
              length "1..31";
            }
            description
              "Chassis id. The chassis-id is expressed in the format of chassisID. For example, 1. Here 1 is an example. The value may vary with devices.";
          }
          leaf current-run-mode {
            type live_ncs_driver-run-mode-type;
            description
              "Current run mode.";
          }
          leaf next-run-mode {
            type live_ncs_driver-run-mode-type;
            description
              "Next run mode.";
          }
          leaf current-run-cluster {
            type string {
              length "1..4";
            }
            description
              "Current cluster id.";
          }
          leaf next-run-cluster {
            type string {
              length "1..3";
            }
            description
              "Next cluster id.";
          }
        }
      }
      container stratum-3-clocks {
        description
          "List of status information about the stratum-3 clocks of the system.";
        list stratum-3-clock {
          key "slot-id";
          description
            "Statistics of status information about the stratum-3 clock of the system.";
          leaf slot-id {
            type string {
              length "1..32";
            }
            description
              "ID of the slot where the board resides. The slot-id is expressed in the format of slotID. For example, 1. Here 1 is an example. The value may vary with devices.";
          }
          leaf board-device-type {
            type string {
              length "1..32";
            }
            description
              "Type of the board.";
          }
          leaf clock-type {
            type live_ncs_driver-clock-type;
            description
              "Type of the clock associated with the board.";
          }
          leaf clock-slot-id {
            type string {
              length "1..32";
            }
            description
              "ID of the clock associated with the board.";
          }
          leaf switch-mode {
            type live_ncs_driver-switch-mode-type;
            description
              "Mode of the clock associated with the board.";
          }
        }
      }
      container system-sync-clocks {
        description
          "List of status information about the synchronization clocks of the system.";
        list system-sync-clock {
          key "slot-id";
          description
            "Statistics of status information about the synchronization clock of the system.";
          leaf slot-id {
            type string {
              length "1..32";
            }
            description
              "ID of the slot where the board resides. The slot-id is expressed in the format of slotID. For example, 1. Here 1 is an example. The value may vary with devices.";
          }
          leaf board-device-type {
            type string {
              length "1..32";
            }
            description
              "Type of the board.";
          }
          leaf clock-type {
            type live_ncs_driver-clock-type;
            description
              "Type of the clock associated with the board.";
          }
          leaf clock-slot-id {
            type string {
              length "1..32";
            }
            description
              "ID of the clock associated with the board.";
          }
          leaf switch-mode {
            type live_ncs_driver-switch-mode-type;
            description
              "Mode of the clock associated with the board.";
          }
          leaf lock-state {
            type live_ncs_driver-lock-state-type;
            description
              "Locking status of the clock.";
          }
        }
      }
      container rollback-attribute {
        description
          "Statistics of rollback information.";
        leaf rollback-soft-pack {
          type string {
            length "1..255";
          }
          description
            "Rollback software package info.";
        }
        leaf rollback-patch-file {
          type string {
            length "1..255";
          }
          description
            "Rollback patch file info.";
        }
        leaf rollback-config-file {
          type string {
            length "1..255";
          }
          description
            "Rollback config file info.";
        }
        leaf rollback-paf-file {
          type string {
            length "1..255";
          }
          description
            "Rollback paf file info.";
        }
        leaf rollback-result {
          type string {
            length "1..255";
          }
          description
            "Rollback result info.";
        }
        leaf rollback-remain-time {
          type string {
            length "1..255";
          }
          description
            "Rollback remain time info.";
        }
      }
      container slave-defaults {
        description
          "List of slave default.";
        list slave-default {
          key "chassis-id slot-id";
          description
            "Statistics of slave default.";
          leaf chassis-id {
            type string {
              length "1..32";
            }
            description
              "Chassis ID. The chassis-id is expressed in the format of chassisID. For example, 1. Here 1 is an example. The value may vary with devices.";
          }
          leaf slot-id {
            type string {
              length "1..32";
            }
            description
              "Slot ID. The slot-id is expressed in the format of slotID. For example, 1. Here 1 is an example. The value may vary with devices.";
          }
          leaf slave-default {
            type string {
              length "1..64";
            }
            description
              "Slave Default.";
          }
        }
      }
      container inner-links {
        description
          "List of inner links.";
        list inner-link {
          key "link-type left-chassis-position right-chassis-position";
          description
            "Statistics of inner link.";
          leaf link-type {
            type live_ncs_driver-inner-link-type;
            description
              "Link type.";
          }
          leaf left-chassis-position {
            type string {
              length "1..32";
            }
            description
              "Position of the left chassis.";
          }
          leaf right-chassis-position {
            type string {
              length "1..32";
            }
            description
              "Position of the right chassis.";
          }
          leaf link-name {
            type string {
              length "1..64";
            }
            description
              "Inner link name.";
          }
          leaf link-index {
            type string {
              length "1..64";
            }
            description
              "Inner link index.";
          }
          leaf left-chassis-type {
            type live_ncs_driver-link-chassis-type;
            description
              "Type of the left chassis.";
          }
          leaf right-chassis-type {
            type live_ncs_driver-link-chassis-type;
            description
              "Type of the right chassis.";
          }
          leaf operation-state {
            type live_ncs_driver-link-state-type;
            description
              "Operation state.";
          }
          leaf alarm-state {
            type live_ncs_driver-link-state-type;
            description
              "Alarm states whose values inherit HUAWEI-INNER-LINK-MIB.";
          }
          container physical-inner-links {
            description
              "List of physical inner links.";
            list physical-inner-link {
              key "physical-link-name";
              description
                "Statistics of physical inner link.";
              leaf physical-link-name {
                type string {
                  length "1..128";
                }
                description
                  "Physical link name. The physical-link-name is expressed in the format of slotID/cardID/portID. For example, 1/0/1. Here 1/0/1 is an example. The value may vary with devices.";
              }
              leaf left-port-name {
                type string {
                  length "1..128";
                }
                description
                  "Left port name.";
              }
              leaf right-port-name {
                type string {
                  length "1..128";
                }
                description
                  "Right port name.";
              }
              leaf operation-status {
                type live_ncs_driver-link-state-type;
                description
                  "Operation status.";
              }
              leaf repair-id {
                type uint32;
                description
                  "Repair ID.";
              }
              leaf repair-description {
                type string {
                  length "1..255";
                }
                description
                  "Repair description.";
              }
              container check-points {
                description
                  "List of checking points.";
                list check-point {
                  key "index";
                  description
                    "Statistics of checking point.";
                  leaf index {
                    type uint32;
                    description
                      "Check point index.";
                  }
                  leaf entity-name {
                    type string {
                      length "1..255";
                    }
                    description
                      "Check point name.";
                  }
                  leaf entity-class {
                    type hardware-type:live_ncs_hardware-entityclass-type;
                    description
                      "Check point type.";
                  }
                  leaf status {
                    type live_ncs_driver-link-state-type;
                    description
                      "Check point status.";
                  }
                  leaf reason-id {
                    type uint32;
                    description
                      "Reason ID.";
                  }
                  leaf reason-description {
                    type string {
                      length "1..255";
                    }
                    description
                      "Reason description.";
                  }
                  leaf repair-id {
                    type uint32;
                    description
                      "Repair ID.";
                  }
                  leaf repair-description {
                    type string {
                      length "1..255";
                    }
                    description
                      "Repair description.";
                  }
                }
              }
            }
          }
        }
      }
      container slot-statistics {
        description
          "List of slot statistics.";
        list slot-statistic {
          key "chassis-id slot-type";
          description
            "Statistics of slot.";
          leaf chassis-id {
            type string {
              length "1..32";
            }
            description
              "ChassisId. The chassis-id is expressed in the format of chassisID. For example, 1. Here 1 is an example. The value may vary with devices.";
          }
          leaf slot-type {
            type live_ncs_driver-slot-infos-type;
            description
              "SlotType.";
          }
          leaf total-slot-number {
            type uint32 {
              range "1..65535";
            }
            description
              "TotalSlotnum.";
          }
          leaf online-slot-number {
            type uint32 {
              range "0..65535";
            }
            description
              "OnlineSlotnum.";
          }
        }
      }
    }
  }
  augment "/ncs:devices/ncs:template/ncs:ned-id/ncs:config" {
    container driver {
      description
        "Configuration of the driver.";
      container global-attribute {
        description
          "Configure global attribute.";
        leaf board-power-on-delay {
          type string;
          units "min";
          // NCS drop default statement
          description
            "Board Power-on-delay (0 stands for cancel operation).";
        }
        leaf card-power-on-delay {
          type string;
          units "min";
          // NCS drop default statement
          description
            "Pic Power-on-delay (0 stands for cancel operation).";
        }
        leaf dustproof-check {
          type ncs_template_driver-bool;
          // NCS drop default statement
          description
            "Dustproof Gate Check.";
        }
        leaf energy-mode {
          type ncs_template_energy-mode-type;
          // NCS drop default statement
          description
            "Energy saving mode.";
        }
        leaf energy-saving-pm {
          ext:dynamic-default;
          type ncs_template_energy-saving-pm-type;
          // NCS drop must statement
          description
            "PM Energy-saving Mode (which includes disable, enable. The default value is disable).";
        }
        leaf entity-fault-board-isolate {
          type ncs_template_driver-entity-bool;
          // NCS drop default statement
          description
            "Enable Board Abnormal Reset Detection.";
        }
        leaf entity-fault-card-isolate {
          type ncs_template_driver-entity-bool;
          // NCS drop default statement
          description
            "Enable Card Abnormal Reset Detection.";
        }
        leaf fault-strategy {
          type ncs_template_global-card-fault-process-mode;
          // NCS drop default statement
          description
            "Global Card-Fault Process-Mode.";
        }
        leaf high-temp-switch {
          type ncs_template_driver-bool;
          // NCS drop default statement
          description
            "High Temperature Switch.";
        }
        leaf interface-match-check {
          type ncs_template_driver-interface-match-check-flag;
          // NCS drop default statement
          description
            "Used to configure interface matching check functionality.";
        }
        leaf least-sfu-number {
          type string;
          // NCS drop default statement
          description
            "Least number of sfu (Dynamic parameter range, which may be smaller).";
        }
        leaf offline-function {
          type ncs_template_offline-function-type;
          // NCS drop default statement
          description
            "Offline function mask (which includes disable, enable. The default value is enable).";
        }
        leaf optional-entity-fault-isolate {
          type ncs_template_entity-fault-isolate-type;
          // NCS drop default statement
          description
            "EntFaultIso mode.";
        }
        leaf pic-reload-cycle {
          type ncs_template_reload-time;
          // NCS drop default statement
          description
            "Set the pic reload cycle after the pic failed to register 10 times.";
        }
        leaf sampling-period {
          type ncs_template_sampling-period-type;
          // NCS drop default statement
          description
            "Power sampling period.";
        }
        leaf sfu-switch-mode {
          type ncs_template_sfu-switch-mode-type;
          // NCS drop default statement
          description
            "SfuSwitchMode.";
        }
        leaf system-mac-address {
          type pub-type:ncs_template_mac-address;
          description
            "The system MAC address, with the value being a unicast MAC address that is not composed of all 0s. It will take effect only after the system is rebooted.";
        }
        leaf system-mac-number {
          // NCS drop when statement
          type string;
          // NCS drop default statement
          description
            "The number of system MAC address.";
        }
        leaf system-trap {
          type ncs_template_trap-type;
          // NCS drop default statement
          description
            "Switch trap type.";
        }
        leaf temp-query-mode {
          type ncs_template_mib-query-mode-type;
          // NCS drop default statement
          description
            "MIB Temperatue Brief Query Mode.";
        }
        leaf vlt-query-mode {
          type ncs_template_mib-query-mode-type;
          // NCS drop default statement
          description
            "MIB Voltage Brief Query Mode.";
        }
        // NCS drop config false leaf 'cur-forward-mode'
        leaf next-forward-mode {
          type ncs_template_forwarding-mode;
          ext:dynamic-default;
          description
            "Next forward mode, compatible or enhance, which some boards can not support. The default value varies with the forward mode of a device. Generally, the default value is compatible. However, it changes to enhance if the device supports only enhance (warning:system will restart after success, and then take effect).";
        }
        // NCS drop config false leaf 'cur-work-mode'
        // NCS drop config false leaf 'next-work-mode'
        // NCS drop config false leaf 'warm-backup-states'
        leaf warm-backup-mode {
          type ncs_template_warm-backup-mode;
          // NCS drop must statement
          // NCS drop default statement
          description
            "Cur warm-backup mode.";
        }
        // NCS drop config false leaf 'cur-device-work-mode'
        // NCS drop config false leaf 'next-device-work-mode'
        // NCS drop config false leaf 'dcn-management-plane-lock-status'
        // NCS drop config false leaf 'cur-dcn-plane-mode'
        // NCS drop config false leaf 'next-dcn-plane-mode'
        // NCS drop config false leaf 'cur-system-mode'
        // NCS drop config false leaf 'next-system-mode'
        // NCS drop config false leaf 'auto-upgrade-model'
        // NCS drop config false leaf 'chassis-last-change-time'
        // NCS drop config false leaf 'cur-chassis-number'
        // NCS drop config false leaf 'max-chassis-number'
        // NCS drop config false leaf 'power-consumption'
        // NCS drop config false leaf 'split-resume'
        // NCS drop config false leaf 'switch-port-mode'
        // NCS drop config false leaf 'system-service-type'
        // NCS drop config false leaf 'usb-uart-status'
        // NCS drop config false leaf 'cur-system-mac-address'
        // NCS drop config false leaf 'board-channel-check-status'
        // NCS drop config false leaf 'energy-saving-pm-status'
      }
      // NCS drop config false container 'io-inspect-states'
      container io-inspect-attributes {
        description
          "List of IO inspect attributes.";
        list io-inspect-attribute {
          // NCS patched for predictable order
          ordered-by user;
          key "position index";
          description
            "Configure IO inspect attribute.";
          leaf position {
            type string;
            description
              "Position. The position is expressed in the format of slotID. For example, 1. Here 1 is an example. The value may vary with devices.";
          }
          leaf index {
            type string;
            description
              "Index.";
          }
          leaf default-states {
            type ncs_template_driver-default-states;
            // NCS drop mandatory statement
            description
              "Default status.";
          }
          leaf alarm-name {
            ext:operation-exclude "update|delete";
            type string;
            description
              "Alarm name.";
          }
        }
      }
      container temperatures {
        ext:operation-exclude "create";
        description
          "List of temperature information about a board.";
        list temperature {
          // NCS patched for predictable order
          ordered-by user;
          ext:generated-by "system";
          ext:operation-exclude "create";
          key "position i2c address channel";
          description
            "Configure temperature information about a board.";
          leaf position {
            type string;
            description
              "Location of a board. The position is expressed in the format of slotID. For example, 1. Here 1 is an example. The value may vary with devices.";
          }
          leaf i2c {
            type string;
            description
              "I2C bus number of a board.";
          }
          leaf address {
            type string;
            description
              "Sensor address of a board. The address is expressed in the format of a number. For example, 0. Here 0 is an example. The value may vary with devices.";
          }
          leaf channel {
            type string;
            description
              "ID of the sensor channel of a board.";
          }
          leaf minor {
            type string;
            description
              "Minor high temperature alarm threshold of a board. The relationships between temperature alarm threshold percentages are as follows: 1. The minor high-temperature alarm threshold percentage multiplying the default minor high-temperature alarm threshold must be less than the major high-temperature alarm threshold percentage multiplying the default major high-temperature alarm threshold. 2. The major high-temperature alarm threshold percentage multiplying the default major high-temperature alarm threshold must be less than the critical high-temperature alarm threshold percentage multiplying the default critical high-temperature alarm threshold.";
          }
          leaf major {
            type string;
            description
              "Major high temperature alarm threshold of a board. The relationships between temperature alarm threshold percentages are as follows: 1. The minor high-temperature alarm threshold percentage multiplying the default minor high-temperature alarm threshold must be less than the major high-temperature alarm threshold percentage multiplying the default major high-temperature alarm threshold. 2. The major high-temperature alarm threshold percentage multiplying the default major high-temperature alarm threshold must be less than the critical high-temperature alarm threshold percentage multiplying the default critical high-temperature alarm threshold.";
          }
          leaf fatal {
            type string;
            description
              "Fatal high temperature alarm threshold of a board. The relationships between temperature alarm threshold percentages are as follows: 1. The minor high-temperature alarm threshold percentage multiplying the default minor high-temperature alarm threshold must be less than the major high-temperature alarm threshold percentage multiplying the default major high-temperature alarm threshold. 2. The major high-temperature alarm threshold percentage multiplying the default major high-temperature alarm threshold must be less than the critical high-temperature alarm threshold percentage multiplying the default critical high-temperature alarm threshold.";
          }
          leaf fan-tmax {
            ext:dynamic-default;
            // NCS drop when statement
            type string;
            // NCS drop must statement
            description
              "Fan Speed Adjust High Threshold.[-50,127]for get operation,[-50,127]for edit operation. Each board has a different default fan-tmax value.";
          }
          leaf fan-tmin {
            ext:dynamic-default;
            // NCS drop when statement
            type string;
            // NCS drop must statement
            description
              "Fan Speed Adjust Low Threshold.[-50,127]for get operation,[-50,127]for edit operation. Each board has a different default fan-tmin value.";
          }
          // NCS drop config false leaf 'pcb-name'
          // NCS drop config false leaf 'entity-index'
          // NCS drop config false leaf state
          // NCS drop config false leaf 'current-temperature'
          // NCS drop config false leaf 'minor-alarm-threshold'
          // NCS drop config false leaf 'major-alarm-threshold'
          // NCS drop config false leaf 'fatal-alarm-threshold'
          // NCS drop config false leaf 'fan-tmax-states'
          // NCS drop config false leaf 'fan-tmin-states'
        }
      }
      container voltageinfos {
        ext:operation-exclude "create";
        description
          "List of voltage information about a board.";
        list voltageinfo {
          // NCS patched for predictable order
          ordered-by user;
          ext:generated-by "system";
          ext:operation-exclude "create";
          key "position i2c address channel";
          description
            "Configure voltage information about a board.";
          leaf position {
            type string;
            description
              "Location of a board. The position is expressed in the format of slotID. For example, 1. Here 1 is an example. The value may vary with devices.";
          }
          leaf i2c {
            type string;
            description
              "I2C bus number of a board.";
          }
          leaf address {
            type string;
            description
              "Sensor address of a board. The address is expressed in the format of a number. For example, 0. Here 0 is an example. The value may vary with devices.";
          }
          leaf channel {
            type string;
            description
              "ID of the sensor channel of a board.";
          }
          leaf major-voltage-threshold-low {
            type string;
            description
              "The percentage of the major voltage threshold below the default voltage. The relationships between voltage alarm threshold percentages are as follows: 1. The fatal undervoltage alarm threshold percentage multiplying the default fatal undervoltage alarm threshold must be less than the major undervoltage alarm threshold percentage multiplying the default major undervoltage alarm threshold. 2. The major undervoltage alarm threshold percentage multiplying the default major undervoltage alarm threshold must be less than the major overvoltage alarm threshold percentage multiplying the default major overvoltage alarm threshold. 3. The major overvoltage alarm threshold percentage multiplying the default major overvoltage alarm threshold must be less than the fatal overvoltage alarm threshold percentage multiplying the default fatal overvoltage alarm threshold.";
          }
          leaf major-voltage-threshold-high {
            type string;
            description
              "The percentage of the major voltage threshold above the default voltage. The relationships between voltage alarm threshold percentages are as follows: 1. The fatal undervoltage alarm threshold percentage multiplying the default fatal undervoltage alarm threshold must be less than the major undervoltage alarm threshold percentage multiplying the default major undervoltage alarm threshold. 2. The major undervoltage alarm threshold percentage multiplying the default major undervoltage alarm threshold must be less than the major overvoltage alarm threshold percentage multiplying the default major overvoltage alarm threshold. 3. The major overvoltage alarm threshold percentage multiplying the default major overvoltage alarm threshold must be less than the fatal overvoltage alarm threshold percentage multiplying the default fatal overvoltage alarm threshold.";
          }
          leaf fatal-voltage-threshold-low {
            type string;
            description
              "The percentage of the fatal voltage threshold below the default voltage. The relationships between voltage alarm threshold percentages are as follows: 1. The fatal undervoltage alarm threshold percentage multiplying the default fatal undervoltage alarm threshold must be less than the major undervoltage alarm threshold percentage multiplying the default major undervoltage alarm threshold. 2. The major undervoltage alarm threshold percentage multiplying the default major undervoltage alarm threshold must be less than the major overvoltage alarm threshold percentage multiplying the default major overvoltage alarm threshold. 3. The major overvoltage alarm threshold percentage multiplying the default major overvoltage alarm threshold must be less than the fatal overvoltage alarm threshold percentage multiplying the default fatal overvoltage alarm threshold.";
          }
          leaf fatal-voltage-threshold-high {
            type string;
            description
              "The percentage of the fatal voltage threshold above the default voltage. The relationships between voltage alarm threshold percentages are as follows: 1. The fatal undervoltage alarm threshold percentage multiplying the default fatal undervoltage alarm threshold must be less than the major undervoltage alarm threshold percentage multiplying the default major undervoltage alarm threshold. 2. The major undervoltage alarm threshold percentage multiplying the default major undervoltage alarm threshold must be less than the major overvoltage alarm threshold percentage multiplying the default major overvoltage alarm threshold. 3. The major overvoltage alarm threshold percentage multiplying the default major overvoltage alarm threshold must be less than the fatal overvoltage alarm threshold percentage multiplying the default fatal overvoltage alarm threshold.";
          }
          // NCS drop config false leaf 'pcb-name'
          // NCS drop config false leaf 'entity-index'
          // NCS drop config false leaf state
          // NCS drop config false leaf 'current-voltage'
          // NCS drop config false leaf 'required-voltage'
          // NCS drop config false leaf 'major-low-threshold'
          // NCS drop config false leaf 'low-threshold'
          // NCS drop config false leaf 'major-high-threshold'
          // NCS drop config false leaf 'high-threshold'
          // NCS drop config false leaf 'voltage-ratio'
        }
      }
      // NCS drop config false container 'electric-current-infos'
      // NCS drop config false container 'interface-match-check-states'
      // NCS drop config false container 'area-energyinfos'
      // NCS drop config false container 'board-powers'
      // NCS drop config false container 'electronic-labels'
      // NCS drop config false container mbusnodes
      // NCS drop config false container 'check-running-software-safes'
      // NCS drop config false container bootinfos
      // NCS drop config false container 'multi-chassis-attributes'
      // NCS drop config false container 'chassis-run-modes'
      // NCS drop config false container 'stratum-3-clocks'
      // NCS drop config false container 'system-sync-clocks'
      // NCS drop config false container 'rollback-attribute'
      // NCS drop config false container 'slave-defaults'
      // NCS drop config false container 'inner-links'
      // NCS drop config false container 'slot-statistics'
    }
  }
  augment "/ncs:devices/ncs:template/ncs:ned-id/ncs:config/devm:devm/devm:chassiss/devm:chassis" {
    description
      "Adds driver configuration to devm model.";
    container fan-attribute {
      // NCS drop must statement
      description
        "Configure the working mode and speed of the fan.";
      leaf workmode {
        type ncs_template_fan-workmode;
        // NCS drop default statement
        description
          "Fan working mode.";
      }
      leaf speed {
        ext:dynamic-default;
        type string;
        description
          "Fan speed which is a percentage of the highest speed and the range of value changes with the workmode and the hardtype of fan. The current range is determined by combining the minimum and maximum values of all cases.";
      }
    }
    container power-supply-attribute {
      description
        "Configure power supply information.";
      leaf pm-output-limit {
        type string;
        units "W";
        // NCS drop default statement
        description
          "PM output limited value. The value range of this parameter is dynamically determined by the rated power, used power, and number of PMs.";
      }
      leaf pm-input-voltage-110 {
        type ncs_template_driver-bool;
        ext:dynamic-default;
        description
          "Set pm input voltage 110V. The input voltage 110V mode of the PM can be set only when the power supply type is PHD-3000W or PAC-2700W or PAH-3000W.";
      }
      leaf power-supply-mode {
        type ncs_template_pwr-supply-mode-type;
        // NCS drop default statement
        description
          "Power supply mode.";
      }
      leaf power-supply-input {
        // NCS drop when statement
        type string;
        units "W";
        description
          "Power supply input power. The value range of this parameter is dynamically determined by the rated power, used power, and number of power supply partitions.";
      }
      leaf power-supply-temp {
        // NCS drop when statement
        type ncs_template_pwr-supply-temp-type;
        // NCS drop default statement
        description
          "Chassis Working Temperature. Some temperature modes are not supported on specific device models or in specific scenarios.";
      }
      // NCS drop config false leaf 'power-supply-limit'
      // NCS drop config false leaf 'power-supply-alarm-limit'
      // NCS drop config false leaf 'power-supply-assigned'
      // NCS drop config false leaf 'power-supply-assigned-utility'
      // NCS drop config false leaf 'power-supply-left'
      // NCS drop config false leaf 'power-supply-real'
      // NCS drop config false leaf 'power-supply-real-utility'
    }
    container dustproof-attribute {
      description
        "Configure the state of checking dustproof gate.";
      leaf dustproofcheck {
        type ncs_template_dustproof-gate-state;
        // NCS drop default statement
        description
          "The state of checking dustproof gate.";
      }
      leaf dustproof-delay-time {
        type string;
        units "min";
        // NCS drop default statement
        description
          "The alarm delay time of checking dustproof gate.";
      }
    }
    // NCS drop config false container 'chassis-id'
    // NCS drop config false container 'chassis-run-mode'
  }
  augment "/ncs:devices/ncs:device/ncs:live-status/devm:devm/devm:chassiss/devm:chassis" {
    description
      "Adds driver configuration to devm model.";
    container fan-attribute {
      tailf:ncs-device-type "netconf";
      tailf:display-when "not(../../../../../ncs:module) or ../../../../../ncs:module[ncs:name='huawei-driver'] or (../../../../../ncs:live-status-protocol[not(ncs:capability)]) or (../../../../../ncs:live-status-protocol/ncs:capability/ncs:module[.='huawei-driver'])";
      // NCS drop must statement
      description
        "Configure the working mode and speed of the fan.";
      leaf workmode {
        type live_ncs_fan-workmode;
        // NCS drop default statement
        description
          "Fan working mode.";
      }
      leaf speed {
        ext:dynamic-default;
        type uint32 {
          range "0..100";
        }
        description
          "Fan speed which is a percentage of the highest speed and the range of value changes with the workmode and the hardtype of fan. The current range is determined by combining the minimum and maximum values of all cases.";
      }
    }
    container power-supply-attribute {
      tailf:ncs-device-type "netconf";
      tailf:display-when "not(../../../../../ncs:module) or ../../../../../ncs:module[ncs:name='huawei-driver'] or (../../../../../ncs:live-status-protocol[not(ncs:capability)]) or (../../../../../ncs:live-status-protocol/ncs:capability/ncs:module[.='huawei-driver'])";
      description
        "Configure power supply information.";
      leaf pm-output-limit {
        type uint32 {
          range "0..4294967295";
        }
        units "W";
        // NCS drop default statement
        description
          "PM output limited value. The value range of this parameter is dynamically determined by the rated power, used power, and number of PMs.";
      }
      leaf pm-input-voltage-110 {
        type live_ncs_driver-bool;
        ext:dynamic-default;
        description
          "Set pm input voltage 110V. The input voltage 110V mode of the PM can be set only when the power supply type is PHD-3000W or PAC-2700W or PAH-3000W.";
      }
      leaf power-supply-mode {
        type live_ncs_pwr-supply-mode-type;
        // NCS drop default statement
        description
          "Power supply mode.";
      }
      leaf power-supply-input {
        // NCS drop when statement
        type uint32 {
          range "0..11200";
        }
        units "W";
        description
          "Power supply input power. The value range of this parameter is dynamically determined by the rated power, used power, and number of power supply partitions.";
      }
      leaf power-supply-temp {
        // NCS drop when statement
        type live_ncs_pwr-supply-temp-type;
        // NCS drop default statement
        description
          "Chassis Working Temperature. Some temperature modes are not supported on specific device models or in specific scenarios.";
      }
      leaf power-supply-limit {
        type uint32 {
          range "1..4294967295";
        }
        units "W";
        description
          "Limit Power.";
      }
      leaf power-supply-alarm-limit {
        type uint32 {
          range "1..4294967295";
        }
        units "W";
        description
          "Alarm Limit Power.";
      }
      leaf power-supply-assigned {
        type uint32;
        units "W";
        // NCS drop default statement
        description
          "Assigned Power.";
      }
      leaf power-supply-assigned-utility {
        type string {
          length "1..255";
        }
        // NCS drop default statement
        description
          "Assigned Power Utility.";
      }
      leaf power-supply-left {
        type int32;
        units "W";
        // NCS drop default statement
        description
          "Left Power.";
      }
      leaf power-supply-real {
        type uint32;
        units "W";
        description
          "Real Power.";
      }
      leaf power-supply-real-utility {
        type string {
          length "1..255";
        }
        // NCS drop default statement
        description
          "Real Power Utility.";
      }
    }
    container dustproof-attribute {
      tailf:ncs-device-type "netconf";
      tailf:display-when "not(../../../../../ncs:module) or ../../../../../ncs:module[ncs:name='huawei-driver'] or (../../../../../ncs:live-status-protocol[not(ncs:capability)]) or (../../../../../ncs:live-status-protocol/ncs:capability/ncs:module[.='huawei-driver'])";
      description
        "Configure the state of checking dustproof gate.";
      leaf dustproofcheck {
        type live_ncs_dustproof-gate-state;
        // NCS drop default statement
        description
          "The state of checking dustproof gate.";
      }
      leaf dustproof-delay-time {
        type uint32 {
          range "0..480";
        }
        units "min";
        // NCS drop default statement
        description
          "The alarm delay time of checking dustproof gate.";
      }
    }
    container chassis-id {
      tailf:ncs-device-type "netconf";
      tailf:display-when "not(../../../../../ncs:module) or ../../../../../ncs:module[ncs:name='huawei-driver'] or (../../../../../ncs:live-status-protocol[not(ncs:capability)]) or (../../../../../ncs:live-status-protocol/ncs:capability/ncs:module[.='huawei-driver'])";
      description
        "Statistics of chassis ID.";
      leaf current-id {
        type uint32 {
          range "1..8";
        }
        description
          "Current chassis ID.";
      }
      leaf next-id {
        type uint32 {
          range "1..8";
        }
        description
          "Chassis ID to be used at the next startup.";
      }
    }
    container chassis-run-mode {
      tailf:ncs-device-type "netconf";
      tailf:display-when "not(../../../../../ncs:module) or ../../../../../ncs:module[ncs:name='huawei-driver'] or (../../../../../ncs:live-status-protocol[not(ncs:capability)]) or (../../../../../ncs:live-status-protocol/ncs:capability/ncs:module[.='huawei-driver'])";
      description
        "Statistics of chassis run mode.";
      leaf current-run-mode {
        type live_ncs_driver-run-mode-type;
        description
          "Current chassis operating mode.";
      }
      leaf next-run-mode {
        type live_ncs_driver-run-mode-type;
        description
          "Chassis operating mode to be used at the next startup.";
      }
    }
  }
  augment "/ncs:devices/ncs:device/ncs:config/devm:devm/devm:chassiss/devm:chassis" {
    description
      "Adds driver configuration to devm model.";
    container fan-attribute {
      tailf:ncs-device-type "netconf";
      tailf:display-when "not(../../../../../ncs:module) or ../../../../../ncs:module[ncs:name='huawei-driver']";
      must "((./workmode='manual' or ./workmode='minimum-percent') and ./speed) or ((./workmode!='manual' and ./workmode!='minimum-percent') and not(./speed))" {
        tailf:xpath-root 3;
      }
      description
        "Configure the working mode and speed of the fan.";
      leaf workmode {
        type fan-workmode;
        default "auto";
        description
          "Fan working mode.";
      }
      leaf speed {
        ext:dynamic-default;
        type uint32 {
          range "0..100";
        }
        description
          "Fan speed which is a percentage of the highest speed and the range of value changes with the workmode and the hardtype of fan. The current range is determined by combining the minimum and maximum values of all cases.";
      }
    }
    container power-supply-attribute {
      tailf:ncs-device-type "netconf";
      tailf:display-when "not(../../../../../ncs:module) or ../../../../../ncs:module[ncs:name='huawei-driver']";
      description
        "Configure power supply information.";
      leaf pm-output-limit {
        type uint32 {
          range "0..4294967295";
        }
        units "W";
        default "0";
        description
          "PM output limited value. The value range of this parameter is dynamically determined by the rated power, used power, and number of PMs.";
      }
      leaf pm-input-voltage-110 {
        type driver-bool;
        ext:dynamic-default;
        description
          "Set pm input voltage 110V. The input voltage 110V mode of the PM can be set only when the power supply type is PHD-3000W or PAC-2700W or PAH-3000W.";
      }
      leaf power-supply-mode {
        type pwr-supply-mode-type;
        default "standard";
        description
          "Power supply mode.";
      }
      leaf power-supply-input {
        when "../power-supply-mode='assign'" {
          tailf:xpath-root 3;
        }
        type uint32 {
          range "0..11200";
        }
        units "W";
        description
          "Power supply input power. The value range of this parameter is dynamically determined by the rated power, used power, and number of power supply partitions.";
      }
      leaf power-supply-temp {
        when "../power-supply-mode='standard'" {
          tailf:xpath-root 3;
        }
        type pwr-supply-temp-type;
        default "temphigh";
        description
          "Chassis Working Temperature. Some temperature modes are not supported on specific device models or in specific scenarios.";
      }
      // NCS drop config false leaf 'power-supply-limit'
      // NCS drop config false leaf 'power-supply-alarm-limit'
      // NCS drop config false leaf 'power-supply-assigned'
      // NCS drop config false leaf 'power-supply-assigned-utility'
      // NCS drop config false leaf 'power-supply-left'
      // NCS drop config false leaf 'power-supply-real'
      // NCS drop config false leaf 'power-supply-real-utility'
    }
    container dustproof-attribute {
      tailf:ncs-device-type "netconf";
      tailf:display-when "not(../../../../../ncs:module) or ../../../../../ncs:module[ncs:name='huawei-driver']";
      description
        "Configure the state of checking dustproof gate.";
      leaf dustproofcheck {
        type dustproof-gate-state;
        default "enable";
        description
          "The state of checking dustproof gate.";
      }
      leaf dustproof-delay-time {
        type uint32 {
          range "0..480";
        }
        units "min";
        default "30";
        description
          "The alarm delay time of checking dustproof gate.";
      }
    }
    // NCS drop config false container 'chassis-id'
    // NCS drop config false container 'chassis-run-mode'
  }
  augment "/ncs:devices/ncs:template/ncs:ned-id/ncs:config/devm:devm/devm:lpu-boards/devm:lpu-board" {
    description
      "Adds driver configuration to devm model.";
    // NCS drop config false container driver
  }
  augment "/ncs:devices/ncs:device/ncs:live-status/devm:devm/devm:lpu-boards/devm:lpu-board" {
    description
      "Adds driver configuration to devm model.";
    container driver {
      tailf:ncs-device-type "netconf";
      tailf:display-when "not(../../../../../ncs:module) or ../../../../../ncs:module[ncs:name='huawei-driver'] or (../../../../../ncs:live-status-protocol[not(ncs:capability)]) or (../../../../../ncs:live-status-protocol/ncs:capability/ncs:module[.='huawei-driver'])";
      description
        "Statistics of driver apply.";
      container l3-clocks {
        description
          "List of l3 clocks.";
        list l3-clock {
          key "clock-id";
          description
            "Statistics of l3 clock.";
          leaf clock-id {
            type string {
              length "1..255";
            }
            description
              "L3 clock ID. The clock-id is expressed in the format of slotID. For example, 1. Here 1 is an example. The value may vary with devices.";
          }
          leaf l3-clock-state {
            type live_ncs_driver-clock-status;
            description
              "L3 clock state.";
          }
        }
      }
    }
  }
  augment "/ncs:devices/ncs:device/ncs:config/devm:devm/devm:lpu-boards/devm:lpu-board" {
    description
      "Adds driver configuration to devm model.";
    // NCS drop config false container driver
  }
  augment "/ncs:devices/ncs:template/ncs:ned-id/ncs:config/devm:devm" {
    description
      "Adds driver configuration to devm model.";
    container driver {
      description
        "Configure driver apply.";
      container cmus {
        ext:operation-exclude "create|delete";
        description
          "List of CMUs.";
        list cmu {
          // NCS patched for predictable order
          ordered-by user;
          ext:generated-by "system";
          ext:operation-exclude "create|delete";
          key "position";
          description
            "Configure CMU.";
          leaf position {
            type string;
            description
              "CMU position. The position is expressed in the format of slotID. For example, 1. Here 1 is an example. The value may vary with devices.";
          }
          // NCS drop config false leaf 'entity-index'
          // NCS drop config false leaf 'board-type'
          // NCS drop config false leaf 'sdram-size'
          // NCS drop config false leaf 'flash-size'
          // NCS drop config false leaf 'up-time'
          // NCS drop config false leaf role
          container cmu-switchs {
            description
              "List of CMU Switch.";
            list cmu-switch {
              // NCS patched for predictable order
              ordered-by user;
              key "switch-id";
              description
                "Configure CMU Switch.";
              leaf switch-id {
                type string;
                description
                  "Switch ID.";
              }
              leaf switch-name {
                type string;
                // NCS drop default statement
                description
                  "Switch Name.";
              }
              leaf alarm-mode {
                type ncs_template_driver-cmu-alarm-mode;
                // NCS drop default statement
                description
                  "Alarm Mode.";
              }
              leaf switch-fog {
                type ncs_template_driver-cmu-switch-fog;
                // NCS drop default statement
                description
                  "Object.";
              }
            }
          }
          container cmu-relays {
            description
              "List of CMU Relays.";
            list cmu-relay {
              // NCS patched for predictable order
              ordered-by user;
              key "relay-id";
              description
                "Configure CMU Relay.";
              leaf relay-id {
                type string;
                description
                  "Ralay ID.";
              }
              leaf relay-name {
                type string;
                // NCS drop default statement
                description
                  "Relay Name.";
              }
              leaf relay-alarm-mode {
                type ncs_template_driver-cmu-alarm-mode;
                // NCS drop default statement
                description
                  "Alarm Mode.";
              }
            }
          }
          container cmu-analogs {
            description
              "List of CMU Analogs.";
            list cmu-analog {
              // NCS patched for predictable order
              ordered-by user;
              key "analog-id";
              description
                "Configure CMU Analog.";
              leaf analog-id {
                type string;
                description
                  "CMU Analog ID.";
              }
              leaf analog-name {
                type string;
                // NCS drop default statement
                description
                  "CMU Analog Name.";
              }
              leaf analog-type {
                type ncs_template_driver-analog-type;
                // NCS drop default statement
                description
                  "Specify cmu analog sensor type.";
              }
              leaf analog-object {
                type ncs_template_driver-analog-object-type;
                // NCS drop default statement
                description
                  "Specify object monitored by this cmu analog sensor.";
              }
              leaf work-low {
                type string;
                // NCS drop default statement
                description
                  "Specify cmu analog workLow.";
              }
              leaf work-high {
                type string;
                // NCS drop default statement
                description
                  "Specify cmu analog workHigh.";
              }
              leaf wanted {
                type string;
                // NCS drop default statement
                description
                  "Specify cmu analog cmuWanted.";
              }
              leaf alarm-low {
                type string;
                // NCS drop default statement
                description
                  "Specify cmu analog alrmLow.";
              }
              leaf alarm-high {
                type string;
                // NCS drop default statement
                description
                  "Specify cmu analog alarmHigh.";
              }
            }
          }
          container cmu-alarms {
            description
              "List of CMU alarms.";
            list cmu-alarm {
              // NCS patched for predictable order
              ordered-by user;
              key "alarm-id";
              description
                "Configure CMU alarm.";
              leaf alarm-id {
                type string;
                description
                  "CMU alarm ID.";
              }
              leaf alarm-level {
                type ncs_template_driver-cmu-alarm-mode;
                // NCS drop default statement
                description
                  "Alarm Level.";
              }
            }
          }
        }
      }
      container pms {
        ext:operation-exclude "create";
        description
          "List of PM.";
        list pm {
          // NCS patched for predictable order
          ordered-by user;
          ext:generated-by "system";
          ext:operation-exclude "create";
          key "position serial-number";
          description
            "Configure PM.";
          leaf position {
            type string;
            description
              "PM position. The position is expressed in the format of slotID/pmID. For example, 1/1. Here 1/1 is an example. The value may vary with devices.";
          }
          leaf serial-number {
            type string;
            description
              "Serial Number.";
          }
          leaf single-input {
            type ncs_template_driver-single-input-type;
            // NCS drop default statement
            description
              "Set Single Input. The power supply management mode can be switched only when DC power supply is used.";
          }
          // NCS drop config false leaf 'board-type'
          // NCS drop config false leaf 'entity-index'
          // NCS drop config false leaf 'monitor-cable-state'
          // NCS drop config false leaf 'input-voltage-value'
          // NCS drop config false leaf 'input-electrical-value'
          // NCS drop config false leaf 'input-power-value'
          // NCS drop config false leaf 'output-voltage-value'
          // NCS drop config false leaf 'output-electrical-value'
          // NCS drop config false leaf 'output-power-value'
          // NCS drop config false leaf 'pm-area'
          // NCS drop config false leaf 'pm-status'
        }
      }
      // NCS drop config false container ccus
      // NCS drop config false container dacss
      // NCS drop config false container fans
      // NCS drop config false container icus
      // NCS drop config false container pmus
      // NCS drop config false container 'power-supplys'
      // NCS drop config false container dmus
      // NCS drop config false container pdus
      // NCS drop config false container vsus
    }
  }
  augment "/ncs:devices/ncs:device/ncs:live-status/devm:devm" {
    description
      "Adds driver configuration to devm model.";
    container driver {
      tailf:ncs-device-type "netconf";
      tailf:display-when "not(../../../ncs:module) or ../../../ncs:module[ncs:name='huawei-driver'] or (../../../ncs:live-status-protocol[not(ncs:capability)]) or (../../../ncs:live-status-protocol/ncs:capability/ncs:module[.='huawei-driver'])";
      description
        "Configure driver apply.";
      container cmus {
        ext:operation-exclude "create|delete";
        description
          "List of CMUs.";
        list cmu {
          ext:generated-by "system";
          ext:operation-exclude "create|delete";
          key "position";
          description
            "Configure CMU.";
          leaf position {
            type string {
              length "1..32";
            }
            description
              "CMU position. The position is expressed in the format of slotID. For example, 1. Here 1 is an example. The value may vary with devices.";
          }
          leaf entity-index {
            type uint32;
            description
              "CMU supply index.";
          }
          leaf board-type {
            type hardware-type:live_ncs_hardware-hard-type;
            description
              "Type of a CMU board.";
          }
          leaf sdram-size {
            type uint32;
            units "MB";
            description
              "SDRAM size.";
          }
          leaf flash-size {
            type uint32;
            units "MB";
            description
              "Flash size.";
          }
          leaf up-time {
            type pub-type:live_ncs_time-tick;
            description
              "Up time of an CMU, the unit is timetick.";
          }
          leaf role {
            type live_ncs_driver-cmu-role;
            description
              "CMU role.";
          }
          container cmu-switchs {
            description
              "List of CMU Switch.";
            list cmu-switch {
              key "switch-id";
              description
                "Configure CMU Switch.";
              leaf switch-id {
                type uint32 {
                  range "0..6";
                }
                description
                  "Switch ID.";
              }
              leaf switch-name {
                type string {
                  length "1..24";
                }
                // NCS drop default statement
                description
                  "Switch Name.";
              }
              leaf alarm-mode {
                type live_ncs_driver-cmu-alarm-mode;
                // NCS drop default statement
                description
                  "Alarm Mode.";
              }
              leaf switch-fog {
                type live_ncs_driver-cmu-switch-fog;
                // NCS drop default statement
                description
                  "Object.";
              }
            }
          }
          container cmu-relays {
            description
              "List of CMU Relays.";
            list cmu-relay {
              key "relay-id";
              description
                "Configure CMU Relay.";
              leaf relay-id {
                type uint32 {
                  range "0..1";
                }
                description
                  "Ralay ID.";
              }
              leaf relay-name {
                type string {
                  length "1..24";
                }
                // NCS drop default statement
                description
                  "Relay Name.";
              }
              leaf relay-alarm-mode {
                type live_ncs_driver-cmu-alarm-mode;
                // NCS drop default statement
                description
                  "Alarm Mode.";
              }
            }
          }
          container cmu-analogs {
            description
              "List of CMU Analogs.";
            list cmu-analog {
              key "analog-id";
              description
                "Configure CMU Analog.";
              leaf analog-id {
                type uint32 {
                  range "0..1";
                }
                description
                  "CMU Analog ID.";
              }
              leaf analog-name {
                type string {
                  length "1..24";
                }
                // NCS drop default statement
                description
                  "CMU Analog Name.";
              }
              leaf analog-type {
                type live_ncs_driver-analog-type;
                // NCS drop default statement
                description
                  "Specify cmu analog sensor type.";
              }
              leaf analog-object {
                type live_ncs_driver-analog-object-type;
                // NCS drop default statement
                description
                  "Specify object monitored by this cmu analog sensor.";
              }
              leaf work-low {
                type int32 {
                  range "0..10";
                }
                // NCS drop default statement
                description
                  "Specify cmu analog workLow.";
              }
              leaf work-high {
                type int32 {
                  range "0..10";
                }
                // NCS drop default statement
                description
                  "Specify cmu analog workHigh.";
              }
              leaf wanted {
                type int32 {
                  range "0..10";
                }
                // NCS drop default statement
                description
                  "Specify cmu analog cmuWanted.";
              }
              leaf alarm-low {
                type int32 {
                  range "0..10";
                }
                // NCS drop default statement
                description
                  "Specify cmu analog alrmLow.";
              }
              leaf alarm-high {
                type int32 {
                  range "0..10";
                }
                // NCS drop default statement
                description
                  "Specify cmu analog alarmHigh.";
              }
            }
          }
          container cmu-alarms {
            description
              "List of CMU alarms.";
            list cmu-alarm {
              key "alarm-id";
              description
                "Configure CMU alarm.";
              leaf alarm-id {
                type uint32 {
                  range "0..1";
                }
                description
                  "CMU alarm ID.";
              }
              leaf alarm-level {
                type live_ncs_driver-cmu-alarm-mode;
                // NCS drop default statement
                description
                  "Alarm Level.";
              }
            }
          }
        }
      }
      container pms {
        ext:operation-exclude "create";
        description
          "List of PM.";
        list pm {
          ext:generated-by "system";
          ext:operation-exclude "create";
          key "position serial-number";
          description
            "Configure PM.";
          leaf position {
            type string {
              length "1..32";
            }
            description
              "PM position. The position is expressed in the format of slotID/pmID. For example, 1/1. Here 1/1 is an example. The value may vary with devices.";
          }
          leaf serial-number {
            type uint32;
            description
              "Serial Number.";
          }
          leaf single-input {
            type live_ncs_driver-single-input-type;
            // NCS drop default statement
            description
              "Set Single Input. The power supply management mode can be switched only when DC power supply is used.";
          }
          leaf board-type {
            type hardware-type:live_ncs_hardware-board-type;
            description
              "Type of a PM board.";
          }
          leaf entity-index {
            type uint32;
            description
              "PM index.";
          }
          leaf monitor-cable-state {
            type live_ncs_driver-cable-state;
            description
              "State of a PM monitor cable.";
          }
          leaf input-voltage-value {
            type string {
              length "1..255";
            }
            description
              "Input voltage value.";
          }
          leaf input-electrical-value {
            type string {
              length "1..255";
            }
            description
              "Input electrical value.";
          }
          leaf input-power-value {
            type string {
              length "1..255";
            }
            description
              "Input power.";
          }
          leaf output-voltage-value {
            type string {
              length "1..255";
            }
            description
              "Output voltage value.";
          }
          leaf output-electrical-value {
            type string {
              length "1..255";
            }
            description
              "Output electrical value.";
          }
          leaf output-power-value {
            type string {
              length "1..255";
            }
            description
              "Output power.";
          }
          leaf pm-area {
            type string {
              length "1..16";
            }
            description
              "PM area.";
          }
          leaf pm-status {
            type live_ncs_driver-pm-status;
            description
              "PM Status Information.";
          }
        }
      }
      container ccus {
        description
          "Statistics of CCU information.";
        container ccu {
          presence "ccu";
          description
            "Statistics of CCU information.";
          leaf software-version {
            type string {
              length "1..32";
            }
            description
              "CCU version.";
          }
        }
      }
      container dacss {
        description
          "List of DACS.";
        list dacs {
          key "position serial-number";
          description
            "Statistics of DACS.";
          leaf position {
            type string {
              length "1..32";
            }
            description
              "DACS position. The position is expressed in the format of slotID. For example, PDU1. Here PDU1 is an example. The value may vary with devices.";
          }
          leaf serial-number {
            type uint32;
            description
              "Serial Number.";
          }
          leaf board-type {
            type hardware-type:live_ncs_hardware-board-type;
            description
              "Type of a DACS board.";
          }
          leaf dacs-area {
            type string {
              length "1..16";
            }
            description
              "DACS area.";
          }
          leaf entity-index {
            type uint32;
            description
              "DACS index.";
          }
          leaf status {
            type live_ncs_driver-dacs-status;
            description
              "State of a DACS monitor.";
          }
          leaf insource-plane {
            type string {
              length "1..255";
            }
            description
              "InSource plane.";
          }
          leaf insource-plane-a {
            type string {
              length "1..255";
            }
            description
              "InSource A plane value (A).";
          }
          leaf insource-plane-b {
            type string {
              length "1..255";
            }
            description
              "InSource B plane value (B).";
          }
          leaf output-voltage-value {
            type string {
              length "1..255";
            }
            description
              "Output voltage value (V).";
          }
          leaf output-electrical-value {
            type string {
              length "1..255";
            }
            description
              "Output electrical value (A).";
          }
          leaf output-status {
            type string {
              length "1..255";
            }
            description
              "Output Status.";
          }
        }
      }
      container fans {
        description
          "List of information about all fans on a device.";
        list fan {
          key "position";
          description
            "Statistics of fan information on a device.";
          leaf position {
            type string {
              length "1..50";
            }
            description
              "Position of the fan board. The position is expressed in the format of slotID. For example, 1. Here 1 is an example. The value may vary with devices.";
          }
          leaf entity-index {
            type uint32;
            description
              "Index of the fan board.";
          }
          leaf board-type {
            type hardware-type:live_ncs_hardware-board-type;
            description
              "Type of a fan board.";
          }
          leaf work-mode {
            type live_ncs_fan-workmode;
            // NCS drop default statement
            description
              "Working mode of a fan.";
          }
          leaf speed {
            type uint32 {
              range "0..100";
            }
            description
              "Fan speed, which is the highest percentage of the fan speed.";
          }
          leaf fan-rate {
            type uint32;
            units "r/min";
            description
              "Rated rotational speed of the fan.";
          }
          leaf monitor-cable-state {
            type live_ncs_driver-cable-state;
            description
              "Monitors the fan status.";
          }
          leaf register {
            type live_ncs_driver-bool;
            description
              "Whether the fan is registered.";
          }
          leaf present {
            type live_ncs_driver-bool;
            description
              "Check whether the fan is in position.";
          }
          leaf fan-number {
            type uint32;
            description
              "Number of fans.";
          }
          leaf global-speed {
            type string {
              length "1..128";
            }
            // NCS drop default statement
            description
              "Fan speed percentage, which is the percentage of the maximum rate.";
          }
        }
      }
      container icus {
        description
          "List of ICUs.";
        list icu {
          key "position";
          description
            "Statistics of ICU board.";
          leaf position {
            type string {
              length "1..32";
            }
            description
              "ICU position. The position is expressed in the format of slotID. For example, 1. Here 1 is an example. The value may vary with devices.";
          }
          leaf entity-index {
            type uint32;
            description
              "ICU index.";
          }
          leaf board-type {
            type hardware-type:live_ncs_hardware-board-type;
            // NCS drop mandatory statement
            description
              "ICU type.";
          }
          leaf sdram-size {
            type uint32;
            units "MB";
            description
              "SDRAM size.";
          }
          leaf flash-size {
            type uint32;
            units "MB";
            description
              "Flash size.";
          }
          leaf up-time {
            type pub-type:live_ncs_time-tick;
            description
              "Up time of an ICU, the unit is timetick.";
          }
        }
      }
      container pmus {
        description
          "List of PMU.";
        list pmu {
          key "position";
          description
            "Statistics of PMU.";
          leaf position {
            type string {
              length "1..32";
            }
            description
              "PMU position. The position is expressed in the format of slotID. For example, 1. Here 1 is an example. The value may vary with devices.";
          }
          leaf entity-index {
            type uint32;
            description
              "PMU index.";
          }
          leaf board-type {
            type hardware-type:live_ncs_hardware-board-type;
            description
              "Type of a PMU board.";
          }
          leaf present {
            type string {
              length "1..16";
            }
            description
              "Present.";
          }
          leaf ha-status {
            type string {
              length "1..16";
            }
            description
              "HaStatus.";
          }
          leaf register {
            type string {
              length "1..16";
            }
            description
              "Register.";
          }
          leaf work {
            type string {
              length "1..16";
            }
            description
              "Work.";
          }
        }
      }
      container power-supplys {
        description
          "List of information about all power supplies on a device.";
        list power-supply {
          key "position";
          description
            "Statistics of power supply information on a device.";
          leaf position {
            type string {
              length "1..50";
            }
            description
              "Position of the power supply. The position is expressed in the format of slotID. For example, 1. Here 1 is an example. The value may vary with devices.";
          }
          leaf entity-index {
            type uint32;
            description
              "Index of the power supply.";
          }
          leaf board-type {
            type hardware-type:live_ncs_hardware-board-type;
            description
              "Hardware type of the power supply.";
          }
          leaf work-mode {
            type live_ncs_driver-power-work-mode;
            description
              "Working mode of a power supply board.";
          }
          leaf monitor-cable-state {
            type live_ncs_driver-cable-state;
            description
              "Status of the power monitoring point.";
          }
          leaf power-state {
            type string {
              length "1..255";
            }
            description
              "Working mode of the power supply.";
          }
          leaf abnormal-number {
            type uint32;
            description
              "Number of faulty power modules on a device.";
          }
          leaf normal-number {
            type uint32;
            description
              "Number of normal power modules on a device.";
          }
          container power-environments {
            description
              "List of environment information about the power supply on a device.";
            list power-environment {
              key "pem-index";
              description
                "Statistics of environment information about the power supply on a device.";
              leaf pem-index {
                type uint32;
                description
                  "Index of the power supply.";
              }
              leaf voltage-value {
                type string {
                  length "1..255";
                }
                units "V";
                description
                  "Voltage of an existing device.";
              }
              leaf electrical-value {
                type string {
                  length "1..255";
                }
                units "A";
                description
                  "Current value of an existing device.";
              }
              leaf temperature-value {
                type string {
                  length "1..255";
                }
                description
                  "Temperature of an existing device.";
              }
              leaf power-value {
                type string {
                  length "1..255";
                }
                units "W";
                description
                  "Query the current power.";
              }
              leaf out-voltage-value {
                type string {
                  length "1..255";
                }
                units "V";
                description
                  "Current output voltage value of an existing device.";
              }
              leaf out-electrical-value {
                type string {
                  length "1..255";
                }
                units "A";
                description
                  "Current output electrical value of an existing device.";
              }
              leaf out-power-value {
                type string {
                  length "1..255";
                }
                units "W";
                description
                  "Current output power value of an existing device.";
              }
            }
          }
        }
      }
      container dmus {
        description
          "List of DMU.";
        list dmu {
          key "position";
          description
            "Statistics of DMU.";
          leaf position {
            type string {
              length "1..32";
            }
            description
              "DMU position. The position is expressed in the format of slotID. For example, PDU1. Here PDU1 is an example. The value may vary with devices.";
          }
          leaf entity-index {
            type uint32;
            description
              "DMU index.";
          }
          leaf board-type {
            type hardware-type:live_ncs_hardware-board-type;
            description
              "Type of a DMU board.";
          }
          leaf present {
            type string {
              length "1..16";
            }
            description
              "Present.";
          }
          leaf register {
            type string {
              length "1..16";
            }
            description
              "Register.";
          }
          leaf work {
            type string {
              length "1..16";
            }
            description
              "Work.";
          }
        }
      }
      container pdus {
        description
          "List of PDU.";
        list pdu {
          key "position";
          description
            "Statistics of PDU.";
          leaf position {
            type string {
              length "1..32";
            }
            description
              "PDU position. The position is expressed in the format of slotID. For example, PDU1. Here PDU1 is an example. The value may vary with devices.";
          }
          leaf entity-index {
            type uint32;
            description
              "Index.";
          }
          leaf board-type {
            type hardware-type:live_ncs_hardware-board-type;
            description
              "Type of a pdu board.";
          }
          leaf work-mode {
            type live_ncs_driver-power-work-mode;
            description
              "Working mode of a pdu board.";
          }
          leaf power-state {
            type string {
              length "1..255";
            }
            description
              "Power Running State.";
          }
          leaf abnormal-number {
            type string {
              length "1..255";
            }
            description
              "Abnormal PowerModule Number.";
          }
          leaf normal-number {
            type string {
              length "1..255";
            }
            description
              "Normal PowerModule Number.";
          }
        }
      }
      container vsus {
        description
          "List of VSU.";
        list vsu {
          key "position";
          description
            "Statistics of VSU.";
          leaf position {
            type string {
              length "1..32";
            }
            description
              "VSU position. The position is expressed in the format of slotID. For example, 1. Here 1 is an example. The value may vary with devices.";
          }
          leaf service-type {
            type live_ncs_driver-vsu-service-type;
            description
              "Service type of a VSU board.";
          }
        }
      }
    }
  }
  augment "/ncs:devices/ncs:device/ncs:config/devm:devm" {
    description
      "Adds driver configuration to devm model.";
    container driver {
      tailf:ncs-device-type "netconf";
      tailf:display-when "not(../../../ncs:module) or ../../../ncs:module[ncs:name='huawei-driver']";
      description
        "Configure driver apply.";
      container cmus {
        ext:operation-exclude "create|delete";
        description
          "List of CMUs.";
        list cmu {
          ext:generated-by "system";
          ext:operation-exclude "create|delete";
          key "position";
          description
            "Configure CMU.";
          leaf position {
            type string {
              length "1..32";
            }
            description
              "CMU position. The position is expressed in the format of slotID. For example, 1. Here 1 is an example. The value may vary with devices.";
          }
          // NCS drop config false leaf 'entity-index'
          // NCS drop config false leaf 'board-type'
          // NCS drop config false leaf 'sdram-size'
          // NCS drop config false leaf 'flash-size'
          // NCS drop config false leaf 'up-time'
          // NCS drop config false leaf role
          container cmu-switchs {
            description
              "List of CMU Switch.";
            list cmu-switch {
              key "switch-id";
              description
                "Configure CMU Switch.";
              leaf switch-id {
                type uint32 {
                  range "0..6";
                }
                description
                  "Switch ID.";
              }
              leaf switch-name {
                type string {
                  length "1..24";
                }
                default "unknown";
                description
                  "Switch Name.";
              }
              leaf alarm-mode {
                type driver-cmu-alarm-mode;
                default "undo";
                description
                  "Alarm Mode.";
              }
              leaf switch-fog {
                type driver-cmu-switch-fog;
                default "unknown";
                description
                  "Object.";
              }
            }
          }
          container cmu-relays {
            description
              "List of CMU Relays.";
            list cmu-relay {
              key "relay-id";
              description
                "Configure CMU Relay.";
              leaf relay-id {
                type uint32 {
                  range "0..1";
                }
                description
                  "Ralay ID.";
              }
              leaf relay-name {
                type string {
                  length "1..24";
                }
                default "unknown";
                description
                  "Relay Name.";
              }
              leaf relay-alarm-mode {
                type driver-cmu-alarm-mode;
                default "undo";
                description
                  "Alarm Mode.";
              }
            }
          }
          container cmu-analogs {
            description
              "List of CMU Analogs.";
            list cmu-analog {
              key "analog-id";
              description
                "Configure CMU Analog.";
              leaf analog-id {
                type uint32 {
                  range "0..1";
                }
                description
                  "CMU Analog ID.";
              }
              leaf analog-name {
                type string {
                  length "1..24";
                }
                default "unknown";
                description
                  "CMU Analog Name.";
              }
              leaf analog-type {
                type driver-analog-type;
                default "unknown";
                description
                  "Specify cmu analog sensor type.";
              }
              leaf analog-object {
                type driver-analog-object-type;
                default "unknown";
                description
                  "Specify object monitored by this cmu analog sensor.";
              }
              leaf work-low {
                type int32 {
                  range "0..10";
                }
                default "0";
                description
                  "Specify cmu analog workLow.";
              }
              leaf work-high {
                type int32 {
                  range "0..10";
                }
                default "0";
                description
                  "Specify cmu analog workHigh.";
              }
              leaf wanted {
                type int32 {
                  range "0..10";
                }
                default "0";
                description
                  "Specify cmu analog cmuWanted.";
              }
              leaf alarm-low {
                type int32 {
                  range "0..10";
                }
                default "0";
                description
                  "Specify cmu analog alrmLow.";
              }
              leaf alarm-high {
                type int32 {
                  range "0..10";
                }
                default "0";
                description
                  "Specify cmu analog alarmHigh.";
              }
            }
          }
          container cmu-alarms {
            description
              "List of CMU alarms.";
            list cmu-alarm {
              key "alarm-id";
              description
                "Configure CMU alarm.";
              leaf alarm-id {
                type uint32 {
                  range "0..1";
                }
                description
                  "CMU alarm ID.";
              }
              leaf alarm-level {
                type driver-cmu-alarm-mode;
                default "undo";
                description
                  "Alarm Level.";
              }
            }
          }
        }
      }
      container pms {
        ext:operation-exclude "create";
        description
          "List of PM.";
        list pm {
          ext:generated-by "system";
          ext:operation-exclude "create";
          key "position serial-number";
          description
            "Configure PM.";
          leaf position {
            type string {
              length "1..32";
            }
            description
              "PM position. The position is expressed in the format of slotID/pmID. For example, 1/1. Here 1/1 is an example. The value may vary with devices.";
          }
          leaf serial-number {
            type uint32;
            description
              "Serial Number.";
          }
          leaf single-input {
            type driver-single-input-type;
            default "NA";
            description
              "Set Single Input. The power supply management mode can be switched only when DC power supply is used.";
          }
          // NCS drop config false leaf 'board-type'
          // NCS drop config false leaf 'entity-index'
          // NCS drop config false leaf 'monitor-cable-state'
          // NCS drop config false leaf 'input-voltage-value'
          // NCS drop config false leaf 'input-electrical-value'
          // NCS drop config false leaf 'input-power-value'
          // NCS drop config false leaf 'output-voltage-value'
          // NCS drop config false leaf 'output-electrical-value'
          // NCS drop config false leaf 'output-power-value'
          // NCS drop config false leaf 'pm-area'
          // NCS drop config false leaf 'pm-status'
        }
      }
      // NCS drop config false container ccus
      // NCS drop config false container dacss
      // NCS drop config false container fans
      // NCS drop config false container icus
      // NCS drop config false container pmus
      // NCS drop config false container 'power-supplys'
      // NCS drop config false container dmus
      // NCS drop config false container pdus
      // NCS drop config false container vsus
    }
  }
  augment "/ncs:devices/ncs:template/ncs:ned-id/ncs:config/lcs:license" {
    description
      "Adds driver configuration to lcs model.";
    container lcs-boards {
      description
        "List of license information about all boards capacity improvement.";
      list lcs-board {
        // NCS patched for predictable order
        ordered-by user;
        key "position capacity";
        description
          "Configure license information about a board capacity improvement.";
        leaf position {
          type string;
          description
            "Position which the license for the capacity improvement feature is activated. The position is expressed in the format of slotID. For example, 1. Here 1 is an example. The value may vary with devices.";
        }
        leaf capacity {
          type ncs_template_lcs-improve-capacity-type;
          units "bit/s";
          description
            "Capacity. The capacity is related to a specific board.";
        }
      }
    }
    // NCS drop config false container 'lcs-usage-board-capacitys'
  }
  augment "/ncs:devices/ncs:device/ncs:live-status/lcs:license" {
    description
      "Adds driver configuration to lcs model.";
    container lcs-boards {
      tailf:ncs-device-type "netconf";
      tailf:display-when "not(../../../ncs:module) or ../../../ncs:module[ncs:name='huawei-driver'] or (../../../ncs:live-status-protocol[not(ncs:capability)]) or (../../../ncs:live-status-protocol/ncs:capability/ncs:module[.='huawei-driver'])";
      description
        "List of license information about all boards capacity improvement.";
      list lcs-board {
        key "position capacity";
        description
          "Configure license information about a board capacity improvement.";
        leaf position {
          type string {
            length "1..32";
          }
          description
            "Position which the license for the capacity improvement feature is activated. The position is expressed in the format of slotID. For example, 1. Here 1 is an example. The value may vary with devices.";
        }
        leaf capacity {
          type live_ncs_lcs-improve-capacity-type;
          units "bit/s";
          description
            "Capacity. The capacity is related to a specific board.";
        }
      }
    }
    container lcs-usage-board-capacitys {
      tailf:ncs-device-type "netconf";
      tailf:display-when "not(../../../ncs:module) or ../../../ncs:module[ncs:name='huawei-driver'] or (../../../ncs:live-status-protocol[not(ncs:capability)]) or (../../../ncs:live-status-protocol/ncs:capability/ncs:module[.='huawei-driver'])";
      description
        "List of capacity improvement license usage information.";
      list lcs-usage-board-capacity {
        key "feature-name";
        description
          "Statistics of capacity improvement license usage information.";
        leaf feature-name {
          type string {
            length "1..31";
          }
          description
            "Name of the control item corresponding to the board license.";
        }
        leaf feature-description {
          type string {
            length "1..255";
          }
          description
            "Description of the control item corresponding to the board license.";
        }
        leaf offline {
          type uint32;
          description
            "Number of offline resources to be activated.";
        }
        leaf allocated {
          type uint32;
          description
            "Number of allocated resources to be activated.";
        }
        leaf activated {
          type uint32;
          description
            "Number of activated resources.";
        }
        leaf available {
          type uint32;
          description
            "Number of remaining available resources.";
        }
        leaf total {
          type uint32;
          description
            "Total number of resources.";
        }
        container boards {
          description
            "List of capacity improvement license usage information on all boards.";
          list board {
            key "position";
            description
              "Statistics of capacity improvement license usage information on a board.";
            leaf position {
              type string {
                length "1..32";
              }
              description
                "Position which the license for the capacity improvement feature is activated. The position is expressed in the format of slotID. For example, 1. Here 1 is an example. The value may vary with devices.";
            }
            leaf needed {
              type uint32;
              description
                "Number of needed resources.";
            }
            leaf used {
              type uint32;
              description
                "Number of used resources.";
            }
            leaf active-status {
              type live_ncs_lcs-active-status-type;
              description
                "License status.";
            }
          }
        }
      }
    }
  }
  augment "/ncs:devices/ncs:device/ncs:config/lcs:license" {
    description
      "Adds driver configuration to lcs model.";
    container lcs-boards {
      tailf:ncs-device-type "netconf";
      tailf:display-when "not(../../../ncs:module) or ../../../ncs:module[ncs:name='huawei-driver']";
      description
        "List of license information about all boards capacity improvement.";
      list lcs-board {
        key "position capacity";
        description
          "Configure license information about a board capacity improvement.";
        leaf position {
          type string {
            length "1..32";
          }
          description
            "Position which the license for the capacity improvement feature is activated. The position is expressed in the format of slotID. For example, 1. Here 1 is an example. The value may vary with devices.";
        }
        leaf capacity {
          type lcs-improve-capacity-type;
          units "bit/s";
          description
            "Capacity. The capacity is related to a specific board.";
        }
      }
    }
    // NCS drop config false container 'lcs-usage-board-capacitys'
  }
}
