submodule huawei-te-interface-type {
  // Generated by yanger -t ncs
  tailf:mount-id "huawei-nc-1.0:huawei-nc-1.0";

  belongs-to huawei-te-interface {
    prefix te-interface;
  }

  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Specifies the multi-protocol label switching protocol.";

  revision 2020-03-10 {
    description
      "Fixed some descriptions.";
    reference "Huawei private.";
  }
  revision 2019-07-29 {
    description
      "Init revision.";
    reference "Huawei private.";
  }

  typedef ncs_template_line-protocol-status {
    type string;
    description
      "Interface line protocol type.";
  }

  typedef ncs_template_rsvp-fast-reroute-mode {
    type string;
    description
      "RSVP TE FRR mode.";
  }

  typedef ncs_template_hex-binary {
    type string;
    description
      "This is a hexadecimal variable.";
  }

  typedef ncs_rpc_notif_line-protocol-status {
    type enumeration {
      enum "down" {
        value 0;
        description
          "The interface is in down state.";
      }
      enum "up" {
        value 1;
        description
          "The interface is in up state.";
      }
    }
    description
      "Interface line protocol type.";
  }

  typedef ncs_rpc_notif_rsvp-fast-reroute-mode {
    type enumeration {
      enum "default" {
        value 0;
        description
          "Inherit from global configuration defaultly.";
      }
      enum "link" {
        value 1;
        description
          "Link protection mode.";
      }
      enum "node" {
        value 2;
        description
          "Node protection mode.";
      }
      enum "self-adapting" {
        value 3;
        description
          "Self-adapting mode.";
      }
      enum "disable" {
        value 4;
        description
          "No protection.";
      }
    }
    description
      "RSVP TE FRR mode.";
  }

  typedef ncs_rpc_notif_hex-binary {
    type string {
      length "1..8";
      pattern '(0x|0X)?[0-9a-fA-F]+';
    }
    description
      "This is a hexadecimal variable.";
  }

  typedef live_ncs_line-protocol-status {
    type enumeration {
      enum "down" {
        value 0;
        description
          "The interface is in down state.";
      }
      enum "up" {
        value 1;
        description
          "The interface is in up state.";
      }
    }
    description
      "Interface line protocol type.";
  }

  typedef live_ncs_rsvp-fast-reroute-mode {
    type enumeration {
      enum "default" {
        value 0;
        description
          "Inherit from global configuration defaultly.";
      }
      enum "link" {
        value 1;
        description
          "Link protection mode.";
      }
      enum "node" {
        value 2;
        description
          "Node protection mode.";
      }
      enum "self-adapting" {
        value 3;
        description
          "Self-adapting mode.";
      }
      enum "disable" {
        value 4;
        description
          "No protection.";
      }
    }
    description
      "RSVP TE FRR mode.";
  }

  typedef live_ncs_hex-binary {
    type string {
      length "1..8";
      pattern '(0x|0X)?[0-9a-fA-F]+';
    }
    description
      "This is a hexadecimal variable.";
  }

  typedef line-protocol-status {
    type enumeration {
      enum "down" {
        value 0;
        description
          "The interface is in down state.";
      }
      enum "up" {
        value 1;
        description
          "The interface is in up state.";
      }
    }
    description
      "Interface line protocol type.";
  }

  typedef rsvp-fast-reroute-mode {
    type enumeration {
      enum "default" {
        value 0;
        description
          "Inherit from global configuration defaultly.";
      }
      enum "link" {
        value 1;
        description
          "Link protection mode.";
      }
      enum "node" {
        value 2;
        description
          "Node protection mode.";
      }
      enum "self-adapting" {
        value 3;
        description
          "Self-adapting mode.";
      }
      enum "disable" {
        value 4;
        description
          "No protection.";
      }
    }
    description
      "RSVP TE FRR mode.";
  }

  typedef hex-binary {
    type string {
      length "1..8";
      pattern '(0x|0X)?[0-9a-fA-F]+';
    }
    description
      "This is a hexadecimal variable.";
  }
}
