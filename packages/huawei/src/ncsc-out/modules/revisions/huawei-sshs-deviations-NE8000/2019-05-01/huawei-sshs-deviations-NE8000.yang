module huawei-sshs-deviations-NE8000 {
  // Generated by yanger -t ncs
  tailf:mount-id "huawei-nc-1.0:huawei-nc-1.0";
  tailf:ncs-device-type "netconf";

  namespace "urn:huawei:yang:huawei-sshs-deviations-NE8000";
  prefix sshs-devs-NE8000;

  import huawei-sshs {
    prefix sshs;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Sshs management.";

  revision 2019-05-01 {
    description
      "Initial revision.";
    reference "Huawei private.";
  }

  typedef ncs_template_sshs-user-auth-deviations {
    type string;
    description
      "SSH server user authentication type list.";
  }

  typedef ncs_template_sshs-user-pubkey-type-deviations {
    type string;
    description
      "SSH server public key encryption type list for user.";
  }

  typedef ncs_rpc_notif_sshs-user-auth-deviations {
    type enumeration {
      enum "not-set" {
        value 0;
        description
          "The user authentication type is not set.";
      }
      enum "password" {
        value 1;
        description
          "User authentication type password.";
      }
      enum "rsa" {
        value 2;
        description
          "User authentication type RSA.";
      }
      enum "all" {
        value 3;
        description
          "User authentication type all.";
      }
      enum "password-rsa" {
        value 4;
        description
          "User authentication type password RSA.";
      }
      enum "dsa" {
        value 5;
        description
          "User authentication type DSA.";
      }
      enum "password-dsa" {
        value 6;
        description
          "User authentication type password DSA.";
      }
      enum "ecc" {
        value 7;
        description
          "User authentication type ECC.";
      }
      enum "password-ecc" {
        value 8;
        description
          "User authentication type password ECC.";
      }
      enum "sm2" {
        value 9;
        description
          "User authentication type SM2.";
      }
      enum "password-sm2" {
        value 10;
        description
          "User authentication type password SM2.";
      }
    }
    description
      "SSH server user authentication type list.";
  }

  typedef ncs_rpc_notif_sshs-user-pubkey-type-deviations {
    type enumeration {
      enum "not-set" {
        value 0;
        description
          "Server public key is not set.";
      }
      enum "RSA" {
        value 1;
        description
          "RSA server public key.";
      }
      enum "DSA" {
        value 2;
        description
          "DSA server public key.";
      }
      enum "ECC" {
        value 3;
        description
          "ECC server public key.";
      }
      enum "SM2" {
        value 5;
        description
          "SM2 server public key.";
      }
    }
    description
      "SSH server public key encryption type list for user.";
  }

  typedef live_ncs_sshs-user-auth-deviations {
    type enumeration {
      enum "not-set" {
        value 0;
        description
          "The user authentication type is not set.";
      }
      enum "password" {
        value 1;
        description
          "User authentication type password.";
      }
      enum "rsa" {
        value 2;
        description
          "User authentication type RSA.";
      }
      enum "all" {
        value 3;
        description
          "User authentication type all.";
      }
      enum "password-rsa" {
        value 4;
        description
          "User authentication type password RSA.";
      }
      enum "dsa" {
        value 5;
        description
          "User authentication type DSA.";
      }
      enum "password-dsa" {
        value 6;
        description
          "User authentication type password DSA.";
      }
      enum "ecc" {
        value 7;
        description
          "User authentication type ECC.";
      }
      enum "password-ecc" {
        value 8;
        description
          "User authentication type password ECC.";
      }
      enum "sm2" {
        value 9;
        description
          "User authentication type SM2.";
      }
      enum "password-sm2" {
        value 10;
        description
          "User authentication type password SM2.";
      }
    }
    description
      "SSH server user authentication type list.";
  }

  typedef live_ncs_sshs-user-pubkey-type-deviations {
    type enumeration {
      enum "not-set" {
        value 0;
        description
          "Server public key is not set.";
      }
      enum "RSA" {
        value 1;
        description
          "RSA server public key.";
      }
      enum "DSA" {
        value 2;
        description
          "DSA server public key.";
      }
      enum "ECC" {
        value 3;
        description
          "ECC server public key.";
      }
      enum "SM2" {
        value 5;
        description
          "SM2 server public key.";
      }
    }
    description
      "SSH server public key encryption type list for user.";
  }

  typedef sshs-user-auth-deviations {
    type enumeration {
      enum "not-set" {
        value 0;
        description
          "The user authentication type is not set.";
      }
      enum "password" {
        value 1;
        description
          "User authentication type password.";
      }
      enum "rsa" {
        value 2;
        description
          "User authentication type RSA.";
      }
      enum "all" {
        value 3;
        description
          "User authentication type all.";
      }
      enum "password-rsa" {
        value 4;
        description
          "User authentication type password RSA.";
      }
      enum "dsa" {
        value 5;
        description
          "User authentication type DSA.";
      }
      enum "password-dsa" {
        value 6;
        description
          "User authentication type password DSA.";
      }
      enum "ecc" {
        value 7;
        description
          "User authentication type ECC.";
      }
      enum "password-ecc" {
        value 8;
        description
          "User authentication type password ECC.";
      }
      enum "sm2" {
        value 9;
        description
          "User authentication type SM2.";
      }
      enum "password-sm2" {
        value 10;
        description
          "User authentication type password SM2.";
      }
    }
    description
      "SSH server user authentication type list.";
  }

  typedef sshs-user-pubkey-type-deviations {
    type enumeration {
      enum "not-set" {
        value 0;
        description
          "Server public key is not set.";
      }
      enum "RSA" {
        value 1;
        description
          "RSA server public key.";
      }
      enum "DSA" {
        value 2;
        description
          "DSA server public key.";
      }
      enum "ECC" {
        value 3;
        description
          "ECC server public key.";
      }
      enum "SM2" {
        value 5;
        description
          "SM2 server public key.";
      }
    }
    description
      "SSH server public key encryption type list for user.";
  }

  deviation "/ncs:devices/ncs:template/ncs:ned-id/ncs:config/sshs:sshs/sshs:users/sshs:user/sshs:auth-type" {
    deviate replace {
      type sshs-devs-NE8000:ncs_template_sshs-user-auth-deviations;
    }
  }
  deviation "/ncs:devices/ncs:device/ncs:live-status/sshs:sshs/sshs:users/sshs:user/sshs:auth-type" {
    deviate replace {
      type sshs-devs-NE8000:live_ncs_sshs-user-auth-deviations;
    }
  }
  deviation "/ncs:devices/ncs:device/ncs:config/sshs:sshs/sshs:users/sshs:user/sshs:auth-type" {
    deviate replace {
      type sshs-devs-NE8000:sshs-user-auth-deviations;
    }
  }
  deviation "/ncs:devices/ncs:template/ncs:ned-id/ncs:config/sshs:sshs/sshs:users/sshs:user/sshs:pub-key-type" {
    deviate replace {
      type sshs-devs-NE8000:ncs_template_sshs-user-pubkey-type-deviations;
    }
  }
  deviation "/ncs:devices/ncs:device/ncs:live-status/sshs:sshs/sshs:users/sshs:user/sshs:pub-key-type" {
    deviate replace {
      type sshs-devs-NE8000:live_ncs_sshs-user-pubkey-type-deviations;
    }
  }
  deviation "/ncs:devices/ncs:device/ncs:config/sshs:sshs/sshs:users/sshs:user/sshs:pub-key-type" {
    deviate replace {
      type sshs-devs-NE8000:sshs-user-pubkey-type-deviations;
    }
  }
  deviation "/ncs:devices/ncs:template/ncs:ned-id/ncs:config/sshs:sshs/sshs:server/sshs:pki-domain" {
    deviate not-supported;
  }
  deviation "/ncs:devices/ncs:device/ncs:live-status/sshs:sshs/sshs:server/sshs:pki-domain" {
    deviate not-supported;
  }
  deviation "/ncs:devices/ncs:device/ncs:config/sshs:sshs/sshs:server/sshs:pki-domain" {
    deviate not-supported;
  }
  deviation "/ncs:devices/ncs:template/ncs:ned-id/ncs:config/sshs:sshs/sshs:pubkey-alg" {
    deviate delete {
      // NCS drop must statement
    }
    deviate add {
      // NCS drop must statement
    }
  }
  deviation "/ncs:devices/ncs:device/ncs:live-status/sshs:sshs/sshs:pubkey-alg" {
    deviate delete {
      // NCS drop must statement
    }
    deviate add {
      // NCS drop must statement
    }
  }
  deviation "/ncs:devices/ncs:device/ncs:config/sshs:sshs/sshs:pubkey-alg" {
    deviate delete {
      must "../pubkey-alg/dsa = 'true' or ../pubkey-alg/ecc = 'true' or ../pubkey-alg/rsa = 'true' or ../pubkey-alg/sm2 = 'true' or ../pubkey-alg/x509v3-ssh-rsa = 'true' or ../pubkey-alg/rsa-sha2-256 = 'true' or ../pubkey-alg/rsa-sha2-512 = 'true'" {
        tailf:xpath-root 3;
      }
    }
    deviate add {
      must "../pubkey-alg/dsa = 'true' or ../pubkey-alg/ecc = 'true' or ../pubkey-alg/rsa = 'true' or ../pubkey-alg/sm2 = 'true' or ../pubkey-alg/rsa-sha2-256 = 'true' or ../pubkey-alg/rsa-sha2-512 = 'true'" {
        tailf:xpath-root 3;
      }
    }
  }
  deviation "/ncs:devices/ncs:template/ncs:ned-id/ncs:config/sshs:sshs/sshs:pubkey-alg/sshs:x509v3-ssh-rsa" {
    deviate not-supported;
  }
  deviation "/ncs:devices/ncs:device/ncs:live-status/sshs:sshs/sshs:pubkey-alg/sshs:x509v3-ssh-rsa" {
    deviate not-supported;
  }
  deviation "/ncs:devices/ncs:device/ncs:config/sshs:sshs/sshs:pubkey-alg/sshs:x509v3-ssh-rsa" {
    deviate not-supported;
  }
  deviation "/ncs:devices/ncs:template/ncs:ned-id/ncs:config/sshs:sshs/sshs:key-exc-alg" {
    deviate delete {
      // NCS drop must statement
    }
    deviate add {
      // NCS drop must statement
    }
  }
  deviation "/ncs:devices/ncs:device/ncs:live-status/sshs:sshs/sshs:key-exc-alg" {
    deviate delete {
      // NCS drop must statement
    }
    deviate add {
      // NCS drop must statement
    }
  }
  deviation "/ncs:devices/ncs:device/ncs:config/sshs:sshs/sshs:key-exc-alg" {
    deviate delete {
      must "../key-exc-alg/dh-group14-sha1 = 'true' or ../key-exc-alg/dh-group1-sha1 = 'true' or ../key-exc-alg/ecdh-sha2-nistp521 = 'true' or ../key-exc-alg/ecdh-sha2-nistp384 = 'true' or ../key-exc-alg/ecdh-sha2-nistp384 = 'true' or ../key-exc-alg/ecdh-sha2-nistp256 = 'true' or ../key-exc-alg/dh-group-exchange-sha256 = 'true' or ../key-exc-alg/sm2-kep-sha2-nistp256 = 'true' or ../key-exc-alg/dh-group16-sha512 = 'true' or ../key-exc-alg/dh-group18-sha512 = 'true' or ../key-exc-alg/curve25519-sha256 = 'true'" {
        tailf:xpath-root 3;
      }
    }
    deviate add {
      must "../key-exc-alg/dh-group14-sha1 = 'true' or ../key-exc-alg/dh-group1-sha1 = 'true' or ../key-exc-alg/ecdh-sha2-nistp521 = 'true' or ../key-exc-alg/ecdh-sha2-nistp384 = 'true' or ../key-exc-alg/ecdh-sha2-nistp384 = 'true' or ../key-exc-alg/ecdh-sha2-nistp256 = 'true' or ../key-exc-alg/dh-group-exchange-sha256 = 'true' or ../key-exc-alg/sm2-kep-sha2-nistp256 = 'true'" {
        tailf:xpath-root 3;
      }
    }
  }
  deviation "/ncs:devices/ncs:template/ncs:ned-id/ncs:config/sshs:sshs/sshs:key-exc-alg/sshs:dh-group18-sha512" {
    deviate not-supported;
  }
  deviation "/ncs:devices/ncs:device/ncs:live-status/sshs:sshs/sshs:key-exc-alg/sshs:dh-group18-sha512" {
    deviate not-supported;
  }
  deviation "/ncs:devices/ncs:device/ncs:config/sshs:sshs/sshs:key-exc-alg/sshs:dh-group18-sha512" {
    deviate not-supported;
  }
  deviation "/ncs:devices/ncs:template/ncs:ned-id/ncs:config/sshs:sshs/sshs:key-exc-alg/sshs:curve25519-sha256" {
    deviate not-supported;
  }
  deviation "/ncs:devices/ncs:device/ncs:live-status/sshs:sshs/sshs:key-exc-alg/sshs:curve25519-sha256" {
    deviate not-supported;
  }
  deviation "/ncs:devices/ncs:device/ncs:config/sshs:sshs/sshs:key-exc-alg/sshs:curve25519-sha256" {
    deviate not-supported;
  }
}
