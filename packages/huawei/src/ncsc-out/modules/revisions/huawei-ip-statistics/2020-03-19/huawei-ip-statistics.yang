module huawei-ip-statistics {
  // Generated by yanger -t ncs
  tailf:mount-id "huawei-nc-1.0:huawei-nc-1.0";
  tailf:ncs-device-type "netconf";

  namespace "urn:huawei:yang:huawei-ip-statistics";
  prefix ip-stats;

  import huawei-ip {
    prefix ip;
  }
  import huawei-extension {
    prefix ext;
  }
  import huawei-ifm {
    prefix ifm;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Dual-stack traffic statistics on an interface.";

  revision 2020-03-19 {
    description
      "Initial revision.";
    reference "Huawei private.";
  }
  ext:task-name "ip-stack";

  augment "/ncs:devices/ncs:device/ncs:live-status/ifm:ifm/ifm:interfaces/ifm:interface/ip:ipv4/ip:state" {
    description
      "IPv4 traffic statistics on an interface.";
    container statistics {
      tailf:ncs-device-type "netconf";
      tailf:display-when "not(../../../../../../../ncs:module) or ../../../../../../../ncs:module[ncs:name='huawei-ip-statistics'] or (../../../../../../../ncs:live-status-protocol[not(ncs:capability)]) or (../../../../../../../ncs:live-status-protocol/ncs:capability/ncs:module[.='huawei-ip-statistics'])";
      description
        "A collection of IPv4 layer statistics for IP traffic
         received and transmitted by an interface.";
      leaf in-receives {
        type uint64;
        units "packet";
        description
          "Total number of IPv4 packets received on an interface.";
      }
      leaf in-octets {
        type uint64;
        units "Octet";
        description
          "Total number of IPv4 packet bytes received on an interface.";
      }
      leaf in-rate-pkts {
        type uint64;
        units "pps";
        description
          "Rate for receiving IPv4 packets on an interface.";
      }
      leaf in-rate-bits {
        type uint64;
        units "bit/s";
        description
          "Rate for receiving IPv4 packet bits on an interface.";
      }
      leaf in-rate-byte-bandwidth-usage {
        type string {
          length "1..7";
        }
        description
          "Bandwidth usage for an interface to receive IPv4 packets.";
      }
      leaf in-ucast-pkts {
        type uint64;
        units "packet";
        description
          "Total number of IPv4 unicast packets received on an interface.";
      }
      leaf in-ucast-octets {
        type uint64;
        units "Octet";
        description
          "Total number of IPv4 unicast packet bytes received on an interface.";
      }
      leaf in-mcast-pkts {
        type uint64;
        units "packet";
        description
          "Total number of IPv4 multicast packets received on an interface.";
      }
      leaf in-mcast-octets {
        type uint64;
        units "Octet";
        description
          "Total number of IPv4 multicast packet bytes received on an interface.";
      }
      leaf in-bcast-pkts {
        type uint64;
        units "packet";
        description
          "Total number of IPv4 broadcast packets received on an interface.";
      }
      leaf in-bcast-octets {
        type uint64;
        units "Octet";
        description
          "Total number of IPv4 broadcast packet bytes received on an interface.";
      }
      leaf out-ucast-pkts {
        type uint64;
        units "packet";
        description
          "Total number of IPv4 unicast packets sent on an interface.";
      }
      leaf out-ucast-octets {
        type uint64;
        units "Octet";
        description
          "Total number of IPv4 unicast packet bytes sent on an interface.";
      }
      leaf out-mcast-pkts {
        type uint64;
        units "packet";
        description
          "Total number of IPv4 multicast packets sent on an interface.";
      }
      leaf out-mcast-octets {
        type uint64;
        units "Octet";
        description
          "Total number of IPv4 multicast packet bytes sent on an interface.";
      }
      leaf out-bcast-pkts {
        type uint64;
        units "packet";
        description
          "Total number of IPv4 broadcast packets sent on an interface.";
      }
      leaf out-bcast-octets {
        type uint64;
        units "Octet";
        description
          "Total number of IPv4 broadcast packet bytes sent on an interface.";
      }
      leaf out-rate-pkts {
        type uint64;
        units "packet";
        description
          "Rate for sending IPv4 packets on an interface.";
      }
      leaf out-rate-bits {
        type uint64;
        units "bit/s";
        description
          "Rate for sending IPv4 packet bits on an interface.";
      }
      leaf out-rate-byte-bandwidth-usage {
        type string {
          length "1..7";
        }
        description
          "Bandwidth usage for an interface to send IPv4 packets.";
      }
      leaf out-transmits {
        type uint64;
        units "packet";
        description
          "Total number of IPv4 packets sent on an interface.";
      }
      leaf out-octets {
        type uint64;
        units "Octet";
        description
          "Total number of IPv4 packet bytes sent on an interface.";
      }
      leaf out-frag-requires {
        type uint64;
        units "packet";
        description
          "Total number of IPv4 packets to be fragmented.";
      }
      leaf out-frag-fails {
        type uint32;
        units "packet";
        description
          "Total number of IPv4 packets that fail to be fragmented.";
      }
      leaf out-frag-oks {
        type uint64;
        units "packet";
        description
          "Total number of IPv4 packets that are successfully fragmented.";
      }
      leaf out-frag-creates {
        type uint64;
        units "packet";
        description
          "Total number of IPv4 fragments.";
      }
    }
  }
  augment "/ncs:devices/ncs:device/ncs:live-status/ifm:ifm/ifm:interfaces/ifm:interface/ip:ipv6/ip:state" {
    description
      "IPv6 traffic statistics on an interface.";
    container statistics {
      tailf:ncs-device-type "netconf";
      tailf:display-when "not(../../../../../../../ncs:module) or ../../../../../../../ncs:module[ncs:name='huawei-ip-statistics'] or (../../../../../../../ncs:live-status-protocol[not(ncs:capability)]) or (../../../../../../../ncs:live-status-protocol/ncs:capability/ncs:module[.='huawei-ip-statistics'])";
      description
        "A collection of IPv6 layer statistics for IP traffic
         received and transmitted by an interface.";
      leaf in-receives {
        type uint64;
        units "packet";
        description
          "Total number of IPv6 packets received on an interface.";
      }
      leaf in-octets {
        type uint64;
        units "Octet";
        description
          "Total number of IPv6 packet bytes received on an interface.";
      }
      leaf in-rate-pkts {
        type uint64;
        units "pps";
        description
          "Rate for receiving IPv6 packets on an interface.";
      }
      leaf in-rate-bits {
        type uint64;
        units "bit/s";
        description
          "Rate for receiving IPv6 packet bits on an interface.";
      }
      leaf in-rate-byte-bandwidth-usage {
        type string {
          length "1..7";
        }
        description
          "Bandwidth usage for an interface to receive IPv6 packets.";
      }
      leaf in-ucast-pkts {
        type uint64;
        units "packet";
        description
          "Total number of IPv6 unicast packets received on an interface.";
      }
      leaf in-ucast-octets {
        type uint64;
        units "Octet";
        description
          "Total number of IPv6 unicast packet bytes received on an interface.";
      }
      leaf in-mcast-pkts {
        type uint64;
        units "packet";
        description
          "Total number of IPv6 multicast packets received on an interface.";
      }
      leaf in-mcast-octets {
        type uint64;
        units "Octet";
        description
          "Total number of IPv6 multicast packet bytes received on an interface.";
      }
      leaf out-ucast-pkts {
        type uint64;
        units "packet";
        description
          "Total number of IPv6 unicast packets sent on an interface.";
      }
      leaf out-ucast-octets {
        type uint64;
        units "Octet";
        description
          "Total number of IPv6 unicast packet bytes sent on an interface.";
      }
      leaf out-mcast-pkts {
        type uint64;
        units "packet";
        description
          "Total number of IPv6 multicast packets sent on an interface.";
      }
      leaf out-mcast-octets {
        type uint64;
        units "Octet";
        description
          "Total number of IPv6 multicast packet bytes sent on an interface.";
      }
      leaf out-rate-pkts {
        type uint64;
        units "packet";
        description
          "Rate for sending IPv6 packets on an interface.";
      }
      leaf out-rate-bits {
        type uint64;
        units "bit/s";
        description
          "Rate for sending IPv6 packet bits on an interface.";
      }
      leaf out-rate-byte-bandwidth-usage {
        type string {
          length "1..7";
        }
        description
          "Bandwidth usage for an interface to send IPv6 packets.";
      }
      leaf out-transmits {
        type uint64;
        units "packet";
        description
          "Total number of IPv6 packets sent on an interface.";
      }
      leaf out-octets {
        type uint64;
        units "Octet";
        description
          "Total number of IPv6 packet bytes sent on an interface.";
      }
    }
  }
}
