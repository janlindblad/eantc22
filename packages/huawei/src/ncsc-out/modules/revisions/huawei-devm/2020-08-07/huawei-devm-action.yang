submodule huawei-devm-action {
  // Generated by yanger -t ncs
  tailf:mount-id "huawei-nc-1.0:huawei-nc-1.0";

  belongs-to huawei-devm {
    prefix devm;
  }

  import huawei-pub-type {
    prefix pub-type;
  }
  import ietf-inet-types {
    prefix inet;
  }
  import huawei-extension {
    prefix ext;
  }
  include huawei-devm-type;
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "The submodule of devm : devm_action.";

  revision 2020-08-07 {
    description
      "Add clear-active-hardware-alarm and clear-history-hardware-alarm.";
    reference "Huawei private.";
  }
  revision 2020-04-10 {
    description
      "Modify description warnings.";
    reference "Huawei private.";
  }
  revision 2019-09-09 {
    description
      "Change description.";
    reference "Huawei private.";
  }
  revision 2019-04-03 {
    description
      "Initial revision.";
    reference "Huawei private.";
  }

  augment "/ncs:devices/ncs:device/ncs:rpc" {
    container rpc-clear-history-hardware-alarm {
      tailf:ncs-device-type "netconf";
      tailf:display-when "not(../../ncs:module) or ../../ncs:module[ncs:name='huawei-devm']";
      tailf:action clear-history-hardware-alarm {
        tailf:actionpoint ncsproxy {
          tailf:internal;
        }
        description
          "Clear history hardware alarm.";
        input {
          choice clear-mode {
            default "all";
            description
              "The mode to clear alarm.";
            case all {
              description
                "Clear all alarm.";
              leaf all {
                type empty;
                description
                  "Clear all alarm.";
              }
            }
            case position {
              description
                "Clear alarm by hardware entity position.";
              leaf position {
                type string {
                  length "1..32";
                }
                mandatory true;
                description
                  "Hardware entity position.";
              }
            }
          }
        }
      }
    }
  }
  augment "/ncs:devices/ncs:device-group/ncs:ned-id/ncs:rpc" {
    container rpc-clear-history-hardware-alarm {
      tailf:ncs-device-type "netconf";
      tailf:display-when "/ncs:devices/ncs:device[ncs:name=current()/../../../ncs:member]/ncs:module[ncs:name='huawei-devm']";
      tailf:action clear-history-hardware-alarm {
        tailf:actionpoint ncsproxy {
          tailf:internal;
        }
        description
          "Clear history hardware alarm.";
        input {
          choice clear-mode {
            default "all";
            description
              "The mode to clear alarm.";
            case all {
              description
                "Clear all alarm.";
              leaf all {
                type empty;
                description
                  "Clear all alarm.";
              }
            }
            case position {
              description
                "Clear alarm by hardware entity position.";
              leaf position {
                type string {
                  length "1..32";
                }
                mandatory true;
                description
                  "Hardware entity position.";
              }
            }
          }
        }
      }
    }
  }
  augment "/ncs:devices/ncs:device/ncs:rpc" {
    container rpc-clear-active-hardware-alarm {
      tailf:ncs-device-type "netconf";
      tailf:display-when "not(../../ncs:module) or ../../ncs:module[ncs:name='huawei-devm']";
      tailf:action clear-active-hardware-alarm {
        tailf:actionpoint ncsproxy {
          tailf:internal;
        }
        description
          "Clear active hardware alarm.";
        input {
          choice clear-mode {
            default "all";
            description
              "The mode to clear alarm.";
            case all {
              description
                "Clear all alarm.";
              leaf all {
                type empty;
                description
                  "Clear all alarm.";
              }
            }
            case position {
              description
                "Clear alarm by hardware entity position.";
              leaf position {
                type string {
                  length "1..32";
                }
                mandatory true;
                description
                  "Hardware entity position.";
              }
            }
            case sequence {
              description
                "Clear alarm by sequence.";
              leaf sequence {
                type uint32 {
                  range "1..4294967295";
                }
                mandatory true;
                description
                  "The sequence of all active alarm.";
              }
            }
          }
        }
      }
    }
  }
  augment "/ncs:devices/ncs:device-group/ncs:ned-id/ncs:rpc" {
    container rpc-clear-active-hardware-alarm {
      tailf:ncs-device-type "netconf";
      tailf:display-when "/ncs:devices/ncs:device[ncs:name=current()/../../../ncs:member]/ncs:module[ncs:name='huawei-devm']";
      tailf:action clear-active-hardware-alarm {
        tailf:actionpoint ncsproxy {
          tailf:internal;
        }
        description
          "Clear active hardware alarm.";
        input {
          choice clear-mode {
            default "all";
            description
              "The mode to clear alarm.";
            case all {
              description
                "Clear all alarm.";
              leaf all {
                type empty;
                description
                  "Clear all alarm.";
              }
            }
            case position {
              description
                "Clear alarm by hardware entity position.";
              leaf position {
                type string {
                  length "1..32";
                }
                mandatory true;
                description
                  "Hardware entity position.";
              }
            }
            case sequence {
              description
                "Clear alarm by sequence.";
              leaf sequence {
                type uint32 {
                  range "1..4294967295";
                }
                mandatory true;
                description
                  "The sequence of all active alarm.";
              }
            }
          }
        }
      }
    }
  }
  augment "/ncs:devices/ncs:device/ncs:rpc" {
    container rpc-undo-schedule-reboot {
      tailf:ncs-device-type "netconf";
      tailf:display-when "not(../../ncs:module) or ../../ncs:module[ncs:name='huawei-devm']";
      tailf:action undo-schedule-reboot {
        tailf:actionpoint ncsproxy {
          tailf:internal;
        }
        description
          "Undo Schedule reboot.";
      }
    }
  }
  augment "/ncs:devices/ncs:device-group/ncs:ned-id/ncs:rpc" {
    container rpc-undo-schedule-reboot {
      tailf:ncs-device-type "netconf";
      tailf:display-when "/ncs:devices/ncs:device[ncs:name=current()/../../../ncs:member]/ncs:module[ncs:name='huawei-devm']";
      tailf:action undo-schedule-reboot {
        tailf:actionpoint ncsproxy {
          tailf:internal;
        }
        description
          "Undo Schedule reboot.";
      }
    }
  }
  augment "/ncs:devices/ncs:device/ncs:rpc" {
    container rpc-schedule-reboot-delay-time {
      tailf:ncs-device-type "netconf";
      tailf:display-when "not(../../ncs:module) or ../../ncs:module[ncs:name='huawei-devm']";
      tailf:action schedule-reboot-delay-time {
        tailf:actionpoint ncsproxy {
          tailf:internal;
        }
        description
          "Schedule reboot delay time.";
        input {
          leaf delay-time {
            type string {
              length "1..6";
            }
            mandatory true;
            description
              "Delay time, total minutes or hours:minutes (mm or hh:mm), the max value is 720 hours.";
          }
          leaf save-flag {
            type boolean;
            default "true";
            description
              "Flag indicating whether save config.";
          }
        }
      }
    }
  }
  augment "/ncs:devices/ncs:device-group/ncs:ned-id/ncs:rpc" {
    container rpc-schedule-reboot-delay-time {
      tailf:ncs-device-type "netconf";
      tailf:display-when "/ncs:devices/ncs:device[ncs:name=current()/../../../ncs:member]/ncs:module[ncs:name='huawei-devm']";
      tailf:action schedule-reboot-delay-time {
        tailf:actionpoint ncsproxy {
          tailf:internal;
        }
        description
          "Schedule reboot delay time.";
        input {
          leaf delay-time {
            type string {
              length "1..6";
            }
            mandatory true;
            description
              "Delay time, total minutes or hours:minutes (mm or hh:mm), the max value is 720 hours.";
          }
          leaf save-flag {
            type boolean;
            default "true";
            description
              "Flag indicating whether save config.";
          }
        }
      }
    }
  }
  augment "/ncs:devices/ncs:device/ncs:rpc" {
    container rpc-schedule-reboot-at-time {
      tailf:ncs-device-type "netconf";
      tailf:display-when "not(../../ncs:module) or ../../ncs:module[ncs:name='huawei-devm']";
      tailf:action schedule-reboot-at-time {
        tailf:actionpoint ncsproxy {
          tailf:internal;
        }
        description
          "Schedule reboot at time.";
        input {
          leaf schedule-date {
            type pub-type:ncs_rpc_notif_date;
            mandatory true;
            description
              "Date.";
          }
          leaf schedule-datetime {
            type pub-type:ncs_rpc_notif_time-hhmm;
            mandatory true;
            description
              "Time.";
          }
          leaf save-flag {
            type boolean;
            default "true";
            description
              "Flag indicating whether save config.";
          }
        }
      }
    }
  }
  augment "/ncs:devices/ncs:device-group/ncs:ned-id/ncs:rpc" {
    container rpc-schedule-reboot-at-time {
      tailf:ncs-device-type "netconf";
      tailf:display-when "/ncs:devices/ncs:device[ncs:name=current()/../../../ncs:member]/ncs:module[ncs:name='huawei-devm']";
      tailf:action schedule-reboot-at-time {
        tailf:actionpoint ncsproxy {
          tailf:internal;
        }
        description
          "Schedule reboot at time.";
        input {
          leaf schedule-date {
            type pub-type:ncs_rpc_notif_date;
            mandatory true;
            description
              "Date.";
          }
          leaf schedule-datetime {
            type pub-type:ncs_rpc_notif_time-hhmm;
            mandatory true;
            description
              "Time.";
          }
          leaf save-flag {
            type boolean;
            default "true";
            description
              "Flag indicating whether save config.";
          }
        }
      }
    }
  }
  augment "/ncs:devices/ncs:device/ncs:rpc" {
    container rpc-warm-reset-mpu {
      tailf:ncs-device-type "netconf";
      tailf:display-when "not(../../ncs:module) or ../../ncs:module[ncs:name='huawei-devm']";
      tailf:action warm-reset-mpu {
        tailf:actionpoint ncsproxy {
          tailf:internal;
        }
        description
          "Warm reset MPU.";
        ext:node-ref "/devm/mpu-boards/mpu-board";
        input {
          leaf board-position {
            type string {
              length "1..32";
            }
            mandatory true;
            description
              "Board position.";
          }
        }
      }
    }
  }
  augment "/ncs:devices/ncs:device-group/ncs:ned-id/ncs:rpc" {
    container rpc-warm-reset-mpu {
      tailf:ncs-device-type "netconf";
      tailf:display-when "/ncs:devices/ncs:device[ncs:name=current()/../../../ncs:member]/ncs:module[ncs:name='huawei-devm']";
      tailf:action warm-reset-mpu {
        tailf:actionpoint ncsproxy {
          tailf:internal;
        }
        description
          "Warm reset MPU.";
        ext:node-ref "/devm/mpu-boards/mpu-board";
        input {
          leaf board-position {
            type string {
              length "1..32";
            }
            mandatory true;
            description
              "Board position.";
          }
        }
      }
    }
  }
  augment "/ncs:devices/ncs:device/ncs:rpc" {
    container rpc-cold-reset-mpu {
      tailf:ncs-device-type "netconf";
      tailf:display-when "not(../../ncs:module) or ../../ncs:module[ncs:name='huawei-devm']";
      tailf:action cold-reset-mpu {
        tailf:actionpoint ncsproxy {
          tailf:internal;
        }
        description
          "Cold reset MPU.";
        ext:node-ref "/devm/mpu-boards/mpu-board";
        input {
          leaf board-position {
            type string {
              length "1..32";
            }
            mandatory true;
            description
              "Board position.";
          }
        }
      }
    }
  }
  augment "/ncs:devices/ncs:device-group/ncs:ned-id/ncs:rpc" {
    container rpc-cold-reset-mpu {
      tailf:ncs-device-type "netconf";
      tailf:display-when "/ncs:devices/ncs:device[ncs:name=current()/../../../ncs:member]/ncs:module[ncs:name='huawei-devm']";
      tailf:action cold-reset-mpu {
        tailf:actionpoint ncsproxy {
          tailf:internal;
        }
        description
          "Cold reset MPU.";
        ext:node-ref "/devm/mpu-boards/mpu-board";
        input {
          leaf board-position {
            type string {
              length "1..32";
            }
            mandatory true;
            description
              "Board position.";
          }
        }
      }
    }
  }
  augment "/ncs:devices/ncs:device/ncs:rpc" {
    container rpc-warm-reset-lpu {
      tailf:ncs-device-type "netconf";
      tailf:display-when "not(../../ncs:module) or ../../ncs:module[ncs:name='huawei-devm']";
      tailf:action warm-reset-lpu {
        tailf:actionpoint ncsproxy {
          tailf:internal;
        }
        description
          "Warm reset LPU.";
        ext:node-ref "/devm/lpu-boards/lpu-board";
        input {
          leaf board-position {
            type string {
              length "1..32";
            }
            mandatory true;
            description
              "Board position.";
          }
        }
      }
    }
  }
  augment "/ncs:devices/ncs:device-group/ncs:ned-id/ncs:rpc" {
    container rpc-warm-reset-lpu {
      tailf:ncs-device-type "netconf";
      tailf:display-when "/ncs:devices/ncs:device[ncs:name=current()/../../../ncs:member]/ncs:module[ncs:name='huawei-devm']";
      tailf:action warm-reset-lpu {
        tailf:actionpoint ncsproxy {
          tailf:internal;
        }
        description
          "Warm reset LPU.";
        ext:node-ref "/devm/lpu-boards/lpu-board";
        input {
          leaf board-position {
            type string {
              length "1..32";
            }
            mandatory true;
            description
              "Board position.";
          }
        }
      }
    }
  }
  augment "/ncs:devices/ncs:device/ncs:rpc" {
    container rpc-cold-reset-lpu {
      tailf:ncs-device-type "netconf";
      tailf:display-when "not(../../ncs:module) or ../../ncs:module[ncs:name='huawei-devm']";
      tailf:action cold-reset-lpu {
        tailf:actionpoint ncsproxy {
          tailf:internal;
        }
        description
          "Cold reset LPU.";
        ext:node-ref "/devm/lpu-boards/lpu-board";
        input {
          leaf board-position {
            type string {
              length "1..32";
            }
            mandatory true;
            description
              "Board position.";
          }
        }
      }
    }
  }
  augment "/ncs:devices/ncs:device-group/ncs:ned-id/ncs:rpc" {
    container rpc-cold-reset-lpu {
      tailf:ncs-device-type "netconf";
      tailf:display-when "/ncs:devices/ncs:device[ncs:name=current()/../../../ncs:member]/ncs:module[ncs:name='huawei-devm']";
      tailf:action cold-reset-lpu {
        tailf:actionpoint ncsproxy {
          tailf:internal;
        }
        description
          "Cold reset LPU.";
        ext:node-ref "/devm/lpu-boards/lpu-board";
        input {
          leaf board-position {
            type string {
              length "1..32";
            }
            mandatory true;
            description
              "Board position.";
          }
        }
      }
    }
  }
  augment "/ncs:devices/ncs:device/ncs:rpc" {
    container rpc-clear-inactive-config {
      tailf:ncs-device-type "netconf";
      tailf:display-when "not(../../ncs:module) or ../../ncs:module[ncs:name='huawei-devm']";
      tailf:action clear-inactive-config {
        tailf:actionpoint ncsproxy {
          tailf:internal;
        }
        description
          "Clear Inactive Configuration.";
        input {
          leaf entity-class {
            type ncs_rpc_notif_offline-class-type;
            mandatory true;
            description
              "Class.";
          }
          leaf position {
            type string {
              length "1..32";
            }
            mandatory true;
            description
              "Position.";
          }
        }
      }
    }
  }
  augment "/ncs:devices/ncs:device-group/ncs:ned-id/ncs:rpc" {
    container rpc-clear-inactive-config {
      tailf:ncs-device-type "netconf";
      tailf:display-when "/ncs:devices/ncs:device[ncs:name=current()/../../../ncs:member]/ncs:module[ncs:name='huawei-devm']";
      tailf:action clear-inactive-config {
        tailf:actionpoint ncsproxy {
          tailf:internal;
        }
        description
          "Clear Inactive Configuration.";
        input {
          leaf entity-class {
            type ncs_rpc_notif_offline-class-type;
            mandatory true;
            description
              "Class.";
          }
          leaf position {
            type string {
              length "1..32";
            }
            mandatory true;
            description
              "Position.";
          }
        }
      }
    }
  }
  augment "/ncs:devices/ncs:device/ncs:rpc" {
    container rpc-reset-offline-config {
      tailf:ncs-device-type "netconf";
      tailf:display-when "not(../../ncs:module) or ../../ncs:module[ncs:name='huawei-devm']";
      tailf:action reset-offline-config {
        tailf:actionpoint ncsproxy {
          tailf:internal;
        }
        description
          "Reset offline configuration.";
        input {
          leaf board-position {
            type string {
              length "1..32";
            }
            mandatory true;
            description
              "Board position.";
          }
        }
      }
    }
  }
  augment "/ncs:devices/ncs:device-group/ncs:ned-id/ncs:rpc" {
    container rpc-reset-offline-config {
      tailf:ncs-device-type "netconf";
      tailf:display-when "/ncs:devices/ncs:device[ncs:name=current()/../../../ncs:member]/ncs:module[ncs:name='huawei-devm']";
      tailf:action reset-offline-config {
        tailf:actionpoint ncsproxy {
          tailf:internal;
        }
        description
          "Reset offline configuration.";
        input {
          leaf board-position {
            type string {
              length "1..32";
            }
            mandatory true;
            description
              "Board position.";
          }
        }
      }
    }
  }
  augment "/ncs:devices/ncs:device/ncs:rpc" {
    container rpc-transfer-pnpp {
      tailf:ncs-device-type "netconf";
      tailf:display-when "not(../../ncs:module) or ../../ncs:module[ncs:name='huawei-devm']";
      tailf:action transfer-pnpp {
        tailf:actionpoint ncsproxy {
          tailf:internal;
        }
        description
          "Transfer pnpp files.";
        input {
          leaf server-ip-address {
            type inet:ip-address-no-zone;
            mandatory true;
            description
              "FTP server IP address.";
          }
          leaf server-port {
            type uint32 {
              range "21..65535";
            }
            default "21";
            description
              "Server port.";
          }
          leaf vpn-instance-name {
            type string {
              length "1..128";
            }
            description
              "VPN instance name.";
          }
          leaf source-ipv4-address {
            type inet:ipv4-address-no-zone;
            description
              "Source IPv4 address.";
          }
          leaf source-interface-name {
            type pub-type:ncs_rpc_notif_if-name;
            description
              "Source interface name.";
          }
          leaf server-type {
            type ncs_rpc_notif_server-type;
            default "ftp";
            description
              "Server type.";
          }
          leaf command-type {
            type ncs_rpc_notif_trans-type;
            default "put";
            description
              "Transmission type.";
          }
          leaf user-name {
            type string {
              length "1..85";
            }
            mandatory true;
            description
              "User name.";
          }
          leaf password {
            type pub-type:ncs_rpc_notif_password;
            mandatory true;
            description
              "Password.";
          }
          leaf local-file-name {
            type string {
              length "1..128";
            }
            default "pnpp.7z";
            description
              "Local file name.";
          }
          leaf remote-file-name {
            type string {
              length "1..128";
            }
            description
              "File name on the FTP server.";
          }
          leaf remote-extension {
            type string {
              length "1..5";
            }
            default ".hw!";
            description
              "Temporary file name extension used for reliability.";
          }
          container secure-transfer-options {
            description
              "Transfer encryption options.";
            leaf prefer-kex {
              type ncs_rpc_notif_prefer-kex-type;
              description
                "Encryption algorithm.";
            }
            leaf prefer-stoc-cipher {
              type ncs_rpc_notif_cipher-type;
              description
                "Encryption algorithm for messages from a client to server.";
            }
            leaf prefer-ctos-cipher {
              type ncs_rpc_notif_cipher-type;
              description
                "Encryption algorithm for messages from a server to client.";
            }
            leaf prefer-stoc-hmac {
              type ncs_rpc_notif_stoc-hmac-type;
              description
                "Prefer Stoc Hmac.";
            }
            leaf prefer-ctos-hmac {
              type ncs_rpc_notif_stoc-hmac-type;
              description
                "Prefer Ctos Hmac.";
            }
            leaf keep-alive-interval {
              type uint32 {
                range "0..60";
              }
              default "0";
              description
                "Keepalive interval.";
            }
            leaf keep-alive-count {
              type uint32 {
                range "0..100";
              }
              default "0";
              description
                "Number of Keepalive packets.";
            }
          }
        }
      }
    }
  }
  augment "/ncs:devices/ncs:device-group/ncs:ned-id/ncs:rpc" {
    container rpc-transfer-pnpp {
      tailf:ncs-device-type "netconf";
      tailf:display-when "/ncs:devices/ncs:device[ncs:name=current()/../../../ncs:member]/ncs:module[ncs:name='huawei-devm']";
      tailf:action transfer-pnpp {
        tailf:actionpoint ncsproxy {
          tailf:internal;
        }
        description
          "Transfer pnpp files.";
        input {
          leaf server-ip-address {
            type inet:ip-address-no-zone;
            mandatory true;
            description
              "FTP server IP address.";
          }
          leaf server-port {
            type uint32 {
              range "21..65535";
            }
            default "21";
            description
              "Server port.";
          }
          leaf vpn-instance-name {
            type string {
              length "1..128";
            }
            description
              "VPN instance name.";
          }
          leaf source-ipv4-address {
            type inet:ipv4-address-no-zone;
            description
              "Source IPv4 address.";
          }
          leaf source-interface-name {
            type pub-type:ncs_rpc_notif_if-name;
            description
              "Source interface name.";
          }
          leaf server-type {
            type ncs_rpc_notif_server-type;
            default "ftp";
            description
              "Server type.";
          }
          leaf command-type {
            type ncs_rpc_notif_trans-type;
            default "put";
            description
              "Transmission type.";
          }
          leaf user-name {
            type string {
              length "1..85";
            }
            mandatory true;
            description
              "User name.";
          }
          leaf password {
            type pub-type:ncs_rpc_notif_password;
            mandatory true;
            description
              "Password.";
          }
          leaf local-file-name {
            type string {
              length "1..128";
            }
            default "pnpp.7z";
            description
              "Local file name.";
          }
          leaf remote-file-name {
            type string {
              length "1..128";
            }
            description
              "File name on the FTP server.";
          }
          leaf remote-extension {
            type string {
              length "1..5";
            }
            default ".hw!";
            description
              "Temporary file name extension used for reliability.";
          }
          container secure-transfer-options {
            description
              "Transfer encryption options.";
            leaf prefer-kex {
              type ncs_rpc_notif_prefer-kex-type;
              description
                "Encryption algorithm.";
            }
            leaf prefer-stoc-cipher {
              type ncs_rpc_notif_cipher-type;
              description
                "Encryption algorithm for messages from a client to server.";
            }
            leaf prefer-ctos-cipher {
              type ncs_rpc_notif_cipher-type;
              description
                "Encryption algorithm for messages from a server to client.";
            }
            leaf prefer-stoc-hmac {
              type ncs_rpc_notif_stoc-hmac-type;
              description
                "Prefer Stoc Hmac.";
            }
            leaf prefer-ctos-hmac {
              type ncs_rpc_notif_stoc-hmac-type;
              description
                "Prefer Ctos Hmac.";
            }
            leaf keep-alive-interval {
              type uint32 {
                range "0..60";
              }
              default "0";
              description
                "Keepalive interval.";
            }
            leaf keep-alive-count {
              type uint32 {
                range "0..100";
              }
              default "0";
              description
                "Number of Keepalive packets.";
            }
          }
        }
      }
    }
  }
  augment "/ncs:devices/ncs:device/ncs:rpc" {
    container rpc-reboot {
      tailf:ncs-device-type "netconf";
      tailf:display-when "not(../../ncs:module) or ../../ncs:module[ncs:name='huawei-devm']";
      tailf:action reboot {
        tailf:actionpoint ncsproxy {
          tailf:internal;
        }
        description
          "Reboot.";
        input {
          leaf save-flag {
            type boolean;
            default "true";
            description
              "Flag indicating whether to save the configuration. True: save; False: not save.";
          }
        }
      }
    }
  }
  augment "/ncs:devices/ncs:device-group/ncs:ned-id/ncs:rpc" {
    container rpc-reboot {
      tailf:ncs-device-type "netconf";
      tailf:display-when "/ncs:devices/ncs:device[ncs:name=current()/../../../ncs:member]/ncs:module[ncs:name='huawei-devm']";
      tailf:action reboot {
        tailf:actionpoint ncsproxy {
          tailf:internal;
        }
        description
          "Reboot.";
        input {
          leaf save-flag {
            type boolean;
            default "true";
            description
              "Flag indicating whether to save the configuration. True: save; False: not save.";
          }
        }
      }
    }
  }
  augment "/ncs:devices/ncs:device/ncs:rpc" {
    container rpc-reset-card {
      tailf:ncs-device-type "netconf";
      tailf:display-when "not(../../ncs:module) or ../../ncs:module[ncs:name='huawei-devm']";
      tailf:action reset-card {
        tailf:actionpoint ncsproxy {
          tailf:internal;
        }
        description
          "Reset Card.";
        ext:node-ref "/devm/cards/card";
        input {
          leaf card-position {
            type string {
              length "1..32";
            }
            mandatory true;
            description
              "Card position.";
          }
        }
      }
    }
  }
  augment "/ncs:devices/ncs:device-group/ncs:ned-id/ncs:rpc" {
    container rpc-reset-card {
      tailf:ncs-device-type "netconf";
      tailf:display-when "/ncs:devices/ncs:device[ncs:name=current()/../../../ncs:member]/ncs:module[ncs:name='huawei-devm']";
      tailf:action reset-card {
        tailf:actionpoint ncsproxy {
          tailf:internal;
        }
        description
          "Reset Card.";
        ext:node-ref "/devm/cards/card";
        input {
          leaf card-position {
            type string {
              length "1..32";
            }
            mandatory true;
            description
              "Card position.";
          }
        }
      }
    }
  }
  augment "/ncs:devices/ncs:device/ncs:rpc" {
    container rpc-reset-sfu-board {
      tailf:ncs-device-type "netconf";
      tailf:display-when "not(../../ncs:module) or ../../ncs:module[ncs:name='huawei-devm']";
      tailf:action reset-sfu-board {
        tailf:actionpoint ncsproxy {
          tailf:internal;
        }
        description
          "Reset SFU.";
        ext:node-ref "/devm/sfu-boards/sfu-board";
        input {
          leaf board-position {
            type string {
              length "1..32";
            }
            mandatory true;
            description
              "Board position.";
          }
        }
      }
    }
  }
  augment "/ncs:devices/ncs:device-group/ncs:ned-id/ncs:rpc" {
    container rpc-reset-sfu-board {
      tailf:ncs-device-type "netconf";
      tailf:display-when "/ncs:devices/ncs:device[ncs:name=current()/../../../ncs:member]/ncs:module[ncs:name='huawei-devm']";
      tailf:action reset-sfu-board {
        tailf:actionpoint ncsproxy {
          tailf:internal;
        }
        description
          "Reset SFU.";
        ext:node-ref "/devm/sfu-boards/sfu-board";
        input {
          leaf board-position {
            type string {
              length "1..32";
            }
            mandatory true;
            description
              "Board position.";
          }
        }
      }
    }
  }
  augment "/ncs:devices/ncs:device/ncs:rpc" {
    container rpc-reset-lpu-board {
      tailf:ncs-device-type "netconf";
      tailf:display-when "not(../../ncs:module) or ../../ncs:module[ncs:name='huawei-devm']";
      tailf:action reset-lpu-board {
        tailf:actionpoint ncsproxy {
          tailf:internal;
        }
        description
          "Reset LPU.";
        ext:node-ref "/devm/lpu-boards/lpu-board";
        input {
          leaf board-position {
            type string {
              length "1..32";
            }
            mandatory true;
            description
              "Board position.";
          }
        }
      }
    }
  }
  augment "/ncs:devices/ncs:device-group/ncs:ned-id/ncs:rpc" {
    container rpc-reset-lpu-board {
      tailf:ncs-device-type "netconf";
      tailf:display-when "/ncs:devices/ncs:device[ncs:name=current()/../../../ncs:member]/ncs:module[ncs:name='huawei-devm']";
      tailf:action reset-lpu-board {
        tailf:actionpoint ncsproxy {
          tailf:internal;
        }
        description
          "Reset LPU.";
        ext:node-ref "/devm/lpu-boards/lpu-board";
        input {
          leaf board-position {
            type string {
              length "1..32";
            }
            mandatory true;
            description
              "Board position.";
          }
        }
      }
    }
  }
  augment "/ncs:devices/ncs:device/ncs:rpc" {
    container rpc-reset-mpu-board {
      tailf:ncs-device-type "netconf";
      tailf:display-when "not(../../ncs:module) or ../../ncs:module[ncs:name='huawei-devm']";
      tailf:action reset-mpu-board {
        tailf:actionpoint ncsproxy {
          tailf:internal;
        }
        description
          "Reset MPU.";
        ext:node-ref "/devm/mpu-boards/mpu-board";
        input {
          leaf board-position {
            type string {
              length "1..32";
            }
            mandatory true;
            description
              "Board position.";
          }
        }
      }
    }
  }
  augment "/ncs:devices/ncs:device-group/ncs:ned-id/ncs:rpc" {
    container rpc-reset-mpu-board {
      tailf:ncs-device-type "netconf";
      tailf:display-when "/ncs:devices/ncs:device[ncs:name=current()/../../../ncs:member]/ncs:module[ncs:name='huawei-devm']";
      tailf:action reset-mpu-board {
        tailf:actionpoint ncsproxy {
          tailf:internal;
        }
        description
          "Reset MPU.";
        ext:node-ref "/devm/mpu-boards/mpu-board";
        input {
          leaf board-position {
            type string {
              length "1..32";
            }
            mandatory true;
            description
              "Board position.";
          }
        }
      }
    }
  }
  augment "/ncs:devices/ncs:device/ncs:rpc" {
    container rpc-reset-board {
      tailf:ncs-device-type "netconf";
      tailf:display-when "not(../../ncs:module) or ../../ncs:module[ncs:name='huawei-devm']";
      tailf:action reset-board {
        tailf:actionpoint ncsproxy {
          tailf:internal;
        }
        description
          "Reset board.";
        input {
          leaf board-position {
            type string {
              length "1..32";
            }
            mandatory true;
            description
              "Board position.";
          }
        }
      }
    }
  }
  augment "/ncs:devices/ncs:device-group/ncs:ned-id/ncs:rpc" {
    container rpc-reset-board {
      tailf:ncs-device-type "netconf";
      tailf:display-when "/ncs:devices/ncs:device[ncs:name=current()/../../../ncs:member]/ncs:module[ncs:name='huawei-devm']";
      tailf:action reset-board {
        tailf:actionpoint ncsproxy {
          tailf:internal;
        }
        description
          "Reset board.";
        input {
          leaf board-position {
            type string {
              length "1..32";
            }
            mandatory true;
            description
              "Board position.";
          }
        }
      }
    }
  }
}
