module huawei-bras-pwve-access {
  // Generated by yanger -t ncs
  tailf:mount-id "huawei-nc-1.0:huawei-nc-1.0";
  tailf:ncs-device-type "netconf";

  namespace "urn:huawei:yang:huawei-bras-pwve-access";
  prefix bras-pwve-access;

  import huawei-ifm {
    prefix ifm;
  }
  import huawei-bras-cu-agent {
    prefix bras-cu-agent;
  }
  import huawei-extension {
    prefix ext;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Bras PWVE access.";

  revision 2019-11-16 {
    description
      "Initial revision.";
    reference "Huawei private.";
  }
  ext:task-name "bras-control";

  augment "/ncs:devices/ncs:device/ncs:config" {
    container bras-pwve-access {
      tailf:ncs-device-type "netconf";
      tailf:display-when "not(../../ncs:module) or ../../ncs:module[ncs:name='huawei-bras-pwve-access']";
      description
        "Bras PWVE access.";
      container location-groups {
        description
          "List of the location group.";
        list location-group {
          must '/bras-cu-agent:bras-cu-agent/bras-cu-agent:cu-agent' {
            tailf:xpath-root 3;
          }
          key "name";
          max-elements 256;
          description
            "Configure the location group.";
          leaf name {
            type string {
              length "1..63";
            }
            description
              "The specify name of location group.";
          }
          container interfaces {
            description
              "List of the specify interface.";
            list interface {
              key "name";
              max-elements 32;
              description
                "Configure the specify interface.";
              leaf name {
                type leafref {
                  path "/ncs:devices/ncs:device/ncs:config/ifm:ifm/ifm:interfaces/ifm:interface/ifm:name" {
                    tailf:xpath-root 3;
                  }
                }
                must "/ifm:ifm/ifm:interfaces/ifm:interface[ifm:name=current()]/ifm:type='GigabitEthernet' or
/ifm:ifm/ifm:interfaces/ifm:interface[ifm:name=current()]/ifm:type='10GE' or
/ifm:ifm/ifm:interfaces/ifm:interface[ifm:name=current()]/ifm:type='40GE' or
/ifm:ifm/ifm:interfaces/ifm:interface[ifm:name=current()]/ifm:type='100GE' or
/ifm:ifm/ifm:interfaces/ifm:interface[ifm:name=current()]/ifm:type='25GE' or
/ifm:ifm/ifm:interfaces/ifm:interface[ifm:name=current()]/ifm:type='50GE' or
/ifm:ifm/ifm:interfaces/ifm:interface[ifm:name=current()]/ifm:type='50|100GE'" {
                  tailf:xpath-root 3;
                }
                must "/ifm:ifm/ifm:interfaces/ifm:interface[ifm:name=current()]/ifm:class='main-interface'" {
                  tailf:xpath-root 3;
                }
                description
                  "The specify name of interface.";
              }
            }
          }
        }
      }
    }
  }
  augment "/ncs:devices/ncs:device/ncs:live-status" {
    container bras-pwve-access {
      tailf:ncs-device-type "netconf";
      tailf:display-when "not(../../ncs:module) or ../../ncs:module[ncs:name='huawei-bras-pwve-access'] or (../../ncs:live-status-protocol[not(ncs:capability)]) or (../../ncs:live-status-protocol/ncs:capability/ncs:module[.='huawei-bras-pwve-access'])";
      description
        "Bras PWVE access.";
      container location-groups {
        description
          "List of the location group.";
        list location-group {
          // NCS drop must statement
          key "name";
          // NCS drop max-elements statement
          description
            "Configure the location group.";
          leaf name {
            type string {
              length "1..63";
            }
            description
              "The specify name of location group.";
          }
          container interfaces {
            description
              "List of the specify interface.";
            list interface {
              key "name";
              // NCS drop max-elements statement
              description
                "Configure the specify interface.";
              leaf name {
                type leafref {
                  path "/ncs:devices/ncs:device/ncs:live-status/ifm:ifm/ifm:interfaces/ifm:interface/ifm:name" {
                    tailf:xpath-root 3;
                  }
                }
                // NCS drop must statement
                // NCS drop must statement
                description
                  "The specify name of interface.";
              }
            }
          }
        }
      }
    }
  }
  augment "/ncs:devices/ncs:template/ncs:ned-id/ncs:config" {
    container bras-pwve-access {
      description
        "Bras PWVE access.";
      container location-groups {
        description
          "List of the location group.";
        list location-group {
          // NCS patched for predictable order
          ordered-by user;
          // NCS drop must statement
          key "name";
          // NCS drop max-elements statement
          description
            "Configure the location group.";
          leaf name {
            type string;
            description
              "The specify name of location group.";
          }
          container interfaces {
            description
              "List of the specify interface.";
            list interface {
              // NCS patched for predictable order
              ordered-by user;
              key "name";
              // NCS drop max-elements statement
              description
                "Configure the specify interface.";
              leaf name {
                type string;
                // NCS drop must statement
                // NCS drop must statement
                description
                  "The specify name of interface.";
              }
            }
          }
        }
      }
    }
  }
  augment "/ncs:devices/ncs:template/ncs:ned-id/ncs:config/ifm:ifm/ifm:interfaces/ifm:interface" {
    description
      "Configure PWVE access to interface model.";
    container pwve-access {
      description
        "Configure PWVE access to interface model.";
      container pwve-interface {
        // NCS drop when statement
        description
          "Configure PWVE interface.";
        container push-vlan-tag {
          description
            "Configure user VLAN tags.";
          leaf pe-vid {
            type string;
            description
              "Configure PE VLAN ID.";
          }
          leaf ce-vid {
            // NCS drop when statement
            type string;
            description
              "Configure CE VLAN ID.";
          }
        }
        container bind-location-group {
          description
            "Configure the name of location group.";
          leaf name {
            type string;
            description
              "Specify the name of location group.";
          }
        }
      }
    }
  }
  augment "/ncs:devices/ncs:device/ncs:live-status/ifm:ifm/ifm:interfaces/ifm:interface" {
    description
      "Configure PWVE access to interface model.";
    container pwve-access {
      tailf:ncs-device-type "netconf";
      tailf:display-when "not(../../../../../ncs:module) or ../../../../../ncs:module[ncs:name='huawei-bras-pwve-access'] or (../../../../../ncs:live-status-protocol[not(ncs:capability)]) or (../../../../../ncs:live-status-protocol/ncs:capability/ncs:module[.='huawei-bras-pwve-access'])";
      description
        "Configure PWVE access to interface model.";
      container pwve-interface {
        // NCS drop when statement
        description
          "Configure PWVE interface.";
        container push-vlan-tag {
          description
            "Configure user VLAN tags.";
          leaf pe-vid {
            type uint16 {
              range "1..4094";
            }
            description
              "Configure PE VLAN ID.";
          }
          leaf ce-vid {
            // NCS drop when statement
            type uint16 {
              range "1..4094";
            }
            description
              "Configure CE VLAN ID.";
          }
        }
        container bind-location-group {
          description
            "Configure the name of location group.";
          leaf name {
            type leafref {
              path "/ncs:devices/ncs:device/ncs:live-status/bras-pwve-access:bras-pwve-access/bras-pwve-access:location-groups/bras-pwve-access:location-group/bras-pwve-access:name" {
                tailf:xpath-root 3;
              }
            }
            description
              "Specify the name of location group.";
          }
        }
      }
    }
  }
  augment "/ncs:devices/ncs:device/ncs:config/ifm:ifm/ifm:interfaces/ifm:interface" {
    description
      "Configure PWVE access to interface model.";
    container pwve-access {
      tailf:ncs-device-type "netconf";
      tailf:display-when "not(../../../../../ncs:module) or ../../../../../ncs:module[ncs:name='huawei-bras-pwve-access']";
      description
        "Configure PWVE access to interface model.";
      container pwve-interface {
        when "../../ifm:type = 'PW-VE'" {
          tailf:xpath-root 3;
        }
        description
          "Configure PWVE interface.";
        container push-vlan-tag {
          description
            "Configure user VLAN tags.";
          leaf pe-vid {
            type uint16 {
              range "1..4094";
            }
            description
              "Configure PE VLAN ID.";
          }
          leaf ce-vid {
            when '../pe-vid' {
              tailf:xpath-root 3;
            }
            type uint16 {
              range "1..4094";
            }
            description
              "Configure CE VLAN ID.";
          }
        }
        container bind-location-group {
          description
            "Configure the name of location group.";
          leaf name {
            type leafref {
              path "/ncs:devices/ncs:device/ncs:config/bras-pwve-access:bras-pwve-access/bras-pwve-access:location-groups/bras-pwve-access:location-group/bras-pwve-access:name" {
                tailf:xpath-root 3;
              }
            }
            description
              "Specify the name of location group.";
          }
        }
      }
    }
  }
}
