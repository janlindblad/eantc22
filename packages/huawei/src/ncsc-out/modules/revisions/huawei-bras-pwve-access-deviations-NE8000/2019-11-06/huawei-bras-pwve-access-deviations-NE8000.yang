module huawei-bras-pwve-access-deviations-NE8000 {
  // Generated by yanger -t ncs
  tailf:mount-id "huawei-nc-1.0:huawei-nc-1.0";
  tailf:ncs-device-type "netconf";

  namespace "urn:huawei:yang:huawei-bras-pwve-access-deviations-NE8000";
  prefix bras-pwve-access-devs-NE8000;

  import huawei-bras-pwve-access {
    prefix bras-pwve-access;
  }
  import huawei-ifm {
    prefix ifm;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "This module defines deviation statements for huawei-bras-pwve-access module.";

  revision 2019-11-06 {
    description
      "Initial revision.";
    reference "Huawei private.";
  }

  deviation "/ncs:devices/ncs:template/ncs:ned-id/ncs:config/ifm:ifm/ifm:interfaces/ifm:interface/bras-pwve-access:pwve-access/bras-pwve-access:pwve-interface/bras-pwve-access:push-vlan-tag" {
    deviate not-supported;
  }
  deviation "/ncs:devices/ncs:device/ncs:live-status/ifm:ifm/ifm:interfaces/ifm:interface/bras-pwve-access:pwve-access/bras-pwve-access:pwve-interface/bras-pwve-access:push-vlan-tag" {
    deviate not-supported;
  }
  deviation "/ncs:devices/ncs:device/ncs:config/ifm:ifm/ifm:interfaces/ifm:interface/bras-pwve-access:pwve-access/bras-pwve-access:pwve-interface/bras-pwve-access:push-vlan-tag" {
    deviate not-supported;
  }
}
