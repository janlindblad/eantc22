module huawei-lmp {
  // Generated by yanger -t ncs
  tailf:mount-id "huawei-nc-1.0:huawei-nc-1.0";
  tailf:ncs-device-type "netconf";

  yang-version 1;
  namespace "urn:huawei:yang:huawei-lmp";
  prefix lmp;

  import huawei-extension {
    prefix ext;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Link management protocol.";

  revision 2019-09-21 {
    description
      "Initial revision.";
    reference "Huawei private.";
  }
  ext:task-name "lmp";

  typedef ncs_template_neighbor-mode {
    type string;
    description
      "The LMP neighbor mode.";
  }

  typedef ncs_template_link-state {
    type string;
    description
      "The link state.";
  }

  typedef ncs_template_encode-type {
    type string;
    description
      "The data link encode type.";
  }

  typedef ncs_rpc_notif_neighbor-mode {
    type enumeration {
      enum "none" {
        value 0;
        description
          "None mode.";
      }
      enum "static" {
        value 1;
        description
          "Static mode.";
      }
    }
    description
      "The LMP neighbor mode.";
  }

  typedef ncs_rpc_notif_link-state {
    type enumeration {
      enum "up" {
        value 0;
        description
          "State up.";
      }
      enum "down" {
        value 1;
        description
          "State down.";
      }
    }
    description
      "The link state.";
  }

  typedef ncs_rpc_notif_encode-type {
    type enumeration {
      enum "ethernet" {
        value 2;
        description
          "Ethernet.";
      }
    }
    description
      "The data link encode type.";
  }

  typedef live_ncs_neighbor-mode {
    type enumeration {
      enum "none" {
        value 0;
        description
          "None mode.";
      }
      enum "static" {
        value 1;
        description
          "Static mode.";
      }
    }
    description
      "The LMP neighbor mode.";
  }

  typedef live_ncs_link-state {
    type enumeration {
      enum "up" {
        value 0;
        description
          "State up.";
      }
      enum "down" {
        value 1;
        description
          "State down.";
      }
    }
    description
      "The link state.";
  }

  typedef live_ncs_encode-type {
    type enumeration {
      enum "ethernet" {
        value 2;
        description
          "Ethernet.";
      }
    }
    description
      "The data link encode type.";
  }

  typedef neighbor-mode {
    type enumeration {
      enum "none" {
        value 0;
        description
          "None mode.";
      }
      enum "static" {
        value 1;
        description
          "Static mode.";
      }
    }
    description
      "The LMP neighbor mode.";
  }

  typedef link-state {
    type enumeration {
      enum "up" {
        value 0;
        description
          "State up.";
      }
      enum "down" {
        value 1;
        description
          "State down.";
      }
    }
    description
      "The link state.";
  }

  typedef encode-type {
    type enumeration {
      enum "ethernet" {
        value 2;
        description
          "Ethernet.";
      }
    }
    description
      "The data link encode type.";
  }

  augment "/ncs:devices/ncs:device/ncs:config" {
    container lmp {
      tailf:ncs-device-type "netconf";
      tailf:display-when "not(../../ncs:module) or ../../ncs:module[ncs:name='huawei-lmp']";
      description
        "Configure link management protocol.";
      container global {
        description
          "Configure LMP global attributes.";
        leaf enable {
          type boolean;
          default "false";
          description
            "Enable/disable LMP.";
        }
      }
      container neighbors {
        when "../global/enable='true'" {
          tailf:xpath-root 3;
        }
        description
          "List of LMP peers.";
        list neighbor {
          key "name";
          max-elements 255;
          description
            "Configure LMP operations on devices. It lists a series of LMP operation entries.";
          leaf name {
            type string {
              length "1..32";
              pattern "[a-zA-Z][^?'\"|<>]{0,}";
            }
            description
              "LMP peer name.";
          }
          leaf mode {
            type neighbor-mode;
            default "none";
            description
              "LMP peer type.";
          }
        }
      }
    }
  }
  augment "/ncs:devices/ncs:device/ncs:live-status" {
    container lmp {
      tailf:ncs-device-type "netconf";
      tailf:display-when "not(../../ncs:module) or ../../ncs:module[ncs:name='huawei-lmp'] or (../../ncs:live-status-protocol[not(ncs:capability)]) or (../../ncs:live-status-protocol/ncs:capability/ncs:module[.='huawei-lmp'])";
      description
        "Configure link management protocol.";
      container global {
        description
          "Configure LMP global attributes.";
        leaf enable {
          type boolean;
          // NCS drop default statement
          description
            "Enable/disable LMP.";
        }
      }
      container neighbors {
        // NCS drop when statement
        description
          "List of LMP peers.";
        list neighbor {
          key "name";
          // NCS drop max-elements statement
          description
            "Configure LMP operations on devices. It lists a series of LMP operation entries.";
          leaf name {
            type string {
              length "1..32";
              pattern "[a-zA-Z][^?'\"|<>]{0,}";
            }
            description
              "LMP peer name.";
          }
          leaf mode {
            type live_ncs_neighbor-mode;
            // NCS drop default statement
            description
              "LMP peer type.";
          }
        }
      }
    }
  }
  augment "/ncs:devices/ncs:template/ncs:ned-id/ncs:config" {
    container lmp {
      description
        "Configure link management protocol.";
      container global {
        description
          "Configure LMP global attributes.";
        leaf enable {
          type string;
          // NCS drop default statement
          description
            "Enable/disable LMP.";
        }
      }
      container neighbors {
        // NCS drop when statement
        description
          "List of LMP peers.";
        list neighbor {
          // NCS patched for predictable order
          ordered-by user;
          key "name";
          // NCS drop max-elements statement
          description
            "Configure LMP operations on devices. It lists a series of LMP operation entries.";
          leaf name {
            type string;
            description
              "LMP peer name.";
          }
          leaf mode {
            type ncs_template_neighbor-mode;
            // NCS drop default statement
            description
              "LMP peer type.";
          }
        }
      }
    }
  }
}
