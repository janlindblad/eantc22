module huawei-devm-deviations-NE8000 {
  // Generated by yanger -t ncs
  tailf:mount-id "huawei-nc-1.0:huawei-nc-1.0";
  tailf:ncs-device-type "netconf";

  namespace "urn:huawei:yang:huawei-devm-deviations-NE8000";
  prefix devm-devs-NE8000;

  import huawei-devm {
    prefix devm;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Global Configuration.";

  revision 2019-04-03 {
    description
      "Initial revision.";
    reference "Huawei private.";
  }

  deviation "/ncs:devices/ncs:template/ncs:ned-id/ncs:config/devm:devm/devm:logic-entitys" {
    deviate not-supported;
  }
  deviation "/ncs:devices/ncs:device/ncs:live-status/devm:devm/devm:logic-entitys" {
    deviate not-supported;
  }
  deviation "/ncs:devices/ncs:device/ncs:config/devm:devm/devm:logic-entitys" {
    deviate not-supported;
  }
  deviation "/ncs:devices/ncs:device/ncs:live-status/devm:devm/devm:ports/devm:port/devm:hard-type" {
    deviate replace {
      type string {
        length "1..32";
      }
    }
  }
  deviation "/ncs:devices/ncs:device/ncs:live-status/devm:devm/devm:logic-containers" {
    deviate not-supported;
  }
  deviation "/ncs:devices/ncs:template/ncs:ned-id/ncs:config/devm:devm/devm:logic-ports" {
    deviate not-supported;
  }
  deviation "/ncs:devices/ncs:device/ncs:live-status/devm:devm/devm:logic-ports" {
    deviate not-supported;
  }
  deviation "/ncs:devices/ncs:device/ncs:config/devm:devm/devm:logic-ports" {
    deviate not-supported;
  }
  deviation "/ncs:devices/ncs:device/ncs:live-status/devm:devm/devm:inconsistent-entitys" {
    deviate not-supported;
  }
  deviation "/ncs:devices/ncs:device/ncs:live-status/devm:devm/devm:containers/devm:container/devm:supported-entity-types" {
    deviate not-supported;
  }
  deviation "/ncs:devices/ncs:template/ncs:ned-id/ncs:config/devm:devm/devm:lpu-boards/devm:lpu-board/devm:clock-8k-port" {
    deviate not-supported;
  }
  deviation "/ncs:devices/ncs:device/ncs:live-status/devm:devm/devm:lpu-boards/devm:lpu-board/devm:clock-8k-port" {
    deviate not-supported;
  }
  deviation "/ncs:devices/ncs:device/ncs:config/devm:devm/devm:lpu-boards/devm:lpu-board/devm:clock-8k-port" {
    deviate not-supported;
  }
  deviation "/ncs:devices/ncs:device/ncs:rpc/devm:rpc-cold-reset-lpu/devm:cold-reset-lpu" {
    deviate not-supported;
  }
  deviation "/ncs:devices/ncs:device/ncs:rpc/devm:rpc-warm-reset-lpu/devm:warm-reset-lpu" {
    deviate not-supported;
  }
  deviation "/ncs:devices/ncs:device/ncs:rpc/devm:rpc-cold-reset-mpu/devm:cold-reset-mpu" {
    deviate not-supported;
  }
  deviation "/ncs:devices/ncs:device/ncs:rpc/devm:rpc-warm-reset-mpu/devm:warm-reset-mpu" {
    deviate not-supported;
  }
  deviation "/ncs:devices/ncs:device/ncs:rpc/devm:rpc-reset-offline-config/devm:reset-offline-config" {
    deviate not-supported;
  }
  deviation "/ncs:devices/ncs:device/ncs:rpc/devm:rpc-transfer-pnpp/devm:transfer-pnpp" {
    deviate not-supported;
  }
}
