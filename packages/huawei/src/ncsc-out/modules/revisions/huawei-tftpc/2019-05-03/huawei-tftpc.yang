module huawei-tftpc {
  // Generated by yanger -t ncs
  tailf:mount-id "huawei-nc-1.0:huawei-nc-1.0";
  tailf:ncs-device-type "netconf";

  namespace "urn:huawei:yang:huawei-tftpc";
  prefix tftpc;

  import huawei-pub-type {
    prefix pub-type;
  }
  import ietf-inet-types {
    prefix inet;
  }
  import huawei-extension {
    prefix ext;
  }
  import huawei-acl {
    prefix acl;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Trivial file transfer protocol (TFTP) client.";

  revision 2019-05-03 {
    description
      "Initial revision.";
    reference "Huawei private.";
  }
  ext:task-name "tftp-client";

  typedef ncs_template_trans-cmd-type {
    type string;
    description
      "TFTP client transfer command type.";
  }

  typedef ncs_rpc_notif_trans-cmd-type {
    type enumeration {
      enum "put" {
        value 2;
        description
          "Upload the local file to the remote server.";
      }
      enum "get" {
        value 1;
        description
          "Download a file from the remote server to the client.";
      }
    }
    description
      "TFTP client transfer command type.";
  }

  typedef live_ncs_trans-cmd-type {
    type enumeration {
      enum "put" {
        value 2;
        description
          "Upload the local file to the remote server.";
      }
      enum "get" {
        value 1;
        description
          "Download a file from the remote server to the client.";
      }
    }
    description
      "TFTP client transfer command type.";
  }

  typedef trans-cmd-type {
    type enumeration {
      enum "put" {
        value 2;
        description
          "Upload the local file to the remote server.";
      }
      enum "get" {
        value 1;
        description
          "Download a file from the remote server to the client.";
      }
    }
    description
      "TFTP client transfer command type.";
  }

  augment "/ncs:devices/ncs:device/ncs:rpc" {
    container rpc-tftpc-transfer-file {
      tailf:ncs-device-type "netconf";
      tailf:display-when "not(../../ncs:module) or ../../ncs:module[ncs:name='huawei-tftpc']";
      tailf:action tftpc-transfer-file {
        tailf:actionpoint ncsproxy {
          tailf:internal;
        }
        description
          "TFTP client file transfer.";
        input {
          leaf source-ipv4-address {
            type inet:ipv4-address-no-zone;
            must '../server-ipv4-address' {
              tailf:xpath-root 3;
            }
            description
              "Specify the source IPv4 address to transfer files.";
          }
          leaf server-ipv4-address {
            type string {
              length "1..255";
            }
            must 'not(../server-ipv6-address)' {
              tailf:xpath-root 3;
            }
            description
              "Specify the server IPv4 address or server hostname for file transfer.";
          }
          leaf source-ipv6-address {
            type inet:ipv6-address-no-zone;
            must '../server-ipv6-address' {
              tailf:xpath-root 3;
            }
            description
              "Specify the source IPv4 address to transfer files.";
          }
          leaf server-ipv6-address {
            type string {
              length "1..255";
            }
            description
              "Specify the server IPv6 address or server hostname for file transfer.";
          }
          leaf local-file-name {
            type string {
              length "1..128";
            }
            description
              "Specify the local file name for transfer.";
          }
          leaf remote-file-name {
            type string {
              length "1..128";
            }
            description
              "Specify the remote file name. The server uses the file to store received data.";
          }
          leaf command-type {
            type ncs_rpc_notif_trans-cmd-type;
            description
              "Specify the type of the operation to be performed.";
          }
          leaf vpn-name {
            type string {
              length "1..31";
            }
            must '(../server-ipv4-address) and not(../public-net) and not(../source-interface-name)' {
              tailf:xpath-root 3;
            }
            description
              "Specify the VPN instance name for connection to the server.";
          }
          leaf ipv6-vpn-name {
            type string {
              length "1..31";
            }
            must '(../server-ipv6-address) and not(../public-net) and not(../source-interface-name)' {
              tailf:xpath-root 3;
            }
            description
              "Specify the IPv6 VPN instance name for connection to the server.";
          }
          leaf public-net {
            type boolean;
            description
              "Using public net or not.";
          }
          leaf source-interface-name {
            type pub-type:ncs_rpc_notif_if-name;
            must 'not(../public-net)' {
              tailf:xpath-root 3;
            }
            description
              "Specify the source interface name for file transfer.";
          }
        }
      }
    }
  }
  augment "/ncs:devices/ncs:device-group/ncs:ned-id/ncs:rpc" {
    container rpc-tftpc-transfer-file {
      tailf:ncs-device-type "netconf";
      tailf:display-when "/ncs:devices/ncs:device[ncs:name=current()/../../../ncs:member]/ncs:module[ncs:name='huawei-tftpc']";
      tailf:action tftpc-transfer-file {
        tailf:actionpoint ncsproxy {
          tailf:internal;
        }
        description
          "TFTP client file transfer.";
        input {
          leaf source-ipv4-address {
            type inet:ipv4-address-no-zone;
            must '../server-ipv4-address' {
              tailf:xpath-root 4;
            }
            description
              "Specify the source IPv4 address to transfer files.";
          }
          leaf server-ipv4-address {
            type string {
              length "1..255";
            }
            must 'not(../server-ipv6-address)' {
              tailf:xpath-root 4;
            }
            description
              "Specify the server IPv4 address or server hostname for file transfer.";
          }
          leaf source-ipv6-address {
            type inet:ipv6-address-no-zone;
            must '../server-ipv6-address' {
              tailf:xpath-root 4;
            }
            description
              "Specify the source IPv4 address to transfer files.";
          }
          leaf server-ipv6-address {
            type string {
              length "1..255";
            }
            description
              "Specify the server IPv6 address or server hostname for file transfer.";
          }
          leaf local-file-name {
            type string {
              length "1..128";
            }
            description
              "Specify the local file name for transfer.";
          }
          leaf remote-file-name {
            type string {
              length "1..128";
            }
            description
              "Specify the remote file name. The server uses the file to store received data.";
          }
          leaf command-type {
            type ncs_rpc_notif_trans-cmd-type;
            description
              "Specify the type of the operation to be performed.";
          }
          leaf vpn-name {
            type string {
              length "1..31";
            }
            must '(../server-ipv4-address) and not(../public-net) and not(../source-interface-name)' {
              tailf:xpath-root 4;
            }
            description
              "Specify the VPN instance name for connection to the server.";
          }
          leaf ipv6-vpn-name {
            type string {
              length "1..31";
            }
            must '(../server-ipv6-address) and not(../public-net) and not(../source-interface-name)' {
              tailf:xpath-root 4;
            }
            description
              "Specify the IPv6 VPN instance name for connection to the server.";
          }
          leaf public-net {
            type boolean;
            description
              "Using public net or not.";
          }
          leaf source-interface-name {
            type pub-type:ncs_rpc_notif_if-name;
            must 'not(../public-net)' {
              tailf:xpath-root 4;
            }
            description
              "Specify the source interface name for file transfer.";
          }
        }
      }
    }
  }
  augment "/ncs:devices/ncs:device/ncs:config" {
    container tftpc {
      tailf:ncs-device-type "netconf";
      tailf:display-when "not(../../ncs:module) or ../../ncs:module[ncs:name='huawei-tftpc']";
      description
        "Trivial file transfer protocol (TFTP) client.";
      container client {
        description
          "Configure TFTP client configuration table.";
        leaf src-ipv4-addr {
          when 'not(../src-interface)' {
            tailf:xpath-root 3;
          }
          type inet:ipv4-address-no-zone;
          description
            "Specify the source IPv4 address.";
        }
        leaf src-interface {
          type pub-type:if-name;
          description
            "Specify the source interface name. The specified source interface must exist and an IP address must be configured on the interface.";
        }
        leaf ipv4-acl {
          type leafref {
            path "/ncs:devices/ncs:device/ncs:config/acl:acl/acl:groups/acl:group/acl:identity" {
              tailf:xpath-root 3;
            }
          }
          must "/acl:acl/acl:groups/acl:group[acl:identity=current()]/acl:type='basic'" {
            tailf:xpath-root 3;
          }
          description
            "Specify the IPv4 ACL number.";
        }
        leaf ipv6-acl {
          type leafref {
            path "/ncs:devices/ncs:device/ncs:config/acl:acl/acl:group6s/acl:group6/acl:identity" {
              tailf:xpath-root 3;
            }
          }
          must "/acl:acl/acl:group6s/acl:group6[acl:identity=current()]/acl:type='basic'" {
            tailf:xpath-root 3;
          }
          description
            "Specify the IPv6 ACL number.";
        }
      }
    }
  }
  augment "/ncs:devices/ncs:device/ncs:live-status" {
    container tftpc {
      tailf:ncs-device-type "netconf";
      tailf:display-when "not(../../ncs:module) or ../../ncs:module[ncs:name='huawei-tftpc'] or (../../ncs:live-status-protocol[not(ncs:capability)]) or (../../ncs:live-status-protocol/ncs:capability/ncs:module[.='huawei-tftpc'])";
      description
        "Trivial file transfer protocol (TFTP) client.";
      container client {
        description
          "Configure TFTP client configuration table.";
        leaf src-ipv4-addr {
          // NCS drop when statement
          type inet:ipv4-address-no-zone;
          description
            "Specify the source IPv4 address.";
        }
        leaf src-interface {
          type pub-type:live_ncs_if-name;
          description
            "Specify the source interface name. The specified source interface must exist and an IP address must be configured on the interface.";
        }
        leaf ipv4-acl {
          type leafref {
            path "/ncs:devices/ncs:device/ncs:live-status/acl:acl/acl:groups/acl:group/acl:identity" {
              tailf:xpath-root 3;
            }
          }
          // NCS drop must statement
          description
            "Specify the IPv4 ACL number.";
        }
        leaf ipv6-acl {
          type leafref {
            path "/ncs:devices/ncs:device/ncs:live-status/acl:acl/acl:group6s/acl:group6/acl:identity" {
              tailf:xpath-root 3;
            }
          }
          // NCS drop must statement
          description
            "Specify the IPv6 ACL number.";
        }
      }
    }
  }
  augment "/ncs:devices/ncs:template/ncs:ned-id/ncs:config" {
    container tftpc {
      description
        "Trivial file transfer protocol (TFTP) client.";
      container client {
        description
          "Configure TFTP client configuration table.";
        leaf src-ipv4-addr {
          // NCS drop when statement
          type string;
          description
            "Specify the source IPv4 address.";
        }
        leaf src-interface {
          type pub-type:ncs_template_if-name;
          description
            "Specify the source interface name. The specified source interface must exist and an IP address must be configured on the interface.";
        }
        leaf ipv4-acl {
          type string;
          // NCS drop must statement
          description
            "Specify the IPv4 ACL number.";
        }
        leaf ipv6-acl {
          type string;
          // NCS drop must statement
          description
            "Specify the IPv6 ACL number.";
        }
      }
    }
  }
}
