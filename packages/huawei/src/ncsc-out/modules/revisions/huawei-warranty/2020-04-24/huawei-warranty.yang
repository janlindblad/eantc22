module huawei-warranty {
  // Generated by yanger -t ncs
  tailf:mount-id "huawei-nc-1.0:huawei-nc-1.0";
  tailf:ncs-device-type "netconf";

  namespace "urn:huawei:yang:huawei-warranty";
  prefix warranty;

  import huawei-pub-type {
    prefix pub-type;
  }
  import huawei-extension {
    prefix ext;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Electronic warranty management module.";

  revision 2020-04-24 {
    description
      "Init revision.";
    reference "Huawei private.";
  }
  ext:task-name "warranty";

  typedef ncs_template_warranty-status {
    type string;
    description
      "Warranty status.";
  }

  typedef ncs_template_unit-type {
    type string;
    description
      "Unit type.";
  }

  typedef ncs_rpc_notif_warranty-status {
    type enumeration {
      enum "normal" {
        value 1;
        description
          "Normal.";
      }
      enum "to-be-expired" {
        value 2;
        description
          "To be expired.";
      }
      enum "expired" {
        value 3;
        description
          "Expired.";
      }
    }
    description
      "Warranty status.";
  }

  typedef ncs_rpc_notif_unit-type {
    type enumeration {
      enum "device" {
        value 1;
        description
          "Device.";
      }
      enum "board" {
        value 2;
        description
          "Board.";
      }
      enum "card" {
        value 3;
        description
          "Card.";
      }
    }
    description
      "Unit type.";
  }

  typedef live_ncs_warranty-status {
    type enumeration {
      enum "normal" {
        value 1;
        description
          "Normal.";
      }
      enum "to-be-expired" {
        value 2;
        description
          "To be expired.";
      }
      enum "expired" {
        value 3;
        description
          "Expired.";
      }
    }
    description
      "Warranty status.";
  }

  typedef live_ncs_unit-type {
    type enumeration {
      enum "device" {
        value 1;
        description
          "Device.";
      }
      enum "board" {
        value 2;
        description
          "Board.";
      }
      enum "card" {
        value 3;
        description
          "Card.";
      }
    }
    description
      "Unit type.";
  }

  typedef warranty-status {
    type enumeration {
      enum "normal" {
        value 1;
        description
          "Normal.";
      }
      enum "to-be-expired" {
        value 2;
        description
          "To be expired.";
      }
      enum "expired" {
        value 3;
        description
          "Expired.";
      }
    }
    description
      "Warranty status.";
  }

  typedef unit-type {
    type enumeration {
      enum "device" {
        value 1;
        description
          "Device.";
      }
      enum "board" {
        value 2;
        description
          "Board.";
      }
      enum "card" {
        value 3;
        description
          "Card.";
      }
    }
    description
      "Unit type.";
  }

  augment "/ncs:devices/ncs:device/ncs:rpc" {
    container rpc-activate-warranty {
      tailf:ncs-device-type "netconf";
      tailf:display-when "not(../../ncs:module) or ../../ncs:module[ncs:name='huawei-warranty']";
      tailf:action activate-warranty {
        tailf:actionpoint ncsproxy {
          tailf:internal;
        }
        description
          "Activate the electronic warranty on a device.";
        input {
          container warrantys {
            description
              "List of information about electronic warranty.";
            list warranty {
              key "serial-number";
              description
                "The list of warranty information to be activated.";
              leaf serial-number {
                type string {
                  length "1..100";
                }
                mandatory true;
                description
                  "Serial number of the electronic warranty.";
              }
              leaf start-date {
                type pub-type:ncs_rpc_notif_date;
                description
                  "Starting date for the electronic warranty.";
              }
              leaf life-span {
                type uint32 {
                  range "1..600";
                }
                units "month";
                description
                  "Life span for the electronic warranty.";
              }
            }
          }
        }
      }
    }
  }
  augment "/ncs:devices/ncs:device-group/ncs:ned-id/ncs:rpc" {
    container rpc-activate-warranty {
      tailf:ncs-device-type "netconf";
      tailf:display-when "/ncs:devices/ncs:device[ncs:name=current()/../../../ncs:member]/ncs:module[ncs:name='huawei-warranty']";
      tailf:action activate-warranty {
        tailf:actionpoint ncsproxy {
          tailf:internal;
        }
        description
          "Activate the electronic warranty on a device.";
        input {
          container warrantys {
            description
              "List of information about electronic warranty.";
            list warranty {
              key "serial-number";
              description
                "The list of warranty information to be activated.";
              leaf serial-number {
                type string {
                  length "1..100";
                }
                mandatory true;
                description
                  "Serial number of the electronic warranty.";
              }
              leaf start-date {
                type pub-type:ncs_rpc_notif_date;
                description
                  "Starting date for the electronic warranty.";
              }
              leaf life-span {
                type uint32 {
                  range "1..600";
                }
                units "month";
                description
                  "Life span for the electronic warranty.";
              }
            }
          }
        }
      }
    }
  }
  augment "/ncs:devices/ncs:device/ncs:config" {
    container warranty {
      tailf:ncs-device-type "netconf";
      tailf:display-when "not(../../ncs:module) or ../../ncs:module[ncs:name='huawei-warranty']";
      description
        "Electronic warranty management module.";
      container global {
        presence "warranty global information";
        ext:generated-by "system";
        ext:operation-exclude "create";
        description
          "Configure the electronic warranty management alarm feature.";
        leaf alarm-enable {
          type boolean;
          default "true";
          description
            "Enable/disable function to report the alarms of electronic warranty management.";
        }
      }
      // NCS drop config false container 'warranty-infos'
    }
  }
  augment "/ncs:devices/ncs:device/ncs:live-status" {
    container warranty {
      tailf:ncs-device-type "netconf";
      tailf:display-when "not(../../ncs:module) or ../../ncs:module[ncs:name='huawei-warranty'] or (../../ncs:live-status-protocol[not(ncs:capability)]) or (../../ncs:live-status-protocol/ncs:capability/ncs:module[.='huawei-warranty'])";
      description
        "Electronic warranty management module.";
      container global {
        presence "warranty global information";
        ext:generated-by "system";
        ext:operation-exclude "create";
        description
          "Configure the electronic warranty management alarm feature.";
        leaf alarm-enable {
          type boolean;
          // NCS drop default statement
          description
            "Enable/disable function to report the alarms of electronic warranty management.";
        }
      }
      container warranty-infos {
        description
          "List of information about electronic warranty Informations.";
        list warranty-info {
          key "slot type serial-number";
          description
            "Operational state of information about a electronic warranty.";
          leaf slot {
            type pub-type:live_ncs_position;
            description
              "Specify the slot path.";
          }
          leaf type {
            type live_ncs_unit-type;
            description
              "Specify the type of the electronic warranty.";
          }
          leaf serial-number {
            type string {
              length "1..100";
            }
            description
              "Serial number of the electronic warranty.";
          }
          leaf start-date {
            type pub-type:live_ncs_date;
            description
              "Starting point date for the electronic warranty.";
          }
          leaf life-span {
            type uint32 {
              range "1..600";
            }
            description
              "Life span for the electronic warranty.";
          }
          leaf status {
            type live_ncs_warranty-status;
            description
              "Status for the electronic warranty.";
          }
        }
      }
    }
  }
  augment "/ncs:devices/ncs:template/ncs:ned-id/ncs:config" {
    container warranty {
      description
        "Electronic warranty management module.";
      container global {
        presence "warranty global information";
        ext:generated-by "system";
        ext:operation-exclude "create";
        description
          "Configure the electronic warranty management alarm feature.";
        leaf alarm-enable {
          type string;
          // NCS drop default statement
          description
            "Enable/disable function to report the alarms of electronic warranty management.";
        }
      }
      // NCS drop config false container 'warranty-infos'
    }
  }
}
