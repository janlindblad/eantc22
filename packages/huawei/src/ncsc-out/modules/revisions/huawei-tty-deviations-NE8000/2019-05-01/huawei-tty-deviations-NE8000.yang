module huawei-tty-deviations-NE8000 {
  // Generated by yanger -t ncs
  tailf:mount-id "huawei-nc-1.0:huawei-nc-1.0";
  tailf:ncs-device-type "netconf";

  namespace "urn:huawei:yang:huawei-tty-deviations-NE8000";
  prefix tty-devs-NE8000;

  import huawei-tty {
    prefix tty;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "TTY Component.";

  revision 2019-05-01 {
    description
      "Initial revision.";
    reference "Huawei private.";
  }

  typedef ncs_template_tty-authmode-type-deviations {
    type string;
    description
      "TTY authentication mode type list.";
  }

  typedef ncs_rpc_notif_tty-authmode-type-deviations {
    type enumeration {
      enum "password" {
        value 2;
        description
          "Authentication mode password.";
      }
      enum "aaa" {
        value 3;
        description
          "Authentication mode aaa.";
      }
      enum "init" {
        value 4;
        description
          "Undo authentication mode.";
      }
    }
    description
      "TTY authentication mode type list.";
  }

  typedef live_ncs_tty-authmode-type-deviations {
    type enumeration {
      enum "password" {
        value 2;
        description
          "Authentication mode password.";
      }
      enum "aaa" {
        value 3;
        description
          "Authentication mode aaa.";
      }
      enum "init" {
        value 4;
        description
          "Undo authentication mode.";
      }
    }
    description
      "TTY authentication mode type list.";
  }

  typedef tty-authmode-type-deviations {
    type enumeration {
      enum "password" {
        value 2;
        description
          "Authentication mode password.";
      }
      enum "aaa" {
        value 3;
        description
          "Authentication mode aaa.";
      }
      enum "init" {
        value 4;
        description
          "Undo authentication mode.";
      }
    }
    description
      "TTY authentication mode type list.";
  }

  deviation "/ncs:devices/ncs:template/ncs:ned-id/ncs:config/tty:tty/tty:console/tty:auth-mode" {
    deviate replace {
      type tty-devs-NE8000:ncs_template_tty-authmode-type-deviations;
    }
  }
  deviation "/ncs:devices/ncs:device/ncs:live-status/tty:tty/tty:console/tty:auth-mode" {
    deviate replace {
      type tty-devs-NE8000:live_ncs_tty-authmode-type-deviations;
    }
  }
  deviation "/ncs:devices/ncs:device/ncs:config/tty:tty/tty:console/tty:auth-mode" {
    deviate replace {
      type tty-devs-NE8000:tty-authmode-type-deviations;
    }
  }
  deviation "/ncs:devices/ncs:template/ncs:ned-id/ncs:config/tty:tty/tty:console/tty:shutdown-enble" {
    deviate not-supported;
  }
  deviation "/ncs:devices/ncs:device/ncs:live-status/tty:tty/tty:console/tty:shutdown-enble" {
    deviate not-supported;
  }
  deviation "/ncs:devices/ncs:device/ncs:config/tty:tty/tty:console/tty:shutdown-enble" {
    deviate not-supported;
  }
  deviation "/ncs:devices/ncs:template/ncs:ned-id/ncs:config/tty:tty/tty:aux" {
    deviate not-supported;
  }
  deviation "/ncs:devices/ncs:device/ncs:live-status/tty:tty/tty:aux" {
    deviate not-supported;
  }
  deviation "/ncs:devices/ncs:device/ncs:config/tty:tty/tty:aux" {
    deviate not-supported;
  }
}
