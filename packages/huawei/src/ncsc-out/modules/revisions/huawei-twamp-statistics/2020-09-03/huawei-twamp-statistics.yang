module huawei-twamp-statistics {
  // Generated by yanger -t ncs
  tailf:mount-id "huawei-nc-1.0:huawei-nc-1.0";
  tailf:ncs-device-type "netconf";

  namespace "urn:huawei:yang:huawei-twamp-statistics";
  prefix twamp-statistics;

  import huawei-twamp-controller {
    prefix twamp-controller;
  }
  import huawei-extension {
    prefix ext;
  }
  import huawei-ifm {
    prefix ifm;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "TWAMP statistics.";

  revision 2020-09-03 {
    description
      "Add new container: link-bundle-statistics.";
    reference "Huawei private.";
  }
  revision 2020-03-05 {
    description
      "Modify initial revision's description.";
    reference "Huawei private.";
  }
  revision 2019-05-05 {
    description
      "Init revision.";
    reference "Huawei private.";
  }
  ext:task-name "twampclient";

  augment "/ncs:devices/ncs:template/ncs:ned-id/ncs:config/twamp-controller:twamp-controller/twamp-controller:client/twamp-controller:sessions/twamp-controller:session" {
    description
      "TWAMP augment.";
    // NCS drop config false container statistics
    // NCS drop config false container 'link-bundle-statistics'
  }
  augment "/ncs:devices/ncs:device/ncs:live-status/twamp-controller:twamp-controller/twamp-controller:client/twamp-controller:sessions/twamp-controller:session" {
    description
      "TWAMP augment.";
    container statistics {
      tailf:ncs-device-type "netconf";
      tailf:display-when "not(../../../../../../ncs:module) or ../../../../../../ncs:module[ncs:name='huawei-twamp-statistics'] or (../../../../../../ncs:live-status-protocol[not(ncs:capability)]) or (../../../../../../ncs:live-status-protocol/ncs:capability/ncs:module[.='huawei-twamp-statistics'])";
      description
        "TWAMP statistics.";
      leaf avg-delay {
        type uint32;
        units "us";
        description
          "The average delay.";
      }
      leaf avg-jitter {
        type uint32;
        units "us";
        description
          "The average jitter.";
      }
      leaf loss-count {
        type uint32;
        description
          "The loss count.";
      }
      leaf send-count {
        type uint32;
        description
          "The send count.";
      }
    }
    container link-bundle-statistics {
      tailf:ncs-device-type "netconf";
      tailf:display-when "not(../../../../../../ncs:module) or ../../../../../../ncs:module[ncs:name='huawei-twamp-statistics'] or (../../../../../../ncs:live-status-protocol[not(ncs:capability)]) or (../../../../../../ncs:live-status-protocol/ncs:capability/ncs:module[.='huawei-twamp-statistics'])";
      description
        "List of TWAMP link-bundle statistics.";
      list link-bundle-statistic {
        key "if-name";
        description
          "Statistics of TWAMP link-bundle.";
        leaf if-name {
          type leafref {
            path "/ncs:devices/ncs:device/ncs:live-status/ifm:ifm/ifm:interfaces/ifm:interface/ifm:name" {
              tailf:xpath-root 3;
            }
          }
          description
            "Interface Name.";
        }
        leaf if-index {
          type uint32;
          description
            "Interface ID.";
        }
        leaf loss-count {
          type uint32;
          description
            "The loss count.";
        }
        leaf send-count {
          type uint32;
          description
            "The send count.";
        }
        leaf avg-delay {
          type uint32;
          units "us";
          description
            "The average delay.";
        }
        leaf avg-jitter {
          type uint32;
          units "us";
          description
            "The average jitter.";
        }
        leaf avg-tx-jitter {
          type uint32;
          units "us";
          description
            "The average TX jitter.";
        }
        leaf avg-rx-jitter {
          type uint32;
          units "us";
          description
            "The average RX jitter.";
        }
        leaf max-delay {
          type uint32;
          units "us";
          description
            "The maximum delay.";
        }
        leaf min-delay {
          type uint32;
          units "us";
          description
            "The minimum delay.";
        }
        leaf max-jitter {
          type uint32;
          units "us";
          description
            "The maximum jitter.";
        }
        leaf min-jitter {
          type uint32;
          units "us";
          description
            "The minimum jitter.";
        }
        leaf max-tx-jitter {
          type uint32;
          units "us";
          description
            "The maximum TX jitter.";
        }
        leaf min-tx-jitter {
          type uint32;
          units "us";
          description
            "The minimum TX jitter.";
        }
        leaf max-rx-jitter {
          type uint32;
          units "us";
          description
            "The maximum RX jitter.";
        }
        leaf min-rx-jitter {
          type uint32;
          units "us";
          description
            "The minimum RX jitter.";
        }
        leaf member-id-error-count {
          type uint32;
          description
            "The member-id error count.";
        }
        leaf checksum-error-count {
          type uint32;
          description
            "The checksum error count.";
        }
      }
    }
  }
  augment "/ncs:devices/ncs:device/ncs:config/twamp-controller:twamp-controller/twamp-controller:client/twamp-controller:sessions/twamp-controller:session" {
    description
      "TWAMP augment.";
    // NCS drop config false container statistics
    // NCS drop config false container 'link-bundle-statistics'
  }
}
