module huawei-ifm-cpos-trunk {
  // Generated by yanger -t ncs
  tailf:mount-id "huawei-nc-1.0:huawei-nc-1.0";
  tailf:ncs-device-type "netconf";

  namespace "urn:huawei:yang:huawei-ifm-cpos-trunk";
  prefix ifm-cpos-trunk;

  import huawei-ifm {
    prefix ifm;
  }
  import huawei-extension {
    prefix ext;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Defines the Cpos-Trunk bundling technology, which bundles multiple physical interfaces into a logical interface.";

  revision 2020-02-14 {
    description
      "Initial revision.";
    reference "Huawei private.";
  }
  ext:task-name "trunk";

  typedef ncs_template_channel-mode-type {
    type string;
    description
      "Cpos Trunk Channel Mode.";
  }

  typedef ncs_template_active-status-type {
    type string;
    description
      "Cpos trunk member active state.";
  }

  typedef ncs_template_e1t1-work-mode-type {
    type string;
    description
      "E1T1 work mode type.";
  }

  typedef ncs_rpc_notif_channel-mode-type {
    type enumeration {
      enum "vc12" {
        value 0;
        description
          "VC12.";
      }
      enum "vc4" {
        value 1;
        description
          "VC4.";
      }
    }
    description
      "Cpos Trunk Channel Mode.";
  }

  typedef ncs_rpc_notif_active-status-type {
    type enumeration {
      enum "invalid" {
        value 0;
        description
          "Invalid.";
      }
      enum "active" {
        value 1;
        description
          "The interface is in Active state.";
      }
      enum "inactive" {
        value 2;
        description
          "The interface is in InActive state.";
      }
    }
    description
      "Cpos trunk member active state.";
  }

  typedef ncs_rpc_notif_e1t1-work-mode-type {
    type enumeration {
      enum "framed" {
        value 0;
        description
          "Framed.";
      }
      enum "unframed" {
        value 1;
        description
          "Unframed.";
      }
    }
    description
      "E1T1 work mode type.";
  }

  typedef live_ncs_channel-mode-type {
    type enumeration {
      enum "vc12" {
        value 0;
        description
          "VC12.";
      }
      enum "vc4" {
        value 1;
        description
          "VC4.";
      }
    }
    description
      "Cpos Trunk Channel Mode.";
  }

  typedef live_ncs_active-status-type {
    type enumeration {
      enum "invalid" {
        value 0;
        description
          "Invalid.";
      }
      enum "active" {
        value 1;
        description
          "The interface is in Active state.";
      }
      enum "inactive" {
        value 2;
        description
          "The interface is in InActive state.";
      }
    }
    description
      "Cpos trunk member active state.";
  }

  typedef live_ncs_e1t1-work-mode-type {
    type enumeration {
      enum "framed" {
        value 0;
        description
          "Framed.";
      }
      enum "unframed" {
        value 1;
        description
          "Unframed.";
      }
    }
    description
      "E1T1 work mode type.";
  }

  typedef channel-mode-type {
    type enumeration {
      enum "vc12" {
        value 0;
        description
          "VC12.";
      }
      enum "vc4" {
        value 1;
        description
          "VC4.";
      }
    }
    description
      "Cpos Trunk Channel Mode.";
  }

  typedef active-status-type {
    type enumeration {
      enum "invalid" {
        value 0;
        description
          "Invalid.";
      }
      enum "active" {
        value 1;
        description
          "The interface is in Active state.";
      }
      enum "inactive" {
        value 2;
        description
          "The interface is in InActive state.";
      }
    }
    description
      "Cpos trunk member active state.";
  }

  typedef e1t1-work-mode-type {
    type enumeration {
      enum "framed" {
        value 0;
        description
          "Framed.";
      }
      enum "unframed" {
        value 1;
        description
          "Unframed.";
      }
    }
    description
      "E1T1 work mode type.";
  }

  augment "/ncs:devices/ncs:template/ncs:ned-id/ncs:config/ifm:ifm/ifm:interfaces/ifm:interface" {
    // NCS drop when statement
    description
      "Active when the interface is set to type Cpos-Trunk.";
    container cpos-trunk {
      description
        "Configure the Cpos-Trunk interface, which is a logical interface with multiple physical interfaces being bundled.";
      leaf channel-mode {
        type ncs_template_channel-mode-type;
        // NCS drop default statement
        description
          "Channel mode.";
      }
      // NCS drop config false leaf 'up-member-num'
      container members {
        description
          "List of cpos-trunk member interfaces.";
        list member {
          // NCS patched for predictable order
          ordered-by user;
          key "name";
          // NCS drop max-elements statement
          description
            "Configure cpos-trunk member interfaces.";
          leaf name {
            type string;
            // NCS drop must statement
            description
              "Configures a name for a cpos-trunk member interface.";
          }
          // NCS drop config false leaf 'port-status'
          // NCS drop config false leaf 'active-status'
        }
      }
      container e1t1s {
        // NCS drop when statement
        description
          "List of E1T1 port attributes.";
        list e1t1 {
          // NCS patched for predictable order
          ordered-by user;
          key "number";
          // NCS drop max-elements statement
          ext:operation-exclude "create";
          ext:generated-by "system" {
            // NCS drop when statement
            description
              "The all instances are generated automatically when channel-mode is not vc4.";
          }
          description
            "Configure E1T1 port attribute.";
          leaf number {
            type string;
            description
              "E1T1 number.";
          }
          leaf work-mode {
            type ncs_template_e1t1-work-mode-type;
            // NCS drop default statement
            description
              "Work mode.";
          }
          container channel-sets {
            // NCS drop when statement
            description
              "List of channel-sets.";
            list channel-set {
              // NCS patched for predictable order
              ordered-by user;
              key "number";
              // NCS drop max-elements statement
              description
                "Configure channel-set.";
              leaf number {
                type string;
                description
                  "Channel-set number.";
              }
              leaf timeslot-list {
                type string;
                // NCS drop mandatory statement
                description
                  "Timeslot list. Please enter a number from 0 to 31 with ',' or '-' in the middle, like '1-10,11'.";
              }
            }
          }
        }
      }
    }
  }
  augment "/ncs:devices/ncs:device/ncs:live-status/ifm:ifm/ifm:interfaces/ifm:interface" {
    // NCS drop when statement
    description
      "Active when the interface is set to type Cpos-Trunk.";
    container cpos-trunk {
      tailf:ncs-device-type "netconf";
      tailf:display-when "not(../../../../../ncs:module) or ../../../../../ncs:module[ncs:name='huawei-ifm-cpos-trunk'] or (../../../../../ncs:live-status-protocol[not(ncs:capability)]) or (../../../../../ncs:live-status-protocol/ncs:capability/ncs:module[.='huawei-ifm-cpos-trunk'])";
      description
        "Configure the Cpos-Trunk interface, which is a logical interface with multiple physical interfaces being bundled.";
      leaf channel-mode {
        type live_ncs_channel-mode-type;
        // NCS drop default statement
        description
          "Channel mode.";
      }
      leaf up-member-num {
        type uint32 {
          range "0..2";
        }
        description
          "Specifies the number of member interfaces in the Up state.";
      }
      container members {
        description
          "List of cpos-trunk member interfaces.";
        list member {
          key "name";
          // NCS drop max-elements statement
          description
            "Configure cpos-trunk member interfaces.";
          leaf name {
            type leafref {
              path "/ncs:devices/ncs:device/ncs:live-status/ifm:ifm/ifm:interfaces/ifm:interface/ifm:name" {
                tailf:xpath-root 3;
              }
            }
            // NCS drop must statement
            description
              "Configures a name for a cpos-trunk member interface.";
          }
          leaf port-status {
            type ifm:live_ncs_port-status;
            description
              "Displays the status of a cpos-trunk member interface.";
          }
          leaf active-status {
            type live_ncs_active-status-type;
            description
              "Displays the active status of a cpos-trunk member interface.";
          }
        }
      }
      container e1t1s {
        // NCS drop when statement
        description
          "List of E1T1 port attributes.";
        list e1t1 {
          key "number";
          // NCS drop max-elements statement
          ext:operation-exclude "create";
          ext:generated-by "system" {
            // NCS drop when statement
            description
              "The all instances are generated automatically when channel-mode is not vc4.";
          }
          description
            "Configure E1T1 port attribute.";
          leaf number {
            type uint32 {
              range "1..63";
            }
            description
              "E1T1 number.";
          }
          leaf work-mode {
            type live_ncs_e1t1-work-mode-type;
            // NCS drop default statement
            description
              "Work mode.";
          }
          container channel-sets {
            // NCS drop when statement
            description
              "List of channel-sets.";
            list channel-set {
              key "number";
              // NCS drop max-elements statement
              description
                "Configure channel-set.";
              leaf number {
                type uint32 {
                  range "0..30";
                }
                description
                  "Channel-set number.";
              }
              leaf timeslot-list {
                type string {
                  length "1..83";
                }
                // NCS drop mandatory statement
                description
                  "Timeslot list. Please enter a number from 0 to 31 with ',' or '-' in the middle, like '1-10,11'.";
              }
            }
          }
        }
      }
    }
  }
  augment "/ncs:devices/ncs:device/ncs:config/ifm:ifm/ifm:interfaces/ifm:interface" {
    when "ifm:type='Cpos-Trunk'" {
      tailf:xpath-root 3;
    }
    description
      "Active when the interface is set to type Cpos-Trunk.";
    container cpos-trunk {
      tailf:ncs-device-type "netconf";
      tailf:display-when "not(../../../../../ncs:module) or ../../../../../ncs:module[ncs:name='huawei-ifm-cpos-trunk']";
      description
        "Configure the Cpos-Trunk interface, which is a logical interface with multiple physical interfaces being bundled.";
      leaf channel-mode {
        type channel-mode-type;
        default "vc12";
        description
          "Channel mode.";
      }
      // NCS drop config false leaf 'up-member-num'
      container members {
        description
          "List of cpos-trunk member interfaces.";
        list member {
          key "name";
          max-elements 2;
          description
            "Configure cpos-trunk member interfaces.";
          leaf name {
            type leafref {
              path "/ncs:devices/ncs:device/ncs:config/ifm:ifm/ifm:interfaces/ifm:interface/ifm:name" {
                tailf:xpath-root 3;
              }
            }
            must "/ifm:ifm/ifm:interfaces/ifm:interface[ifm:name=current()]/ifm:type='Cpos'" {
              tailf:xpath-root 3;
            }
            description
              "Configures a name for a cpos-trunk member interface.";
          }
          // NCS drop config false leaf 'port-status'
          // NCS drop config false leaf 'active-status'
        }
      }
      container e1t1s {
        when "not(../channel-mode='vc4')" {
          tailf:xpath-root 3;
        }
        description
          "List of E1T1 port attributes.";
        list e1t1 {
          key "number";
          max-elements 63;
          ext:operation-exclude "create";
          ext:generated-by "system" {
            when "not(../../channel-mode='vc4')" {
              tailf:xpath-root 3;
            }
            description
              "The all instances are generated automatically when channel-mode is not vc4.";
          }
          description
            "Configure E1T1 port attribute.";
          leaf number {
            type uint32 {
              range "1..63";
            }
            description
              "E1T1 number.";
          }
          leaf work-mode {
            type e1t1-work-mode-type;
            default "framed";
            description
              "Work mode.";
          }
          container channel-sets {
            when "not(../work-mode='unframed')" {
              tailf:xpath-root 3;
            }
            description
              "List of channel-sets.";
            list channel-set {
              key "number";
              max-elements 31;
              description
                "Configure channel-set.";
              leaf number {
                type uint32 {
                  range "0..30";
                }
                description
                  "Channel-set number.";
              }
              leaf timeslot-list {
                type string {
                  length "1..83";
                }
                mandatory true;
                description
                  "Timeslot list. Please enter a number from 0 to 31 with ',' or '-' in the middle, like '1-10,11'.";
              }
            }
          }
        }
      }
    }
  }
}
