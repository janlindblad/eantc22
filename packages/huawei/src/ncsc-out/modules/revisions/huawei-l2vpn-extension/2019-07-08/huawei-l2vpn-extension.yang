module huawei-l2vpn-extension {
  // Generated by yanger -t ncs
  tailf:mount-id "huawei-nc-1.0:huawei-nc-1.0";
  tailf:ncs-device-type "netconf";

  yang-version 1;
  namespace "urn:huawei:yang:huawei-l2vpn-extension";
  prefix l2vpn-extension;

  import huawei-ifm {
    prefix ifm;
  }
  import huawei-qos {
    prefix qos;
  }
  import huawei-l2vpn {
    prefix l2vpn;
  }
  import huawei-extension {
    prefix ext;
  }
  import huawei-vrrp {
    prefix vrrp;
  }
  import huawei-ip {
    prefix ip;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "L2 virtual private network extensions.";

  revision 2019-07-08 {
    description
      "Init revision.";
    reference "Huawei private.";
  }
  ext:task-name "l2vpn";

  typedef ncs_template_qos-query-type {
    type string;
    description
      "L2VPN QoS query.";
  }

  typedef ncs_rpc_notif_qos-query-type {
    type enumeration {
      enum "be" {
        value 0;
        description
          "Best effort (BE) service-class.";
      }
      enum "af1" {
        value 1;
        description
          "Assured forwarding 1 (AF1) service-class.";
      }
      enum "af2" {
        value 2;
        description
          "Assured forwarding 2 (AF2) service-class.";
      }
      enum "af3" {
        value 3;
        description
          "Assured forwarding 3 (AF3) service-class.";
      }
      enum "af4" {
        value 4;
        description
          "Assured forwarding 4 (AF4) service-class.";
      }
      enum "ef" {
        value 5;
        description
          "Expedited forwarding (EF) service-class.";
      }
      enum "cs6" {
        value 6;
        description
          "Class selector 6 (CS6) service-class.";
      }
      enum "cs7" {
        value 7;
        description
          "Class selector 7 (CS7) service-class.";
      }
    }
    description
      "L2VPN QoS query.";
  }

  typedef live_ncs_qos-query-type {
    type enumeration {
      enum "be" {
        value 0;
        description
          "Best effort (BE) service-class.";
      }
      enum "af1" {
        value 1;
        description
          "Assured forwarding 1 (AF1) service-class.";
      }
      enum "af2" {
        value 2;
        description
          "Assured forwarding 2 (AF2) service-class.";
      }
      enum "af3" {
        value 3;
        description
          "Assured forwarding 3 (AF3) service-class.";
      }
      enum "af4" {
        value 4;
        description
          "Assured forwarding 4 (AF4) service-class.";
      }
      enum "ef" {
        value 5;
        description
          "Expedited forwarding (EF) service-class.";
      }
      enum "cs6" {
        value 6;
        description
          "Class selector 6 (CS6) service-class.";
      }
      enum "cs7" {
        value 7;
        description
          "Class selector 7 (CS7) service-class.";
      }
    }
    description
      "L2VPN QoS query.";
  }

  typedef qos-query-type {
    type enumeration {
      enum "be" {
        value 0;
        description
          "Best effort (BE) service-class.";
      }
      enum "af1" {
        value 1;
        description
          "Assured forwarding 1 (AF1) service-class.";
      }
      enum "af2" {
        value 2;
        description
          "Assured forwarding 2 (AF2) service-class.";
      }
      enum "af3" {
        value 3;
        description
          "Assured forwarding 3 (AF3) service-class.";
      }
      enum "af4" {
        value 4;
        description
          "Assured forwarding 4 (AF4) service-class.";
      }
      enum "ef" {
        value 5;
        description
          "Expedited forwarding (EF) service-class.";
      }
      enum "cs6" {
        value 6;
        description
          "Class selector 6 (CS6) service-class.";
      }
      enum "cs7" {
        value 7;
        description
          "Class selector 7 (CS7) service-class.";
      }
    }
    description
      "L2VPN QoS query.";
  }

  grouping ncs_template_qos-query-info-grp {
    description
      "QoS query info.";
    leaf packets {
      type string;
      units "packet";
      description
        "The total number of output packets.";
    }
    leaf bytes {
      type string;
      units "Byte";
      description
        "The total number of output bytes.";
    }
    leaf packets-rate {
      type string;
      units "pps";
      description
        "The last 300 seconds packets rate.";
    }
    leaf bits-rate {
      type string;
      units "bit/s";
      description
        "The last 300 seconds bits rate.";
    }
    leaf discard-packets {
      type string;
      units "packet";
      description
        "The total discard number of the packets.";
    }
    leaf discard-bytes {
      type string;
      units "Byte";
      description
        "The total discard number of the bytes.";
    }
    leaf discard-packets-rate {
      type string;
      units "pps";
      description
        "The last 300 seconds discard packets rate.";
    }
    leaf discard-bit-rate {
      type string;
      units "bit/s";
      description
        "The last 300 seconds discard bits rate.";
    }
  }

  grouping ncs_template_qos-traffic-statistics-grp {
    description
      "QoS traffic-statistics table.";
    leaf last-clear-time {
      type string;
      description
        "Last time of clean out.";
    }
    leaf bits-rate {
      type string;
      units "bit/s";
      description
        "The traffic bits rate received on the PW.";
    }
    leaf packets-rate {
      type string;
      units "pps";
      description
        "The traffic packet rate received on the PW.";
    }
    leaf output-bytes {
      type string;
      units "Byte";
      description
        "The traffic bytes transmitted out of the PW.";
    }
    leaf output-packets {
      type string;
      units "packet";
      description
        "The traffic packets transmitted out of the PW.";
    }
    container qos-querys {
      description
        "List of the QoS traffic-statistics.";
      list qos-query {
        // NCS patched for predictable order
        ordered-by user;
        key "query";
        description
          "Indicates the query table of the QoS traffic statistics.";
        leaf query {
          type ncs_template_qos-query-type;
          description
            "Indicates the query of the QoS traffic statistics.";
        }
        uses ncs_template_qos-query-info-grp;
      }
    }
  }

  grouping ncs_template_qos-parameter-grp {
    description
      "QoS parameter information.";
    leaf cir {
      type string;
      units "kbit/s";
      // NCS drop default statement
      description
        "Specify the CIR.";
    }
    leaf pir {
      type string;
      units "kbit/s";
      description
        "Specify the PIR.";
    }
    leaf profile-name {
      // NCS drop when statement
      type string;
      description
        "Specify the name of QoS profile.";
    }
  }

  grouping ncs_rpc_notif_qos-query-info-grp {
    description
      "QoS query info.";
    leaf packets {
      type uint64;
      units "packet";
      description
        "The total number of output packets.";
    }
    leaf bytes {
      type uint64;
      units "Byte";
      description
        "The total number of output bytes.";
    }
    leaf packets-rate {
      type uint64;
      units "pps";
      description
        "The last 300 seconds packets rate.";
    }
    leaf bits-rate {
      type uint64;
      units "bit/s";
      description
        "The last 300 seconds bits rate.";
    }
    leaf discard-packets {
      type uint64;
      units "packet";
      description
        "The total discard number of the packets.";
    }
    leaf discard-bytes {
      type uint64;
      units "Byte";
      description
        "The total discard number of the bytes.";
    }
    leaf discard-packets-rate {
      type uint64;
      units "pps";
      description
        "The last 300 seconds discard packets rate.";
    }
    leaf discard-bit-rate {
      type uint64;
      units "bit/s";
      description
        "The last 300 seconds discard bits rate.";
    }
  }

  grouping ncs_rpc_notif_qos-traffic-statistics-grp {
    description
      "QoS traffic-statistics table.";
    leaf last-clear-time {
      type string {
        length "1..60";
      }
      description
        "Last time of clean out.";
    }
    leaf bits-rate {
      type uint64;
      units "bit/s";
      description
        "The traffic bits rate received on the PW.";
    }
    leaf packets-rate {
      type uint64;
      units "pps";
      description
        "The traffic packet rate received on the PW.";
    }
    leaf output-bytes {
      type uint64;
      units "Byte";
      description
        "The traffic bytes transmitted out of the PW.";
    }
    leaf output-packets {
      type uint64;
      units "packet";
      description
        "The traffic packets transmitted out of the PW.";
    }
    container qos-querys {
      description
        "List of the QoS traffic-statistics.";
      list qos-query {
        key "query";
        description
          "Indicates the query table of the QoS traffic statistics.";
        leaf query {
          type ncs_rpc_notif_qos-query-type;
          description
            "Indicates the query of the QoS traffic statistics.";
        }
        uses ncs_rpc_notif_qos-query-info-grp;
      }
    }
  }

  grouping ncs_rpc_notif_qos-parameter-grp {
    description
      "QoS parameter information.";
    leaf cir {
      type uint32 {
        range "0 | 16..4294967294";
      }
      units "kbit/s";
      default "0";
      description
        "Specify the CIR.";
    }
    leaf pir {
      type uint32 {
        range "0 | 16..4294967294";
      }
      units "kbit/s";
      description
        "Specify the PIR.";
    }
    leaf profile-name {
      when '../pir>0' {
        tailf:xpath-root 3;
      }
      type string;
      description
        "Specify the name of QoS profile.";
    }
  }

  grouping live_ncs_qos-query-info-grp {
    description
      "QoS query info.";
    leaf packets {
      type uint64;
      units "packet";
      description
        "The total number of output packets.";
    }
    leaf bytes {
      type uint64;
      units "Byte";
      description
        "The total number of output bytes.";
    }
    leaf packets-rate {
      type uint64;
      units "pps";
      description
        "The last 300 seconds packets rate.";
    }
    leaf bits-rate {
      type uint64;
      units "bit/s";
      description
        "The last 300 seconds bits rate.";
    }
    leaf discard-packets {
      type uint64;
      units "packet";
      description
        "The total discard number of the packets.";
    }
    leaf discard-bytes {
      type uint64;
      units "Byte";
      description
        "The total discard number of the bytes.";
    }
    leaf discard-packets-rate {
      type uint64;
      units "pps";
      description
        "The last 300 seconds discard packets rate.";
    }
    leaf discard-bit-rate {
      type uint64;
      units "bit/s";
      description
        "The last 300 seconds discard bits rate.";
    }
  }

  grouping live_ncs_qos-traffic-statistics-grp {
    description
      "QoS traffic-statistics table.";
    leaf last-clear-time {
      type string {
        length "1..60";
      }
      description
        "Last time of clean out.";
    }
    leaf bits-rate {
      type uint64;
      units "bit/s";
      description
        "The traffic bits rate received on the PW.";
    }
    leaf packets-rate {
      type uint64;
      units "pps";
      description
        "The traffic packet rate received on the PW.";
    }
    leaf output-bytes {
      type uint64;
      units "Byte";
      description
        "The traffic bytes transmitted out of the PW.";
    }
    leaf output-packets {
      type uint64;
      units "packet";
      description
        "The traffic packets transmitted out of the PW.";
    }
    container qos-querys {
      description
        "List of the QoS traffic-statistics.";
      list qos-query {
        key "query";
        description
          "Indicates the query table of the QoS traffic statistics.";
        leaf query {
          type live_ncs_qos-query-type;
          description
            "Indicates the query of the QoS traffic statistics.";
        }
        uses live_ncs_qos-query-info-grp;
      }
    }
  }

  grouping live_ncs_qos-parameter-grp {
    description
      "QoS parameter information.";
    leaf cir {
      type uint32 {
        range "0 | 16..4294967294";
      }
      units "kbit/s";
      // NCS drop default statement
      description
        "Specify the CIR.";
    }
    leaf pir {
      type uint32 {
        range "0 | 16..4294967294";
      }
      units "kbit/s";
      description
        "Specify the PIR.";
    }
    leaf profile-name {
      // NCS drop when statement
      type leafref {
        path "/ncs:devices/ncs:device/ncs:live-status/qos:qos/qos:queue-scheduler-template/qos:profiles/qos:profile/qos:name" {
          tailf:xpath-root 3;
        }
      }
      description
        "Specify the name of QoS profile.";
    }
  }

  grouping qos-query-info-grp {
    description
      "QoS query info.";
    leaf packets {
      type uint64;
      units "packet";
      description
        "The total number of output packets.";
    }
    leaf bytes {
      type uint64;
      units "Byte";
      description
        "The total number of output bytes.";
    }
    leaf packets-rate {
      type uint64;
      units "pps";
      description
        "The last 300 seconds packets rate.";
    }
    leaf bits-rate {
      type uint64;
      units "bit/s";
      description
        "The last 300 seconds bits rate.";
    }
    leaf discard-packets {
      type uint64;
      units "packet";
      description
        "The total discard number of the packets.";
    }
    leaf discard-bytes {
      type uint64;
      units "Byte";
      description
        "The total discard number of the bytes.";
    }
    leaf discard-packets-rate {
      type uint64;
      units "pps";
      description
        "The last 300 seconds discard packets rate.";
    }
    leaf discard-bit-rate {
      type uint64;
      units "bit/s";
      description
        "The last 300 seconds discard bits rate.";
    }
  }

  grouping qos-traffic-statistics-grp {
    description
      "QoS traffic-statistics table.";
    leaf last-clear-time {
      type string {
        length "1..60";
      }
      description
        "Last time of clean out.";
    }
    leaf bits-rate {
      type uint64;
      units "bit/s";
      description
        "The traffic bits rate received on the PW.";
    }
    leaf packets-rate {
      type uint64;
      units "pps";
      description
        "The traffic packet rate received on the PW.";
    }
    leaf output-bytes {
      type uint64;
      units "Byte";
      description
        "The traffic bytes transmitted out of the PW.";
    }
    leaf output-packets {
      type uint64;
      units "packet";
      description
        "The traffic packets transmitted out of the PW.";
    }
    container qos-querys {
      description
        "List of the QoS traffic-statistics.";
      list qos-query {
        key "query";
        description
          "Indicates the query table of the QoS traffic statistics.";
        leaf query {
          type qos-query-type;
          description
            "Indicates the query of the QoS traffic statistics.";
        }
        uses qos-query-info-grp;
      }
    }
  }

  grouping qos-parameter-grp {
    description
      "QoS parameter information.";
    leaf cir {
      type uint32 {
        range "0 | 16..4294967294";
      }
      units "kbit/s";
      default "0";
      description
        "Specify the CIR.";
    }
    leaf pir {
      type uint32 {
        range "0 | 16..4294967294";
      }
      units "kbit/s";
      description
        "Specify the PIR.";
    }
    leaf profile-name {
      when '../pir>0' {
        tailf:xpath-root 3;
      }
      type leafref {
        path "/ncs:devices/ncs:device/ncs:config/qos:qos/qos:queue-scheduler-template/qos:profiles/qos:profile/qos:name" {
          tailf:xpath-root 3;
        }
      }
      description
        "Specify the name of QoS profile.";
    }
  }

  augment "/ncs:devices/ncs:template/ncs:ned-id/ncs:config/l2vpn:l2vpn/l2vpn:instances/l2vpn:instance/l2vpn:vpls" {
    description
      "Configure the vpls QoS traffic statistics.";
    container qos-parameter {
      // NCS drop must statement
      // NCS drop must statement
      // NCS drop must statement
      presence "enable QoS for pw";
      description
        "Enable/disable the QoS parameter information.";
      uses ncs_template_qos-parameter-grp;
    }
    // NCS drop config false container 'qos-traffic-statistics'
  }
  augment "/ncs:devices/ncs:device/ncs:live-status/l2vpn:l2vpn/l2vpn:instances/l2vpn:instance/l2vpn:vpls" {
    description
      "Configure the vpls QoS traffic statistics.";
    container qos-parameter {
      tailf:ncs-device-type "netconf";
      tailf:display-when "not(../../../../../../ncs:module) or ../../../../../../ncs:module[ncs:name='huawei-l2vpn-extension'] or (../../../../../../ncs:live-status-protocol[not(ncs:capability)]) or (../../../../../../ncs:live-status-protocol/ncs:capability/ncs:module[.='huawei-l2vpn-extension'])";
      // NCS drop must statement
      // NCS drop must statement
      // NCS drop must statement
      presence "enable QoS for pw";
      description
        "Enable/disable the QoS parameter information.";
      uses live_ncs_qos-parameter-grp;
    }
    container qos-traffic-statistics {
      tailf:ncs-device-type "netconf";
      tailf:display-when "not(../../../../../../ncs:module) or ../../../../../../ncs:module[ncs:name='huawei-l2vpn-extension'] or (../../../../../../ncs:live-status-protocol[not(ncs:capability)]) or (../../../../../../ncs:live-status-protocol/ncs:capability/ncs:module[.='huawei-l2vpn-extension'])";
      description
        "Operational data of QoS traffic statistics table.";
      uses live_ncs_qos-traffic-statistics-grp;
    }
  }
  augment "/ncs:devices/ncs:device/ncs:config/l2vpn:l2vpn/l2vpn:instances/l2vpn:instance/l2vpn:vpls" {
    description
      "Configure the vpls QoS traffic statistics.";
    container qos-parameter {
      tailf:ncs-device-type "netconf";
      tailf:display-when "not(../../../../../../ncs:module) or ../../../../../../ncs:module[ncs:name='huawei-l2vpn-extension']";
      must 'cir<=pir' {
        tailf:xpath-root 3;
        error-message "The pir value is less than cir value.";
      }
      must 'not(cir=0 and pir=0)' {
        tailf:xpath-root 3;
        error-message "The cir and pir value can not be zero at same time.";
      }
      must "not(/l2vpn:l2vpn/l2vpn:instances/l2vpn:instance[l2vpn:name=current()/../../l2vpn:name][l2vpn:type='vpls']/l2vpn:vpls/l2vpn:ldp-signaling/l2vpn:pws/l2vpn:pw/l2vpn-extension:qos-parameter)" {
        tailf:xpath-root 3;
      }
      presence "enable QoS for pw";
      description
        "Enable/disable the QoS parameter information.";
      uses qos-parameter-grp;
    }
    // NCS drop config false container 'qos-traffic-statistics'
  }
  augment "/ncs:devices/ncs:template/ncs:ned-id/ncs:config/l2vpn:l2vpn/l2vpn:instances/l2vpn:instance/l2vpn:vpls/l2vpn:ldp-signaling/l2vpn:pws/l2vpn:pw" {
    description
      "Configure the vpls ldp pw QoS traffic statistics.";
    container qos-parameter {
      // NCS drop when statement
      // NCS drop must statement
      // NCS drop must statement
      // NCS drop must statement
      presence "enable QoS for pw";
      description
        "Enable/disable the QoS parameter information.";
      uses ncs_template_qos-parameter-grp;
    }
    // NCS drop config false container 'qos-traffic-statistics'
  }
  augment "/ncs:devices/ncs:device/ncs:live-status/l2vpn:l2vpn/l2vpn:instances/l2vpn:instance/l2vpn:vpls/l2vpn:ldp-signaling/l2vpn:pws/l2vpn:pw" {
    description
      "Configure the vpls ldp pw QoS traffic statistics.";
    container qos-parameter {
      tailf:ncs-device-type "netconf";
      tailf:display-when "not(../../../../../../../../../ncs:module) or ../../../../../../../../../ncs:module[ncs:name='huawei-l2vpn-extension'] or (../../../../../../../../../ncs:live-status-protocol[not(ncs:capability)]) or (../../../../../../../../../ncs:live-status-protocol/ncs:capability/ncs:module[.='huawei-l2vpn-extension'])";
      // NCS drop when statement
      // NCS drop must statement
      // NCS drop must statement
      // NCS drop must statement
      presence "enable QoS for pw";
      description
        "Enable/disable the QoS parameter information.";
      uses live_ncs_qos-parameter-grp;
    }
    container qos-traffic-statistics {
      tailf:ncs-device-type "netconf";
      tailf:display-when "not(../../../../../../../../../ncs:module) or ../../../../../../../../../ncs:module[ncs:name='huawei-l2vpn-extension'] or (../../../../../../../../../ncs:live-status-protocol[not(ncs:capability)]) or (../../../../../../../../../ncs:live-status-protocol/ncs:capability/ncs:module[.='huawei-l2vpn-extension'])";
      description
        "Operational data of QoS traffic statistics table.";
      uses live_ncs_qos-traffic-statistics-grp;
    }
  }
  augment "/ncs:devices/ncs:device/ncs:config/l2vpn:l2vpn/l2vpn:instances/l2vpn:instance/l2vpn:vpls/l2vpn:ldp-signaling/l2vpn:pws/l2vpn:pw" {
    description
      "Configure the vpls ldp pw QoS traffic statistics.";
    container qos-parameter {
      tailf:ncs-device-type "netconf";
      tailf:display-when "not(../../../../../../../../../ncs:module) or ../../../../../../../../../ncs:module[ncs:name='huawei-l2vpn-extension']";
      when '../l2vpn:name' {
        tailf:xpath-root 3;
      }
      must 'cir<=pir' {
        tailf:xpath-root 3;
        error-message "The pir value is less than cir value.";
      }
      must 'not(cir=0 and pir=0)' {
        tailf:xpath-root 3;
        error-message "The cir and pir value can not be zero at same time.";
      }
      must "not(/l2vpn:l2vpn/l2vpn:instances/l2vpn:instance[l2vpn:name=current()/../../../../../l2vpn:name][l2vpn:type='vpls']/l2vpn:vpls/l2vpn-extension:qos-parameter)" {
        tailf:xpath-root 3;
      }
      presence "enable QoS for pw";
      description
        "Enable/disable the QoS parameter information.";
      uses qos-parameter-grp;
    }
    // NCS drop config false container 'qos-traffic-statistics'
  }
  augment "/ncs:devices/ncs:template/ncs:ned-id/ncs:config/l2vpn:l2vpn/l2vpn:instances/l2vpn:instance/l2vpn:vpws-bgp/l2vpn:pws/l2vpn:pw" {
    description
      "Configure the vpws-bgp pw QoS traffic statistics.";
    container qos-parameter {
      // NCS drop must statement
      // NCS drop must statement
      presence "enable QoS for pw";
      description
        "Enable/disable the QoS parameter information.";
      uses ncs_template_qos-parameter-grp;
    }
    // NCS drop config false container 'qos-traffic-statistics'
  }
  augment "/ncs:devices/ncs:device/ncs:live-status/l2vpn:l2vpn/l2vpn:instances/l2vpn:instance/l2vpn:vpws-bgp/l2vpn:pws/l2vpn:pw" {
    description
      "Configure the vpws-bgp pw QoS traffic statistics.";
    container qos-parameter {
      tailf:ncs-device-type "netconf";
      tailf:display-when "not(../../../../../../../../ncs:module) or ../../../../../../../../ncs:module[ncs:name='huawei-l2vpn-extension'] or (../../../../../../../../ncs:live-status-protocol[not(ncs:capability)]) or (../../../../../../../../ncs:live-status-protocol/ncs:capability/ncs:module[.='huawei-l2vpn-extension'])";
      // NCS drop must statement
      // NCS drop must statement
      presence "enable QoS for pw";
      description
        "Enable/disable the QoS parameter information.";
      uses live_ncs_qos-parameter-grp;
    }
    container qos-traffic-statistics {
      tailf:ncs-device-type "netconf";
      tailf:display-when "not(../../../../../../../../ncs:module) or ../../../../../../../../ncs:module[ncs:name='huawei-l2vpn-extension'] or (../../../../../../../../ncs:live-status-protocol[not(ncs:capability)]) or (../../../../../../../../ncs:live-status-protocol/ncs:capability/ncs:module[.='huawei-l2vpn-extension'])";
      description
        "Operational data of QoS traffic statistics table.";
      leaf interface-name {
        type leafref {
          path "/ncs:devices/ncs:device/ncs:live-status/ifm:ifm/ifm:interfaces/ifm:interface/ifm:name" {
            tailf:xpath-root 3;
          }
        }
        description
          "Indicates the type and number of the AC interface.";
      }
      uses live_ncs_qos-traffic-statistics-grp;
    }
  }
  augment "/ncs:devices/ncs:device/ncs:config/l2vpn:l2vpn/l2vpn:instances/l2vpn:instance/l2vpn:vpws-bgp/l2vpn:pws/l2vpn:pw" {
    description
      "Configure the vpws-bgp pw QoS traffic statistics.";
    container qos-parameter {
      tailf:ncs-device-type "netconf";
      tailf:display-when "not(../../../../../../../../ncs:module) or ../../../../../../../../ncs:module[ncs:name='huawei-l2vpn-extension']";
      must 'cir<=pir' {
        tailf:xpath-root 3;
        error-message "The pir value is less than cir value.";
      }
      must 'not(cir=0 and pir=0)' {
        tailf:xpath-root 3;
        error-message "The cir and pir value can not be zero at same time.";
      }
      presence "enable QoS for pw";
      description
        "Enable/disable the QoS parameter information.";
      uses qos-parameter-grp;
    }
    // NCS drop config false container 'qos-traffic-statistics'
  }
  augment "/ncs:devices/ncs:template/ncs:ned-id/ncs:config/l2vpn:l2vpn/l2vpn:instances/l2vpn:instance/l2vpn:vpws-ldp/l2vpn:pws/l2vpn:pw" {
    description
      "Configure the vpws-ldp pw QoS traffic statistics.";
    container qos-parameter {
      // NCS drop when statement
      // NCS drop must statement
      // NCS drop must statement
      presence "enable QoS for pw";
      description
        "Enable/disable the QoS parameter information.";
      uses ncs_template_qos-parameter-grp;
    }
    // NCS drop config false container 'qos-traffic-statistics'
  }
  augment "/ncs:devices/ncs:device/ncs:live-status/l2vpn:l2vpn/l2vpn:instances/l2vpn:instance/l2vpn:vpws-ldp/l2vpn:pws/l2vpn:pw" {
    description
      "Configure the vpws-ldp pw QoS traffic statistics.";
    container qos-parameter {
      tailf:ncs-device-type "netconf";
      tailf:display-when "not(../../../../../../../../ncs:module) or ../../../../../../../../ncs:module[ncs:name='huawei-l2vpn-extension'] or (../../../../../../../../ncs:live-status-protocol[not(ncs:capability)]) or (../../../../../../../../ncs:live-status-protocol/ncs:capability/ncs:module[.='huawei-l2vpn-extension'])";
      // NCS drop when statement
      // NCS drop must statement
      // NCS drop must statement
      presence "enable QoS for pw";
      description
        "Enable/disable the QoS parameter information.";
      uses live_ncs_qos-parameter-grp;
    }
    container qos-traffic-statistics {
      tailf:ncs-device-type "netconf";
      tailf:display-when "not(../../../../../../../../ncs:module) or ../../../../../../../../ncs:module[ncs:name='huawei-l2vpn-extension'] or (../../../../../../../../ncs:live-status-protocol[not(ncs:capability)]) or (../../../../../../../../ncs:live-status-protocol/ncs:capability/ncs:module[.='huawei-l2vpn-extension'])";
      description
        "Operational data of QoS traffic statistics table.";
      leaf interface-name {
        type leafref {
          path "/ncs:devices/ncs:device/ncs:live-status/ifm:ifm/ifm:interfaces/ifm:interface/ifm:name" {
            tailf:xpath-root 3;
          }
        }
        description
          "Indicates the type and number of the AC interface.";
      }
      uses live_ncs_qos-traffic-statistics-grp;
    }
  }
  augment "/ncs:devices/ncs:device/ncs:config/l2vpn:l2vpn/l2vpn:instances/l2vpn:instance/l2vpn:vpws-ldp/l2vpn:pws/l2vpn:pw" {
    description
      "Configure the vpws-ldp pw QoS traffic statistics.";
    container qos-parameter {
      tailf:ncs-device-type "netconf";
      tailf:display-when "not(../../../../../../../../ncs:module) or ../../../../../../../../ncs:module[ncs:name='huawei-l2vpn-extension']";
      when "../l2vpn:role!='ac-bypass' and ../l2vpn:role!='pw-bypass'" {
        tailf:xpath-root 3;
      }
      must 'cir<=pir' {
        tailf:xpath-root 3;
        error-message "The pir value is less than cir value.";
      }
      must 'not(cir=0 and pir=0)' {
        tailf:xpath-root 3;
        error-message "The cir and pir value can not be zero at same time.";
      }
      presence "enable QoS for pw";
      description
        "Enable/disable the QoS parameter information.";
      uses qos-parameter-grp;
    }
    // NCS drop config false container 'qos-traffic-statistics'
  }
  augment "/ncs:devices/ncs:template/ncs:ned-id/ncs:config/l2vpn:l2vpn/l2vpn:instances/l2vpn:instance/l2vpn:vpws-switch/l2vpn:pws/l2vpn:pw" {
    description
      "Configure the vpws-switch pw QoS traffic statistics.";
    container qos-parameter {
      // NCS drop when statement
      // NCS drop must statement
      // NCS drop must statement
      presence "enable QoS for pw";
      description
        "Enable/disable QoS parameter information.";
      uses ncs_template_qos-parameter-grp;
    }
  }
  augment "/ncs:devices/ncs:device/ncs:live-status/l2vpn:l2vpn/l2vpn:instances/l2vpn:instance/l2vpn:vpws-switch/l2vpn:pws/l2vpn:pw" {
    description
      "Configure the vpws-switch pw QoS traffic statistics.";
    container qos-parameter {
      tailf:ncs-device-type "netconf";
      tailf:display-when "not(../../../../../../../../ncs:module) or ../../../../../../../../ncs:module[ncs:name='huawei-l2vpn-extension'] or (../../../../../../../../ncs:live-status-protocol[not(ncs:capability)]) or (../../../../../../../../ncs:live-status-protocol/ncs:capability/ncs:module[.='huawei-l2vpn-extension'])";
      // NCS drop when statement
      // NCS drop must statement
      // NCS drop must statement
      presence "enable QoS for pw";
      description
        "Enable/disable QoS parameter information.";
      uses live_ncs_qos-parameter-grp;
    }
  }
  augment "/ncs:devices/ncs:device/ncs:config/l2vpn:l2vpn/l2vpn:instances/l2vpn:instance/l2vpn:vpws-switch/l2vpn:pws/l2vpn:pw" {
    description
      "Configure the vpws-switch pw QoS traffic statistics.";
    container qos-parameter {
      tailf:ncs-device-type "netconf";
      tailf:display-when "not(../../../../../../../../ncs:module) or ../../../../../../../../ncs:module[ncs:name='huawei-l2vpn-extension']";
      when "../../../l2vpn:switch-type != 'ldp-ldp-bak'" {
        tailf:xpath-root 3;
      }
      must 'cir<=pir' {
        tailf:xpath-root 3;
        error-message "The pir value is less than cir value.";
      }
      must 'not(cir=0 and pir=0)' {
        tailf:xpath-root 3;
        error-message "The cir and pir value can not be zero at same time.";
      }
      presence "enable QoS for pw";
      description
        "Enable/disable QoS parameter information.";
      uses qos-parameter-grp;
    }
  }
  augment "/ncs:devices/ncs:template/ncs:ned-id/ncs:config/l2vpn:l2vpn/l2vpn:common/l2vpn:pw-templates/l2vpn:pw-template" {
    description
      "Configure the QoS traffic statistics in pw-template.";
    container qos-parameter {
      // NCS drop must statement
      // NCS drop must statement
      presence "enable QoS for pw";
      description
        "Enable/disable QoS parameter information.";
      uses ncs_template_qos-parameter-grp;
    }
  }
  augment "/ncs:devices/ncs:device/ncs:live-status/l2vpn:l2vpn/l2vpn:common/l2vpn:pw-templates/l2vpn:pw-template" {
    description
      "Configure the QoS traffic statistics in pw-template.";
    container qos-parameter {
      tailf:ncs-device-type "netconf";
      tailf:display-when "not(../../../../../../ncs:module) or ../../../../../../ncs:module[ncs:name='huawei-l2vpn-extension'] or (../../../../../../ncs:live-status-protocol[not(ncs:capability)]) or (../../../../../../ncs:live-status-protocol/ncs:capability/ncs:module[.='huawei-l2vpn-extension'])";
      // NCS drop must statement
      // NCS drop must statement
      presence "enable QoS for pw";
      description
        "Enable/disable QoS parameter information.";
      uses live_ncs_qos-parameter-grp;
    }
  }
  augment "/ncs:devices/ncs:device/ncs:config/l2vpn:l2vpn/l2vpn:common/l2vpn:pw-templates/l2vpn:pw-template" {
    description
      "Configure the QoS traffic statistics in pw-template.";
    container qos-parameter {
      tailf:ncs-device-type "netconf";
      tailf:display-when "not(../../../../../../ncs:module) or ../../../../../../ncs:module[ncs:name='huawei-l2vpn-extension']";
      must 'cir<=pir' {
        tailf:xpath-root 3;
        error-message "The pir value is less than cir value.";
      }
      must 'not(cir=0 and pir=0)' {
        tailf:xpath-root 3;
        error-message "The cir and pir value can not be zero at same time.";
      }
      presence "enable QoS for pw";
      description
        "Enable/disable QoS parameter information.";
      uses qos-parameter-grp;
    }
  }
  augment "/ncs:devices/ncs:template/ncs:ned-id/ncs:config/l2vpn:l2vpn/l2vpn:instances/l2vpn:instance/l2vpn:vpls/l2vpn:acs/l2vpn:ac" {
    description
      "Configure the VPLS OAM mapping.";
    container ac-oam-mapping {
      // NCS drop when statement
      ext:operation-exclude "update";
      presence "enable ac oam mapping";
      description
        "Enable/disable OAM mapping.";
      leaf type {
        type l2vpn:ncs_template_ac-oam-mapping-type;
        // NCS drop must statement
        // NCS drop mandatory statement
        description
          "VPLS OAM mapping type.";
      }
      leaf md-name {
        // NCS drop when statement
        type string;
        description
          "VPLS OAM mapping parameter MD name.";
      }
      leaf ma-name {
        // NCS drop when statement
        type string;
        description
          "VPLS OAM mapping parameter MA name.";
      }
    }
  }
  augment "/ncs:devices/ncs:device/ncs:live-status/l2vpn:l2vpn/l2vpn:instances/l2vpn:instance/l2vpn:vpls/l2vpn:acs/l2vpn:ac" {
    description
      "Configure the VPLS OAM mapping.";
    container ac-oam-mapping {
      tailf:ncs-device-type "netconf";
      tailf:display-when "not(../../../../../../../../ncs:module) or ../../../../../../../../ncs:module[ncs:name='huawei-l2vpn-extension'] or (../../../../../../../../ncs:live-status-protocol[not(ncs:capability)]) or (../../../../../../../../ncs:live-status-protocol/ncs:capability/ncs:module[.='huawei-l2vpn-extension'])";
      // NCS drop when statement
      ext:operation-exclude "update";
      presence "enable ac oam mapping";
      description
        "Enable/disable OAM mapping.";
      leaf type {
        type l2vpn:live_ncs_ac-oam-mapping-type;
        // NCS drop must statement
        // NCS drop mandatory statement
        description
          "VPLS OAM mapping type.";
      }
      leaf md-name {
        // NCS drop when statement
        type string {
          length "1..43";
        }
        description
          "VPLS OAM mapping parameter MD name.";
      }
      leaf ma-name {
        // NCS drop when statement
        type string {
          length "1..43";
        }
        description
          "VPLS OAM mapping parameter MA name.";
      }
    }
  }
  augment "/ncs:devices/ncs:device/ncs:config/l2vpn:l2vpn/l2vpn:instances/l2vpn:instance/l2vpn:vpls/l2vpn:acs/l2vpn:ac" {
    description
      "Configure the VPLS OAM mapping.";
    container ac-oam-mapping {
      tailf:ncs-device-type "netconf";
      tailf:display-when "not(../../../../../../../../ncs:module) or ../../../../../../../../ncs:module[ncs:name='huawei-l2vpn-extension']";
      when "../../../l2vpn:work-mode='normal' and /ifm:ifm/ifm:interfaces/ifm:interface[ifm:name=current()/../l2vpn:interface-name]/ifm:class='sub-interface'" {
        tailf:xpath-root 3;
      }
      ext:operation-exclude "update";
      presence "enable ac oam mapping";
      description
        "Enable/disable OAM mapping.";
      leaf type {
        type l2vpn:ac-oam-mapping-type;
        must "../type='1ag' and ../md-name and ../ma-name" {
          tailf:xpath-root 3;
        }
        mandatory true;
        description
          "VPLS OAM mapping type.";
      }
      leaf md-name {
        when "../type='1ag'" {
          tailf:xpath-root 3;
        }
        type string {
          length "1..43";
        }
        description
          "VPLS OAM mapping parameter MD name.";
      }
      leaf ma-name {
        when "../type='1ag'" {
          tailf:xpath-root 3;
        }
        type string {
          length "1..43";
        }
        description
          "VPLS OAM mapping parameter MA name.";
      }
    }
  }
  augment "/ncs:devices/ncs:template/ncs:ned-id/ncs:config/l2vpn:l2vpn/l2vpn:instances/l2vpn:instance/l2vpn:vpls/l2vpn:ldp-signaling/l2vpn:pws/l2vpn:pw" {
    description
      "Configure the vpls track VRRP.";
    container track-vrrp {
      ext:operation-exclude "update";
      // NCS drop when statement
      presence "enable pw track vrrp";
      description
        "Configure VRRP parameter list.";
      leaf vrrp-interface-name {
        type string;
        // NCS drop must statement
        // NCS drop mandatory statement
        description
          "VRRP interface.";
      }
      leaf vrrp-vrid {
        type string;
        // NCS drop mandatory statement
        description
          "VRID of a VRRP backup group.";
      }
      leaf pw-redundancy {
        type string;
        // NCS drop must statement
        // NCS drop default statement
        description
          "Enable/disable VRRP PW redundancy mode.";
      }
      leaf backup-block-all {
        type string;
        // NCS drop must statement
        // NCS drop default statement
        description
          "Enable/disable block the traffic on the backup PW.";
      }
    }
  }
  augment "/ncs:devices/ncs:device/ncs:live-status/l2vpn:l2vpn/l2vpn:instances/l2vpn:instance/l2vpn:vpls/l2vpn:ldp-signaling/l2vpn:pws/l2vpn:pw" {
    description
      "Configure the vpls track VRRP.";
    container track-vrrp {
      tailf:ncs-device-type "netconf";
      tailf:display-when "not(../../../../../../../../../ncs:module) or ../../../../../../../../../ncs:module[ncs:name='huawei-l2vpn-extension'] or (../../../../../../../../../ncs:live-status-protocol[not(ncs:capability)]) or (../../../../../../../../../ncs:live-status-protocol/ncs:capability/ncs:module[.='huawei-l2vpn-extension'])";
      ext:operation-exclude "update";
      // NCS drop when statement
      presence "enable pw track vrrp";
      description
        "Configure VRRP parameter list.";
      leaf vrrp-interface-name {
        type leafref {
          path "/ncs:devices/ncs:device/ncs:live-status/ifm:ifm/ifm:interfaces/ifm:interface/ifm:name" {
            tailf:xpath-root 3;
          }
        }
        // NCS drop must statement
        // NCS drop mandatory statement
        description
          "VRRP interface.";
      }
      leaf vrrp-vrid {
        type uint32 {
          range "1..255";
        }
        // NCS drop mandatory statement
        description
          "VRID of a VRRP backup group.";
      }
      leaf pw-redundancy {
        type boolean;
        // NCS drop must statement
        // NCS drop default statement
        description
          "Enable/disable VRRP PW redundancy mode.";
      }
      leaf backup-block-all {
        type boolean;
        // NCS drop must statement
        // NCS drop default statement
        description
          "Enable/disable block the traffic on the backup PW.";
      }
    }
  }
  augment "/ncs:devices/ncs:device/ncs:config/l2vpn:l2vpn/l2vpn:instances/l2vpn:instance/l2vpn:vpls/l2vpn:ldp-signaling/l2vpn:pws/l2vpn:pw" {
    description
      "Configure the vpls track VRRP.";
    container track-vrrp {
      tailf:ncs-device-type "netconf";
      tailf:display-when "not(../../../../../../../../../ncs:module) or ../../../../../../../../../ncs:module[ncs:name='huawei-l2vpn-extension']";
      ext:operation-exclude "update";
      when "../../../../l2vpn:work-mode='bd-mode'" {
        tailf:xpath-root 3;
      }
      presence "enable pw track vrrp";
      description
        "Configure VRRP parameter list.";
      leaf vrrp-interface-name {
        type leafref {
          path "/ncs:devices/ncs:device/ncs:config/ifm:ifm/ifm:interfaces/ifm:interface/ifm:name" {
            tailf:xpath-root 3;
          }
        }
        must '/ifm:ifm/ifm:interfaces/ifm:interface[ifm:name=current()]/ip:ipv4/vrrp:vrrp/vrrp:groups/vrrp:group[vrrp:id=current()/../vrrp-vrid]/vrrp:admin-flag' {
          tailf:xpath-root 3;
        }
        mandatory true;
        description
          "VRRP interface.";
      }
      leaf vrrp-vrid {
        type uint32 {
          range "1..255";
        }
        mandatory true;
        description
          "VRID of a VRRP backup group.";
      }
      leaf pw-redundancy {
        type boolean;
        must "../pw-redundancy='true'" {
          tailf:xpath-root 3;
        }
        default "true";
        description
          "Enable/disable VRRP PW redundancy mode.";
      }
      leaf backup-block-all {
        type boolean;
        must "../backup-block-all='true'" {
          tailf:xpath-root 3;
        }
        default "true";
        description
          "Enable/disable block the traffic on the backup PW.";
      }
    }
  }
}
