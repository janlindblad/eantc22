module huawei-http {
  // Generated by yanger -t ncs
  tailf:mount-id "huawei-nc-1.0:huawei-nc-1.0";
  tailf:ncs-device-type "netconf";

  namespace "urn:huawei:yang:huawei-http";
  prefix http;

  import huawei-extension {
    prefix ext;
  }
  import huawei-ssl {
    prefix ssl;
  }
  import huawei-acl {
    prefix acl;
  }
  import huawei-pub-type {
    prefix pub-type;
  }
  import ietf-inet-types {
    prefix inet;
  }
  import huawei-network-instance {
    prefix ni;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "HTTP server and client.";

  revision 2020-07-21 {
    description
      "Initial revision.";
    reference "Huawei private.";
  }
  ext:task-name "https";

  typedef ncs_template_http-server-type {
    type string;
    description
      "HTTP service type.";
  }

  typedef ncs_template_httpc-trans-cmd-type {
    type string;
    description
      "FTP client transfer command type.";
  }

  typedef ncs_rpc_notif_http-server-type {
    type enumeration {
      enum "restconf" {
        value 1;
        description
          "Restconf: restconf service type.";
      }
    }
    description
      "HTTP service type.";
  }

  typedef ncs_rpc_notif_httpc-trans-cmd-type {
    type enumeration {
      enum "upload" {
        value 1;
        description
          "Upload local files to the remote server.";
      }
      enum "download" {
        value 2;
        description
          "Download files from the remote server to the client.";
      }
    }
    description
      "FTP client transfer command type.";
  }

  typedef live_ncs_http-server-type {
    type enumeration {
      enum "restconf" {
        value 1;
        description
          "Restconf: restconf service type.";
      }
    }
    description
      "HTTP service type.";
  }

  typedef live_ncs_httpc-trans-cmd-type {
    type enumeration {
      enum "upload" {
        value 1;
        description
          "Upload local files to the remote server.";
      }
      enum "download" {
        value 2;
        description
          "Download files from the remote server to the client.";
      }
    }
    description
      "FTP client transfer command type.";
  }

  typedef http-server-type {
    type enumeration {
      enum "restconf" {
        value 1;
        description
          "Restconf: restconf service type.";
      }
    }
    description
      "HTTP service type.";
  }

  typedef httpc-trans-cmd-type {
    type enumeration {
      enum "upload" {
        value 1;
        description
          "Upload local files to the remote server.";
      }
      enum "download" {
        value 2;
        description
          "Download files from the remote server to the client.";
      }
    }
    description
      "FTP client transfer command type.";
  }

  augment "/ncs:devices/ncs:device/ncs:rpc" {
    container rpc-httpc-transfer-file {
      tailf:ncs-device-type "netconf";
      tailf:display-when "not(../../ncs:module) or ../../ncs:module[ncs:name='huawei-http']";
      tailf:action httpc-transfer-file {
        tailf:actionpoint ncsproxy {
          tailf:internal;
        }
        description
          "HTTP client transfer file.";
        input {
          leaf operation-type {
            type ncs_rpc_notif_httpc-trans-cmd-type;
            mandatory true;
            description
              "Specify the type of the operation to be performed.";
          }
          leaf file-url {
            type string {
              length "1..255";
            }
            mandatory true;
            description
              "Download/upload file URL.";
          }
          leaf file-full-path {
            type string {
              length "1..255";
            }
            mandatory true;
            description
              "Download/upload file full path including file name.";
          }
          leaf ssl-policy-name {
            type string;
            description
              "SSL policy name.";
          }
          leaf ssl-verify {
            type boolean;
            must '../ssl-policy-name' {
              tailf:xpath-root 3;
            }
            description
              "Enable/disable SSL verify.";
          }
          leaf user-name {
            type string {
              length "1..127";
            }
            description
              "Specifies the authentication user name for file transfer.";
          }
          leaf password {
            type pub-type:ncs_rpc_notif_password-extend;
            description
              "Specifies the authentication password for file transfer.";
          }
          leaf source-ipv4-address {
            type inet:ipv4-address-no-zone;
            description
              "Specifies the source IPv4 address of the server connection.";
          }
          leaf vpn-name {
            type string;
            must '../source-ipv4-address' {
              tailf:xpath-root 3;
            }
            description
              "Specifies the VPN name of the server connection.";
          }
        }
      }
    }
  }
  augment "/ncs:devices/ncs:device-group/ncs:ned-id/ncs:rpc" {
    container rpc-httpc-transfer-file {
      tailf:ncs-device-type "netconf";
      tailf:display-when "/ncs:devices/ncs:device[ncs:name=current()/../../../ncs:member]/ncs:module[ncs:name='huawei-http']";
      tailf:action httpc-transfer-file {
        tailf:actionpoint ncsproxy {
          tailf:internal;
        }
        description
          "HTTP client transfer file.";
        input {
          leaf operation-type {
            type ncs_rpc_notif_httpc-trans-cmd-type;
            mandatory true;
            description
              "Specify the type of the operation to be performed.";
          }
          leaf file-url {
            type string {
              length "1..255";
            }
            mandatory true;
            description
              "Download/upload file URL.";
          }
          leaf file-full-path {
            type string {
              length "1..255";
            }
            mandatory true;
            description
              "Download/upload file full path including file name.";
          }
          leaf ssl-policy-name {
            type string;
            description
              "SSL policy name.";
          }
          leaf ssl-verify {
            type boolean;
            must '../ssl-policy-name' {
              tailf:xpath-root 4;
            }
            description
              "Enable/disable SSL verify.";
          }
          leaf user-name {
            type string {
              length "1..127";
            }
            description
              "Specifies the authentication user name for file transfer.";
          }
          leaf password {
            type pub-type:ncs_rpc_notif_password-extend;
            description
              "Specifies the authentication password for file transfer.";
          }
          leaf source-ipv4-address {
            type inet:ipv4-address-no-zone;
            description
              "Specifies the source IPv4 address of the server connection.";
          }
          leaf vpn-name {
            type string;
            must '../source-ipv4-address' {
              tailf:xpath-root 4;
            }
            description
              "Specifies the VPN name of the server connection.";
          }
        }
      }
    }
  }
  augment "/ncs:devices/ncs:device/ncs:config" {
    container http {
      tailf:ncs-device-type "netconf";
      tailf:display-when "not(../../ncs:module) or ../../ncs:module[ncs:name='huawei-http']";
      description
        "HTTP.";
      container comp-enable {
        description
          "Configure HTTP enable.";
        leaf comp-enable {
          type boolean;
          default "false";
          description
            "Enable/disable HTTP function.";
        }
      }
      container client {
        when "../comp-enable/comp-enable = 'true'" {
          tailf:xpath-root 3;
        }
        description
          "Configure HTTP client.";
        leaf ssl-policy-name {
          type leafref {
            path "/ncs:devices/ncs:device/ncs:config/ssl:ssl/ssl:ssl-policys/ssl:ssl-policy/ssl:policy-name" {
              tailf:xpath-root 3;
            }
          }
          description
            "SSL policy name.";
        }
        leaf ssl-verify-type {
          when '../ssl-policy-name' {
            tailf:xpath-root 3;
          }
          type boolean;
          default "false";
          description
            "Enable/disable SSL verify peer.";
        }
      }
      container servers {
        when "../comp-enable/comp-enable = 'true'" {
          tailf:xpath-root 3;
        }
        description
          "List of HTTP server configuration.";
        list server {
          key "server-type";
          description
            "Configure HTTP server.";
          leaf server-type {
            type http-server-type;
            description
              "HTTP server type.";
          }
          leaf server-enable {
            type boolean;
            must "../secure-enable != 'true' or (../secure-enable = 'true' and ../server-enable = 'false')" {
              tailf:xpath-root 3;
            }
            default "false";
            description
              "Enable/disable HTTP server.";
          }
          leaf secure-enable {
            type boolean;
            must "../server-enable != 'true' or (../server-enable = 'true' and ../secure-enable = 'false')" {
              tailf:xpath-root 3;
            }
            default "false";
            description
              "Enable/disable HTTP secure server.";
          }
          leaf server-port {
            type uint32 {
              range "80 | 1025..65535";
            }
            default "80";
            description
              "HTTP server port.";
          }
          leaf secure-port {
            type uint32 {
              range "443 | 1025..65535";
            }
            default "443";
            description
              "HTTP secure server port.";
          }
          leaf acl-name {
            type leafref {
              path "/ncs:devices/ncs:device/ncs:config/acl:acl/acl:groups/acl:group/acl:identity" {
                tailf:xpath-root 3;
              }
            }
            must "/acl:acl/acl:groups/acl:group[acl:identity=current()]/acl:type='basic' or /acl:acl/acl:groups/acl:group[acl:identity=current()]/acl:type='advance'" {
              tailf:xpath-root 3;
            }
            description
              "HTTP server ACL name or number for IPv4 connections.";
          }
          leaf ssl-policy-name {
            type leafref {
              path "/ncs:devices/ncs:device/ncs:config/ssl:ssl/ssl:ssl-policys/ssl:ssl-policy/ssl:policy-name" {
                tailf:xpath-root 3;
              }
            }
            must "../secure-enable = 'true' " {
              tailf:xpath-root 3;
            }
            description
              "SSL policy name.";
          }
          leaf ssl-verify-type {
            when "../secure-enable = 'true'  and ../ssl-policy-name" {
              tailf:xpath-root 3;
            }
            type boolean;
            default "false";
            description
              "Enable/disable SSL verify.";
          }
          leaf idle-timeout {
            type uint32 {
              range "1..60";
            }
            default "20";
            description
              "Idle timeout.";
          }
        }
      }
      container server-source {
        when "../comp-enable/comp-enable = 'true' and count(../servers/server[server-type = 'restconf']) > 0 " {
          tailf:xpath-root 3;
        }
        description
          "Configure http server interfaces.";
        leaf src-interface {
          when "../all-interface = 'false'" {
            tailf:xpath-root 3;
          }
          type pub-type:if-name;
          description
            "Specify the source interface name. The specified source interface must exist and an IP address must be configured on the interface.";
        }
        leaf all-interface {
          type boolean;
          default "false";
          description
            "Enable/disable specify all interfaces.";
        }
      }
    }
  }
  augment "/ncs:devices/ncs:device/ncs:live-status" {
    container http {
      tailf:ncs-device-type "netconf";
      tailf:display-when "not(../../ncs:module) or ../../ncs:module[ncs:name='huawei-http'] or (../../ncs:live-status-protocol[not(ncs:capability)]) or (../../ncs:live-status-protocol/ncs:capability/ncs:module[.='huawei-http'])";
      description
        "HTTP.";
      container comp-enable {
        description
          "Configure HTTP enable.";
        leaf comp-enable {
          type boolean;
          // NCS drop default statement
          description
            "Enable/disable HTTP function.";
        }
      }
      container client {
        // NCS drop when statement
        description
          "Configure HTTP client.";
        leaf ssl-policy-name {
          type leafref {
            path "/ncs:devices/ncs:device/ncs:live-status/ssl:ssl/ssl:ssl-policys/ssl:ssl-policy/ssl:policy-name" {
              tailf:xpath-root 3;
            }
          }
          description
            "SSL policy name.";
        }
        leaf ssl-verify-type {
          // NCS drop when statement
          type boolean;
          // NCS drop default statement
          description
            "Enable/disable SSL verify peer.";
        }
      }
      container servers {
        // NCS drop when statement
        description
          "List of HTTP server configuration.";
        list server {
          key "server-type";
          description
            "Configure HTTP server.";
          leaf server-type {
            type live_ncs_http-server-type;
            description
              "HTTP server type.";
          }
          leaf server-enable {
            type boolean;
            // NCS drop must statement
            // NCS drop default statement
            description
              "Enable/disable HTTP server.";
          }
          leaf secure-enable {
            type boolean;
            // NCS drop must statement
            // NCS drop default statement
            description
              "Enable/disable HTTP secure server.";
          }
          leaf server-port {
            type uint32 {
              range "80 | 1025..65535";
            }
            // NCS drop default statement
            description
              "HTTP server port.";
          }
          leaf secure-port {
            type uint32 {
              range "443 | 1025..65535";
            }
            // NCS drop default statement
            description
              "HTTP secure server port.";
          }
          leaf acl-name {
            type leafref {
              path "/ncs:devices/ncs:device/ncs:live-status/acl:acl/acl:groups/acl:group/acl:identity" {
                tailf:xpath-root 3;
              }
            }
            // NCS drop must statement
            description
              "HTTP server ACL name or number for IPv4 connections.";
          }
          leaf ssl-policy-name {
            type leafref {
              path "/ncs:devices/ncs:device/ncs:live-status/ssl:ssl/ssl:ssl-policys/ssl:ssl-policy/ssl:policy-name" {
                tailf:xpath-root 3;
              }
            }
            // NCS drop must statement
            description
              "SSL policy name.";
          }
          leaf ssl-verify-type {
            // NCS drop when statement
            type boolean;
            // NCS drop default statement
            description
              "Enable/disable SSL verify.";
          }
          leaf idle-timeout {
            type uint32 {
              range "1..60";
            }
            // NCS drop default statement
            description
              "Idle timeout.";
          }
        }
      }
      container server-source {
        // NCS drop when statement
        description
          "Configure http server interfaces.";
        leaf src-interface {
          // NCS drop when statement
          type pub-type:live_ncs_if-name;
          description
            "Specify the source interface name. The specified source interface must exist and an IP address must be configured on the interface.";
        }
        leaf all-interface {
          type boolean;
          // NCS drop default statement
          description
            "Enable/disable specify all interfaces.";
        }
      }
    }
  }
  augment "/ncs:devices/ncs:template/ncs:ned-id/ncs:config" {
    container http {
      description
        "HTTP.";
      container comp-enable {
        description
          "Configure HTTP enable.";
        leaf comp-enable {
          type string;
          // NCS drop default statement
          description
            "Enable/disable HTTP function.";
        }
      }
      container client {
        // NCS drop when statement
        description
          "Configure HTTP client.";
        leaf ssl-policy-name {
          type string;
          description
            "SSL policy name.";
        }
        leaf ssl-verify-type {
          // NCS drop when statement
          type string;
          // NCS drop default statement
          description
            "Enable/disable SSL verify peer.";
        }
      }
      container servers {
        // NCS drop when statement
        description
          "List of HTTP server configuration.";
        list server {
          // NCS patched for predictable order
          ordered-by user;
          key "server-type";
          description
            "Configure HTTP server.";
          leaf server-type {
            type ncs_template_http-server-type;
            description
              "HTTP server type.";
          }
          leaf server-enable {
            type string;
            // NCS drop must statement
            // NCS drop default statement
            description
              "Enable/disable HTTP server.";
          }
          leaf secure-enable {
            type string;
            // NCS drop must statement
            // NCS drop default statement
            description
              "Enable/disable HTTP secure server.";
          }
          leaf server-port {
            type string;
            // NCS drop default statement
            description
              "HTTP server port.";
          }
          leaf secure-port {
            type string;
            // NCS drop default statement
            description
              "HTTP secure server port.";
          }
          leaf acl-name {
            type string;
            // NCS drop must statement
            description
              "HTTP server ACL name or number for IPv4 connections.";
          }
          leaf ssl-policy-name {
            type string;
            // NCS drop must statement
            description
              "SSL policy name.";
          }
          leaf ssl-verify-type {
            // NCS drop when statement
            type string;
            // NCS drop default statement
            description
              "Enable/disable SSL verify.";
          }
          leaf idle-timeout {
            type string;
            // NCS drop default statement
            description
              "Idle timeout.";
          }
        }
      }
      container server-source {
        // NCS drop when statement
        description
          "Configure http server interfaces.";
        leaf src-interface {
          // NCS drop when statement
          type pub-type:ncs_template_if-name;
          description
            "Specify the source interface name. The specified source interface must exist and an IP address must be configured on the interface.";
        }
        leaf all-interface {
          type string;
          // NCS drop default statement
          description
            "Enable/disable specify all interfaces.";
        }
      }
    }
  }
}
