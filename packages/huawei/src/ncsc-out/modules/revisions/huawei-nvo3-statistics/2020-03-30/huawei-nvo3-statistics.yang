module huawei-nvo3-statistics {
  // Generated by yanger -t ncs
  tailf:mount-id "huawei-nc-1.0:huawei-nc-1.0";
  tailf:ncs-device-type "netconf";

  namespace "urn:huawei:yang:huawei-nvo3-statistics";
  prefix nvo3-statistics;

  import ietf-inet-types {
    prefix inet;
  }
  import huawei-nvo3 {
    prefix nvo3;
  }
  import huawei-ifm {
    prefix ifm;
  }
  import huawei-extension {
    prefix ext;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Management for data center network virtualization over Layer 3.";

  revision 2020-03-30 {
    description
      "Initial revision.";
    reference "Huawei private.";
  }
  ext:task-name "nvo3";

  typedef ncs_template_vxlan-mode {
    type string;
    description
      "VXLAN mode.";
  }

  typedef ncs_template_statistics-direction {
    type string;
    description
      "VXLAN tunnel traffic statistics type.";
  }

  typedef ncs_rpc_notif_vxlan-mode {
    type enumeration {
      enum "l2" {
        value 0;
        description
          "Layer 2.";
      }
      enum "l3" {
        value 1;
        description
          "Layer 3.";
      }
      enum "both" {
        value 2;
        description
          "Both layer 2 and 3.";
      }
    }
    description
      "VXLAN mode.";
  }

  typedef ncs_rpc_notif_statistics-direction {
    type enumeration {
      enum "inbound" {
        value 0;
        description
          "Inbound direction.";
      }
      enum "outbound" {
        value 1;
        description
          "Outbound direction.";
      }
      enum "bidirection" {
        value 2;
        description
          "Bidirection.";
      }
    }
    description
      "VXLAN tunnel traffic statistics type.";
  }

  typedef live_ncs_vxlan-mode {
    type enumeration {
      enum "l2" {
        value 0;
        description
          "Layer 2.";
      }
      enum "l3" {
        value 1;
        description
          "Layer 3.";
      }
      enum "both" {
        value 2;
        description
          "Both layer 2 and 3.";
      }
    }
    description
      "VXLAN mode.";
  }

  typedef live_ncs_statistics-direction {
    type enumeration {
      enum "inbound" {
        value 0;
        description
          "Inbound direction.";
      }
      enum "outbound" {
        value 1;
        description
          "Outbound direction.";
      }
      enum "bidirection" {
        value 2;
        description
          "Bidirection.";
      }
    }
    description
      "VXLAN tunnel traffic statistics type.";
  }

  typedef vxlan-mode {
    type enumeration {
      enum "l2" {
        value 0;
        description
          "Layer 2.";
      }
      enum "l3" {
        value 1;
        description
          "Layer 3.";
      }
      enum "both" {
        value 2;
        description
          "Both layer 2 and 3.";
      }
    }
    description
      "VXLAN mode.";
  }

  typedef statistics-direction {
    type enumeration {
      enum "inbound" {
        value 0;
        description
          "Inbound direction.";
      }
      enum "outbound" {
        value 1;
        description
          "Outbound direction.";
      }
      enum "bidirection" {
        value 2;
        description
          "Bidirection.";
      }
    }
    description
      "VXLAN tunnel traffic statistics type.";
  }

  grouping ncs_template_vxlan-traffic-collection {
    description
      "VXLAN tunnel traffic statistics collection.";
    leaf send-bits-rate {
      type string;
      units "bit/s";
      description
        "Number of send bits per second.";
    }
    leaf send-pkts-rate {
      type string;
      units "pps";
      description
        "Number of send packets per second.";
    }
    leaf send-unicast-pkts {
      type string;
      units "packet";
      description
        "Number of send unicast packets.";
    }
    leaf send-multicast-pkts {
      type string;
      units "packet";
      description
        "Number of send multicast packets.";
    }
    leaf send-broadcast-pkts {
      type string;
      units "packet";
      description
        "Number of send broadcast packets.";
    }
    leaf send-total-bytes {
      type string;
      units "Byte";
      description
        "Total number of send bytes.";
    }
    leaf send-total-pkts {
      type string;
      units "packet";
      description
        "Total number of send packets.";
    }
    leaf receive-bits-rate {
      type string;
      units "bit/s";
      description
        "Number of receive bits per second.";
    }
    leaf receive-pkts-rate {
      type string;
      units "pps";
      description
        "Number of receive packets per second.";
    }
    leaf receive-unicast-pkts {
      type string;
      units "packet";
      description
        "Number of receive unicast packets.";
    }
    leaf receive-multicast-pkts {
      type string;
      units "packet";
      description
        "Number of receive multicast packets.";
    }
    leaf receive-broadcast-pkts {
      type string;
      units "packet";
      description
        "Number of receive broadcast packets.";
    }
    leaf receive-total-bytes {
      type string;
      units "Byte";
      description
        "Total number of receive bytes.";
    }
    leaf receive-total-pkts {
      type string;
      units "packet";
      description
        "Total number of receive packets.";
    }
    leaf drop-unicast-pkts {
      type string;
      units "packet";
      description
        "Number of discarded unicast packets.";
    }
    leaf drop-multicast-pkts {
      type string;
      units "packet";
      description
        "Number of discarded multicast packets.";
    }
    leaf drop-broadcast-pkts {
      type string;
      units "packet";
      description
        "Number of discarded broadcast packets.";
    }
  }

  grouping ncs_rpc_notif_vxlan-traffic-collection {
    description
      "VXLAN tunnel traffic statistics collection.";
    leaf send-bits-rate {
      type uint64;
      units "bit/s";
      description
        "Number of send bits per second.";
    }
    leaf send-pkts-rate {
      type uint64;
      units "pps";
      description
        "Number of send packets per second.";
    }
    leaf send-unicast-pkts {
      type uint64;
      units "packet";
      description
        "Number of send unicast packets.";
    }
    leaf send-multicast-pkts {
      type uint64;
      units "packet";
      description
        "Number of send multicast packets.";
    }
    leaf send-broadcast-pkts {
      type uint64;
      units "packet";
      description
        "Number of send broadcast packets.";
    }
    leaf send-total-bytes {
      type uint64;
      units "Byte";
      description
        "Total number of send bytes.";
    }
    leaf send-total-pkts {
      type uint64;
      units "packet";
      description
        "Total number of send packets.";
    }
    leaf receive-bits-rate {
      type uint64;
      units "bit/s";
      description
        "Number of receive bits per second.";
    }
    leaf receive-pkts-rate {
      type uint64;
      units "pps";
      description
        "Number of receive packets per second.";
    }
    leaf receive-unicast-pkts {
      type uint64;
      units "packet";
      description
        "Number of receive unicast packets.";
    }
    leaf receive-multicast-pkts {
      type uint64;
      units "packet";
      description
        "Number of receive multicast packets.";
    }
    leaf receive-broadcast-pkts {
      type uint64;
      units "packet";
      description
        "Number of receive broadcast packets.";
    }
    leaf receive-total-bytes {
      type uint64;
      units "Byte";
      description
        "Total number of receive bytes.";
    }
    leaf receive-total-pkts {
      type uint64;
      units "packet";
      description
        "Total number of receive packets.";
    }
    leaf drop-unicast-pkts {
      type uint64;
      units "packet";
      description
        "Number of discarded unicast packets.";
    }
    leaf drop-multicast-pkts {
      type uint64;
      units "packet";
      description
        "Number of discarded multicast packets.";
    }
    leaf drop-broadcast-pkts {
      type uint64;
      units "packet";
      description
        "Number of discarded broadcast packets.";
    }
  }

  grouping live_ncs_vxlan-traffic-collection {
    description
      "VXLAN tunnel traffic statistics collection.";
    leaf send-bits-rate {
      type uint64;
      units "bit/s";
      description
        "Number of send bits per second.";
    }
    leaf send-pkts-rate {
      type uint64;
      units "pps";
      description
        "Number of send packets per second.";
    }
    leaf send-unicast-pkts {
      type uint64;
      units "packet";
      description
        "Number of send unicast packets.";
    }
    leaf send-multicast-pkts {
      type uint64;
      units "packet";
      description
        "Number of send multicast packets.";
    }
    leaf send-broadcast-pkts {
      type uint64;
      units "packet";
      description
        "Number of send broadcast packets.";
    }
    leaf send-total-bytes {
      type uint64;
      units "Byte";
      description
        "Total number of send bytes.";
    }
    leaf send-total-pkts {
      type uint64;
      units "packet";
      description
        "Total number of send packets.";
    }
    leaf receive-bits-rate {
      type uint64;
      units "bit/s";
      description
        "Number of receive bits per second.";
    }
    leaf receive-pkts-rate {
      type uint64;
      units "pps";
      description
        "Number of receive packets per second.";
    }
    leaf receive-unicast-pkts {
      type uint64;
      units "packet";
      description
        "Number of receive unicast packets.";
    }
    leaf receive-multicast-pkts {
      type uint64;
      units "packet";
      description
        "Number of receive multicast packets.";
    }
    leaf receive-broadcast-pkts {
      type uint64;
      units "packet";
      description
        "Number of receive broadcast packets.";
    }
    leaf receive-total-bytes {
      type uint64;
      units "Byte";
      description
        "Total number of receive bytes.";
    }
    leaf receive-total-pkts {
      type uint64;
      units "packet";
      description
        "Total number of receive packets.";
    }
    leaf drop-unicast-pkts {
      type uint64;
      units "packet";
      description
        "Number of discarded unicast packets.";
    }
    leaf drop-multicast-pkts {
      type uint64;
      units "packet";
      description
        "Number of discarded multicast packets.";
    }
    leaf drop-broadcast-pkts {
      type uint64;
      units "packet";
      description
        "Number of discarded broadcast packets.";
    }
  }

  grouping vxlan-traffic-collection {
    description
      "VXLAN tunnel traffic statistics collection.";
    leaf send-bits-rate {
      type uint64;
      units "bit/s";
      description
        "Number of send bits per second.";
    }
    leaf send-pkts-rate {
      type uint64;
      units "pps";
      description
        "Number of send packets per second.";
    }
    leaf send-unicast-pkts {
      type uint64;
      units "packet";
      description
        "Number of send unicast packets.";
    }
    leaf send-multicast-pkts {
      type uint64;
      units "packet";
      description
        "Number of send multicast packets.";
    }
    leaf send-broadcast-pkts {
      type uint64;
      units "packet";
      description
        "Number of send broadcast packets.";
    }
    leaf send-total-bytes {
      type uint64;
      units "Byte";
      description
        "Total number of send bytes.";
    }
    leaf send-total-pkts {
      type uint64;
      units "packet";
      description
        "Total number of send packets.";
    }
    leaf receive-bits-rate {
      type uint64;
      units "bit/s";
      description
        "Number of receive bits per second.";
    }
    leaf receive-pkts-rate {
      type uint64;
      units "pps";
      description
        "Number of receive packets per second.";
    }
    leaf receive-unicast-pkts {
      type uint64;
      units "packet";
      description
        "Number of receive unicast packets.";
    }
    leaf receive-multicast-pkts {
      type uint64;
      units "packet";
      description
        "Number of receive multicast packets.";
    }
    leaf receive-broadcast-pkts {
      type uint64;
      units "packet";
      description
        "Number of receive broadcast packets.";
    }
    leaf receive-total-bytes {
      type uint64;
      units "Byte";
      description
        "Total number of receive bytes.";
    }
    leaf receive-total-pkts {
      type uint64;
      units "packet";
      description
        "Total number of receive packets.";
    }
    leaf drop-unicast-pkts {
      type uint64;
      units "packet";
      description
        "Number of discarded unicast packets.";
    }
    leaf drop-multicast-pkts {
      type uint64;
      units "packet";
      description
        "Number of discarded multicast packets.";
    }
    leaf drop-broadcast-pkts {
      type uint64;
      units "packet";
      description
        "Number of discarded broadcast packets.";
    }
  }

  augment "/ncs:devices/ncs:device/ncs:rpc" {
    container rpc-reset-vtep-statistics {
      tailf:ncs-device-type "netconf";
      tailf:display-when "not(../../ncs:module) or ../../ncs:module[ncs:name='huawei-nvo3-statistics']";
      tailf:action reset-vtep-statistics {
        tailf:actionpoint ncsproxy {
          tailf:internal;
        }
        description
          "Clear VXLAN tunnel traffic statistics collection for a VTEP.";
        ext:node-ref "/ifm:ifm/ifm:interfaces/ifm:interface/nvo3-statistics:nvo3-vtep-statistics/nvo3-statistics:nvo3-vtep-statistic/nvo3-statistics:collections/nvo3-statistics:collection";
        input {
          leaf vni {
            type uint32 {
              range "1..16777215";
            }
            mandatory true;
            description
              "VXLAN network identifier.";
          }
          leaf source {
            type inet:ipv4-address-no-zone;
            mandatory true;
            description
              "The srource address of VTEP.";
          }
          leaf peer {
            type inet:ipv4-address-no-zone;
            mandatory true;
            description
              "The address of VTEP.";
          }
          leaf mode {
            type ncs_rpc_notif_vxlan-mode;
            mandatory true;
            description
              "The type of VXLAN tunnel traffic statistics.";
          }
          leaf direction {
            type ncs_rpc_notif_statistics-direction;
            must "(../mode = 'l2') or (../mode = 'l3' and (../direction != 'bidirection'))" {
              tailf:xpath-root 3;
            }
            mandatory true;
            description
              "Traffic statistics direction.";
          }
        }
      }
    }
  }
  augment "/ncs:devices/ncs:device-group/ncs:ned-id/ncs:rpc" {
    container rpc-reset-vtep-statistics {
      tailf:ncs-device-type "netconf";
      tailf:display-when "/ncs:devices/ncs:device[ncs:name=current()/../../../ncs:member]/ncs:module[ncs:name='huawei-nvo3-statistics']";
      tailf:action reset-vtep-statistics {
        tailf:actionpoint ncsproxy {
          tailf:internal;
        }
        description
          "Clear VXLAN tunnel traffic statistics collection for a VTEP.";
        ext:node-ref "/ifm:ifm/ifm:interfaces/ifm:interface/nvo3-statistics:nvo3-vtep-statistics/nvo3-statistics:nvo3-vtep-statistic/nvo3-statistics:collections/nvo3-statistics:collection";
        input {
          leaf vni {
            type uint32 {
              range "1..16777215";
            }
            mandatory true;
            description
              "VXLAN network identifier.";
          }
          leaf source {
            type inet:ipv4-address-no-zone;
            mandatory true;
            description
              "The srource address of VTEP.";
          }
          leaf peer {
            type inet:ipv4-address-no-zone;
            mandatory true;
            description
              "The address of VTEP.";
          }
          leaf mode {
            type ncs_rpc_notif_vxlan-mode;
            mandatory true;
            description
              "The type of VXLAN tunnel traffic statistics.";
          }
          leaf direction {
            type ncs_rpc_notif_statistics-direction;
            must "(../mode = 'l2') or (../mode = 'l3' and (../direction != 'bidirection'))" {
              tailf:xpath-root 4;
            }
            mandatory true;
            description
              "Traffic statistics direction.";
          }
        }
      }
    }
  }
  augment "/ncs:devices/ncs:device/ncs:rpc" {
    container rpc-reset-vni-label-statistics {
      tailf:ncs-device-type "netconf";
      tailf:display-when "not(../../ncs:module) or ../../ncs:module[ncs:name='huawei-nvo3-statistics']";
      tailf:action reset-vni-label-statistics {
        tailf:actionpoint ncsproxy {
          tailf:internal;
        }
        description
          "Clear VXLAN tunnel traffic statistics collection for a VNI.";
        ext:node-ref "/nvo3:nvo3/nvo3:vni-labels/nvo3:vni-label/nvo3-statistics:statistics/nvo3-statistics:collections";
        input {
          leaf vni {
            type uint32 {
              range "1..16777215";
            }
            mandatory true;
            description
              "VXLAN network identifier.";
          }
        }
      }
    }
  }
  augment "/ncs:devices/ncs:device-group/ncs:ned-id/ncs:rpc" {
    container rpc-reset-vni-label-statistics {
      tailf:ncs-device-type "netconf";
      tailf:display-when "/ncs:devices/ncs:device[ncs:name=current()/../../../ncs:member]/ncs:module[ncs:name='huawei-nvo3-statistics']";
      tailf:action reset-vni-label-statistics {
        tailf:actionpoint ncsproxy {
          tailf:internal;
        }
        description
          "Clear VXLAN tunnel traffic statistics collection for a VNI.";
        ext:node-ref "/nvo3:nvo3/nvo3:vni-labels/nvo3:vni-label/nvo3-statistics:statistics/nvo3-statistics:collections";
        input {
          leaf vni {
            type uint32 {
              range "1..16777215";
            }
            mandatory true;
            description
              "VXLAN network identifier.";
          }
        }
      }
    }
  }
  augment "/ncs:devices/ncs:template/ncs:ned-id/ncs:config/ifm:ifm/ifm:interfaces/ifm:interface" {
    description
      "The NVO3 statistics for interface.";
    container nvo3-vtep-statistics {
      // NCS drop when statement
      description
        "List of VXLAN tunnel statistics.";
      list nvo3-vtep-statistic {
        // NCS patched for predictable order
        ordered-by user;
        key "vni peer mode direction";
        description
          "Configure VTEP statistics collection.";
        leaf vni {
          type string;
          // NCS drop must statement
          description
            "VXLAN network identifier.";
        }
        leaf peer {
          type string;
          description
            "The peer address of VTEP.";
        }
        leaf mode {
          type ncs_template_vxlan-mode;
          // NCS drop must statement
          description
            "The type of VXLAN tunnel traffic statistics.";
        }
        leaf direction {
          type ncs_template_statistics-direction;
          // NCS drop must statement
          description
            "Traffic statistics direction.";
        }
        // NCS drop config false container collections
      }
    }
  }
  augment "/ncs:devices/ncs:device/ncs:live-status/ifm:ifm/ifm:interfaces/ifm:interface" {
    description
      "The NVO3 statistics for interface.";
    container nvo3-vtep-statistics {
      tailf:ncs-device-type "netconf";
      tailf:display-when "not(../../../../../ncs:module) or ../../../../../ncs:module[ncs:name='huawei-nvo3-statistics'] or (../../../../../ncs:live-status-protocol[not(ncs:capability)]) or (../../../../../ncs:live-status-protocol/ncs:capability/ncs:module[.='huawei-nvo3-statistics'])";
      // NCS drop when statement
      description
        "List of VXLAN tunnel statistics.";
      list nvo3-vtep-statistic {
        key "vni peer mode direction";
        description
          "Configure VTEP statistics collection.";
        leaf vni {
          type uint32 {
            range "0..16777215";
          }
          // NCS drop must statement
          description
            "VXLAN network identifier.";
        }
        leaf peer {
          type inet:ipv4-address-no-zone;
          description
            "The peer address of VTEP.";
        }
        leaf mode {
          type live_ncs_vxlan-mode;
          // NCS drop must statement
          description
            "The type of VXLAN tunnel traffic statistics.";
        }
        leaf direction {
          type live_ncs_statistics-direction;
          // NCS drop must statement
          description
            "Traffic statistics direction.";
        }
        container collections {
          description
            "List of Traffic statistics collection.";
          list collection {
            key "source-addr";
            description
              "Statistics of VXLAN tunnel traffic collection.";
            leaf source-addr {
              type inet:ipv4-address-no-zone;
              description
                "The address of VTEP.";
            }
            uses live_ncs_vxlan-traffic-collection;
          }
        }
      }
    }
  }
  augment "/ncs:devices/ncs:device/ncs:config/ifm:ifm/ifm:interfaces/ifm:interface" {
    description
      "The NVO3 statistics for interface.";
    container nvo3-vtep-statistics {
      tailf:ncs-device-type "netconf";
      tailf:display-when "not(../../../../../ncs:module) or ../../../../../ncs:module[ncs:name='huawei-nvo3-statistics']";
      when "../ifm:type='Nve'" {
        tailf:xpath-root 3;
      }
      description
        "List of VXLAN tunnel statistics.";
      list nvo3-vtep-statistic {
        key "vni peer mode direction";
        description
          "Configure VTEP statistics collection.";
        leaf vni {
          type uint32 {
            range "0..16777215";
          }
          must "(../vni = 0 and ../mode = 'l3' and ../direction = 'outbound' and not(../../nvo3-statistics:nvo3-vtep-statistic[nvo3-statistics:vni != 0][nvo3-statistics:peer = current()/../peer][nvo3-statistics:mode = current()/../mode][nvo3-statistics:direction = current()/../direction])) or (../vni != 0)" {
            tailf:xpath-root 3;
          }
          description
            "VXLAN network identifier.";
        }
        leaf peer {
          type inet:ipv4-address-no-zone;
          description
            "The peer address of VTEP.";
        }
        leaf mode {
          type vxlan-mode;
          must "(../mode = 'l2' and not((../../nvo3-statistics:nvo3-vtep-statistic[nvo3-statistics:vni = current()/../vni][nvo3-statistics:peer = current()/../peer][nvo3-statistics:direction = 'inbound'] or ../../nvo3-statistics:nvo3-vtep-statistic[nvo3-statistics:vni = current()/../vni][nvo3-statistics:peer = current()/../peer][nvo3-statistics:direction = 'outbound']) and ../../nvo3-statistics:nvo3-vtep-statistic[nvo3-statistics:vni = current()/../vni][nvo3-statistics:peer = current()/../peer][nvo3-statistics:direction = 'bidirection'])) or (../mode != 'l2')" {
            tailf:xpath-root 3;
          }
          description
            "The type of VXLAN tunnel traffic statistics.";
        }
        leaf direction {
          type statistics-direction;
          must "(../mode = 'l2') or (../mode = 'l3' and (../direction != 'bidirection'))" {
            tailf:xpath-root 3;
          }
          description
            "Traffic statistics direction.";
        }
        // NCS drop config false container collections
      }
    }
  }
  augment "/ncs:devices/ncs:template/ncs:ned-id/ncs:config/nvo3:nvo3/nvo3:vni-labels/nvo3:vni-label" {
    description
      "The NVO3 traffic statistics of vni.";
    container statistics {
      description
        "Configure VNI traffic statistics.";
      leaf enable {
        type string;
        // NCS drop default statement
        description
          "Enable/disable VNI traffic statistics.";
      }
      // NCS drop config false container collections
    }
  }
  augment "/ncs:devices/ncs:device/ncs:live-status/nvo3:nvo3/nvo3:vni-labels/nvo3:vni-label" {
    description
      "The NVO3 traffic statistics of vni.";
    container statistics {
      tailf:ncs-device-type "netconf";
      tailf:display-when "not(../../../../../ncs:module) or ../../../../../ncs:module[ncs:name='huawei-nvo3-statistics'] or (../../../../../ncs:live-status-protocol[not(ncs:capability)]) or (../../../../../ncs:live-status-protocol/ncs:capability/ncs:module[.='huawei-nvo3-statistics'])";
      description
        "Configure VNI traffic statistics.";
      leaf enable {
        type boolean;
        // NCS drop default statement
        description
          "Enable/disable VNI traffic statistics.";
      }
      container collections {
        // NCS drop when statement
        description
          "Statistics of VNI traffic statistics collection.";
        uses live_ncs_vxlan-traffic-collection;
      }
    }
  }
  augment "/ncs:devices/ncs:device/ncs:config/nvo3:nvo3/nvo3:vni-labels/nvo3:vni-label" {
    description
      "The NVO3 traffic statistics of vni.";
    container statistics {
      tailf:ncs-device-type "netconf";
      tailf:display-when "not(../../../../../ncs:module) or ../../../../../ncs:module[ncs:name='huawei-nvo3-statistics']";
      description
        "Configure VNI traffic statistics.";
      leaf enable {
        type boolean;
        default "false";
        description
          "Enable/disable VNI traffic statistics.";
      }
      // NCS drop config false container collections
    }
  }
}
