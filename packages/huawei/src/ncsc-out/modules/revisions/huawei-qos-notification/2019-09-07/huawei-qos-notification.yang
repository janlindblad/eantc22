module huawei-qos-notification {
  // Generated by yanger -t ncs
  tailf:mount-id "huawei-nc-1.0:huawei-nc-1.0";
  tailf:ncs-device-type "netconf";

  yang-version 1;
  namespace "urn:huawei:yang:huawei-qos-notification";
  prefix qos-notification;

  import huawei-extension {
    prefix ext;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Notification of qos.";

  revision 2019-09-07 {
    description
      "Init revision.";
    reference "Huawei private.";
  }
  ext:task-name "qos";

  typedef ncs_template_qos-service-class {
    type string;
    description
      "Queue type.";
  }

  typedef ncs_template_drop-type {
    type string;
    description
      "Discard type.";
  }

  typedef ncs_template_qos-direction-type {
    type string;
    description
      "Direction type.";
  }

  typedef ncs_template_pool-type {
    type string;
    description
      "Pool ID.";
  }

  typedef ncs_template_feature-type {
    type string;
    description
      "Feature type.";
  }

  typedef ncs_rpc_notif_qos-service-class {
    type enumeration {
      enum "be" {
        value 1;
        description
          "BE service-class.";
      }
      enum "af1" {
        value 2;
        description
          "AF1 service-class.";
      }
      enum "af2" {
        value 3;
        description
          "AF2 service-class.";
      }
      enum "af3" {
        value 4;
        description
          "AF3 service-class.";
      }
      enum "af4" {
        value 5;
        description
          "AF4 service-class.";
      }
      enum "ef" {
        value 6;
        description
          "EF service-class.";
      }
      enum "cs6" {
        value 7;
        description
          "CS6 service-class.";
      }
      enum "cs7" {
        value 8;
        description
          "CS7 service-class.";
      }
    }
    description
      "Queue type.";
  }

  typedef ncs_rpc_notif_drop-type {
    type enumeration {
      enum "discard-packet" {
        value 1;
        description
          "Discard by packet.";
      }
      enum "discard-byte" {
        value 2;
        description
          "Discard by byte.";
      }
      enum "discard-packet-ratio" {
        value 3;
        description
          "Discard by packet ratio.";
      }
    }
    description
      "Discard type.";
  }

  typedef ncs_rpc_notif_qos-direction-type {
    type enumeration {
      enum "inbound" {
        value 1;
        description
          "Inbound.";
      }
      enum "outbound" {
        value 2;
        description
          "Outbound.";
      }
    }
    description
      "Direction type.";
  }

  typedef ncs_rpc_notif_pool-type {
    type enumeration {
      enum "pool-0" {
        value 1;
        description
          "Pool 0.";
      }
      enum "pool-1" {
        value 2;
        description
          "Pool 1.";
      }
    }
    description
      "Pool ID.";
  }

  typedef ncs_rpc_notif_feature-type {
    type enumeration {
      enum "bgpflow" {
        value 1;
        description
          "BGP Flow.";
      }
      enum "qppb" {
        value 2;
        description
          "QPPB.";
      }
      enum "behavior-of-netstream" {
        value 3;
        description
          "Sampling at a fixed interval and sampling for fixed and random packets with a sampling ratio less than 10000 in the behavior.";
      }
      enum "behavior-of-strict-ip-urpf" {
        value 4;
        description
          "Strict IP URPF in the behavior.";
      }
    }
    description
      "Feature type.";
  }

  typedef live_ncs_qos-service-class {
    type enumeration {
      enum "be" {
        value 1;
        description
          "BE service-class.";
      }
      enum "af1" {
        value 2;
        description
          "AF1 service-class.";
      }
      enum "af2" {
        value 3;
        description
          "AF2 service-class.";
      }
      enum "af3" {
        value 4;
        description
          "AF3 service-class.";
      }
      enum "af4" {
        value 5;
        description
          "AF4 service-class.";
      }
      enum "ef" {
        value 6;
        description
          "EF service-class.";
      }
      enum "cs6" {
        value 7;
        description
          "CS6 service-class.";
      }
      enum "cs7" {
        value 8;
        description
          "CS7 service-class.";
      }
    }
    description
      "Queue type.";
  }

  typedef live_ncs_drop-type {
    type enumeration {
      enum "discard-packet" {
        value 1;
        description
          "Discard by packet.";
      }
      enum "discard-byte" {
        value 2;
        description
          "Discard by byte.";
      }
      enum "discard-packet-ratio" {
        value 3;
        description
          "Discard by packet ratio.";
      }
    }
    description
      "Discard type.";
  }

  typedef live_ncs_qos-direction-type {
    type enumeration {
      enum "inbound" {
        value 1;
        description
          "Inbound.";
      }
      enum "outbound" {
        value 2;
        description
          "Outbound.";
      }
    }
    description
      "Direction type.";
  }

  typedef live_ncs_pool-type {
    type enumeration {
      enum "pool-0" {
        value 1;
        description
          "Pool 0.";
      }
      enum "pool-1" {
        value 2;
        description
          "Pool 1.";
      }
    }
    description
      "Pool ID.";
  }

  typedef live_ncs_feature-type {
    type enumeration {
      enum "bgpflow" {
        value 1;
        description
          "BGP Flow.";
      }
      enum "qppb" {
        value 2;
        description
          "QPPB.";
      }
      enum "behavior-of-netstream" {
        value 3;
        description
          "Sampling at a fixed interval and sampling for fixed and random packets with a sampling ratio less than 10000 in the behavior.";
      }
      enum "behavior-of-strict-ip-urpf" {
        value 4;
        description
          "Strict IP URPF in the behavior.";
      }
    }
    description
      "Feature type.";
  }

  typedef qos-service-class {
    type enumeration {
      enum "be" {
        value 1;
        description
          "BE service-class.";
      }
      enum "af1" {
        value 2;
        description
          "AF1 service-class.";
      }
      enum "af2" {
        value 3;
        description
          "AF2 service-class.";
      }
      enum "af3" {
        value 4;
        description
          "AF3 service-class.";
      }
      enum "af4" {
        value 5;
        description
          "AF4 service-class.";
      }
      enum "ef" {
        value 6;
        description
          "EF service-class.";
      }
      enum "cs6" {
        value 7;
        description
          "CS6 service-class.";
      }
      enum "cs7" {
        value 8;
        description
          "CS7 service-class.";
      }
    }
    description
      "Queue type.";
  }

  typedef drop-type {
    type enumeration {
      enum "discard-packet" {
        value 1;
        description
          "Discard by packet.";
      }
      enum "discard-byte" {
        value 2;
        description
          "Discard by byte.";
      }
      enum "discard-packet-ratio" {
        value 3;
        description
          "Discard by packet ratio.";
      }
    }
    description
      "Discard type.";
  }

  typedef qos-direction-type {
    type enumeration {
      enum "inbound" {
        value 1;
        description
          "Inbound.";
      }
      enum "outbound" {
        value 2;
        description
          "Outbound.";
      }
    }
    description
      "Direction type.";
  }

  typedef pool-type {
    type enumeration {
      enum "pool-0" {
        value 1;
        description
          "Pool 0.";
      }
      enum "pool-1" {
        value 2;
        description
          "Pool 1.";
      }
    }
    description
      "Pool ID.";
  }

  typedef feature-type {
    type enumeration {
      enum "bgpflow" {
        value 1;
        description
          "BGP Flow.";
      }
      enum "qppb" {
        value 2;
        description
          "QPPB.";
      }
      enum "behavior-of-netstream" {
        value 3;
        description
          "Sampling at a fixed interval and sampling for fixed and random packets with a sampling ratio less than 10000 in the behavior.";
      }
      enum "behavior-of-strict-ip-urpf" {
        value 4;
        description
          "Strict IP URPF in the behavior.";
      }
    }
    description
      "Feature type.";
  }

  augment "/ncs:devices/ncs:device/ncs:notifications/ncs:received-notifications/ncs:notification/ncs:data" {
    container xqos-unsupported-feature-alarm-resume {
      presence "";
      config false;
      description
        "The board [board-id] does not support [feature-name] alarm has cleared.";
      leaf board-id {
        type string {
          length "1..16";
        }
        description
          "Board ID.";
      }
      leaf feature-name {
        type ncs_rpc_notif_feature-type;
        description
          "Feature name.";
      }
    }
  }
  augment "/ncs:devices/ncs:device/ncs:notifications/ncs:received-notifications/ncs:notification/ncs:data" {
    container xqos-unsupported-feature-alarm {
      presence "";
      config false;
      description
        "The board [board-id] does not support [feature-name].";
      leaf board-id {
        type string {
          length "1..16";
        }
        description
          "Board ID.";
      }
      leaf feature-name {
        type ncs_rpc_notif_feature-type;
        description
          "Feature name.";
      }
    }
  }
  augment "/ncs:devices/ncs:device/ncs:notifications/ncs:received-notifications/ncs:notification/ncs:data" {
    container xqos-mode-channel-over-portshap-alarm-resume {
      presence "";
      config false;
      description
        "The channelization bandwidth configured on the interface [interface-name] exceeds the port shaping value has cleared.";
      leaf interface-name {
        type string {
          length "1..511";
        }
        description
          "Mode channel interface name.";
      }
    }
  }
  augment "/ncs:devices/ncs:device/ncs:notifications/ncs:received-notifications/ncs:notification/ncs:data" {
    container xqos-mode-channel-over-portshap-alarm {
      presence "";
      config false;
      description
        "The channelization bandwidth configured on the interface [interface-name] exceeds the port shaping value.";
      leaf interface-name {
        type string {
          length "1..511";
        }
        description
          "Mode channel interface name.";
      }
    }
  }
  augment "/ncs:devices/ncs:device/ncs:notifications/ncs:received-notifications/ncs:notification/ncs:data" {
    container global-acl-not-support-board {
      presence "";
      config false;
      description
        "The trap of the board does not support acl.";
      leaf slot-id {
        type uint32;
        description
          "Slot ID.";
      }
      leaf direction {
        type ncs_rpc_notif_qos-direction-type;
        description
          "Direction.";
      }
    }
  }
  augment "/ncs:devices/ncs:device/ncs:notifications/ncs:received-notifications/ncs:notification/ncs:data" {
    container xqos-tm-performance-alarm-resume {
      presence "";
      config false;
      description
        "The TM performance alarm was cleared.";
      leaf slot-id {
        type string {
          length "0..15";
        }
        description
          "Slot ID.";
      }
      leaf chip-id {
        type uint32;
        description
          "Chip ID.";
      }
    }
  }
  augment "/ncs:devices/ncs:device/ncs:notifications/ncs:received-notifications/ncs:notification/ncs:data" {
    container xqos-tm-performance-alarm {
      presence "";
      config false;
      description
        "The traffic bandwidth usage almost reached the maximum forwarding capability of the TM chip.";
      leaf slot-id {
        type string {
          length "0..15";
        }
        description
          "Slot ID.";
      }
      leaf chip-id {
        type uint32;
        description
          "Chip ID.";
      }
    }
  }
  augment "/ncs:devices/ncs:device/ncs:notifications/ncs:received-notifications/ncs:notification/ncs:data" {
    container xqos-soft-pipe-alarm-resume {
      presence "";
      config false;
      description
        "The soft-pipe service alarm on interface [InterfaceName] has cleared.";
      leaf interface-name {
        type string {
          length "1..511";
        }
        description
          "Interface name of the soft pipe.";
      }
    }
  }
  augment "/ncs:devices/ncs:device/ncs:notifications/ncs:received-notifications/ncs:notification/ncs:data" {
    container xqos-soft-pipe-alarm {
      presence "";
      config false;
      description
        "The soft-pipe service on interface [InterfaceName] has reached [BandwidthUsage]%% of interface's soft-pipe capability.";
      leaf interface-name {
        type string {
          length "1..511";
        }
        description
          "Interface name of the soft pipe.";
      }
      leaf bandwidth-usage {
        type uint32;
        units "%";
        description
          "Bandwidth usage of the soft pipe.";
      }
    }
  }
  augment "/ncs:devices/ncs:device/ncs:notifications/ncs:received-notifications/ncs:notification/ncs:data" {
    container xqos-port-queue-alarm-resume {
      presence "";
      config false;
      description
        "Port queue alarm cleared.";
      leaf interface-index {
        type int32;
        description
          "Interface index.";
      }
      leaf queue {
        type string {
          length "1..4";
        }
        description
          "Queue index.";
      }
      leaf trunk-index {
        type int32;
        description
          "Trunk interface index.";
      }
    }
  }
  augment "/ncs:devices/ncs:device/ncs:notifications/ncs:received-notifications/ncs:notification/ncs:data" {
    container xqos-port-queue-alarm {
      presence "";
      config false;
      description
        "The alarm of port-queue occurs, only when the used queue is in excess of the configured length.";
      leaf interface-index {
        type int32;
        description
          "Interface index.";
      }
      leaf queue {
        type string {
          length "1..4";
        }
        description
          "Queue index.";
      }
      leaf trunk-index {
        type int32;
        description
          "Trunk interface index.";
      }
    }
  }
  augment "/ncs:devices/ncs:device/ncs:notifications/ncs:received-notifications/ncs:notification/ncs:data" {
    container xqos-hard-pipe-bandwidth-alarm-resume {
      presence "";
      config false;
      description
        "The hard-pipe config alarm on interface [InterfaceName] has cleared.";
      leaf interface-name {
        type string {
          length "1..511";
        }
        description
          "Interface name of the hard pipe.";
      }
    }
  }
  augment "/ncs:devices/ncs:device/ncs:notifications/ncs:received-notifications/ncs:notification/ncs:data" {
    container xqos-hard-pipe-bandwidth-alarm {
      presence "";
      config false;
      description
        "The hard-pipe bandwidth configuration on interface [InterfaceName] exceeded the max available bandwidth [MaxCfgBandwidth]Kbps.";
      leaf interface-name {
        type string {
          length "1..511";
        }
        description
          "Interface name of the hard pipe.";
      }
      leaf max-cfg-bandwidth {
        type uint32;
        units "kbit/s";
        description
          "Maximum configurable bandwidth of the hard pipe.";
      }
    }
  }
  augment "/ncs:devices/ncs:device/ncs:notifications/ncs:received-notifications/ncs:notification/ncs:data" {
    container xqos-hard-pipe-apply-user-queue-fail-alarm-resume {
      presence "";
      config false;
      description
        "The alarm indicating that the hard pipe of the interface specified by [InterfaceName] fails to apply for forwarding resources is cleared.";
      leaf interface-name {
        type string {
          length "1..511";
        }
        description
          "Interface name.";
      }
    }
  }
  augment "/ncs:devices/ncs:device/ncs:notifications/ncs:received-notifications/ncs:notification/ncs:data" {
    container xqos-hard-pipe-apply-user-queue-fail-alarm {
      presence "";
      config false;
      description
        "The hard pipe of the interface specified by [InterfaceName] fails to apply for forwarding resources.";
      leaf interface-name {
        type string {
          length "1..511";
        }
        description
          "Interface name.";
      }
    }
  }
  augment "/ncs:devices/ncs:device/ncs:notifications/ncs:received-notifications/ncs:notification/ncs:data" {
    container xqos-hard-pipe-apply-fail-alarm-resume {
      presence "";
      config false;
      description
        "The hard pipe not taking effect alarm on the interface [InterfaceName] has cleared.";
      leaf interface-name {
        type string {
          length "1..511";
        }
        description
          "Hardpipe interface name.";
      }
    }
  }
  augment "/ncs:devices/ncs:device/ncs:notifications/ncs:received-notifications/ncs:notification/ncs:data" {
    container xqos-hard-pipe-apply-fail-alarm {
      presence "";
      config false;
      description
        "The hard pipe configured on the interface [InterfaceName] does not take effect.";
      leaf interface-name {
        type string {
          length "1..511";
        }
        description
          "Hardpipe interface name.";
      }
    }
  }
  augment "/ncs:devices/ncs:device/ncs:notifications/ncs:received-notifications/ncs:notification/ncs:data" {
    container xqos-hard-pipe-alarm-resume {
      presence "";
      config false;
      description
        "The hard-pipe service alarm on interface [InterfaceName] has cleared.";
      leaf interface-name {
        type string {
          length "1..511";
        }
        description
          "Hardpipe interface name.";
      }
    }
  }
  augment "/ncs:devices/ncs:device/ncs:notifications/ncs:received-notifications/ncs:notification/ncs:data" {
    container xqos-hard-pipe-alarm {
      presence "";
      config false;
      description
        "The hard-pipe service on interface [InterfaceName] has reached [BandwidthUsage]%% of interface's hard-pipe capability.";
      leaf interface-name {
        type string {
          length "1..511";
        }
        description
          "Hardpipe interface name.";
      }
      leaf bandwidth-usage {
        type uint32;
        units "%";
        description
          "Hardpipe bandwitdh usage.";
      }
    }
  }
  augment "/ncs:devices/ncs:device/ncs:notifications/ncs:received-notifications/ncs:notification/ncs:data" {
    container xqos-hard-pipe-ac-band-over-alarm-resume {
      presence "";
      config false;
      description
        "The hard pipe configured on the interface [InterfaceName] over port bandwidth or port shaping has cleared.";
      leaf interface-name {
        type string {
          length "1..511";
        }
        description
          "Hardpipe interface name.";
      }
    }
  }
  augment "/ncs:devices/ncs:device/ncs:notifications/ncs:received-notifications/ncs:notification/ncs:data" {
    container xqos-hard-pipe-ac-band-over-alarm {
      presence "";
      config false;
      description
        "The hard pipe configured on the interface [InterfaceName] over port bandwidth or port shaping.";
      leaf interface-name {
        type string {
          length "1..511";
        }
        description
          "Hardpipe interface name.";
      }
    }
  }
  augment "/ncs:devices/ncs:device/ncs:notifications/ncs:received-notifications/ncs:notification/ncs:data" {
    container xqos-8queue-resource-pre-alarm-resume {
      presence "";
      config false;
      description
        "The number of outbound 8queue user-queue under 90 percent of the specification of the forwarding engine resources.";
      leaf ent-physical-index {
        type uint32;
        description
          "Indicates the index of the physical entity.";
      }
      leaf ent-physical-name {
        type string {
          length "0..255";
        }
        description
          "Name of a physical entity.";
      }
      leaf chip-id {
        type uint32;
        description
          "Chip ID.";
      }
    }
  }
  augment "/ncs:devices/ncs:device/ncs:notifications/ncs:received-notifications/ncs:notification/ncs:data" {
    container xqos-8queue-resource-pre-alarm {
      presence "";
      config false;
      description
        "The number of outbound 8queue user-queue exceeded 90 percent of the specification of the forwarding engine resources.";
      leaf ent-physical-index {
        type uint32;
        description
          "Indicates the index of the physical entity.";
      }
      leaf ent-physical-name {
        type string {
          length "0..255";
        }
        description
          "Name of a physical entity.";
      }
      leaf chip-id {
        type uint32;
        description
          "Chip ID.";
      }
    }
  }
  augment "/ncs:devices/ncs:device/ncs:notifications/ncs:received-notifications/ncs:notification/ncs:data" {
    container xqos-8queue-resource-over-alarm-resume {
      presence "";
      config false;
      description
        "The number of Outbound 8queue user-queue under the specification of the forwarding engine resources.";
      leaf ent-physical-index {
        type uint32;
        description
          "Indicates the index of the physical entity.";
      }
      leaf ent-physical-name {
        type string {
          length "0..255";
        }
        description
          "Name of a physical entity.";
      }
      leaf chip-id {
        type uint32;
        description
          "Chip ID.";
      }
    }
  }
  augment "/ncs:devices/ncs:device/ncs:notifications/ncs:received-notifications/ncs:notification/ncs:data" {
    container xqos-8queue-resource-over-alarm {
      presence "";
      config false;
      description
        "The number of outbound 8queue user-queue exceeded the specification of the forwarding engine resources.";
      leaf ent-physical-index {
        type uint32;
        description
          "Indicates the index of the physical entity.";
      }
      leaf ent-physical-name {
        type string {
          length "0..255";
        }
        description
          "Name of a physical entity.";
      }
      leaf chip-id {
        type uint32;
        description
          "Chip ID.";
      }
    }
  }
  augment "/ncs:devices/ncs:device/ncs:notifications/ncs:received-notifications/ncs:notification/ncs:data" {
    container xqos-4queue-resource-pre-alarm-resume {
      presence "";
      config false;
      description
        "The number of Outbound 4queue user-queue under 90 percent of the specification of the forwarding engine resources.";
      leaf ent-physical-index {
        type uint32;
        description
          "Indicates the index of the physical entity.";
      }
      leaf ent-physical-name {
        type string {
          length "0..255";
        }
        description
          "Name of a physical entity.";
      }
      leaf chip-id {
        type uint32;
        description
          "Chip ID.";
      }
    }
  }
  augment "/ncs:devices/ncs:device/ncs:notifications/ncs:received-notifications/ncs:notification/ncs:data" {
    container xqos-4queue-resource-pre-alarm {
      presence "";
      config false;
      description
        "The number of outbound 4queue user-queue exceeded 90 percent of the specification of the forwarding engine resources.";
      leaf ent-physical-index {
        type uint32;
        description
          "Indicates the index of the physical entity.";
      }
      leaf ent-physical-name {
        type string {
          length "0..255";
        }
        description
          "Name of a physical entity.";
      }
      leaf chip-id {
        type uint32;
        description
          "Chip ID.";
      }
    }
  }
  augment "/ncs:devices/ncs:device/ncs:notifications/ncs:received-notifications/ncs:notification/ncs:data" {
    container xqos-4queue-resource-over-alarm-resume {
      presence "";
      config false;
      description
        "The number of Outbound 4queue user-queue under the specification of the forwarding engine resources.";
      leaf ent-physical-index {
        type uint32;
        description
          "Indicates the index of the physical entity.";
      }
      leaf ent-physical-name {
        type string {
          length "0..255";
        }
        description
          "Name of a physical entity.";
      }
      leaf chip-id {
        type uint32;
        description
          "Chip ID.";
      }
    }
  }
  augment "/ncs:devices/ncs:device/ncs:notifications/ncs:received-notifications/ncs:notification/ncs:data" {
    container xqos-4queue-resource-over-alarm {
      presence "";
      config false;
      description
        "The number of outbound 4queue user-queue exceeded the specification of the forwarding engine resources.";
      leaf ent-physical-index {
        type uint32;
        description
          "Indicates the index of the physical entity.";
      }
      leaf ent-physical-name {
        type string {
          length "0..255";
        }
        description
          "Name of a physical entity.";
      }
      leaf chip-id {
        type uint32;
        description
          "Chip ID.";
      }
    }
  }
  augment "/ncs:devices/ncs:device/ncs:notifications/ncs:received-notifications/ncs:notification/ncs:data" {
    container hqos-user-queue-apply-pir-from-pool-success-alarm {
      presence "";
      config false;
      description
        "All users successfully requested pirs.";
      leaf ent-physical-index {
        type uint32;
        description
          "Indicates the index of the physical entity.";
      }
      leaf ent-physical-name {
        type string {
          length "0..255";
        }
        description
          "Indicates the name of a physical entity.";
      }
      leaf pool {
        type ncs_rpc_notif_pool-type;
        description
          "Resource pool. - 1: pool-0 - 2: pool-1.";
      }
    }
  }
  augment "/ncs:devices/ncs:device/ncs:notifications/ncs:received-notifications/ncs:notification/ncs:data" {
    container hqos-user-queue-apply-pir-from-pool-fail-alarm {
      presence "";
      config false;
      description
        "The sum of the PIRs requested from resource pool by all users exceeded the maximum configuration specification of the TM chip.";
      leaf ent-physical-index {
        type uint32;
        description
          "Indicates the index of the physical entity.";
      }
      leaf ent-physical-name {
        type string {
          length "0..255";
        }
        description
          "Indicates the name of a physical entity.";
      }
      leaf pool {
        type ncs_rpc_notif_pool-type;
        description
          "Resource pool. - 1: pool-0 - 2: pool-1.";
      }
    }
  }
  augment "/ncs:devices/ncs:device/ncs:notifications/ncs:received-notifications/ncs:notification/ncs:data" {
    container hqos-user-queue-apply-pir-success-alarm {
      presence "";
      config false;
      description
        "All users successfully requested pirs.";
      leaf ent-physical-index {
        type uint32;
        description
          "Indicates the index of the physical entity.";
      }
      leaf ent-physical-name {
        type string {
          length "0..255";
        }
        description
          "Indicates the name of the physical entity.";
      }
      leaf direction {
        type ncs_rpc_notif_qos-direction-type;
        description
          "Direction. - 1: inbound - 2: outbound.";
      }
    }
  }
  augment "/ncs:devices/ncs:device/ncs:notifications/ncs:received-notifications/ncs:notification/ncs:data" {
    container hqos-user-queue-apply-pir-fail-alarm {
      presence "";
      config false;
      description
        "The sum of the pirs requested by all users exceeded the maximum configuration specification of the TM chip.";
      leaf ent-physical-index {
        type uint32;
        description
          "Indicates the index of the physical entity.";
      }
      leaf ent-physical-name {
        type string {
          length "0..255";
        }
        description
          "Indicates the name of the physical entity.";
      }
      leaf direction {
        type ncs_rpc_notif_qos-direction-type;
        description
          "Direction. - 1: inbound - 2: outbound.";
      }
    }
  }
  augment "/ncs:devices/ncs:device/ncs:notifications/ncs:received-notifications/ncs:notification/ncs:data" {
    container hqos-port-queue-statistics-discard-alarm-resume {
      presence "";
      config false;
      description
        "On interface [InterfaceName],[Queue] in queue [DiscardType] is [DiscardValue],it is Less than alarm-threshold.";
      leaf interface-name {
        type string {
          length "1..511";
        }
        description
          "Interface name.";
      }
      leaf queue {
        type ncs_rpc_notif_qos-service-class;
        description
          "Queue index.";
      }
      leaf discard-type {
        type ncs_rpc_notif_drop-type;
        description
          "Discard type.";
      }
      leaf discard-value {
        type string {
          length "1..32";
        }
        description
          "Discard value.";
      }
    }
  }
  augment "/ncs:devices/ncs:device/ncs:notifications/ncs:received-notifications/ncs:notification/ncs:data" {
    container hqos-port-queue-statistics-discard-alarm {
      presence "";
      config false;
      description
        "On interface [InterfaceName],[Queue] in queue [DiscardType] is [DiscardValue],it reached alarm-threshold.";
      leaf interface-name {
        type string {
          length "1..511";
        }
        description
          "Interface name.";
      }
      leaf queue {
        type ncs_rpc_notif_qos-service-class;
        description
          "Queue index.";
      }
      leaf discard-type {
        type ncs_rpc_notif_drop-type;
        description
          "Discard type.";
      }
      leaf discard-value {
        type string {
          length "1..32";
        }
        description
          "Discard value.";
      }
    }
  }
  augment "/ncs:devices/ncs:device/ncs:notifications/ncs:received-notifications/ncs:notification/ncs:data" {
    container hqos-buffer-alarm-resume {
      presence "";
      config false;
      description
        "Queue buffer alarm on slot [SLOTID] chip [CHIPID] cleared.";
      leaf slot-id {
        type string {
          length "0..15";
        }
        description
          "Slot ID.";
      }
      leaf chip-id {
        type string {
          length "0..7";
        }
        description
          "Chip ID.";
      }
      leaf buffer-size {
        type string {
          length "0..63";
        }
        units "kB";
        description
          "Queue buffer size.";
      }
    }
  }
  augment "/ncs:devices/ncs:device/ncs:notifications/ncs:received-notifications/ncs:notification/ncs:data" {
    container hqos-buffer-alarm {
      presence "";
      config false;
      description
        "The buffersize on slot [SLOTID] chip [CHIPID] has reached [BufferSize]%%.";
      leaf slot-id {
        type string {
          length "0..15";
        }
        description
          "Slot ID.";
      }
      leaf chip-id {
        type string {
          length "0..7";
        }
        description
          "Chip ID.";
      }
      leaf buffer-size {
        type string {
          length "0..63";
        }
        units "kB";
        description
          "Queue buffer size.";
      }
    }
  }
  augment "/ncs:devices/ncs:device/ncs:netconf-notifications/ncs:received-notifications/ncs:notification/ncs:data" {
    container xqos-unsupported-feature-alarm-resume {
      presence "";
      config false;
      description
        "The board [board-id] does not support [feature-name] alarm has cleared.";
      leaf board-id {
        type string {
          length "1..16";
        }
        description
          "Board ID.";
      }
      leaf feature-name {
        type ncs_rpc_notif_feature-type;
        description
          "Feature name.";
      }
    }
  }
  augment "/ncs:devices/ncs:device/ncs:netconf-notifications/ncs:received-notifications/ncs:notification/ncs:data" {
    container xqos-unsupported-feature-alarm {
      presence "";
      config false;
      description
        "The board [board-id] does not support [feature-name].";
      leaf board-id {
        type string {
          length "1..16";
        }
        description
          "Board ID.";
      }
      leaf feature-name {
        type ncs_rpc_notif_feature-type;
        description
          "Feature name.";
      }
    }
  }
  augment "/ncs:devices/ncs:device/ncs:netconf-notifications/ncs:received-notifications/ncs:notification/ncs:data" {
    container xqos-mode-channel-over-portshap-alarm-resume {
      presence "";
      config false;
      description
        "The channelization bandwidth configured on the interface [interface-name] exceeds the port shaping value has cleared.";
      leaf interface-name {
        type string {
          length "1..511";
        }
        description
          "Mode channel interface name.";
      }
    }
  }
  augment "/ncs:devices/ncs:device/ncs:netconf-notifications/ncs:received-notifications/ncs:notification/ncs:data" {
    container xqos-mode-channel-over-portshap-alarm {
      presence "";
      config false;
      description
        "The channelization bandwidth configured on the interface [interface-name] exceeds the port shaping value.";
      leaf interface-name {
        type string {
          length "1..511";
        }
        description
          "Mode channel interface name.";
      }
    }
  }
  augment "/ncs:devices/ncs:device/ncs:netconf-notifications/ncs:received-notifications/ncs:notification/ncs:data" {
    container global-acl-not-support-board {
      presence "";
      config false;
      description
        "The trap of the board does not support acl.";
      leaf slot-id {
        type uint32;
        description
          "Slot ID.";
      }
      leaf direction {
        type ncs_rpc_notif_qos-direction-type;
        description
          "Direction.";
      }
    }
  }
  augment "/ncs:devices/ncs:device/ncs:netconf-notifications/ncs:received-notifications/ncs:notification/ncs:data" {
    container xqos-tm-performance-alarm-resume {
      presence "";
      config false;
      description
        "The TM performance alarm was cleared.";
      leaf slot-id {
        type string {
          length "0..15";
        }
        description
          "Slot ID.";
      }
      leaf chip-id {
        type uint32;
        description
          "Chip ID.";
      }
    }
  }
  augment "/ncs:devices/ncs:device/ncs:netconf-notifications/ncs:received-notifications/ncs:notification/ncs:data" {
    container xqos-tm-performance-alarm {
      presence "";
      config false;
      description
        "The traffic bandwidth usage almost reached the maximum forwarding capability of the TM chip.";
      leaf slot-id {
        type string {
          length "0..15";
        }
        description
          "Slot ID.";
      }
      leaf chip-id {
        type uint32;
        description
          "Chip ID.";
      }
    }
  }
  augment "/ncs:devices/ncs:device/ncs:netconf-notifications/ncs:received-notifications/ncs:notification/ncs:data" {
    container xqos-soft-pipe-alarm-resume {
      presence "";
      config false;
      description
        "The soft-pipe service alarm on interface [InterfaceName] has cleared.";
      leaf interface-name {
        type string {
          length "1..511";
        }
        description
          "Interface name of the soft pipe.";
      }
    }
  }
  augment "/ncs:devices/ncs:device/ncs:netconf-notifications/ncs:received-notifications/ncs:notification/ncs:data" {
    container xqos-soft-pipe-alarm {
      presence "";
      config false;
      description
        "The soft-pipe service on interface [InterfaceName] has reached [BandwidthUsage]%% of interface's soft-pipe capability.";
      leaf interface-name {
        type string {
          length "1..511";
        }
        description
          "Interface name of the soft pipe.";
      }
      leaf bandwidth-usage {
        type uint32;
        units "%";
        description
          "Bandwidth usage of the soft pipe.";
      }
    }
  }
  augment "/ncs:devices/ncs:device/ncs:netconf-notifications/ncs:received-notifications/ncs:notification/ncs:data" {
    container xqos-port-queue-alarm-resume {
      presence "";
      config false;
      description
        "Port queue alarm cleared.";
      leaf interface-index {
        type int32;
        description
          "Interface index.";
      }
      leaf queue {
        type string {
          length "1..4";
        }
        description
          "Queue index.";
      }
      leaf trunk-index {
        type int32;
        description
          "Trunk interface index.";
      }
    }
  }
  augment "/ncs:devices/ncs:device/ncs:netconf-notifications/ncs:received-notifications/ncs:notification/ncs:data" {
    container xqos-port-queue-alarm {
      presence "";
      config false;
      description
        "The alarm of port-queue occurs, only when the used queue is in excess of the configured length.";
      leaf interface-index {
        type int32;
        description
          "Interface index.";
      }
      leaf queue {
        type string {
          length "1..4";
        }
        description
          "Queue index.";
      }
      leaf trunk-index {
        type int32;
        description
          "Trunk interface index.";
      }
    }
  }
  augment "/ncs:devices/ncs:device/ncs:netconf-notifications/ncs:received-notifications/ncs:notification/ncs:data" {
    container xqos-hard-pipe-bandwidth-alarm-resume {
      presence "";
      config false;
      description
        "The hard-pipe config alarm on interface [InterfaceName] has cleared.";
      leaf interface-name {
        type string {
          length "1..511";
        }
        description
          "Interface name of the hard pipe.";
      }
    }
  }
  augment "/ncs:devices/ncs:device/ncs:netconf-notifications/ncs:received-notifications/ncs:notification/ncs:data" {
    container xqos-hard-pipe-bandwidth-alarm {
      presence "";
      config false;
      description
        "The hard-pipe bandwidth configuration on interface [InterfaceName] exceeded the max available bandwidth [MaxCfgBandwidth]Kbps.";
      leaf interface-name {
        type string {
          length "1..511";
        }
        description
          "Interface name of the hard pipe.";
      }
      leaf max-cfg-bandwidth {
        type uint32;
        units "kbit/s";
        description
          "Maximum configurable bandwidth of the hard pipe.";
      }
    }
  }
  augment "/ncs:devices/ncs:device/ncs:netconf-notifications/ncs:received-notifications/ncs:notification/ncs:data" {
    container xqos-hard-pipe-apply-user-queue-fail-alarm-resume {
      presence "";
      config false;
      description
        "The alarm indicating that the hard pipe of the interface specified by [InterfaceName] fails to apply for forwarding resources is cleared.";
      leaf interface-name {
        type string {
          length "1..511";
        }
        description
          "Interface name.";
      }
    }
  }
  augment "/ncs:devices/ncs:device/ncs:netconf-notifications/ncs:received-notifications/ncs:notification/ncs:data" {
    container xqos-hard-pipe-apply-user-queue-fail-alarm {
      presence "";
      config false;
      description
        "The hard pipe of the interface specified by [InterfaceName] fails to apply for forwarding resources.";
      leaf interface-name {
        type string {
          length "1..511";
        }
        description
          "Interface name.";
      }
    }
  }
  augment "/ncs:devices/ncs:device/ncs:netconf-notifications/ncs:received-notifications/ncs:notification/ncs:data" {
    container xqos-hard-pipe-apply-fail-alarm-resume {
      presence "";
      config false;
      description
        "The hard pipe not taking effect alarm on the interface [InterfaceName] has cleared.";
      leaf interface-name {
        type string {
          length "1..511";
        }
        description
          "Hardpipe interface name.";
      }
    }
  }
  augment "/ncs:devices/ncs:device/ncs:netconf-notifications/ncs:received-notifications/ncs:notification/ncs:data" {
    container xqos-hard-pipe-apply-fail-alarm {
      presence "";
      config false;
      description
        "The hard pipe configured on the interface [InterfaceName] does not take effect.";
      leaf interface-name {
        type string {
          length "1..511";
        }
        description
          "Hardpipe interface name.";
      }
    }
  }
  augment "/ncs:devices/ncs:device/ncs:netconf-notifications/ncs:received-notifications/ncs:notification/ncs:data" {
    container xqos-hard-pipe-alarm-resume {
      presence "";
      config false;
      description
        "The hard-pipe service alarm on interface [InterfaceName] has cleared.";
      leaf interface-name {
        type string {
          length "1..511";
        }
        description
          "Hardpipe interface name.";
      }
    }
  }
  augment "/ncs:devices/ncs:device/ncs:netconf-notifications/ncs:received-notifications/ncs:notification/ncs:data" {
    container xqos-hard-pipe-alarm {
      presence "";
      config false;
      description
        "The hard-pipe service on interface [InterfaceName] has reached [BandwidthUsage]%% of interface's hard-pipe capability.";
      leaf interface-name {
        type string {
          length "1..511";
        }
        description
          "Hardpipe interface name.";
      }
      leaf bandwidth-usage {
        type uint32;
        units "%";
        description
          "Hardpipe bandwitdh usage.";
      }
    }
  }
  augment "/ncs:devices/ncs:device/ncs:netconf-notifications/ncs:received-notifications/ncs:notification/ncs:data" {
    container xqos-hard-pipe-ac-band-over-alarm-resume {
      presence "";
      config false;
      description
        "The hard pipe configured on the interface [InterfaceName] over port bandwidth or port shaping has cleared.";
      leaf interface-name {
        type string {
          length "1..511";
        }
        description
          "Hardpipe interface name.";
      }
    }
  }
  augment "/ncs:devices/ncs:device/ncs:netconf-notifications/ncs:received-notifications/ncs:notification/ncs:data" {
    container xqos-hard-pipe-ac-band-over-alarm {
      presence "";
      config false;
      description
        "The hard pipe configured on the interface [InterfaceName] over port bandwidth or port shaping.";
      leaf interface-name {
        type string {
          length "1..511";
        }
        description
          "Hardpipe interface name.";
      }
    }
  }
  augment "/ncs:devices/ncs:device/ncs:netconf-notifications/ncs:received-notifications/ncs:notification/ncs:data" {
    container xqos-8queue-resource-pre-alarm-resume {
      presence "";
      config false;
      description
        "The number of outbound 8queue user-queue under 90 percent of the specification of the forwarding engine resources.";
      leaf ent-physical-index {
        type uint32;
        description
          "Indicates the index of the physical entity.";
      }
      leaf ent-physical-name {
        type string {
          length "0..255";
        }
        description
          "Name of a physical entity.";
      }
      leaf chip-id {
        type uint32;
        description
          "Chip ID.";
      }
    }
  }
  augment "/ncs:devices/ncs:device/ncs:netconf-notifications/ncs:received-notifications/ncs:notification/ncs:data" {
    container xqos-8queue-resource-pre-alarm {
      presence "";
      config false;
      description
        "The number of outbound 8queue user-queue exceeded 90 percent of the specification of the forwarding engine resources.";
      leaf ent-physical-index {
        type uint32;
        description
          "Indicates the index of the physical entity.";
      }
      leaf ent-physical-name {
        type string {
          length "0..255";
        }
        description
          "Name of a physical entity.";
      }
      leaf chip-id {
        type uint32;
        description
          "Chip ID.";
      }
    }
  }
  augment "/ncs:devices/ncs:device/ncs:netconf-notifications/ncs:received-notifications/ncs:notification/ncs:data" {
    container xqos-8queue-resource-over-alarm-resume {
      presence "";
      config false;
      description
        "The number of Outbound 8queue user-queue under the specification of the forwarding engine resources.";
      leaf ent-physical-index {
        type uint32;
        description
          "Indicates the index of the physical entity.";
      }
      leaf ent-physical-name {
        type string {
          length "0..255";
        }
        description
          "Name of a physical entity.";
      }
      leaf chip-id {
        type uint32;
        description
          "Chip ID.";
      }
    }
  }
  augment "/ncs:devices/ncs:device/ncs:netconf-notifications/ncs:received-notifications/ncs:notification/ncs:data" {
    container xqos-8queue-resource-over-alarm {
      presence "";
      config false;
      description
        "The number of outbound 8queue user-queue exceeded the specification of the forwarding engine resources.";
      leaf ent-physical-index {
        type uint32;
        description
          "Indicates the index of the physical entity.";
      }
      leaf ent-physical-name {
        type string {
          length "0..255";
        }
        description
          "Name of a physical entity.";
      }
      leaf chip-id {
        type uint32;
        description
          "Chip ID.";
      }
    }
  }
  augment "/ncs:devices/ncs:device/ncs:netconf-notifications/ncs:received-notifications/ncs:notification/ncs:data" {
    container xqos-4queue-resource-pre-alarm-resume {
      presence "";
      config false;
      description
        "The number of Outbound 4queue user-queue under 90 percent of the specification of the forwarding engine resources.";
      leaf ent-physical-index {
        type uint32;
        description
          "Indicates the index of the physical entity.";
      }
      leaf ent-physical-name {
        type string {
          length "0..255";
        }
        description
          "Name of a physical entity.";
      }
      leaf chip-id {
        type uint32;
        description
          "Chip ID.";
      }
    }
  }
  augment "/ncs:devices/ncs:device/ncs:netconf-notifications/ncs:received-notifications/ncs:notification/ncs:data" {
    container xqos-4queue-resource-pre-alarm {
      presence "";
      config false;
      description
        "The number of outbound 4queue user-queue exceeded 90 percent of the specification of the forwarding engine resources.";
      leaf ent-physical-index {
        type uint32;
        description
          "Indicates the index of the physical entity.";
      }
      leaf ent-physical-name {
        type string {
          length "0..255";
        }
        description
          "Name of a physical entity.";
      }
      leaf chip-id {
        type uint32;
        description
          "Chip ID.";
      }
    }
  }
  augment "/ncs:devices/ncs:device/ncs:netconf-notifications/ncs:received-notifications/ncs:notification/ncs:data" {
    container xqos-4queue-resource-over-alarm-resume {
      presence "";
      config false;
      description
        "The number of Outbound 4queue user-queue under the specification of the forwarding engine resources.";
      leaf ent-physical-index {
        type uint32;
        description
          "Indicates the index of the physical entity.";
      }
      leaf ent-physical-name {
        type string {
          length "0..255";
        }
        description
          "Name of a physical entity.";
      }
      leaf chip-id {
        type uint32;
        description
          "Chip ID.";
      }
    }
  }
  augment "/ncs:devices/ncs:device/ncs:netconf-notifications/ncs:received-notifications/ncs:notification/ncs:data" {
    container xqos-4queue-resource-over-alarm {
      presence "";
      config false;
      description
        "The number of outbound 4queue user-queue exceeded the specification of the forwarding engine resources.";
      leaf ent-physical-index {
        type uint32;
        description
          "Indicates the index of the physical entity.";
      }
      leaf ent-physical-name {
        type string {
          length "0..255";
        }
        description
          "Name of a physical entity.";
      }
      leaf chip-id {
        type uint32;
        description
          "Chip ID.";
      }
    }
  }
  augment "/ncs:devices/ncs:device/ncs:netconf-notifications/ncs:received-notifications/ncs:notification/ncs:data" {
    container hqos-user-queue-apply-pir-from-pool-success-alarm {
      presence "";
      config false;
      description
        "All users successfully requested pirs.";
      leaf ent-physical-index {
        type uint32;
        description
          "Indicates the index of the physical entity.";
      }
      leaf ent-physical-name {
        type string {
          length "0..255";
        }
        description
          "Indicates the name of a physical entity.";
      }
      leaf pool {
        type ncs_rpc_notif_pool-type;
        description
          "Resource pool. - 1: pool-0 - 2: pool-1.";
      }
    }
  }
  augment "/ncs:devices/ncs:device/ncs:netconf-notifications/ncs:received-notifications/ncs:notification/ncs:data" {
    container hqos-user-queue-apply-pir-from-pool-fail-alarm {
      presence "";
      config false;
      description
        "The sum of the PIRs requested from resource pool by all users exceeded the maximum configuration specification of the TM chip.";
      leaf ent-physical-index {
        type uint32;
        description
          "Indicates the index of the physical entity.";
      }
      leaf ent-physical-name {
        type string {
          length "0..255";
        }
        description
          "Indicates the name of a physical entity.";
      }
      leaf pool {
        type ncs_rpc_notif_pool-type;
        description
          "Resource pool. - 1: pool-0 - 2: pool-1.";
      }
    }
  }
  augment "/ncs:devices/ncs:device/ncs:netconf-notifications/ncs:received-notifications/ncs:notification/ncs:data" {
    container hqos-user-queue-apply-pir-success-alarm {
      presence "";
      config false;
      description
        "All users successfully requested pirs.";
      leaf ent-physical-index {
        type uint32;
        description
          "Indicates the index of the physical entity.";
      }
      leaf ent-physical-name {
        type string {
          length "0..255";
        }
        description
          "Indicates the name of the physical entity.";
      }
      leaf direction {
        type ncs_rpc_notif_qos-direction-type;
        description
          "Direction. - 1: inbound - 2: outbound.";
      }
    }
  }
  augment "/ncs:devices/ncs:device/ncs:netconf-notifications/ncs:received-notifications/ncs:notification/ncs:data" {
    container hqos-user-queue-apply-pir-fail-alarm {
      presence "";
      config false;
      description
        "The sum of the pirs requested by all users exceeded the maximum configuration specification of the TM chip.";
      leaf ent-physical-index {
        type uint32;
        description
          "Indicates the index of the physical entity.";
      }
      leaf ent-physical-name {
        type string {
          length "0..255";
        }
        description
          "Indicates the name of the physical entity.";
      }
      leaf direction {
        type ncs_rpc_notif_qos-direction-type;
        description
          "Direction. - 1: inbound - 2: outbound.";
      }
    }
  }
  augment "/ncs:devices/ncs:device/ncs:netconf-notifications/ncs:received-notifications/ncs:notification/ncs:data" {
    container hqos-port-queue-statistics-discard-alarm-resume {
      presence "";
      config false;
      description
        "On interface [InterfaceName],[Queue] in queue [DiscardType] is [DiscardValue],it is Less than alarm-threshold.";
      leaf interface-name {
        type string {
          length "1..511";
        }
        description
          "Interface name.";
      }
      leaf queue {
        type ncs_rpc_notif_qos-service-class;
        description
          "Queue index.";
      }
      leaf discard-type {
        type ncs_rpc_notif_drop-type;
        description
          "Discard type.";
      }
      leaf discard-value {
        type string {
          length "1..32";
        }
        description
          "Discard value.";
      }
    }
  }
  augment "/ncs:devices/ncs:device/ncs:netconf-notifications/ncs:received-notifications/ncs:notification/ncs:data" {
    container hqos-port-queue-statistics-discard-alarm {
      presence "";
      config false;
      description
        "On interface [InterfaceName],[Queue] in queue [DiscardType] is [DiscardValue],it reached alarm-threshold.";
      leaf interface-name {
        type string {
          length "1..511";
        }
        description
          "Interface name.";
      }
      leaf queue {
        type ncs_rpc_notif_qos-service-class;
        description
          "Queue index.";
      }
      leaf discard-type {
        type ncs_rpc_notif_drop-type;
        description
          "Discard type.";
      }
      leaf discard-value {
        type string {
          length "1..32";
        }
        description
          "Discard value.";
      }
    }
  }
  augment "/ncs:devices/ncs:device/ncs:netconf-notifications/ncs:received-notifications/ncs:notification/ncs:data" {
    container hqos-buffer-alarm-resume {
      presence "";
      config false;
      description
        "Queue buffer alarm on slot [SLOTID] chip [CHIPID] cleared.";
      leaf slot-id {
        type string {
          length "0..15";
        }
        description
          "Slot ID.";
      }
      leaf chip-id {
        type string {
          length "0..7";
        }
        description
          "Chip ID.";
      }
      leaf buffer-size {
        type string {
          length "0..63";
        }
        units "kB";
        description
          "Queue buffer size.";
      }
    }
  }
  augment "/ncs:devices/ncs:device/ncs:netconf-notifications/ncs:received-notifications/ncs:notification/ncs:data" {
    container hqos-buffer-alarm {
      presence "";
      config false;
      description
        "The buffersize on slot [SLOTID] chip [CHIPID] has reached [BufferSize]%%.";
      leaf slot-id {
        type string {
          length "0..15";
        }
        description
          "Slot ID.";
      }
      leaf chip-id {
        type string {
          length "0..7";
        }
        description
          "Chip ID.";
      }
      leaf buffer-size {
        type string {
          length "0..63";
        }
        units "kB";
        description
          "Queue buffer size.";
      }
    }
  }
}
