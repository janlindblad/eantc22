module huawei-netstream {
  // Generated by yanger -t ncs
  tailf:mount-id "huawei-nc-1.0:huawei-nc-1.0";
  tailf:ncs-device-type "netconf";

  namespace "urn:huawei:yang:huawei-netstream";
  prefix netstream;

  import huawei-devm {
    prefix devm;
  }
  import huawei-ifm {
    prefix ifm;
  }
  import ietf-inet-types {
    prefix inet;
  }
  import huawei-extension {
    prefix ext;
  }
  import huawei-network-instance {
    prefix ni;
  }
  import huawei-l3vpn {
    prefix l3vpn;
  }
  import ietf-yang-types {
    prefix yang;
  }
  import huawei-pub-type {
    prefix pub-type;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Netstream.";

  revision 2019-06-27 {
    description
      "Initial revision.";
    reference "Huawei private.";
  }
  ext:task-name "netstream";

  typedef ncs_template_nsm-direction {
    type string;
    description
      "Description of sampler direction.";
  }

  typedef ncs_template_nsm-agg-type {
    type string;
    description
      "Description of aggregation type.";
  }

  typedef ncs_template_nsm-enable {
    type string;
    description
      "Description of enable type.";
  }

  typedef ncs_template_nsm-origin-version {
    type string;
    description
      "Description of origin version type.";
  }

  typedef ncs_template_nsm-as-type {
    type string;
    description
      "Description of as type.";
  }

  typedef ncs_template_nsm-as-mode-index {
    type string;
    description
      "Description of as mode index type.";
  }

  typedef ncs_template_nsm-mpls-aware {
    type string;
    description
      "Description of MPLS aware type.";
  }

  typedef ncs_template_nsm-flow-type {
    type string;
    description
      "Description of flow type.";
  }

  typedef ncs_template_nsm-srv6-aware {
    type string;
    description
      "Description of SRv6 aware.";
  }

  typedef ncs_template_nsm-destination-board {
    type string;
    description
      "Description of destination board type.";
  }

  typedef ncs_template_nsm-statistic-type {
    type string;
    description
      "Description of statistic type.";
  }

  typedef ncs_template_nsm-template-type {
    type string;
    description
      "Description of template type.";
  }

  typedef ncs_template_nsm-tal-type {
    type string;
    description
      "Description of tal type.";
  }

  typedef ncs_template_nsm-pkt-type {
    type string;
    description
      "Description of packet.";
  }

  typedef ncs_rpc_notif_nsm-direction {
    type enumeration {
      enum "inbound" {
        value 0;
        description
          "Inbound.";
      }
      enum "outbound" {
        value 1;
        description
          "Outbound.";
      }
    }
    description
      "Description of sampler direction.";
  }

  typedef ncs_rpc_notif_nsm-agg-type {
    type enumeration {
      enum "as" {
        value 0;
        description
          "AS aggregation.";
      }
      enum "as-tos" {
        value 1;
        description
          "AS-ToS aggregation.";
      }
      enum "protocol-port" {
        value 2;
        description
          "Protocol-port.";
      }
      enum "protocol-port-tos" {
        value 3;
        description
          "Protocol-port-ToS aggregation.";
      }
      enum "source-prefix" {
        value 4;
        description
          "Source-prefix aggregation. It classifies flows by four key values, that is, the source AS number, source mask length, source prefix, and incoming interface index.";
      }
      enum "source-prefix-tos" {
        value 5;
        description
          "Source prefix-ToS aggregation. It classifies flows by five key values, that is, the source AS number, source mask length, source prefix, ToS, and incoming interface index.";
      }
      enum "destination-prefix" {
        value 6;
        description
          "Destination-prefix aggregation. It classifies flows by four key values, that is, the destination AS number, destination mask length, destination prefix, and outgoing interface index.";
      }
      enum "destination-prefix-tos" {
        value 7;
        description
          "Destination prefix-ToS aggregation. It classifies flows by five key values, that is, the destination AS number, destination mask length, destination prefix, ToS, and outgoing interface index.";
      }
      enum "prefix" {
        value 8;
        description
          "Prefix aggregation. It classifies flows by eight key values, that is, the source AS number, destination AS number, source mask length, destination mask length, source prefix, destination prefix, incoming interface index, and outgoing interface index.";
      }
      enum "prefix-tos" {
        value 9;
        description
          "Prefix-ToS aggregation. It classifies flows by nine key values, that is, the source AS number, destination AS number, source mask length, destination mask length, source prefix, destination prefix, ToS, incoming interface index, and outgoing interface index.";
      }
      enum "mpls-label" {
        value 10;
        description
          "MPLS-label aggregation. It classifies flows by six key values, that is, the first layer label, second layer label, third layer label, TopLabelIpAddress, stack bottom symbol of the first layer label, and the EXP value of the first layer label.";
      }
      enum "vlan-id" {
        value 11;
        description
          "VLAN-ID aggregation. It classifies flows by two key values, that is, the VLAN ID and incoming interface index.";
      }
      enum "bgp-nexthop-tos" {
        value 12;
        description
          "BGP next hop-ToS aggregation. It classifies streams by six key values including the BGP next hop, source AS number, destination AS number, incoming interface index, outgoing interface index, and ToS.";
      }
      enum "index-tos" {
        value 13;
        description
          "Interface index-ToS aggregation. It classifies flows by three key values, that is, the incoming interface index, outgoing interface index, and ToS.";
      }
      enum "source-index-tos" {
        value 14;
        description
          "Interface source-index-ToS aggregation.";
      }
      enum "bgp-community" {
        value 15;
        description
          "BGP Community Aggregation.";
      }
      enum "vni-sip-dip" {
        value 16;
        description
          "It classifies flows by three key values, that is, the vni id, sip, and dip.";
      }
    }
    description
      "Description of aggregation type.";
  }

  typedef ncs_rpc_notif_nsm-enable {
    type enumeration {
      enum "false" {
        value 0;
        description
          "Disabling.";
      }
      enum "true" {
        value 1;
        description
          "Enabling.";
      }
    }
    description
      "Description of enable type.";
  }

  typedef ncs_rpc_notif_nsm-origin-version {
    type enumeration {
      enum "5" {
        value 5;
        description
          "Version 5.";
      }
      enum "9" {
        value 9;
        description
          "Version 9.";
      }
      enum "ipfix" {
        value 10;
        description
          "Version ipfix.";
      }
    }
    description
      "Description of origin version type.";
  }

  typedef ncs_rpc_notif_nsm-as-type {
    type enumeration {
      enum "invalid-as" {
        value 0;
        description
          "Invalid system ID.";
      }
      enum "origin-as" {
        value 1;
        description
          "Start AS number.";
      }
      enum "peer-as" {
        value 2;
        description
          "Adjacent AS number.";
      }
    }
    description
      "Description of as type.";
  }

  typedef ncs_rpc_notif_nsm-as-mode-index {
    type enumeration {
      enum "16" {
        value 0;
        description
          "16-bit interface index carried in exported NetStream packets.";
      }
      enum "32" {
        value 1;
        description
          "32-bit interface index carried in exported NetStream packets.";
      }
    }
    description
      "Description of as mode index type.";
  }

  typedef ncs_rpc_notif_nsm-mpls-aware {
    type enumeration {
      enum "ip-only" {
        value 0;
        description
          "IP address collection mode.";
      }
      enum "label-and-ip" {
        value 1;
        description
          "Inner IP packet and label collection mode.";
      }
      enum "label-only" {
        value 2;
        description
          "Label collection mode.";
      }
      enum "invalid-mpls" {
        value 3;
        description
          "Invalid_MPLS.";
      }
    }
    description
      "Description of MPLS aware type.";
  }

  typedef ncs_rpc_notif_nsm-flow-type {
    type enumeration {
      enum "ip-flow" {
        value 0;
        description
          "IPv4.";
      }
      enum "ipv6-flow" {
        value 1;
        description
          "IPv6.";
      }
    }
    description
      "Description of flow type.";
  }

  typedef ncs_rpc_notif_nsm-srv6-aware {
    type enumeration {
      enum "inner-header" {
        value 1;
        description
          "Collect inner layer header.";
      }
    }
    description
      "Description of SRv6 aware.";
  }

  typedef ncs_rpc_notif_nsm-destination-board {
    type enumeration {
      enum "self" {
        value 0;
        description
          "To Self.";
      }
      enum "main" {
        value 1;
        description
          "To Main.";
      }
      enum "bak" {
        value 2;
        description
          "To Bak.";
      }
    }
    description
      "Description of destination board type.";
  }

  typedef ncs_rpc_notif_nsm-statistic-type {
    type enumeration {
      enum "template" {
        value 0;
        description
          "Template statistics.";
      }
      enum "pack" {
        value 1;
        description
          "Packet statistics.";
      }
    }
    description
      "Description of statistic type.";
  }

  typedef ncs_rpc_notif_nsm-template-type {
    type enumeration {
      enum "option" {
        value 0;
        description
          "Option statistics.";
      }
      enum "aggregation" {
        value 1;
        description
          "Aggregation template statistics.";
      }
      enum "origin" {
        value 2;
        description
          "Origin template statistics.";
      }
      enum "record" {
        value 3;
        description
          "Flexible template statistics.";
      }
    }
    description
      "Description of template type.";
  }

  typedef ncs_rpc_notif_nsm-tal-type {
    type enumeration {
      enum "mpls" {
        value 1;
        description
          "MPLS.";
      }
    }
    description
      "Description of tal type.";
  }

  typedef ncs_rpc_notif_nsm-pkt-type {
    type enumeration {
      enum "ipv4" {
        value 1;
        description
          "IPv4 packet.";
      }
      enum "mpls" {
        value 2;
        description
          "MPLS packet.";
      }
    }
    description
      "Description of packet.";
  }

  typedef live_ncs_nsm-direction {
    type enumeration {
      enum "inbound" {
        value 0;
        description
          "Inbound.";
      }
      enum "outbound" {
        value 1;
        description
          "Outbound.";
      }
    }
    description
      "Description of sampler direction.";
  }

  typedef live_ncs_nsm-agg-type {
    type enumeration {
      enum "as" {
        value 0;
        description
          "AS aggregation.";
      }
      enum "as-tos" {
        value 1;
        description
          "AS-ToS aggregation.";
      }
      enum "protocol-port" {
        value 2;
        description
          "Protocol-port.";
      }
      enum "protocol-port-tos" {
        value 3;
        description
          "Protocol-port-ToS aggregation.";
      }
      enum "source-prefix" {
        value 4;
        description
          "Source-prefix aggregation. It classifies flows by four key values, that is, the source AS number, source mask length, source prefix, and incoming interface index.";
      }
      enum "source-prefix-tos" {
        value 5;
        description
          "Source prefix-ToS aggregation. It classifies flows by five key values, that is, the source AS number, source mask length, source prefix, ToS, and incoming interface index.";
      }
      enum "destination-prefix" {
        value 6;
        description
          "Destination-prefix aggregation. It classifies flows by four key values, that is, the destination AS number, destination mask length, destination prefix, and outgoing interface index.";
      }
      enum "destination-prefix-tos" {
        value 7;
        description
          "Destination prefix-ToS aggregation. It classifies flows by five key values, that is, the destination AS number, destination mask length, destination prefix, ToS, and outgoing interface index.";
      }
      enum "prefix" {
        value 8;
        description
          "Prefix aggregation. It classifies flows by eight key values, that is, the source AS number, destination AS number, source mask length, destination mask length, source prefix, destination prefix, incoming interface index, and outgoing interface index.";
      }
      enum "prefix-tos" {
        value 9;
        description
          "Prefix-ToS aggregation. It classifies flows by nine key values, that is, the source AS number, destination AS number, source mask length, destination mask length, source prefix, destination prefix, ToS, incoming interface index, and outgoing interface index.";
      }
      enum "mpls-label" {
        value 10;
        description
          "MPLS-label aggregation. It classifies flows by six key values, that is, the first layer label, second layer label, third layer label, TopLabelIpAddress, stack bottom symbol of the first layer label, and the EXP value of the first layer label.";
      }
      enum "vlan-id" {
        value 11;
        description
          "VLAN-ID aggregation. It classifies flows by two key values, that is, the VLAN ID and incoming interface index.";
      }
      enum "bgp-nexthop-tos" {
        value 12;
        description
          "BGP next hop-ToS aggregation. It classifies streams by six key values including the BGP next hop, source AS number, destination AS number, incoming interface index, outgoing interface index, and ToS.";
      }
      enum "index-tos" {
        value 13;
        description
          "Interface index-ToS aggregation. It classifies flows by three key values, that is, the incoming interface index, outgoing interface index, and ToS.";
      }
      enum "source-index-tos" {
        value 14;
        description
          "Interface source-index-ToS aggregation.";
      }
      enum "bgp-community" {
        value 15;
        description
          "BGP Community Aggregation.";
      }
      enum "vni-sip-dip" {
        value 16;
        description
          "It classifies flows by three key values, that is, the vni id, sip, and dip.";
      }
    }
    description
      "Description of aggregation type.";
  }

  typedef live_ncs_nsm-enable {
    type enumeration {
      enum "false" {
        value 0;
        description
          "Disabling.";
      }
      enum "true" {
        value 1;
        description
          "Enabling.";
      }
    }
    description
      "Description of enable type.";
  }

  typedef live_ncs_nsm-origin-version {
    type enumeration {
      enum "5" {
        value 5;
        description
          "Version 5.";
      }
      enum "9" {
        value 9;
        description
          "Version 9.";
      }
      enum "ipfix" {
        value 10;
        description
          "Version ipfix.";
      }
    }
    description
      "Description of origin version type.";
  }

  typedef live_ncs_nsm-as-type {
    type enumeration {
      enum "invalid-as" {
        value 0;
        description
          "Invalid system ID.";
      }
      enum "origin-as" {
        value 1;
        description
          "Start AS number.";
      }
      enum "peer-as" {
        value 2;
        description
          "Adjacent AS number.";
      }
    }
    description
      "Description of as type.";
  }

  typedef live_ncs_nsm-as-mode-index {
    type enumeration {
      enum "16" {
        value 0;
        description
          "16-bit interface index carried in exported NetStream packets.";
      }
      enum "32" {
        value 1;
        description
          "32-bit interface index carried in exported NetStream packets.";
      }
    }
    description
      "Description of as mode index type.";
  }

  typedef live_ncs_nsm-mpls-aware {
    type enumeration {
      enum "ip-only" {
        value 0;
        description
          "IP address collection mode.";
      }
      enum "label-and-ip" {
        value 1;
        description
          "Inner IP packet and label collection mode.";
      }
      enum "label-only" {
        value 2;
        description
          "Label collection mode.";
      }
      enum "invalid-mpls" {
        value 3;
        description
          "Invalid_MPLS.";
      }
    }
    description
      "Description of MPLS aware type.";
  }

  typedef live_ncs_nsm-flow-type {
    type enumeration {
      enum "ip-flow" {
        value 0;
        description
          "IPv4.";
      }
      enum "ipv6-flow" {
        value 1;
        description
          "IPv6.";
      }
    }
    description
      "Description of flow type.";
  }

  typedef live_ncs_nsm-srv6-aware {
    type enumeration {
      enum "inner-header" {
        value 1;
        description
          "Collect inner layer header.";
      }
    }
    description
      "Description of SRv6 aware.";
  }

  typedef live_ncs_nsm-destination-board {
    type enumeration {
      enum "self" {
        value 0;
        description
          "To Self.";
      }
      enum "main" {
        value 1;
        description
          "To Main.";
      }
      enum "bak" {
        value 2;
        description
          "To Bak.";
      }
    }
    description
      "Description of destination board type.";
  }

  typedef live_ncs_nsm-statistic-type {
    type enumeration {
      enum "template" {
        value 0;
        description
          "Template statistics.";
      }
      enum "pack" {
        value 1;
        description
          "Packet statistics.";
      }
    }
    description
      "Description of statistic type.";
  }

  typedef live_ncs_nsm-template-type {
    type enumeration {
      enum "option" {
        value 0;
        description
          "Option statistics.";
      }
      enum "aggregation" {
        value 1;
        description
          "Aggregation template statistics.";
      }
      enum "origin" {
        value 2;
        description
          "Origin template statistics.";
      }
      enum "record" {
        value 3;
        description
          "Flexible template statistics.";
      }
    }
    description
      "Description of template type.";
  }

  typedef live_ncs_nsm-tal-type {
    type enumeration {
      enum "mpls" {
        value 1;
        description
          "MPLS.";
      }
    }
    description
      "Description of tal type.";
  }

  typedef live_ncs_nsm-pkt-type {
    type enumeration {
      enum "ipv4" {
        value 1;
        description
          "IPv4 packet.";
      }
      enum "mpls" {
        value 2;
        description
          "MPLS packet.";
      }
    }
    description
      "Description of packet.";
  }

  typedef nsm-direction {
    type enumeration {
      enum "inbound" {
        value 0;
        description
          "Inbound.";
      }
      enum "outbound" {
        value 1;
        description
          "Outbound.";
      }
    }
    description
      "Description of sampler direction.";
  }

  typedef nsm-agg-type {
    type enumeration {
      enum "as" {
        value 0;
        description
          "AS aggregation.";
      }
      enum "as-tos" {
        value 1;
        description
          "AS-ToS aggregation.";
      }
      enum "protocol-port" {
        value 2;
        description
          "Protocol-port.";
      }
      enum "protocol-port-tos" {
        value 3;
        description
          "Protocol-port-ToS aggregation.";
      }
      enum "source-prefix" {
        value 4;
        description
          "Source-prefix aggregation. It classifies flows by four key values, that is, the source AS number, source mask length, source prefix, and incoming interface index.";
      }
      enum "source-prefix-tos" {
        value 5;
        description
          "Source prefix-ToS aggregation. It classifies flows by five key values, that is, the source AS number, source mask length, source prefix, ToS, and incoming interface index.";
      }
      enum "destination-prefix" {
        value 6;
        description
          "Destination-prefix aggregation. It classifies flows by four key values, that is, the destination AS number, destination mask length, destination prefix, and outgoing interface index.";
      }
      enum "destination-prefix-tos" {
        value 7;
        description
          "Destination prefix-ToS aggregation. It classifies flows by five key values, that is, the destination AS number, destination mask length, destination prefix, ToS, and outgoing interface index.";
      }
      enum "prefix" {
        value 8;
        description
          "Prefix aggregation. It classifies flows by eight key values, that is, the source AS number, destination AS number, source mask length, destination mask length, source prefix, destination prefix, incoming interface index, and outgoing interface index.";
      }
      enum "prefix-tos" {
        value 9;
        description
          "Prefix-ToS aggregation. It classifies flows by nine key values, that is, the source AS number, destination AS number, source mask length, destination mask length, source prefix, destination prefix, ToS, incoming interface index, and outgoing interface index.";
      }
      enum "mpls-label" {
        value 10;
        description
          "MPLS-label aggregation. It classifies flows by six key values, that is, the first layer label, second layer label, third layer label, TopLabelIpAddress, stack bottom symbol of the first layer label, and the EXP value of the first layer label.";
      }
      enum "vlan-id" {
        value 11;
        description
          "VLAN-ID aggregation. It classifies flows by two key values, that is, the VLAN ID and incoming interface index.";
      }
      enum "bgp-nexthop-tos" {
        value 12;
        description
          "BGP next hop-ToS aggregation. It classifies streams by six key values including the BGP next hop, source AS number, destination AS number, incoming interface index, outgoing interface index, and ToS.";
      }
      enum "index-tos" {
        value 13;
        description
          "Interface index-ToS aggregation. It classifies flows by three key values, that is, the incoming interface index, outgoing interface index, and ToS.";
      }
      enum "source-index-tos" {
        value 14;
        description
          "Interface source-index-ToS aggregation.";
      }
      enum "bgp-community" {
        value 15;
        description
          "BGP Community Aggregation.";
      }
      enum "vni-sip-dip" {
        value 16;
        description
          "It classifies flows by three key values, that is, the vni id, sip, and dip.";
      }
    }
    description
      "Description of aggregation type.";
  }

  typedef nsm-enable {
    type enumeration {
      enum "false" {
        value 0;
        description
          "Disabling.";
      }
      enum "true" {
        value 1;
        description
          "Enabling.";
      }
    }
    description
      "Description of enable type.";
  }

  typedef nsm-origin-version {
    type enumeration {
      enum "5" {
        value 5;
        description
          "Version 5.";
      }
      enum "9" {
        value 9;
        description
          "Version 9.";
      }
      enum "ipfix" {
        value 10;
        description
          "Version ipfix.";
      }
    }
    description
      "Description of origin version type.";
  }

  typedef nsm-as-type {
    type enumeration {
      enum "invalid-as" {
        value 0;
        description
          "Invalid system ID.";
      }
      enum "origin-as" {
        value 1;
        description
          "Start AS number.";
      }
      enum "peer-as" {
        value 2;
        description
          "Adjacent AS number.";
      }
    }
    description
      "Description of as type.";
  }

  typedef nsm-as-mode-index {
    type enumeration {
      enum "16" {
        value 0;
        description
          "16-bit interface index carried in exported NetStream packets.";
      }
      enum "32" {
        value 1;
        description
          "32-bit interface index carried in exported NetStream packets.";
      }
    }
    description
      "Description of as mode index type.";
  }

  typedef nsm-mpls-aware {
    type enumeration {
      enum "ip-only" {
        value 0;
        description
          "IP address collection mode.";
      }
      enum "label-and-ip" {
        value 1;
        description
          "Inner IP packet and label collection mode.";
      }
      enum "label-only" {
        value 2;
        description
          "Label collection mode.";
      }
      enum "invalid-mpls" {
        value 3;
        description
          "Invalid_MPLS.";
      }
    }
    description
      "Description of MPLS aware type.";
  }

  typedef nsm-flow-type {
    type enumeration {
      enum "ip-flow" {
        value 0;
        description
          "IPv4.";
      }
      enum "ipv6-flow" {
        value 1;
        description
          "IPv6.";
      }
    }
    description
      "Description of flow type.";
  }

  typedef nsm-srv6-aware {
    type enumeration {
      enum "inner-header" {
        value 1;
        description
          "Collect inner layer header.";
      }
    }
    description
      "Description of SRv6 aware.";
  }

  typedef nsm-destination-board {
    type enumeration {
      enum "self" {
        value 0;
        description
          "To Self.";
      }
      enum "main" {
        value 1;
        description
          "To Main.";
      }
      enum "bak" {
        value 2;
        description
          "To Bak.";
      }
    }
    description
      "Description of destination board type.";
  }

  typedef nsm-statistic-type {
    type enumeration {
      enum "template" {
        value 0;
        description
          "Template statistics.";
      }
      enum "pack" {
        value 1;
        description
          "Packet statistics.";
      }
    }
    description
      "Description of statistic type.";
  }

  typedef nsm-template-type {
    type enumeration {
      enum "option" {
        value 0;
        description
          "Option statistics.";
      }
      enum "aggregation" {
        value 1;
        description
          "Aggregation template statistics.";
      }
      enum "origin" {
        value 2;
        description
          "Origin template statistics.";
      }
      enum "record" {
        value 3;
        description
          "Flexible template statistics.";
      }
    }
    description
      "Description of template type.";
  }

  typedef nsm-tal-type {
    type enumeration {
      enum "mpls" {
        value 1;
        description
          "MPLS.";
      }
    }
    description
      "Description of tal type.";
  }

  typedef nsm-pkt-type {
    type enumeration {
      enum "ipv4" {
        value 1;
        description
          "IPv4 packet.";
      }
      enum "mpls" {
        value 2;
        description
          "MPLS packet.";
      }
    }
    description
      "Description of packet.";
  }

  augment "/ncs:devices/ncs:device/ncs:config" {
    container netstream {
      tailf:ncs-device-type "netconf";
      tailf:display-when "not(../../ncs:module) or ../../ncs:module[ncs:name='huawei-netstream']";
      description
        "Netstream.";
      container flow-instances {
        description
          "List of configure global instance.";
        list flow-instance {
          key "flow-type";
          description
            "Configure global instance.";
          ext:generated-by "system" {
            description
              "The all instances are generated by system automatically.";
          }
          ext:operation-exclude "create|delete" {
            description
              "The all instances cannot be created or deleted.";
          }
          leaf flow-type {
            type nsm-flow-type;
            description
              "Flow type.";
          }
          leaf source-ipv4-address {
            type inet:ipv4-address-no-zone;
            description
              "Source IPv4 address.";
          }
          leaf source-ipv4-port {
            when 'not(not(../source-ipv4-address))' {
              tailf:xpath-root 3;
            }
            type uint16 {
              range "1..65535";
            }
            default "40000";
            description
              "Source IPv4 port.";
          }
          leaf source-ipv6-address {
            type inet:ipv6-address-no-zone;
            description
              "Source IPv6 address.";
          }
          leaf source-ipv6-port {
            when 'not(not(../source-ipv6-address))' {
              tailf:xpath-root 3;
            }
            type uint16 {
              range "1..65535";
            }
            default "40000";
            description
              "Source IPv6 port.";
          }
          leaf export-version {
            type nsm-origin-version;
            must "(../flow-type='ipv6-flow' and (../export-version='9' or ../export-version='ipfix') ) or ((not(../flow-type='ipv6-flow') and (../export-version='5' or ../export-version='9' or ../export-version='ipfix') ))" {
              tailf:xpath-root 3;
            }
            description
              "Version of NetStream statistics packets. The value of IPv4 can be 5,9 or ipfix, the value of IPv6 can be 9 or ipfix.";
          }
          leaf as-type {
            type nsm-as-type;
            must "../as-type='invalid-as' or (../as-type!='invalid-as' and ../flow-type='ip-flow')" {
              tailf:xpath-root 3;
            }
            default "invalid-as";
            description
              "AS number of a specified IP address. The available options are origin-as (start AS number) and peer-as (adjacent AS number).";
          }
          leaf bgp-nexthop {
            type nsm-enable;
            must "(../export-version and ../export-version != '5' and ../bgp-nexthop= 'true') or ../bgp-nexthop = 'false'" {
              tailf:xpath-root 3;
            }
            default "false";
            description
              "Whether exported statistics contain BGP next hop information. Version 5 does not support BGP next hop.";
          }
          leaf template-timeout-rate {
            type uint16 {
              range "1..3600";
            }
            units "min";
            default "30";
            description
              "The interval for refreshing the template.";
          }
          leaf option-template-timeout-rate {
            type uint16 {
              range "1..3600";
            }
            units "min";
            default "30";
            description
              "Interval for refreshing the Option template.";
          }
          leaf option-template-refresh-rate {
            type uint16 {
              range "1..600";
            }
            units "packet";
            default "20";
            description
              "Packet-interval refreshing time of the option template.";
          }
          leaf option-data-timeout-rate {
            type uint16 {
              range "1..16";
            }
            units "min";
            default "16";
            description
              "Interval for refreshing the option data.";
          }
          choice agg-active-age {
            default "minutes";
            description
              "Specify the active aging time of aggregation flows.";
            case minutes {
              description
                "Specify the active aging time (mins) of aggregation flows.";
              leaf agg-active-age-minutes {
                type uint32 {
                  range "1..60";
                }
                units "min";
                default "5";
                description
                  "Specify the active aging time (mins) of aggregation flows.";
              }
            }
            case seconds {
              description
                "Specify the active aging time (secs) of aggregation flows.";
              leaf agg-active-age-seconds {
                type uint8 {
                  range "15..59";
                }
                units "s";
                description
                  "Specify the active aging time (secs) of aggregation flows.";
              }
            }
          }
          leaf agg-inactive-age-seconds {
            type uint32 {
              range "5..600";
            }
            units "s";
            default "300";
            description
              "Inactive aging time of aggregation flows.";
          }
          choice origin-active-age {
            default "minutes";
            description
              "Active aging time of original flows.";
            case minutes {
              description
                "Active aging time (mins) of original flows.";
              leaf origin-active-age-minutes {
                type uint32 {
                  range "1..60";
                }
                units "min";
                default "30";
                description
                  "Active aging time (mins) of original flows.";
              }
            }
            case seconds {
              description
                "Active aging time (secs) of original flows.";
              leaf origin-active-age-seconds {
                type uint8 {
                  range "15..59";
                }
                units "s";
                description
                  "Active aging time (secs) of original flows.";
              }
            }
          }
          leaf origin-inactive-seconds {
            type uint32 {
              range "5..600";
            }
            units "s";
            default "30";
            description
              "Inactive aging time of original flows.";
          }
          leaf as-mode {
            type nsm-as-mode-index;
            default "16";
            description
              "Mode supported by ASs.";
          }
          leaf index-switch {
            type nsm-as-mode-index;
            default "16";
            description
              "NetStream interface index.";
          }
          leaf tcpflag-enable {
            type nsm-enable;
            default "false";
            description
              "Whether tcp-flag information is extracted during the processing of sampling packets.";
          }
          leaf mpls-aware-enable {
            type nsm-mpls-aware;
            default "ip-only";
            description
              "Whether Layer 3 labels are extracted during the processing of sampling packets. The default value is ip-only, that is, not to extract the label.label-only indicates that only the label is extracted; label-and-ip indicates that both the label and IP address are extracted.";
          }
          leaf interface-option-enable {
            type nsm-enable;
            default "false";
            description
              "Flow of statistics about interface options, including the interface index for enabling NetStream in inbound direction or outbound direction, and corresponding sampling values.";
          }
          leaf ttl-flag {
            type nsm-enable;
            must "(../export-version and ../export-version != '5' and ../ttl-flag= 'true') or ../ttl-flag = 'false'" {
              tailf:xpath-root 3;
            }
            default "false";
            description
              "Whether exported statistics contain TTL information.";
          }
          leaf sequence-number-fix {
            type nsm-enable;
            default "false";
            description
              "Whether the numbering mode of IPFIX version packet is fixed mode.";
          }
          leaf srv6-aware {
            type nsm-srv6-aware;
            must "../flow-type='ipv6-flow'" {
              tailf:xpath-root 3;
            }
            description
              "Whether collect inner layer header of SRv6 packet.";
          }
          container sampler-rates {
            description
              "List of configure global sampler instance.";
            list sampler-rate {
              key "direction";
              description
                "Configure global sampler instance.";
              leaf direction {
                type nsm-direction;
                description
                  "Sampler direction.";
              }
              choice sampler-type {
                mandatory true;
                description
                  "Sampler type.";
                case fix-packets {
                  description
                    "Fix-pack value.";
                  leaf fix-packets-value {
                    type uint32 {
                      range "1..65535";
                    }
                    description
                      "Fix-pack value.";
                  }
                }
                case fix-time {
                  description
                    "Fix-time value.";
                  leaf fix-time-value {
                    type uint32 {
                      range "5..30000";
                    }
                    description
                      "Fix-time value.";
                  }
                }
                case random-packets {
                  description
                    "Random-pack value.";
                  leaf random-packets-value {
                    type uint32 {
                      range "1..65535";
                    }
                    description
                      "Random-pack value.";
                  }
                }
              }
            }
          }
          container export-ipv4-hosts {
            description
              "List of configure export vpn destination IPv4 address instance.";
            list export-ipv4-host {
              key "address port vpn-name";
              max-elements 8;
              description
                "Configure export vpn destination IPv4 address instance.";
              leaf address {
                type inet:ipv4-address-no-zone;
                description
                  "Exported destination IPv4 address.";
              }
              leaf port {
                type uint16 {
                  range "1..65535";
                }
                description
                  "UDP port number of the NSC.";
              }
              leaf vpn-name {
                type leafref {
                  path "/ncs:devices/ncs:device/ncs:config/ni:network-instance/ni:instances/ni:instance/ni:name" {
                    tailf:xpath-root 3;
                  }
                }
                must "/ni:network-instance/ni:instances/ni:instance[ni:name=current()]/l3vpn:afs/l3vpn:af[l3vpn:type='ipv4-unicast']" {
                  tailf:xpath-root 3;
                }
                description
                  "Vpn instance name.";
              }
              leaf dscp-value {
                type uint8 {
                  range "1..63";
                }
                description
                  "Differentiated Services Code Point.";
              }
            }
          }
        }
      }
      container aggregations {
        description
          "List of configure aggregation instance.";
        list aggregation {
          must "./flow-type='ip-flow' or ((./flow-type='ipv6-flow') and (./agg-type!='bgp-community' and ./agg-type!='source-index-tos' and ./agg-type!='vni-sip-dip'))" {
            tailf:xpath-root 3;
          }
          key "flow-type agg-type";
          description
            "Configure aggregation instance.";
          leaf flow-type {
            type nsm-flow-type;
            description
              "Flow type.";
          }
          leaf agg-type {
            type nsm-agg-type;
            description
              "Aggregation type.";
          }
          leaf agg-enable {
            type nsm-enable;
            default "false";
            description
              "Aggregation enabling flag.";
          }
        }
      }
      container monitors {
        description
          "List of configure monitor instance.";
        list monitor {
          key "flow-type monitor-name";
          description
            "Configure monitor instance.";
          leaf flow-type {
            type nsm-flow-type;
            description
              "Flow type.";
          }
          leaf monitor-name {
            type string {
              length "1..31";
            }
            description
              "Monitor name.";
          }
        }
      }
      container flexflow-records {
        description
          "List of configure flexible flow instance.";
        list flexflow-record {
          key "flow-type record-name";
          description
            "Configure flexible flow instance.";
          leaf flow-type {
            type nsm-flow-type;
            description
              "Flow type.";
          }
          leaf record-name {
            type string {
              length "1..32";
              pattern '[a-zA-Z0-9._]{1,32}';
            }
            description
              "Flexible flow record name.";
          }
          leaf source-address {
            type nsm-enable;
            default "false";
            description
              "Indicates the aggregation based on source addresses.";
          }
          leaf source-as {
            type nsm-enable;
            default "false";
            description
              "Indicates that the statistics to be sent to the NSC contain source AS information.";
          }
        }
      }
      // NCS drop config false container 'sampler-rate-lower-limits'
      // NCS drop config false container 'template-export-statistics'
      container option-application-labels {
        description
          "Configure label list.";
        leaf tal-enable {
          type nsm-enable;
          default "false";
          description
            "TAL enabling flag.";
        }
        // NCS drop config false container 'tal-infos'
      }
      // NCS drop config false container 'stream-infos'
      // NCS drop config false container 'stream-log-infos'
    }
  }
  augment "/ncs:devices/ncs:device/ncs:live-status" {
    container netstream {
      tailf:ncs-device-type "netconf";
      tailf:display-when "not(../../ncs:module) or ../../ncs:module[ncs:name='huawei-netstream'] or (../../ncs:live-status-protocol[not(ncs:capability)]) or (../../ncs:live-status-protocol/ncs:capability/ncs:module[.='huawei-netstream'])";
      description
        "Netstream.";
      container flow-instances {
        description
          "List of configure global instance.";
        list flow-instance {
          key "flow-type";
          description
            "Configure global instance.";
          ext:generated-by "system" {
            description
              "The all instances are generated by system automatically.";
          }
          ext:operation-exclude "create|delete" {
            description
              "The all instances cannot be created or deleted.";
          }
          leaf flow-type {
            type live_ncs_nsm-flow-type;
            description
              "Flow type.";
          }
          leaf source-ipv4-address {
            type inet:ipv4-address-no-zone;
            description
              "Source IPv4 address.";
          }
          leaf source-ipv4-port {
            // NCS drop when statement
            type uint16 {
              range "1..65535";
            }
            // NCS drop default statement
            description
              "Source IPv4 port.";
          }
          leaf source-ipv6-address {
            type inet:ipv6-address-no-zone;
            description
              "Source IPv6 address.";
          }
          leaf source-ipv6-port {
            // NCS drop when statement
            type uint16 {
              range "1..65535";
            }
            // NCS drop default statement
            description
              "Source IPv6 port.";
          }
          leaf export-version {
            type live_ncs_nsm-origin-version;
            // NCS drop must statement
            description
              "Version of NetStream statistics packets. The value of IPv4 can be 5,9 or ipfix, the value of IPv6 can be 9 or ipfix.";
          }
          leaf as-type {
            type live_ncs_nsm-as-type;
            // NCS drop must statement
            // NCS drop default statement
            description
              "AS number of a specified IP address. The available options are origin-as (start AS number) and peer-as (adjacent AS number).";
          }
          leaf bgp-nexthop {
            type live_ncs_nsm-enable;
            // NCS drop must statement
            // NCS drop default statement
            description
              "Whether exported statistics contain BGP next hop information. Version 5 does not support BGP next hop.";
          }
          leaf template-timeout-rate {
            type uint16 {
              range "1..3600";
            }
            units "min";
            // NCS drop default statement
            description
              "The interval for refreshing the template.";
          }
          leaf option-template-timeout-rate {
            type uint16 {
              range "1..3600";
            }
            units "min";
            // NCS drop default statement
            description
              "Interval for refreshing the Option template.";
          }
          leaf option-template-refresh-rate {
            type uint16 {
              range "1..600";
            }
            units "packet";
            // NCS drop default statement
            description
              "Packet-interval refreshing time of the option template.";
          }
          leaf option-data-timeout-rate {
            type uint16 {
              range "1..16";
            }
            units "min";
            // NCS drop default statement
            description
              "Interval for refreshing the option data.";
          }
          choice agg-active-age {
            // NCS drop default statement
            description
              "Specify the active aging time of aggregation flows.";
            case minutes {
              description
                "Specify the active aging time (mins) of aggregation flows.";
              leaf agg-active-age-minutes {
                type uint32 {
                  range "1..60";
                }
                units "min";
                // NCS drop default statement
                description
                  "Specify the active aging time (mins) of aggregation flows.";
              }
            }
            case seconds {
              description
                "Specify the active aging time (secs) of aggregation flows.";
              leaf agg-active-age-seconds {
                type uint8 {
                  range "15..59";
                }
                units "s";
                description
                  "Specify the active aging time (secs) of aggregation flows.";
              }
            }
          }
          leaf agg-inactive-age-seconds {
            type uint32 {
              range "5..600";
            }
            units "s";
            // NCS drop default statement
            description
              "Inactive aging time of aggregation flows.";
          }
          choice origin-active-age {
            // NCS drop default statement
            description
              "Active aging time of original flows.";
            case minutes {
              description
                "Active aging time (mins) of original flows.";
              leaf origin-active-age-minutes {
                type uint32 {
                  range "1..60";
                }
                units "min";
                // NCS drop default statement
                description
                  "Active aging time (mins) of original flows.";
              }
            }
            case seconds {
              description
                "Active aging time (secs) of original flows.";
              leaf origin-active-age-seconds {
                type uint8 {
                  range "15..59";
                }
                units "s";
                description
                  "Active aging time (secs) of original flows.";
              }
            }
          }
          leaf origin-inactive-seconds {
            type uint32 {
              range "5..600";
            }
            units "s";
            // NCS drop default statement
            description
              "Inactive aging time of original flows.";
          }
          leaf as-mode {
            type live_ncs_nsm-as-mode-index;
            // NCS drop default statement
            description
              "Mode supported by ASs.";
          }
          leaf index-switch {
            type live_ncs_nsm-as-mode-index;
            // NCS drop default statement
            description
              "NetStream interface index.";
          }
          leaf tcpflag-enable {
            type live_ncs_nsm-enable;
            // NCS drop default statement
            description
              "Whether tcp-flag information is extracted during the processing of sampling packets.";
          }
          leaf mpls-aware-enable {
            type live_ncs_nsm-mpls-aware;
            // NCS drop default statement
            description
              "Whether Layer 3 labels are extracted during the processing of sampling packets. The default value is ip-only, that is, not to extract the label.label-only indicates that only the label is extracted; label-and-ip indicates that both the label and IP address are extracted.";
          }
          leaf interface-option-enable {
            type live_ncs_nsm-enable;
            // NCS drop default statement
            description
              "Flow of statistics about interface options, including the interface index for enabling NetStream in inbound direction or outbound direction, and corresponding sampling values.";
          }
          leaf ttl-flag {
            type live_ncs_nsm-enable;
            // NCS drop must statement
            // NCS drop default statement
            description
              "Whether exported statistics contain TTL information.";
          }
          leaf sequence-number-fix {
            type live_ncs_nsm-enable;
            // NCS drop default statement
            description
              "Whether the numbering mode of IPFIX version packet is fixed mode.";
          }
          leaf srv6-aware {
            type live_ncs_nsm-srv6-aware;
            // NCS drop must statement
            description
              "Whether collect inner layer header of SRv6 packet.";
          }
          container sampler-rates {
            description
              "List of configure global sampler instance.";
            list sampler-rate {
              key "direction";
              description
                "Configure global sampler instance.";
              leaf direction {
                type live_ncs_nsm-direction;
                description
                  "Sampler direction.";
              }
              choice sampler-type {
                // NCS drop mandatory statement
                description
                  "Sampler type.";
                case fix-packets {
                  description
                    "Fix-pack value.";
                  leaf fix-packets-value {
                    type uint32 {
                      range "1..65535";
                    }
                    description
                      "Fix-pack value.";
                  }
                }
                case fix-time {
                  description
                    "Fix-time value.";
                  leaf fix-time-value {
                    type uint32 {
                      range "5..30000";
                    }
                    description
                      "Fix-time value.";
                  }
                }
                case random-packets {
                  description
                    "Random-pack value.";
                  leaf random-packets-value {
                    type uint32 {
                      range "1..65535";
                    }
                    description
                      "Random-pack value.";
                  }
                }
              }
            }
          }
          container export-ipv4-hosts {
            description
              "List of configure export vpn destination IPv4 address instance.";
            list export-ipv4-host {
              key "address port vpn-name";
              // NCS drop max-elements statement
              description
                "Configure export vpn destination IPv4 address instance.";
              leaf address {
                type inet:ipv4-address-no-zone;
                description
                  "Exported destination IPv4 address.";
              }
              leaf port {
                type uint16 {
                  range "1..65535";
                }
                description
                  "UDP port number of the NSC.";
              }
              leaf vpn-name {
                type leafref {
                  path "/ncs:devices/ncs:device/ncs:live-status/ni:network-instance/ni:instances/ni:instance/ni:name" {
                    tailf:xpath-root 3;
                  }
                }
                // NCS drop must statement
                description
                  "Vpn instance name.";
              }
              leaf dscp-value {
                type uint8 {
                  range "1..63";
                }
                description
                  "Differentiated Services Code Point.";
              }
            }
          }
        }
      }
      container aggregations {
        description
          "List of configure aggregation instance.";
        list aggregation {
          // NCS drop must statement
          key "flow-type agg-type";
          description
            "Configure aggregation instance.";
          leaf flow-type {
            type live_ncs_nsm-flow-type;
            description
              "Flow type.";
          }
          leaf agg-type {
            type live_ncs_nsm-agg-type;
            description
              "Aggregation type.";
          }
          leaf agg-enable {
            type live_ncs_nsm-enable;
            // NCS drop default statement
            description
              "Aggregation enabling flag.";
          }
        }
      }
      container monitors {
        description
          "List of configure monitor instance.";
        list monitor {
          key "flow-type monitor-name";
          description
            "Configure monitor instance.";
          leaf flow-type {
            type live_ncs_nsm-flow-type;
            description
              "Flow type.";
          }
          leaf monitor-name {
            type string {
              length "1..31";
            }
            description
              "Monitor name.";
          }
        }
      }
      container flexflow-records {
        description
          "List of configure flexible flow instance.";
        list flexflow-record {
          key "flow-type record-name";
          description
            "Configure flexible flow instance.";
          leaf flow-type {
            type live_ncs_nsm-flow-type;
            description
              "Flow type.";
          }
          leaf record-name {
            type string {
              length "1..32";
              pattern '[a-zA-Z0-9._]{1,32}';
            }
            description
              "Flexible flow record name.";
          }
          leaf source-address {
            type live_ncs_nsm-enable;
            // NCS drop default statement
            description
              "Indicates the aggregation based on source addresses.";
          }
          leaf source-as {
            type live_ncs_nsm-enable;
            // NCS drop default statement
            description
              "Indicates that the statistics to be sent to the NSC contain source AS information.";
          }
        }
      }
      container sampler-rate-lower-limits {
        description
          "List of sampler rate lower-limits state.";
        list sampler-rate-lower-limit {
          key "slot-id";
          description
            "Sampler rate lower-limit state.";
          leaf slot-id {
            type string {
              length "1..16";
            }
            description
              "Slot id.";
          }
          leaf fix-packets-lower-limit {
            type uint32;
            description
              "Lower limit for fixed-packet-number-based sampling ratio.";
          }
          leaf fix-time-lower-limit {
            type uint32;
            description
              "Lower limit for fixed-time-based sampling ratio.";
          }
          leaf random-packets-lower-limit {
            type uint32;
            description
              "Lower limit for random-packet-number-based sampling ratio.";
          }
        }
      }
      container template-export-statistics {
        description
          "List of NSM statistics state.";
        list template-export-statistic {
          key "flow-type statistic-type export-type export-key";
          description
            "NSM statistics state.";
          leaf flow-type {
            type live_ncs_nsm-flow-type;
            description
              "Flow type.";
          }
          leaf statistic-type {
            type live_ncs_nsm-statistic-type;
            description
              "Statistics type.";
          }
          leaf export-type {
            type live_ncs_nsm-template-type;
            description
              "Export type.";
          }
          leaf export-key {
            type string {
              length "1..56";
            }
            description
              "Export keyword.";
          }
          leaf success-num {
            type uint32;
            description
              "Success times of exporting packets or templates.";
          }
          leaf failed-num {
            type uint32;
            description
              "Failure times of exporting packets or templates.";
          }
        }
      }
      container option-application-labels {
        description
          "Configure label list.";
        leaf tal-enable {
          type live_ncs_nsm-enable;
          // NCS drop default statement
          description
            "TAL enabling flag.";
        }
        container tal-infos {
          description
            "List of label information state.";
          list tal-info {
            key "tal-type ip-address";
            description
              "Label information state.";
            leaf tal-type {
              type live_ncs_nsm-tal-type;
              description
                "Label type.";
            }
            leaf ip-address {
              type inet:ipv4-address-no-zone;
              description
                "IP address or address segment of the endpoint of an LSP.";
            }
            leaf total-num {
              type uint32;
              description
                "Number of MPLS public TALs.";
            }
            leaf router-id {
              type inet:ipv4-address-no-zone;
              description
                "Router ID.";
            }
            leaf create-time {
              type yang:date-and-time;
              description
                "Application creating time.";
            }
          }
        }
      }
      container stream-infos {
        description
          "List of flow information.";
        list stream-info {
          description
            "Statistics of flow information.";
          leaf slot-id {
            ext:support-filter "true";
            type string {
              length "1..32";
            }
            description
              "The available slot.";
          }
          leaf source-ipv4-address {
            ext:support-filter "true";
            type inet:ipv4-address-no-zone;
            description
              "IP source address.";
          }
          leaf destination-ipv4-address {
            ext:support-filter "true";
            type inet:ipv4-address-no-zone;
            description
              "IP destination address.";
          }
          leaf source-port {
            ext:support-filter "true";
            type uint16;
            description
              "Source port.";
          }
          leaf destination-port {
            ext:support-filter "true";
            type uint16;
            description
              "Destination port.";
          }
          leaf protocol {
            ext:support-filter "true";
            type uint8;
            description
              "Specifies a protocol.";
          }
          leaf interface-name {
            ext:support-filter "true";
            type pub-type:live_ncs_if-name;
            description
              "The name of interface config netstream.";
          }
          leaf packet-type {
            ext:support-filter "true";
            type live_ncs_nsm-pkt-type;
            description
              "Packet type.";
          }
          leaf start-time {
            type yang:date-and-time;
            description
              "Start time.";
          }
          leaf end-time {
            type yang:date-and-time;
            description
              "End time.";
          }
          leaf direction {
            type live_ncs_nsm-direction;
            description
              "Direction.";
          }
          leaf packet-bytes {
            type uint32;
            description
              "Average packet length.";
          }
          leaf tos {
            type uint8;
            description
              "IP tos.";
          }
          leaf ttl {
            type uint16;
            description
              "IPv4 TTL.";
          }
          leaf tcp-flag {
            type uint8;
            description
              "TCP flag.";
          }
          leaf vni-id {
            type uint32;
            description
              "Vni ID.";
          }
          leaf vlan-id {
            type uint16;
            description
              "VLAN ID.";
          }
          leaf mpls-label1 {
            type uint32;
            description
              "MPLS label.";
          }
          leaf mpls-exp1 {
            type uint8;
            description
              "MPLS exp.";
          }
          leaf mpls-bottom1 {
            type uint8;
            description
              "MPLS bottom.";
          }
          leaf mpls-label2 {
            type uint32;
            description
              "MPLS label.";
          }
          leaf mpls-exp2 {
            type uint8;
            description
              "MPLS exp.";
          }
          leaf mpls-bottom2 {
            type uint8;
            description
              "MPLS bottom.";
          }
          leaf mpls-label3 {
            type uint32;
            description
              "MPLS label.";
          }
          leaf mpls-exp3 {
            type uint8;
            description
              "MPLS exp.";
          }
          leaf mpls-bottom3 {
            type uint8;
            description
              "MPLS bottom.";
          }
        }
      }
      container stream-log-infos {
        description
          "List of flow log information.";
        list stream-log-info {
          description
            "Statistics of flow log information.";
          leaf source-ipv4-address {
            ext:support-filter "true";
            type inet:ipv4-address-no-zone;
            description
              "IP source address.";
          }
          leaf destination-ipv4-address {
            ext:support-filter "true";
            type inet:ipv4-address-no-zone;
            description
              "IP destination address.";
          }
          leaf source-port {
            ext:support-filter "true";
            type uint16;
            description
              "Source port.";
          }
          leaf destination-port {
            ext:support-filter "true";
            type uint16;
            description
              "Destination port.";
          }
          leaf protocol {
            ext:support-filter "true";
            type uint8;
            description
              "Specifies a protocol.";
          }
          leaf interface-name {
            ext:support-filter "true";
            type pub-type:live_ncs_if-name;
            description
              "The name of interface config netstream.";
          }
          leaf packet-type {
            ext:support-filter "true";
            type live_ncs_nsm-pkt-type;
            description
              "Packet type.";
          }
          leaf start-time {
            type yang:date-and-time;
            description
              "Start time.";
          }
          leaf end-time {
            type yang:date-and-time;
            description
              "End time.";
          }
          leaf direction {
            type live_ncs_nsm-direction;
            description
              "Direction.";
          }
          leaf packet-bytes {
            type uint32;
            description
              "Average packet length.";
          }
          leaf tos {
            type uint8;
            description
              "IP tos.";
          }
          leaf ttl {
            type uint16;
            description
              "IPv4 TTL.";
          }
          leaf tcp-flag {
            type uint8;
            description
              "TCP flag.";
          }
          leaf vni-id {
            type uint32;
            description
              "Vni ID.";
          }
          leaf vlan-id {
            type uint16;
            description
              "VLAN ID.";
          }
          leaf mpls-label1 {
            type uint32;
            description
              "MPLS label.";
          }
          leaf mpls-exp1 {
            type uint8;
            description
              "MPLS exp.";
          }
          leaf mpls-bottom1 {
            type uint8;
            description
              "MPLS bottom.";
          }
          leaf mpls-label2 {
            type uint32;
            description
              "MPLS label.";
          }
          leaf mpls-exp2 {
            type uint8;
            description
              "MPLS exp.";
          }
          leaf mpls-bottom2 {
            type uint8;
            description
              "MPLS bottom.";
          }
          leaf mpls-label3 {
            type uint32;
            description
              "MPLS label.";
          }
          leaf mpls-exp3 {
            type uint8;
            description
              "MPLS exp.";
          }
          leaf mpls-bottom3 {
            type uint8;
            description
              "MPLS bottom.";
          }
        }
      }
    }
  }
  augment "/ncs:devices/ncs:template/ncs:ned-id/ncs:config" {
    container netstream {
      description
        "Netstream.";
      container flow-instances {
        description
          "List of configure global instance.";
        list flow-instance {
          // NCS patched for predictable order
          ordered-by user;
          key "flow-type";
          description
            "Configure global instance.";
          ext:generated-by "system" {
            description
              "The all instances are generated by system automatically.";
          }
          ext:operation-exclude "create|delete" {
            description
              "The all instances cannot be created or deleted.";
          }
          leaf flow-type {
            type ncs_template_nsm-flow-type;
            description
              "Flow type.";
          }
          leaf source-ipv4-address {
            type string;
            description
              "Source IPv4 address.";
          }
          leaf source-ipv4-port {
            // NCS drop when statement
            type string;
            // NCS drop default statement
            description
              "Source IPv4 port.";
          }
          leaf source-ipv6-address {
            type string;
            description
              "Source IPv6 address.";
          }
          leaf source-ipv6-port {
            // NCS drop when statement
            type string;
            // NCS drop default statement
            description
              "Source IPv6 port.";
          }
          leaf export-version {
            type ncs_template_nsm-origin-version;
            // NCS drop must statement
            description
              "Version of NetStream statistics packets. The value of IPv4 can be 5,9 or ipfix, the value of IPv6 can be 9 or ipfix.";
          }
          leaf as-type {
            type ncs_template_nsm-as-type;
            // NCS drop must statement
            // NCS drop default statement
            description
              "AS number of a specified IP address. The available options are origin-as (start AS number) and peer-as (adjacent AS number).";
          }
          leaf bgp-nexthop {
            type ncs_template_nsm-enable;
            // NCS drop must statement
            // NCS drop default statement
            description
              "Whether exported statistics contain BGP next hop information. Version 5 does not support BGP next hop.";
          }
          leaf template-timeout-rate {
            type string;
            units "min";
            // NCS drop default statement
            description
              "The interval for refreshing the template.";
          }
          leaf option-template-timeout-rate {
            type string;
            units "min";
            // NCS drop default statement
            description
              "Interval for refreshing the Option template.";
          }
          leaf option-template-refresh-rate {
            type string;
            units "packet";
            // NCS drop default statement
            description
              "Packet-interval refreshing time of the option template.";
          }
          leaf option-data-timeout-rate {
            type string;
            units "min";
            // NCS drop default statement
            description
              "Interval for refreshing the option data.";
          }
          choice agg-active-age {
            // NCS drop default statement
            description
              "Specify the active aging time of aggregation flows.";
            case minutes {
              description
                "Specify the active aging time (mins) of aggregation flows.";
              leaf agg-active-age-minutes {
                type string;
                units "min";
                // NCS drop default statement
                description
                  "Specify the active aging time (mins) of aggregation flows.";
              }
            }
            case seconds {
              description
                "Specify the active aging time (secs) of aggregation flows.";
              leaf agg-active-age-seconds {
                type string;
                units "s";
                description
                  "Specify the active aging time (secs) of aggregation flows.";
              }
            }
          }
          leaf agg-inactive-age-seconds {
            type string;
            units "s";
            // NCS drop default statement
            description
              "Inactive aging time of aggregation flows.";
          }
          choice origin-active-age {
            // NCS drop default statement
            description
              "Active aging time of original flows.";
            case minutes {
              description
                "Active aging time (mins) of original flows.";
              leaf origin-active-age-minutes {
                type string;
                units "min";
                // NCS drop default statement
                description
                  "Active aging time (mins) of original flows.";
              }
            }
            case seconds {
              description
                "Active aging time (secs) of original flows.";
              leaf origin-active-age-seconds {
                type string;
                units "s";
                description
                  "Active aging time (secs) of original flows.";
              }
            }
          }
          leaf origin-inactive-seconds {
            type string;
            units "s";
            // NCS drop default statement
            description
              "Inactive aging time of original flows.";
          }
          leaf as-mode {
            type ncs_template_nsm-as-mode-index;
            // NCS drop default statement
            description
              "Mode supported by ASs.";
          }
          leaf index-switch {
            type ncs_template_nsm-as-mode-index;
            // NCS drop default statement
            description
              "NetStream interface index.";
          }
          leaf tcpflag-enable {
            type ncs_template_nsm-enable;
            // NCS drop default statement
            description
              "Whether tcp-flag information is extracted during the processing of sampling packets.";
          }
          leaf mpls-aware-enable {
            type ncs_template_nsm-mpls-aware;
            // NCS drop default statement
            description
              "Whether Layer 3 labels are extracted during the processing of sampling packets. The default value is ip-only, that is, not to extract the label.label-only indicates that only the label is extracted; label-and-ip indicates that both the label and IP address are extracted.";
          }
          leaf interface-option-enable {
            type ncs_template_nsm-enable;
            // NCS drop default statement
            description
              "Flow of statistics about interface options, including the interface index for enabling NetStream in inbound direction or outbound direction, and corresponding sampling values.";
          }
          leaf ttl-flag {
            type ncs_template_nsm-enable;
            // NCS drop must statement
            // NCS drop default statement
            description
              "Whether exported statistics contain TTL information.";
          }
          leaf sequence-number-fix {
            type ncs_template_nsm-enable;
            // NCS drop default statement
            description
              "Whether the numbering mode of IPFIX version packet is fixed mode.";
          }
          leaf srv6-aware {
            type ncs_template_nsm-srv6-aware;
            // NCS drop must statement
            description
              "Whether collect inner layer header of SRv6 packet.";
          }
          container sampler-rates {
            description
              "List of configure global sampler instance.";
            list sampler-rate {
              // NCS patched for predictable order
              ordered-by user;
              key "direction";
              description
                "Configure global sampler instance.";
              leaf direction {
                type ncs_template_nsm-direction;
                description
                  "Sampler direction.";
              }
              choice sampler-type {
                // NCS drop mandatory statement
                description
                  "Sampler type.";
                case fix-packets {
                  description
                    "Fix-pack value.";
                  leaf fix-packets-value {
                    type string;
                    description
                      "Fix-pack value.";
                  }
                }
                case fix-time {
                  description
                    "Fix-time value.";
                  leaf fix-time-value {
                    type string;
                    description
                      "Fix-time value.";
                  }
                }
                case random-packets {
                  description
                    "Random-pack value.";
                  leaf random-packets-value {
                    type string;
                    description
                      "Random-pack value.";
                  }
                }
              }
            }
          }
          container export-ipv4-hosts {
            description
              "List of configure export vpn destination IPv4 address instance.";
            list export-ipv4-host {
              // NCS patched for predictable order
              ordered-by user;
              key "address port vpn-name";
              // NCS drop max-elements statement
              description
                "Configure export vpn destination IPv4 address instance.";
              leaf address {
                type string;
                description
                  "Exported destination IPv4 address.";
              }
              leaf port {
                type string;
                description
                  "UDP port number of the NSC.";
              }
              leaf vpn-name {
                type string;
                // NCS drop must statement
                description
                  "Vpn instance name.";
              }
              leaf dscp-value {
                type string;
                description
                  "Differentiated Services Code Point.";
              }
            }
          }
        }
      }
      container aggregations {
        description
          "List of configure aggregation instance.";
        list aggregation {
          // NCS patched for predictable order
          ordered-by user;
          // NCS drop must statement
          key "flow-type agg-type";
          description
            "Configure aggregation instance.";
          leaf flow-type {
            type ncs_template_nsm-flow-type;
            description
              "Flow type.";
          }
          leaf agg-type {
            type ncs_template_nsm-agg-type;
            description
              "Aggregation type.";
          }
          leaf agg-enable {
            type ncs_template_nsm-enable;
            // NCS drop default statement
            description
              "Aggregation enabling flag.";
          }
        }
      }
      container monitors {
        description
          "List of configure monitor instance.";
        list monitor {
          // NCS patched for predictable order
          ordered-by user;
          key "flow-type monitor-name";
          description
            "Configure monitor instance.";
          leaf flow-type {
            type ncs_template_nsm-flow-type;
            description
              "Flow type.";
          }
          leaf monitor-name {
            type string;
            description
              "Monitor name.";
          }
        }
      }
      container flexflow-records {
        description
          "List of configure flexible flow instance.";
        list flexflow-record {
          // NCS patched for predictable order
          ordered-by user;
          key "flow-type record-name";
          description
            "Configure flexible flow instance.";
          leaf flow-type {
            type ncs_template_nsm-flow-type;
            description
              "Flow type.";
          }
          leaf record-name {
            type string;
            description
              "Flexible flow record name.";
          }
          leaf source-address {
            type ncs_template_nsm-enable;
            // NCS drop default statement
            description
              "Indicates the aggregation based on source addresses.";
          }
          leaf source-as {
            type ncs_template_nsm-enable;
            // NCS drop default statement
            description
              "Indicates that the statistics to be sent to the NSC contain source AS information.";
          }
        }
      }
      // NCS drop config false container 'sampler-rate-lower-limits'
      // NCS drop config false container 'template-export-statistics'
      container option-application-labels {
        description
          "Configure label list.";
        leaf tal-enable {
          type ncs_template_nsm-enable;
          // NCS drop default statement
          description
            "TAL enabling flag.";
        }
        // NCS drop config false container 'tal-infos'
      }
      // NCS drop config false container 'stream-infos'
      // NCS drop config false container 'stream-log-infos'
    }
  }
  augment "/ncs:devices/ncs:template/ncs:ned-id/ncs:config/devm:devm/devm:lpu-boards/devm:lpu-board" {
    description
      "Add netstream configuration to devm slot model.";
    container netstream {
      description
        "Configure netstream.";
      container sampler-modes {
        description
          "List of configure slot instance.";
        list sampler-mode {
          // NCS patched for predictable order
          ordered-by user;
          key "flow-type sampler-mode";
          description
            "Configure slot instance.";
          leaf flow-type {
            type ncs_template_nsm-flow-type;
            description
              "Flow type.";
          }
          leaf sampler-mode {
            type ncs_template_nsm-destination-board;
            description
              "Type of a sampled board.";
          }
          leaf dest-slot {
            // NCS drop when statement
            type string;
            // NCS drop must statement
            // NCS drop mandatory statement
            description
              "Destination slot name. For example, board 3 is input as 0/3.";
          }
        }
      }
    }
  }
  augment "/ncs:devices/ncs:device/ncs:live-status/devm:devm/devm:lpu-boards/devm:lpu-board" {
    description
      "Add netstream configuration to devm slot model.";
    container netstream {
      tailf:ncs-device-type "netconf";
      tailf:display-when "not(../../../../../ncs:module) or ../../../../../ncs:module[ncs:name='huawei-netstream'] or (../../../../../ncs:live-status-protocol[not(ncs:capability)]) or (../../../../../ncs:live-status-protocol/ncs:capability/ncs:module[.='huawei-netstream'])";
      description
        "Configure netstream.";
      container sampler-modes {
        description
          "List of configure slot instance.";
        list sampler-mode {
          key "flow-type sampler-mode";
          description
            "Configure slot instance.";
          leaf flow-type {
            type live_ncs_nsm-flow-type;
            description
              "Flow type.";
          }
          leaf sampler-mode {
            type live_ncs_nsm-destination-board;
            description
              "Type of a sampled board.";
          }
          leaf dest-slot {
            // NCS drop when statement
            type leafref {
              path "/ncs:devices/ncs:device/ncs:live-status/devm:devm/devm:lpu-boards/devm:lpu-board/devm:position" {
                tailf:xpath-root 3;
              }
            }
            // NCS drop must statement
            // NCS drop mandatory statement
            description
              "Destination slot name. For example, board 3 is input as 0/3.";
          }
        }
      }
    }
  }
  augment "/ncs:devices/ncs:device/ncs:config/devm:devm/devm:lpu-boards/devm:lpu-board" {
    description
      "Add netstream configuration to devm slot model.";
    container netstream {
      tailf:ncs-device-type "netconf";
      tailf:display-when "not(../../../../../ncs:module) or ../../../../../ncs:module[ncs:name='huawei-netstream']";
      description
        "Configure netstream.";
      container sampler-modes {
        description
          "List of configure slot instance.";
        list sampler-mode {
          key "flow-type sampler-mode";
          description
            "Configure slot instance.";
          leaf flow-type {
            type nsm-flow-type;
            description
              "Flow type.";
          }
          leaf sampler-mode {
            type nsm-destination-board;
            description
              "Type of a sampled board.";
          }
          leaf dest-slot {
            when "not(../sampler-mode='self')" {
              tailf:xpath-root 3;
            }
            type leafref {
              path "/ncs:devices/ncs:device/ncs:config/devm:devm/devm:lpu-boards/devm:lpu-board/devm:position" {
                tailf:xpath-root 3;
              }
            }
            must '../../../../devm:position != ../dest-slot' {
              tailf:xpath-root 3;
            }
            mandatory true;
            description
              "Destination slot name. For example, board 3 is input as 0/3.";
          }
        }
      }
    }
  }
  augment "/ncs:devices/ncs:template/ncs:ned-id/ncs:config/devm:devm/devm:mpu-boards/devm:mpu-board" {
    description
      "Add netstream configuration to devm slot model.";
    container netstream {
      description
        "Configure netstream.";
      container sampler-modes {
        description
          "List of configure slot instance.";
        list sampler-mode {
          // NCS patched for predictable order
          ordered-by user;
          key "flow-type sampler-mode";
          description
            "Configure slot instance.";
          leaf flow-type {
            type ncs_template_nsm-flow-type;
            description
              "Flow type.";
          }
          leaf sampler-mode {
            type ncs_template_nsm-destination-board;
            description
              "Type of a sampled board.";
          }
        }
      }
    }
  }
  augment "/ncs:devices/ncs:device/ncs:live-status/devm:devm/devm:mpu-boards/devm:mpu-board" {
    description
      "Add netstream configuration to devm slot model.";
    container netstream {
      tailf:ncs-device-type "netconf";
      tailf:display-when "not(../../../../../ncs:module) or ../../../../../ncs:module[ncs:name='huawei-netstream'] or (../../../../../ncs:live-status-protocol[not(ncs:capability)]) or (../../../../../ncs:live-status-protocol/ncs:capability/ncs:module[.='huawei-netstream'])";
      description
        "Configure netstream.";
      container sampler-modes {
        description
          "List of configure slot instance.";
        list sampler-mode {
          key "flow-type sampler-mode";
          description
            "Configure slot instance.";
          leaf flow-type {
            type live_ncs_nsm-flow-type;
            description
              "Flow type.";
          }
          leaf sampler-mode {
            type live_ncs_nsm-destination-board;
            description
              "Type of a sampled board.";
          }
        }
      }
    }
  }
  augment "/ncs:devices/ncs:device/ncs:config/devm:devm/devm:mpu-boards/devm:mpu-board" {
    description
      "Add netstream configuration to devm slot model.";
    container netstream {
      tailf:ncs-device-type "netconf";
      tailf:display-when "not(../../../../../ncs:module) or ../../../../../ncs:module[ncs:name='huawei-netstream']";
      description
        "Configure netstream.";
      container sampler-modes {
        description
          "List of configure slot instance.";
        list sampler-mode {
          key "flow-type sampler-mode";
          description
            "Configure slot instance.";
          leaf flow-type {
            type nsm-flow-type;
            description
              "Flow type.";
          }
          leaf sampler-mode {
            type nsm-destination-board;
            description
              "Type of a sampled board.";
          }
        }
      }
    }
  }
  augment "/ncs:devices/ncs:template/ncs:ned-id/ncs:config/ifm:ifm/ifm:interfaces/ifm:interface" {
    description
      "Add interface configuration to ifm interface model.";
    container netstream {
      description
        "Configure netstream interface.";
      container sampler-enables {
        description
          "List of configure interface sampling instance.";
        list sampler-enable {
          // NCS patched for predictable order
          ordered-by user;
          key "flow-type direction";
          description
            "Configure interface sampling instance.";
          leaf flow-type {
            type ncs_template_nsm-flow-type;
            description
              "Flow type.";
          }
          leaf direction {
            type ncs_template_nsm-direction;
            description
              "Sampler direction.";
          }
        }
      }
      container sampler-rates {
        description
          "List of Configure interface sampler instance.";
        list sampler-rate {
          // NCS patched for predictable order
          ordered-by user;
          key "flow-type direction";
          description
            "Configure interface sampler instance.";
          leaf flow-type {
            type ncs_template_nsm-flow-type;
            description
              "Flow type.";
          }
          leaf direction {
            type ncs_template_nsm-direction;
            description
              "Sampler direction.";
          }
          choice sampler-type {
            // NCS drop mandatory statement
            description
              "Sampler type.";
            case fix-packets {
              description
                "Fix packets value.";
              leaf fix-packets-value {
                type string;
                description
                  "Fix packets value.";
              }
            }
            case fix-time {
              description
                "Fix time value.";
              leaf fix-time-value {
                type string;
                description
                  "Fix time value.";
              }
            }
            case random-packets {
              description
                "Random packets value.";
              leaf random-packets-value {
                type string;
                description
                  "Random packets value.";
              }
            }
          }
        }
      }
    }
  }
  augment "/ncs:devices/ncs:device/ncs:live-status/ifm:ifm/ifm:interfaces/ifm:interface" {
    description
      "Add interface configuration to ifm interface model.";
    container netstream {
      tailf:ncs-device-type "netconf";
      tailf:display-when "not(../../../../../ncs:module) or ../../../../../ncs:module[ncs:name='huawei-netstream'] or (../../../../../ncs:live-status-protocol[not(ncs:capability)]) or (../../../../../ncs:live-status-protocol/ncs:capability/ncs:module[.='huawei-netstream'])";
      description
        "Configure netstream interface.";
      container sampler-enables {
        description
          "List of configure interface sampling instance.";
        list sampler-enable {
          key "flow-type direction";
          description
            "Configure interface sampling instance.";
          leaf flow-type {
            type live_ncs_nsm-flow-type;
            description
              "Flow type.";
          }
          leaf direction {
            type live_ncs_nsm-direction;
            description
              "Sampler direction.";
          }
        }
      }
      container sampler-rates {
        description
          "List of Configure interface sampler instance.";
        list sampler-rate {
          key "flow-type direction";
          description
            "Configure interface sampler instance.";
          leaf flow-type {
            type live_ncs_nsm-flow-type;
            description
              "Flow type.";
          }
          leaf direction {
            type live_ncs_nsm-direction;
            description
              "Sampler direction.";
          }
          choice sampler-type {
            // NCS drop mandatory statement
            description
              "Sampler type.";
            case fix-packets {
              description
                "Fix packets value.";
              leaf fix-packets-value {
                type uint32 {
                  range "1..65535";
                }
                description
                  "Fix packets value.";
              }
            }
            case fix-time {
              description
                "Fix time value.";
              leaf fix-time-value {
                type uint32 {
                  range "5..30000";
                }
                description
                  "Fix time value.";
              }
            }
            case random-packets {
              description
                "Random packets value.";
              leaf random-packets-value {
                type uint32 {
                  range "1..65535";
                }
                description
                  "Random packets value.";
              }
            }
          }
        }
      }
    }
  }
  augment "/ncs:devices/ncs:device/ncs:config/ifm:ifm/ifm:interfaces/ifm:interface" {
    description
      "Add interface configuration to ifm interface model.";
    container netstream {
      tailf:ncs-device-type "netconf";
      tailf:display-when "not(../../../../../ncs:module) or ../../../../../ncs:module[ncs:name='huawei-netstream']";
      description
        "Configure netstream interface.";
      container sampler-enables {
        description
          "List of configure interface sampling instance.";
        list sampler-enable {
          key "flow-type direction";
          description
            "Configure interface sampling instance.";
          leaf flow-type {
            type nsm-flow-type;
            description
              "Flow type.";
          }
          leaf direction {
            type nsm-direction;
            description
              "Sampler direction.";
          }
        }
      }
      container sampler-rates {
        description
          "List of Configure interface sampler instance.";
        list sampler-rate {
          key "flow-type direction";
          description
            "Configure interface sampler instance.";
          leaf flow-type {
            type nsm-flow-type;
            description
              "Flow type.";
          }
          leaf direction {
            type nsm-direction;
            description
              "Sampler direction.";
          }
          choice sampler-type {
            mandatory true;
            description
              "Sampler type.";
            case fix-packets {
              description
                "Fix packets value.";
              leaf fix-packets-value {
                type uint32 {
                  range "1..65535";
                }
                description
                  "Fix packets value.";
              }
            }
            case fix-time {
              description
                "Fix time value.";
              leaf fix-time-value {
                type uint32 {
                  range "5..30000";
                }
                description
                  "Fix time value.";
              }
            }
            case random-packets {
              description
                "Random packets value.";
              leaf random-packets-value {
                type uint32 {
                  range "1..65535";
                }
                description
                  "Random packets value.";
              }
            }
          }
        }
      }
    }
  }
}
