module huawei-dsvpn-nhrp {
  // Generated by yanger -t ncs
  tailf:mount-id "huawei-nc-1.0:huawei-nc-1.0";
  tailf:ncs-device-type "netconf";

  namespace "urn:huawei:yang:huawei-dsvpn-nhrp";
  prefix dsvpn-nhrp;

  import huawei-extension {
    prefix ext;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Dynamic Smart Virtual Private Network (DSVPN) refers to a technology for dynamically
     establishing VPN between a branch and a headquarters, a branch, and a branch in the
     Hub-Spoke network model.
     The Next Hop Resolution Protocol (NHRP) is an extension of the ATM ARP routing mechanism
     that is sometimes used to improve the efficiency of routing computer network traffic over
     Non-Broadcast, Multiple Access (NBMA) Networks.";

  revision 2020-03-26 {
    description
      "White-box errors are resolved.";
    reference "Huawei private.";
  }
  revision 2019-12-10 {
    description
      "Initial revision.";
    reference "Huawei private.";
  }
  ext:task-name "nhrp";

  typedef ncs_template_entry-type {
    type string;
    description
      "NHRP peer type.";
  }

  typedef ncs_template_entry-flag {
    type string;
    description
      "NHRP peer flag.";
  }

  typedef ncs_template_scenario-type {
    type string;
    description
      "Scenario type.";
  }

  typedef ncs_template_authen-mode {
    type string;
    description
      "Authentication algorithm.";
  }

  typedef ncs_rpc_notif_entry-type {
    type enumeration {
      enum "hub" {
        value 0;
        description
          "Hub.";
      }
      enum "static" {
        value 1;
        description
          "Static.";
      }
      enum "local" {
        value 2;
        description
          "Local.";
      }
      enum "registered" {
        value 3;
        description
          "Registered or spoke.";
      }
      enum "remote" {
        value 4;
        description
          "Remote.";
      }
      enum "remote-network" {
        value 5;
        description
          "Remote-network.";
      }
    }
    description
      "NHRP peer type.";
  }

  typedef ncs_rpc_notif_entry-flag {
    type enumeration {
      enum "up" {
        value 0;
        description
          "Up.";
      }
      enum "down" {
        value 1;
        description
          "Down.";
      }
      enum "up.unique" {
        value 2;
        description
          "Up|unique.";
      }
      enum "up.no-unique" {
        value 3;
        description
          "Up|no-unique.";
      }
    }
    description
      "NHRP peer flag.";
  }

  typedef ncs_rpc_notif_scenario-type {
    type enumeration {
      enum "hub" {
        value 0;
        description
          "Hub.";
      }
      enum "spoke" {
        value 1;
        description
          "Spoke.";
      }
      enum "hub-spoke" {
        value 2;
        description
          "Hub-spoke.";
      }
    }
    description
      "Scenario type.";
  }

  typedef ncs_rpc_notif_authen-mode {
    type enumeration {
      enum "md5" {
        value 0;
        description
          "MD5.";
      }
      enum "sha1" {
        value 1;
        description
          "SHA1.";
      }
      enum "sha2-256" {
        value 2;
        description
          "SHA2-256.";
      }
      enum "sha2-384" {
        value 3;
        description
          "SHA2-384.";
      }
      enum "sha2-512" {
        value 4;
        description
          "SHA2-512.";
      }
    }
    description
      "Authentication algorithm.";
  }

  typedef live_ncs_entry-type {
    type enumeration {
      enum "hub" {
        value 0;
        description
          "Hub.";
      }
      enum "static" {
        value 1;
        description
          "Static.";
      }
      enum "local" {
        value 2;
        description
          "Local.";
      }
      enum "registered" {
        value 3;
        description
          "Registered or spoke.";
      }
      enum "remote" {
        value 4;
        description
          "Remote.";
      }
      enum "remote-network" {
        value 5;
        description
          "Remote-network.";
      }
    }
    description
      "NHRP peer type.";
  }

  typedef live_ncs_entry-flag {
    type enumeration {
      enum "up" {
        value 0;
        description
          "Up.";
      }
      enum "down" {
        value 1;
        description
          "Down.";
      }
      enum "up.unique" {
        value 2;
        description
          "Up|unique.";
      }
      enum "up.no-unique" {
        value 3;
        description
          "Up|no-unique.";
      }
    }
    description
      "NHRP peer flag.";
  }

  typedef live_ncs_scenario-type {
    type enumeration {
      enum "hub" {
        value 0;
        description
          "Hub.";
      }
      enum "spoke" {
        value 1;
        description
          "Spoke.";
      }
      enum "hub-spoke" {
        value 2;
        description
          "Hub-spoke.";
      }
    }
    description
      "Scenario type.";
  }

  typedef live_ncs_authen-mode {
    type enumeration {
      enum "md5" {
        value 0;
        description
          "MD5.";
      }
      enum "sha1" {
        value 1;
        description
          "SHA1.";
      }
      enum "sha2-256" {
        value 2;
        description
          "SHA2-256.";
      }
      enum "sha2-384" {
        value 3;
        description
          "SHA2-384.";
      }
      enum "sha2-512" {
        value 4;
        description
          "SHA2-512.";
      }
    }
    description
      "Authentication algorithm.";
  }

  typedef entry-type {
    type enumeration {
      enum "hub" {
        value 0;
        description
          "Hub.";
      }
      enum "static" {
        value 1;
        description
          "Static.";
      }
      enum "local" {
        value 2;
        description
          "Local.";
      }
      enum "registered" {
        value 3;
        description
          "Registered or spoke.";
      }
      enum "remote" {
        value 4;
        description
          "Remote.";
      }
      enum "remote-network" {
        value 5;
        description
          "Remote-network.";
      }
    }
    description
      "NHRP peer type.";
  }

  typedef entry-flag {
    type enumeration {
      enum "up" {
        value 0;
        description
          "Up.";
      }
      enum "down" {
        value 1;
        description
          "Down.";
      }
      enum "up.unique" {
        value 2;
        description
          "Up|unique.";
      }
      enum "up.no-unique" {
        value 3;
        description
          "Up|no-unique.";
      }
    }
    description
      "NHRP peer flag.";
  }

  typedef scenario-type {
    type enumeration {
      enum "hub" {
        value 0;
        description
          "Hub.";
      }
      enum "spoke" {
        value 1;
        description
          "Spoke.";
      }
      enum "hub-spoke" {
        value 2;
        description
          "Hub-spoke.";
      }
    }
    description
      "Scenario type.";
  }

  typedef authen-mode {
    type enumeration {
      enum "md5" {
        value 0;
        description
          "MD5.";
      }
      enum "sha1" {
        value 1;
        description
          "SHA1.";
      }
      enum "sha2-256" {
        value 2;
        description
          "SHA2-256.";
      }
      enum "sha2-384" {
        value 3;
        description
          "SHA2-384.";
      }
      enum "sha2-512" {
        value 4;
        description
          "SHA2-512.";
      }
    }
    description
      "Authentication algorithm.";
  }

  augment "/ncs:devices/ncs:device/ncs:config" {
    container dsvpn-nhrp {
      tailf:ncs-device-type "netconf";
      tailf:display-when "not(../../ncs:module) or ../../ncs:module[ncs:name='huawei-dsvpn-nhrp']";
      description
        "Dynamic Smart Virtual Private Network, Next Hop Resolution Protocol.";
      container global {
        description
          "Configure NHRP on DSVPN.";
        leaf enabled {
          type boolean;
          default "false";
          description
            "Enable/disable global NHRP on DSVPN.";
        }
      }
    }
  }
  augment "/ncs:devices/ncs:device/ncs:live-status" {
    container dsvpn-nhrp {
      tailf:ncs-device-type "netconf";
      tailf:display-when "not(../../ncs:module) or ../../ncs:module[ncs:name='huawei-dsvpn-nhrp'] or (../../ncs:live-status-protocol[not(ncs:capability)]) or (../../ncs:live-status-protocol/ncs:capability/ncs:module[.='huawei-dsvpn-nhrp'])";
      description
        "Dynamic Smart Virtual Private Network, Next Hop Resolution Protocol.";
      container global {
        description
          "Configure NHRP on DSVPN.";
        leaf enabled {
          type boolean;
          // NCS drop default statement
          description
            "Enable/disable global NHRP on DSVPN.";
        }
      }
    }
  }
  augment "/ncs:devices/ncs:template/ncs:ned-id/ncs:config" {
    container dsvpn-nhrp {
      description
        "Dynamic Smart Virtual Private Network, Next Hop Resolution Protocol.";
      container global {
        description
          "Configure NHRP on DSVPN.";
        leaf enabled {
          type string;
          // NCS drop default statement
          description
            "Enable/disable global NHRP on DSVPN.";
        }
      }
    }
  }
}
