module huawei-sm2 {
  // Generated by yanger -t ncs
  tailf:mount-id "huawei-nc-1.0:huawei-nc-1.0";
  tailf:ncs-device-type "netconf";

  namespace "urn:huawei:yang:huawei-sm2";
  prefix sm2;

  import huawei-extension {
    prefix ext;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "SM2.";

  revision 2019-05-01 {
    description
      "Initial revision.";
    reference "Huawei private.";
  }
  ext:task-name "ssh-server";

  augment "/ncs:devices/ncs:device/ncs:config" {
    container sm2 {
      tailf:ncs-device-type "netconf";
      tailf:display-when "not(../../ncs:module) or ../../ncs:module[ncs:name='huawei-sm2']";
      description
        "SM2.";
      container sm2-peer-keys {
        description
          "List of SM2 peer key.";
        list sm2-peer-key {
          key "key-name";
          max-elements 20;
          description
            "Configure SM2 peer key code. If the key code is bound, it cannot be deleted, you need to unbind and then delete.";
          leaf key-name {
            type string {
              length "1..40";
            }
            description
              "SM2 key name.";
          }
          leaf key-code {
            type string {
              length "1..4096";
            }
            mandatory true;
            ext:support-filter "true";
            description
              "SM2 key code conforming to DER format.";
          }
        }
      }
      container sm2-key-pairs {
        description
          "List of SM2 keypair labels.";
        list sm2-key-pair {
          key "key-pair-label";
          max-elements 20;
          description
            "Configure SM2 keypair label.";
          leaf key-pair-label {
            type string {
              length "1..35";
              pattern '[a-z0-9_]*';
            }
            description
              "SM2 keypair label name : It only contains underscores (_), case-insensitive letters and digits.";
          }
          leaf key-size {
            type uint32 {
              range "256";
            }
            default "256";
            ext:support-filter "true";
            description
              "SM2 size of keypair.";
          }
          // NCS drop config false leaf 'host-key-code'
        }
      }
    }
  }
  augment "/ncs:devices/ncs:device/ncs:live-status" {
    container sm2 {
      tailf:ncs-device-type "netconf";
      tailf:display-when "not(../../ncs:module) or ../../ncs:module[ncs:name='huawei-sm2'] or (../../ncs:live-status-protocol[not(ncs:capability)]) or (../../ncs:live-status-protocol/ncs:capability/ncs:module[.='huawei-sm2'])";
      description
        "SM2.";
      container sm2-peer-keys {
        description
          "List of SM2 peer key.";
        list sm2-peer-key {
          key "key-name";
          // NCS drop max-elements statement
          description
            "Configure SM2 peer key code. If the key code is bound, it cannot be deleted, you need to unbind and then delete.";
          leaf key-name {
            type string {
              length "1..40";
            }
            description
              "SM2 key name.";
          }
          leaf key-code {
            type string {
              length "1..4096";
            }
            // NCS drop mandatory statement
            ext:support-filter "true";
            description
              "SM2 key code conforming to DER format.";
          }
        }
      }
      container sm2-key-pairs {
        description
          "List of SM2 keypair labels.";
        list sm2-key-pair {
          key "key-pair-label";
          // NCS drop max-elements statement
          description
            "Configure SM2 keypair label.";
          leaf key-pair-label {
            type string {
              length "1..35";
              pattern '[a-z0-9_]*';
            }
            description
              "SM2 keypair label name : It only contains underscores (_), case-insensitive letters and digits.";
          }
          leaf key-size {
            type uint32 {
              range "256";
            }
            // NCS drop default statement
            ext:support-filter "true";
            description
              "SM2 size of keypair.";
          }
          leaf host-key-code {
            type string {
              length "0..2048";
            }
            ext:support-filter "true";
            description
              "SM2 hostkey code.";
          }
        }
      }
    }
  }
  augment "/ncs:devices/ncs:template/ncs:ned-id/ncs:config" {
    container sm2 {
      description
        "SM2.";
      container sm2-peer-keys {
        description
          "List of SM2 peer key.";
        list sm2-peer-key {
          // NCS patched for predictable order
          ordered-by user;
          key "key-name";
          // NCS drop max-elements statement
          description
            "Configure SM2 peer key code. If the key code is bound, it cannot be deleted, you need to unbind and then delete.";
          leaf key-name {
            type string;
            description
              "SM2 key name.";
          }
          leaf key-code {
            type string;
            // NCS drop mandatory statement
            ext:support-filter "true";
            description
              "SM2 key code conforming to DER format.";
          }
        }
      }
      container sm2-key-pairs {
        description
          "List of SM2 keypair labels.";
        list sm2-key-pair {
          // NCS patched for predictable order
          ordered-by user;
          key "key-pair-label";
          // NCS drop max-elements statement
          description
            "Configure SM2 keypair label.";
          leaf key-pair-label {
            type string;
            description
              "SM2 keypair label name : It only contains underscores (_), case-insensitive letters and digits.";
          }
          leaf key-size {
            type string;
            // NCS drop default statement
            ext:support-filter "true";
            description
              "SM2 size of keypair.";
          }
          // NCS drop config false leaf 'host-key-code'
        }
      }
    }
  }
}
