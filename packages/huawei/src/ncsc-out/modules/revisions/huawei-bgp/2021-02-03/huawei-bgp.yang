module huawei-bgp {
  // Generated by yanger -t ncs
  tailf:mount-id "huawei-nc-1.0:huawei-nc-1.0";
  tailf:ncs-device-type "netconf";

  namespace "urn:huawei:yang:huawei-bgp";
  prefix bgp;

  import huawei-extension {
    prefix ext;
  }
  import ietf-inet-types {
    prefix inet;
  }
  import ietf-yang-types {
    prefix yang;
  }
  import huawei-network-instance {
    prefix ni;
  }
  import huawei-pub-type {
    prefix pub-type;
  }
  import huawei-routing-policy {
    prefix rtp;
  }
  import huawei-xpl {
    prefix xpl;
  }
  import huawei-routing {
    prefix rt;
  }
  import huawei-tunnel-management {
    prefix tnlm;
  }
  include huawei-bgp-type;
  include huawei-bgp-common;
  include huawei-bgp-common-multiprotocol;
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Inter-AS routing protocol that exchanges Network Layer Reachability Information (NLRI) with other BGP systems.";

  revision 2021-02-03 {
    description
      "Add bgp unicast submodule.";
    reference "Huawei private.";
  }
  revision 2020-02-25 {
    description
      "The YANG descriptions are modified according to new standards.";
    reference "Huawei private.";
  }
  revision 2019-03-22 {
    description
      "Initial revision.";
    reference "Huawei private.";
  }
  ext:task-name "bgp";

  grouping ncs_template_unicast-aggregate-routes-type {
    description
      "BGP IPv4/IPv6 unicast aggregate routes.";
    leaf address {
      type string;
      description
        "Specify the IPv4 address or IPv6 address of a summarized route. Only IPv4 summarized routes can be configured in the IPv4 address family and only IPv6 summarized routes can be configured in the IPv6 address family.";
    }
    leaf mask-length {
      type string;
      description
        "Specify the mask length of a summarized address.";
    }
    leaf as-set {
      type string;
      // NCS drop default statement
      description
        "Enable/disable the generation of routes with the AS-SET attribute. This option can be used to create a summarized route. The AS_Path attribute of the summarized route contains the AS-Path attributes of the specific routes for the route summarization. Exercise caution when using this option if multiple AS_Paths need to be summarized to prevent route flapping.";
    }
    leaf detail-suppressed {
      type string;
      // NCS drop default statement
      description
        "Enable/disable detail-suppressed. Suppress the advertisement of specific routes for the route summarization. Only the summarized route is advertised.";
    }
    choice policy-type {
      description
        "Set route policy or filter.";
      case rtp-ref {
        description
          "Route policy.";
        leaf attribute-policy {
          type string;
          description
            "Specify an attribute of summarized routes. If apply as-path is used to configure the AS_Path attribute that is used in the route Summarization policy, and the as-set keyword is set, the AS_Path attribute in the policy does not take effect. This parameter and any of the following parameters overwrite each other: suppressFilter, originFilter, and attributeFilter.";
        }
        leaf origin-policy {
          type string;
          description
            "Specify the name of a policy for generating summarized routes. Summarized routes are generated only when the routes match route-policy. This parameter and any of the following parameters overwrite each other: suppressFilter, originFilter, and attributeFilter.";
        }
        leaf suppress-policy {
          type string;
          description
            "Specify a policy for suppressing the advertisement of specified routes. The routes matching the policy are not advertised, and other routes are advertised. This parameter and any of the following parameters overwrite each other: suppressFilter, originFilter, and attributeFilter.";
        }
      }
      case xpl-ref {
        description
          "Route filter.";
        leaf attribute-filter-name {
          type string;
          description
            "Specify a route-filter name.";
        }
        leaf attribute-filter-parameter {
          // NCS drop when statement
          type xpl:ncs_template_filter-parameter-type;
          description
            "Specify a route-filter parameter.";
        }
        leaf origin-filter-name {
          type string;
          description
            "Specify a route-filter name.";
        }
        leaf origin-filter-parameter {
          // NCS drop when statement
          type xpl:ncs_template_filter-parameter-type;
          description
            "Specify a route-filter parameter.";
        }
        leaf suppress-filter-name {
          type string;
          description
            "Specify a route-filter name.";
        }
        leaf suppress-filter-parameter {
          // NCS drop when statement
          type xpl:ncs_template_filter-parameter-type;
          description
            "Specify a route-filter parameter.";
        }
      }
    }
  }

  grouping ncs_template_network-route-ipv4 {
    description
      "BGP network routes.";
    leaf address {
      type string;
      description
        "Specify the IP address advertised by BGP. An IPv4 address can be configured in the IPv4 address family. Note: During the configuration of a network route, the IP address is adjusted based on the mask. It is recommended that you click Synchronize All after creating a network route.";
    }
    leaf mask-length {
      type string;
      description
        "Specify the mask length of an IP address.";
    }
    choice policy-type {
      description
        "Specify the route-policy or filter for route advertisement.";
      case rtp-ref {
        description
          "Specify the route policy.";
        leaf policy-name {
          type string;
          description
            "Specify the route policy.";
        }
      }
      case xpl-ref {
        description
          "Route filter.";
        uses ncs_template_route-filter-type;
      }
    }
  }

  grouping ncs_template_network-route-ipv6 {
    description
      "BGP network routes.";
    leaf address {
      type string;
      description
        "Specify the IP address advertised by BGP. An IPv6 routes can be configured in the IPv6 address family. Note: During the configuration of a network route, the IP address is adjusted based on the mask. It is recommended that you click Synchronize All after creating a network route.";
    }
    leaf mask-length {
      type string;
      description
        "Specify the mask length of an IP address.";
    }
    choice policy-type {
      description
        "Specify the route-policy or filter for route advertisement.";
      case rtp-ref {
        description
          "Specify the route policy.";
        leaf policy-name {
          type string;
          description
            "Specify the route policy.";
        }
      }
      case xpl-ref {
        description
          "Route filter.";
        uses ncs_template_route-filter-type;
      }
    }
  }

  grouping ncs_template_advertise-route-to-evpn-type {
    description
      "Advertise-routes-type configuration.";
    list advertise-route-to-evpn {
      // NCS patched for predictable order
      ordered-by user;
      key "protocol";
      description
        "Configure the advertise route protocol.";
      leaf protocol {
        type string;
        description
          "Route protocol.";
      }
      leaf import-multipath {
        type string;
        // NCS drop default statement
        description
          "Enable/disable route import from multiple paths.";
      }
      leaf include-local-cross {
        type string;
        // NCS drop default statement
        description
          "Enable/disable local cross route to advertise l2vpn evpn.";
      }
      leaf advertise-route-mode {
        type string;
        // NCS drop default statement
        description
          "VPN advertise route mode to evrf.";
      }
    }
  }

  grouping ncs_template_vpn-target-type {
    description
      "BGP IPv4/IPv6 VPN target.";
    leaf policy-vpntarget {
      type string;
      // NCS drop default statement
      description
        "Enable/disable VPN target-based filtering for the received VPN routes. Only the VPN route whose Export RT attribute matches the local Import RT attribute can be added to the routing table. This option can be used in the inter-AS VPN Option B solution and the ASBR MP-EBGP inter-AS L2VPN solution in Kompella mode.";
    }
  }

  grouping ncs_template_reflector-cluster-type {
    description
      "BGP reflector cluster-id.";
    choice reflector-type {
      description
        "Set IPv4 address or id.";
      case address {
        description
          "IPv4 address.";
        leaf reflector-cluster-ipv4 {
          type string;
          description
            "Set a cluster ID. The value is expressed in the format of an IPv4 address. Configuring multiple RRs in a cluster can enhance the stability of the network. If a cluster has more than one RR, select this option to set the same cluster ID for all the RRs to avoid routing loops. To allow clients to receive routes from RRs, ensure that the cluster ID of the RRs is different from the router ID of any client. If the cluster ID of the RRs is the same as the router ID of a client, the client will discard received routes.";
        }
      }
      case id {
        description
          "Set value.";
        leaf reflector-cluster-id {
          type string;
          description
            "Set a cluster ID. Configuring multiple RRs in a cluster can enhance the stability of the network. If a cluster has more than one RR, select this option to set the same cluster ID for all the RRs to avoid routing loops. To allow clients to receive routes from RRs, ensure that the cluster ID of the RRs is different from the router ID of any client. If the cluster ID of the RRs is the same as the router ID of a client, the client will discard received routes.";
        }
      }
    }
  }

  grouping ncs_template_reflect-type {
    description
      "Set reflect client or change path-attribute.";
    leaf reflect-change-path {
      type string;
      // NCS drop default statement
      description
        "Enable/disable an RR to use an export policy to change route AS_Path.";
    }
  }

  grouping ncs_template_group-entropy-label-type {
    description
      "Entropy label parameter configuration in a peer group.";
    leaf advertise-entropy-label {
      type string;
      // NCS drop default statement
      description
        "Enable/disable the capability of advertising entropy labels.";
    }
    leaf padding {
      // NCS drop when statement
      type string;
      description
        "Padding format. The value is a hexadecimal string containing 1 to 32 characters (16 hexadecimal numbers). It cannot contain spaces, and can only contain uppercase letters (A to F) and digits (0 to 9), and the length must be an even number.";
    }
    leaf attribute-type {
      // NCS drop when statement
      type ncs_template_entropy-label-attribute-type;
      // NCS drop mandatory statement
      description
        "The attribute-type of advertising entropy labels.";
    }
    leaf entropy-label {
      type string;
      // NCS drop default statement
      description
        "Enable/disable the function of delivering the entropy label capability to the forwarding plane.";
    }
  }

  grouping ncs_template_peer-entropy-label-type {
    description
      "Entropy label parameter configuration in a peer.";
    leaf advertise-entropy-label {
      type ncs_template_peer-comm-config-type;
      // NCS drop default statement
      description
        "Enable the capability of advertising entropy labels.";
    }
    leaf padding {
      // NCS drop when statement
      type string;
      description
        "Padding format. The value is a hexadecimal string containing 1 to 32 characters (16 hexadecimal numbers). It cannot contain spaces, and can only contain uppercase letters (A to F) and digits (0 to 9), and the length must be an even number.";
    }
    leaf attribute-type {
      // NCS drop when statement
      type ncs_template_entropy-label-attribute-type;
      // NCS drop mandatory statement
      description
        "The attribute-type of advertising entropy labels.";
    }
    leaf entropy-label {
      type ncs_template_peer-comm-config-type;
      // NCS drop default statement
      description
        "Enable the function of delivering the entropy label capability to the forwarding plane.";
    }
    // NCS drop config false leaf 'effect-advertise-entropy-label'
    // NCS drop config false leaf 'effect-padding'
    // NCS drop config false leaf 'effect-attribute-type'
    // NCS drop config false leaf 'effect-entropy-label'
  }

  grouping ncs_rpc_notif_unicast-aggregate-routes-type {
    description
      "BGP IPv4/IPv6 unicast aggregate routes.";
    leaf address {
      type inet:ip-address-no-zone;
      description
        "Specify the IPv4 address or IPv6 address of a summarized route. Only IPv4 summarized routes can be configured in the IPv4 address family and only IPv6 summarized routes can be configured in the IPv6 address family.";
    }
    leaf mask-length {
      type uint8 {
        range "1..128";
      }
      description
        "Specify the mask length of a summarized address.";
    }
    leaf as-set {
      type boolean;
      default "false";
      description
        "Enable/disable the generation of routes with the AS-SET attribute. This option can be used to create a summarized route. The AS_Path attribute of the summarized route contains the AS-Path attributes of the specific routes for the route summarization. Exercise caution when using this option if multiple AS_Paths need to be summarized to prevent route flapping.";
    }
    leaf detail-suppressed {
      type boolean;
      default "false";
      description
        "Enable/disable detail-suppressed. Suppress the advertisement of specific routes for the route summarization. Only the summarized route is advertised.";
    }
    choice policy-type {
      description
        "Set route policy or filter.";
      case rtp-ref {
        description
          "Route policy.";
        leaf attribute-policy {
          type string;
          description
            "Specify an attribute of summarized routes. If apply as-path is used to configure the AS_Path attribute that is used in the route Summarization policy, and the as-set keyword is set, the AS_Path attribute in the policy does not take effect. This parameter and any of the following parameters overwrite each other: suppressFilter, originFilter, and attributeFilter.";
        }
        leaf origin-policy {
          type string;
          description
            "Specify the name of a policy for generating summarized routes. Summarized routes are generated only when the routes match route-policy. This parameter and any of the following parameters overwrite each other: suppressFilter, originFilter, and attributeFilter.";
        }
        leaf suppress-policy {
          type string;
          description
            "Specify a policy for suppressing the advertisement of specified routes. The routes matching the policy are not advertised, and other routes are advertised. This parameter and any of the following parameters overwrite each other: suppressFilter, originFilter, and attributeFilter.";
        }
      }
      case xpl-ref {
        description
          "Route filter.";
        leaf attribute-filter-name {
          type string;
          description
            "Specify a route-filter name.";
        }
        leaf attribute-filter-parameter {
          when '../attribute-filter-name' {
            tailf:xpath-root 3;
          }
          type xpl:ncs_rpc_notif_filter-parameter-type;
          description
            "Specify a route-filter parameter.";
        }
        leaf origin-filter-name {
          type string;
          description
            "Specify a route-filter name.";
        }
        leaf origin-filter-parameter {
          when '../origin-filter-name' {
            tailf:xpath-root 3;
          }
          type xpl:ncs_rpc_notif_filter-parameter-type;
          description
            "Specify a route-filter parameter.";
        }
        leaf suppress-filter-name {
          type string;
          description
            "Specify a route-filter name.";
        }
        leaf suppress-filter-parameter {
          when '../suppress-filter-name' {
            tailf:xpath-root 3;
          }
          type xpl:ncs_rpc_notif_filter-parameter-type;
          description
            "Specify a route-filter parameter.";
        }
      }
    }
  }

  grouping ncs_rpc_notif_network-route-ipv4 {
    description
      "BGP network routes.";
    leaf address {
      type inet:ipv4-address-no-zone;
      description
        "Specify the IP address advertised by BGP. An IPv4 address can be configured in the IPv4 address family. Note: During the configuration of a network route, the IP address is adjusted based on the mask. It is recommended that you click Synchronize All after creating a network route.";
    }
    leaf mask-length {
      type uint8 {
        range "1..32";
      }
      description
        "Specify the mask length of an IP address.";
    }
    choice policy-type {
      description
        "Specify the route-policy or filter for route advertisement.";
      case rtp-ref {
        description
          "Specify the route policy.";
        leaf policy-name {
          type string;
          description
            "Specify the route policy.";
        }
      }
      case xpl-ref {
        description
          "Route filter.";
        uses ncs_rpc_notif_route-filter-type;
      }
    }
  }

  grouping ncs_rpc_notif_network-route-ipv6 {
    description
      "BGP network routes.";
    leaf address {
      type inet:ipv6-address-no-zone;
      description
        "Specify the IP address advertised by BGP. An IPv6 routes can be configured in the IPv6 address family. Note: During the configuration of a network route, the IP address is adjusted based on the mask. It is recommended that you click Synchronize All after creating a network route.";
    }
    leaf mask-length {
      type uint8 {
        range "1..128";
      }
      description
        "Specify the mask length of an IP address.";
    }
    choice policy-type {
      description
        "Specify the route-policy or filter for route advertisement.";
      case rtp-ref {
        description
          "Specify the route policy.";
        leaf policy-name {
          type string;
          description
            "Specify the route policy.";
        }
      }
      case xpl-ref {
        description
          "Route filter.";
        uses ncs_rpc_notif_route-filter-type;
      }
    }
  }

  grouping ncs_rpc_notif_advertise-route-to-evpn-type {
    description
      "Advertise-routes-type configuration.";
    list advertise-route-to-evpn {
      key "protocol";
      description
        "Configure the advertise route protocol.";
      leaf protocol {
        type enumeration {
          enum "all" {
            value 0;
            description
              "Advertise all the types of route protocol.";
          }
        }
        description
          "Route protocol.";
      }
      leaf import-multipath {
        type boolean;
        default "false";
        description
          "Enable/disable route import from multiple paths.";
      }
      leaf include-local-cross {
        type boolean;
        default "false";
        description
          "Enable/disable local cross route to advertise l2vpn evpn.";
      }
      leaf advertise-route-mode {
        type enumeration {
          enum "all" {
            value 0;
            description
              "All:";
          }
          enum "best" {
            value 1;
            description
              "Best:";
          }
          enum "valid" {
            value 2;
            description
              "Valid:";
          }
        }
        default "all";
        description
          "VPN advertise route mode to evrf.";
      }
    }
  }

  grouping ncs_rpc_notif_vpn-target-type {
    description
      "BGP IPv4/IPv6 VPN target.";
    leaf policy-vpntarget {
      type boolean;
      default "true";
      description
        "Enable/disable VPN target-based filtering for the received VPN routes. Only the VPN route whose Export RT attribute matches the local Import RT attribute can be added to the routing table. This option can be used in the inter-AS VPN Option B solution and the ASBR MP-EBGP inter-AS L2VPN solution in Kompella mode.";
    }
  }

  grouping ncs_rpc_notif_reflector-cluster-type {
    description
      "BGP reflector cluster-id.";
    choice reflector-type {
      description
        "Set IPv4 address or id.";
      case address {
        description
          "IPv4 address.";
        leaf reflector-cluster-ipv4 {
          type inet:ipv4-address-no-zone;
          description
            "Set a cluster ID. The value is expressed in the format of an IPv4 address. Configuring multiple RRs in a cluster can enhance the stability of the network. If a cluster has more than one RR, select this option to set the same cluster ID for all the RRs to avoid routing loops. To allow clients to receive routes from RRs, ensure that the cluster ID of the RRs is different from the router ID of any client. If the cluster ID of the RRs is the same as the router ID of a client, the client will discard received routes.";
        }
      }
      case id {
        description
          "Set value.";
        leaf reflector-cluster-id {
          type uint32 {
            range "1..4294967295";
          }
          description
            "Set a cluster ID. Configuring multiple RRs in a cluster can enhance the stability of the network. If a cluster has more than one RR, select this option to set the same cluster ID for all the RRs to avoid routing loops. To allow clients to receive routes from RRs, ensure that the cluster ID of the RRs is different from the router ID of any client. If the cluster ID of the RRs is the same as the router ID of a client, the client will discard received routes.";
        }
      }
    }
  }

  grouping ncs_rpc_notif_reflect-type {
    description
      "Set reflect client or change path-attribute.";
    leaf reflect-change-path {
      type boolean;
      default "false";
      description
        "Enable/disable an RR to use an export policy to change route AS_Path.";
    }
  }

  grouping ncs_rpc_notif_group-entropy-label-type {
    description
      "Entropy label parameter configuration in a peer group.";
    leaf advertise-entropy-label {
      type boolean;
      default "false";
      description
        "Enable/disable the capability of advertising entropy labels.";
    }
    leaf padding {
      when "../advertise-entropy-label='true'" {
        tailf:xpath-root 3;
      }
      type string {
        length "1..32";
        pattern '(([0-9A-F])*)';
      }
      description
        "Padding format. The value is a hexadecimal string containing 1 to 32 characters (16 hexadecimal numbers). It cannot contain spaces, and can only contain uppercase letters (A to F) and digits (0 to 9), and the length must be an even number.";
    }
    leaf attribute-type {
      when "../advertise-entropy-label='true'" {
        tailf:xpath-root 3;
      }
      type ncs_rpc_notif_entropy-label-attribute-type;
      mandatory true;
      description
        "The attribute-type of advertising entropy labels.";
    }
    leaf entropy-label {
      type boolean;
      default "false";
      description
        "Enable/disable the function of delivering the entropy label capability to the forwarding plane.";
    }
  }

  grouping ncs_rpc_notif_peer-entropy-label-type {
    description
      "Entropy label parameter configuration in a peer.";
    leaf advertise-entropy-label {
      type ncs_rpc_notif_peer-comm-config-type;
      default "default";
      description
        "Enable the capability of advertising entropy labels.";
    }
    leaf padding {
      when "../advertise-entropy-label='enable'" {
        tailf:xpath-root 3;
      }
      type string {
        length "1..32";
        pattern '(([0-9A-F])*)';
      }
      description
        "Padding format. The value is a hexadecimal string containing 1 to 32 characters (16 hexadecimal numbers). It cannot contain spaces, and can only contain uppercase letters (A to F) and digits (0 to 9), and the length must be an even number.";
    }
    leaf attribute-type {
      when "../advertise-entropy-label='enable'" {
        tailf:xpath-root 3;
      }
      type ncs_rpc_notif_entropy-label-attribute-type;
      mandatory true;
      description
        "The attribute-type of advertising entropy labels.";
    }
    leaf entropy-label {
      type ncs_rpc_notif_peer-comm-config-type;
      default "default";
      description
        "Enable the function of delivering the entropy label capability to the forwarding plane.";
    }
    leaf effect-advertise-entropy-label {
      type boolean;
      default "false";
      config false;
      description
        "Whether the capability of advertising entropy labels is enabled on the BGP peer.";
    }
    leaf effect-padding {
      when "../effect-advertise-entropy-label='true'" {
        tailf:xpath-root 3;
      }
      type string {
        length "1..32";
        pattern '(([0-9A-F])*)';
      }
      config false;
      description
        "Padding format.";
    }
    leaf effect-attribute-type {
      when "../effect-advertise-entropy-label='true'" {
        tailf:xpath-root 3;
      }
      type ncs_rpc_notif_entropy-label-attribute-type;
      config false;
      description
        "The attribute-type of advertising entropy labels.";
    }
    leaf effect-entropy-label {
      type boolean;
      default "false";
      config false;
      description
        "Whether the function of delivering the entropy label capability to the forwarding plane is enabled on the BGP peer.";
    }
  }

  grouping live_ncs_unicast-aggregate-routes-type {
    description
      "BGP IPv4/IPv6 unicast aggregate routes.";
    leaf address {
      type inet:ip-address-no-zone;
      description
        "Specify the IPv4 address or IPv6 address of a summarized route. Only IPv4 summarized routes can be configured in the IPv4 address family and only IPv6 summarized routes can be configured in the IPv6 address family.";
    }
    leaf mask-length {
      type uint8 {
        range "1..128";
      }
      description
        "Specify the mask length of a summarized address.";
    }
    leaf as-set {
      type boolean;
      // NCS drop default statement
      description
        "Enable/disable the generation of routes with the AS-SET attribute. This option can be used to create a summarized route. The AS_Path attribute of the summarized route contains the AS-Path attributes of the specific routes for the route summarization. Exercise caution when using this option if multiple AS_Paths need to be summarized to prevent route flapping.";
    }
    leaf detail-suppressed {
      type boolean;
      // NCS drop default statement
      description
        "Enable/disable detail-suppressed. Suppress the advertisement of specific routes for the route summarization. Only the summarized route is advertised.";
    }
    choice policy-type {
      description
        "Set route policy or filter.";
      case rtp-ref {
        description
          "Route policy.";
        leaf attribute-policy {
          type leafref {
            path "/ncs:devices/ncs:device/ncs:live-status/rtp:routing-policy/rtp:policy-definitions/rtp:policy-definition/rtp:name" {
              tailf:xpath-root 3;
            }
          }
          description
            "Specify an attribute of summarized routes. If apply as-path is used to configure the AS_Path attribute that is used in the route Summarization policy, and the as-set keyword is set, the AS_Path attribute in the policy does not take effect. This parameter and any of the following parameters overwrite each other: suppressFilter, originFilter, and attributeFilter.";
        }
        leaf origin-policy {
          type leafref {
            path "/ncs:devices/ncs:device/ncs:live-status/rtp:routing-policy/rtp:policy-definitions/rtp:policy-definition/rtp:name" {
              tailf:xpath-root 3;
            }
          }
          description
            "Specify the name of a policy for generating summarized routes. Summarized routes are generated only when the routes match route-policy. This parameter and any of the following parameters overwrite each other: suppressFilter, originFilter, and attributeFilter.";
        }
        leaf suppress-policy {
          type leafref {
            path "/ncs:devices/ncs:device/ncs:live-status/rtp:routing-policy/rtp:policy-definitions/rtp:policy-definition/rtp:name" {
              tailf:xpath-root 3;
            }
          }
          description
            "Specify a policy for suppressing the advertisement of specified routes. The routes matching the policy are not advertised, and other routes are advertised. This parameter and any of the following parameters overwrite each other: suppressFilter, originFilter, and attributeFilter.";
        }
      }
      case xpl-ref {
        description
          "Route filter.";
        leaf attribute-filter-name {
          type leafref {
            path "/ncs:devices/ncs:device/ncs:live-status/xpl:xpl/xpl:route-filters/xpl:route-filter/xpl:name" {
              tailf:xpath-root 3;
            }
          }
          description
            "Specify a route-filter name.";
        }
        leaf attribute-filter-parameter {
          // NCS drop when statement
          type xpl:live_ncs_filter-parameter-type;
          description
            "Specify a route-filter parameter.";
        }
        leaf origin-filter-name {
          type leafref {
            path "/ncs:devices/ncs:device/ncs:live-status/xpl:xpl/xpl:route-filters/xpl:route-filter/xpl:name" {
              tailf:xpath-root 3;
            }
          }
          description
            "Specify a route-filter name.";
        }
        leaf origin-filter-parameter {
          // NCS drop when statement
          type xpl:live_ncs_filter-parameter-type;
          description
            "Specify a route-filter parameter.";
        }
        leaf suppress-filter-name {
          type leafref {
            path "/ncs:devices/ncs:device/ncs:live-status/xpl:xpl/xpl:route-filters/xpl:route-filter/xpl:name" {
              tailf:xpath-root 3;
            }
          }
          description
            "Specify a route-filter name.";
        }
        leaf suppress-filter-parameter {
          // NCS drop when statement
          type xpl:live_ncs_filter-parameter-type;
          description
            "Specify a route-filter parameter.";
        }
      }
    }
  }

  grouping live_ncs_network-route-ipv4 {
    description
      "BGP network routes.";
    leaf address {
      type inet:ipv4-address-no-zone;
      description
        "Specify the IP address advertised by BGP. An IPv4 address can be configured in the IPv4 address family. Note: During the configuration of a network route, the IP address is adjusted based on the mask. It is recommended that you click Synchronize All after creating a network route.";
    }
    leaf mask-length {
      type uint8 {
        range "1..32";
      }
      description
        "Specify the mask length of an IP address.";
    }
    choice policy-type {
      description
        "Specify the route-policy or filter for route advertisement.";
      case rtp-ref {
        description
          "Specify the route policy.";
        leaf policy-name {
          type leafref {
            path "/ncs:devices/ncs:device/ncs:live-status/rtp:routing-policy/rtp:policy-definitions/rtp:policy-definition/rtp:name" {
              tailf:xpath-root 3;
            }
          }
          description
            "Specify the route policy.";
        }
      }
      case xpl-ref {
        description
          "Route filter.";
        uses live_ncs_route-filter-type;
      }
    }
  }

  grouping live_ncs_network-route-ipv6 {
    description
      "BGP network routes.";
    leaf address {
      type inet:ipv6-address-no-zone;
      description
        "Specify the IP address advertised by BGP. An IPv6 routes can be configured in the IPv6 address family. Note: During the configuration of a network route, the IP address is adjusted based on the mask. It is recommended that you click Synchronize All after creating a network route.";
    }
    leaf mask-length {
      type uint8 {
        range "1..128";
      }
      description
        "Specify the mask length of an IP address.";
    }
    choice policy-type {
      description
        "Specify the route-policy or filter for route advertisement.";
      case rtp-ref {
        description
          "Specify the route policy.";
        leaf policy-name {
          type leafref {
            path "/ncs:devices/ncs:device/ncs:live-status/rtp:routing-policy/rtp:policy-definitions/rtp:policy-definition/rtp:name" {
              tailf:xpath-root 3;
            }
          }
          description
            "Specify the route policy.";
        }
      }
      case xpl-ref {
        description
          "Route filter.";
        uses live_ncs_route-filter-type;
      }
    }
  }

  grouping live_ncs_advertise-route-to-evpn-type {
    description
      "Advertise-routes-type configuration.";
    list advertise-route-to-evpn {
      key "protocol";
      description
        "Configure the advertise route protocol.";
      leaf protocol {
        type enumeration {
          enum "all" {
            value 0;
            description
              "Advertise all the types of route protocol.";
          }
        }
        description
          "Route protocol.";
      }
      leaf import-multipath {
        type boolean;
        // NCS drop default statement
        description
          "Enable/disable route import from multiple paths.";
      }
      leaf include-local-cross {
        type boolean;
        // NCS drop default statement
        description
          "Enable/disable local cross route to advertise l2vpn evpn.";
      }
      leaf advertise-route-mode {
        type enumeration {
          enum "all" {
            value 0;
            description
              "All:";
          }
          enum "best" {
            value 1;
            description
              "Best:";
          }
          enum "valid" {
            value 2;
            description
              "Valid:";
          }
        }
        // NCS drop default statement
        description
          "VPN advertise route mode to evrf.";
      }
    }
  }

  grouping live_ncs_vpn-target-type {
    description
      "BGP IPv4/IPv6 VPN target.";
    leaf policy-vpntarget {
      type boolean;
      // NCS drop default statement
      description
        "Enable/disable VPN target-based filtering for the received VPN routes. Only the VPN route whose Export RT attribute matches the local Import RT attribute can be added to the routing table. This option can be used in the inter-AS VPN Option B solution and the ASBR MP-EBGP inter-AS L2VPN solution in Kompella mode.";
    }
  }

  grouping live_ncs_reflector-cluster-type {
    description
      "BGP reflector cluster-id.";
    choice reflector-type {
      description
        "Set IPv4 address or id.";
      case address {
        description
          "IPv4 address.";
        leaf reflector-cluster-ipv4 {
          type inet:ipv4-address-no-zone;
          description
            "Set a cluster ID. The value is expressed in the format of an IPv4 address. Configuring multiple RRs in a cluster can enhance the stability of the network. If a cluster has more than one RR, select this option to set the same cluster ID for all the RRs to avoid routing loops. To allow clients to receive routes from RRs, ensure that the cluster ID of the RRs is different from the router ID of any client. If the cluster ID of the RRs is the same as the router ID of a client, the client will discard received routes.";
        }
      }
      case id {
        description
          "Set value.";
        leaf reflector-cluster-id {
          type uint32 {
            range "1..4294967295";
          }
          description
            "Set a cluster ID. Configuring multiple RRs in a cluster can enhance the stability of the network. If a cluster has more than one RR, select this option to set the same cluster ID for all the RRs to avoid routing loops. To allow clients to receive routes from RRs, ensure that the cluster ID of the RRs is different from the router ID of any client. If the cluster ID of the RRs is the same as the router ID of a client, the client will discard received routes.";
        }
      }
    }
  }

  grouping live_ncs_reflect-type {
    description
      "Set reflect client or change path-attribute.";
    leaf reflect-change-path {
      type boolean;
      // NCS drop default statement
      description
        "Enable/disable an RR to use an export policy to change route AS_Path.";
    }
  }

  grouping live_ncs_group-entropy-label-type {
    description
      "Entropy label parameter configuration in a peer group.";
    leaf advertise-entropy-label {
      type boolean;
      // NCS drop default statement
      description
        "Enable/disable the capability of advertising entropy labels.";
    }
    leaf padding {
      // NCS drop when statement
      type string {
        length "1..32";
        pattern '(([0-9A-F])*)';
      }
      description
        "Padding format. The value is a hexadecimal string containing 1 to 32 characters (16 hexadecimal numbers). It cannot contain spaces, and can only contain uppercase letters (A to F) and digits (0 to 9), and the length must be an even number.";
    }
    leaf attribute-type {
      // NCS drop when statement
      type live_ncs_entropy-label-attribute-type;
      // NCS drop mandatory statement
      description
        "The attribute-type of advertising entropy labels.";
    }
    leaf entropy-label {
      type boolean;
      // NCS drop default statement
      description
        "Enable/disable the function of delivering the entropy label capability to the forwarding plane.";
    }
  }

  grouping live_ncs_peer-entropy-label-type {
    description
      "Entropy label parameter configuration in a peer.";
    leaf advertise-entropy-label {
      type live_ncs_peer-comm-config-type;
      // NCS drop default statement
      description
        "Enable the capability of advertising entropy labels.";
    }
    leaf padding {
      // NCS drop when statement
      type string {
        length "1..32";
        pattern '(([0-9A-F])*)';
      }
      description
        "Padding format. The value is a hexadecimal string containing 1 to 32 characters (16 hexadecimal numbers). It cannot contain spaces, and can only contain uppercase letters (A to F) and digits (0 to 9), and the length must be an even number.";
    }
    leaf attribute-type {
      // NCS drop when statement
      type live_ncs_entropy-label-attribute-type;
      // NCS drop mandatory statement
      description
        "The attribute-type of advertising entropy labels.";
    }
    leaf entropy-label {
      type live_ncs_peer-comm-config-type;
      // NCS drop default statement
      description
        "Enable the function of delivering the entropy label capability to the forwarding plane.";
    }
    leaf effect-advertise-entropy-label {
      type boolean;
      // NCS drop default statement
      description
        "Whether the capability of advertising entropy labels is enabled on the BGP peer.";
    }
    leaf effect-padding {
      // NCS drop when statement
      type string {
        length "1..32";
        pattern '(([0-9A-F])*)';
      }
      description
        "Padding format.";
    }
    leaf effect-attribute-type {
      // NCS drop when statement
      type live_ncs_entropy-label-attribute-type;
      description
        "The attribute-type of advertising entropy labels.";
    }
    leaf effect-entropy-label {
      type boolean;
      // NCS drop default statement
      description
        "Whether the function of delivering the entropy label capability to the forwarding plane is enabled on the BGP peer.";
    }
  }

  grouping unicast-aggregate-routes-type {
    description
      "BGP IPv4/IPv6 unicast aggregate routes.";
    leaf address {
      type inet:ip-address-no-zone;
      description
        "Specify the IPv4 address or IPv6 address of a summarized route. Only IPv4 summarized routes can be configured in the IPv4 address family and only IPv6 summarized routes can be configured in the IPv6 address family.";
    }
    leaf mask-length {
      type uint8 {
        range "1..128";
      }
      description
        "Specify the mask length of a summarized address.";
    }
    leaf as-set {
      type boolean;
      default "false";
      description
        "Enable/disable the generation of routes with the AS-SET attribute. This option can be used to create a summarized route. The AS_Path attribute of the summarized route contains the AS-Path attributes of the specific routes for the route summarization. Exercise caution when using this option if multiple AS_Paths need to be summarized to prevent route flapping.";
    }
    leaf detail-suppressed {
      type boolean;
      default "false";
      description
        "Enable/disable detail-suppressed. Suppress the advertisement of specific routes for the route summarization. Only the summarized route is advertised.";
    }
    choice policy-type {
      description
        "Set route policy or filter.";
      case rtp-ref {
        description
          "Route policy.";
        leaf attribute-policy {
          type leafref {
            path "/ncs:devices/ncs:device/ncs:config/rtp:routing-policy/rtp:policy-definitions/rtp:policy-definition/rtp:name" {
              tailf:xpath-root 3;
            }
          }
          description
            "Specify an attribute of summarized routes. If apply as-path is used to configure the AS_Path attribute that is used in the route Summarization policy, and the as-set keyword is set, the AS_Path attribute in the policy does not take effect. This parameter and any of the following parameters overwrite each other: suppressFilter, originFilter, and attributeFilter.";
        }
        leaf origin-policy {
          type leafref {
            path "/ncs:devices/ncs:device/ncs:config/rtp:routing-policy/rtp:policy-definitions/rtp:policy-definition/rtp:name" {
              tailf:xpath-root 3;
            }
          }
          description
            "Specify the name of a policy for generating summarized routes. Summarized routes are generated only when the routes match route-policy. This parameter and any of the following parameters overwrite each other: suppressFilter, originFilter, and attributeFilter.";
        }
        leaf suppress-policy {
          type leafref {
            path "/ncs:devices/ncs:device/ncs:config/rtp:routing-policy/rtp:policy-definitions/rtp:policy-definition/rtp:name" {
              tailf:xpath-root 3;
            }
          }
          description
            "Specify a policy for suppressing the advertisement of specified routes. The routes matching the policy are not advertised, and other routes are advertised. This parameter and any of the following parameters overwrite each other: suppressFilter, originFilter, and attributeFilter.";
        }
      }
      case xpl-ref {
        description
          "Route filter.";
        leaf attribute-filter-name {
          type leafref {
            path "/ncs:devices/ncs:device/ncs:config/xpl:xpl/xpl:route-filters/xpl:route-filter/xpl:name" {
              tailf:xpath-root 3;
            }
          }
          description
            "Specify a route-filter name.";
        }
        leaf attribute-filter-parameter {
          when '../attribute-filter-name' {
            tailf:xpath-root 3;
          }
          type xpl:filter-parameter-type;
          description
            "Specify a route-filter parameter.";
        }
        leaf origin-filter-name {
          type leafref {
            path "/ncs:devices/ncs:device/ncs:config/xpl:xpl/xpl:route-filters/xpl:route-filter/xpl:name" {
              tailf:xpath-root 3;
            }
          }
          description
            "Specify a route-filter name.";
        }
        leaf origin-filter-parameter {
          when '../origin-filter-name' {
            tailf:xpath-root 3;
          }
          type xpl:filter-parameter-type;
          description
            "Specify a route-filter parameter.";
        }
        leaf suppress-filter-name {
          type leafref {
            path "/ncs:devices/ncs:device/ncs:config/xpl:xpl/xpl:route-filters/xpl:route-filter/xpl:name" {
              tailf:xpath-root 3;
            }
          }
          description
            "Specify a route-filter name.";
        }
        leaf suppress-filter-parameter {
          when '../suppress-filter-name' {
            tailf:xpath-root 3;
          }
          type xpl:filter-parameter-type;
          description
            "Specify a route-filter parameter.";
        }
      }
    }
  }

  grouping network-route-ipv4 {
    description
      "BGP network routes.";
    leaf address {
      type inet:ipv4-address-no-zone;
      description
        "Specify the IP address advertised by BGP. An IPv4 address can be configured in the IPv4 address family. Note: During the configuration of a network route, the IP address is adjusted based on the mask. It is recommended that you click Synchronize All after creating a network route.";
    }
    leaf mask-length {
      type uint8 {
        range "1..32";
      }
      description
        "Specify the mask length of an IP address.";
    }
    choice policy-type {
      description
        "Specify the route-policy or filter for route advertisement.";
      case rtp-ref {
        description
          "Specify the route policy.";
        leaf policy-name {
          type leafref {
            path "/ncs:devices/ncs:device/ncs:config/rtp:routing-policy/rtp:policy-definitions/rtp:policy-definition/rtp:name" {
              tailf:xpath-root 3;
            }
          }
          description
            "Specify the route policy.";
        }
      }
      case xpl-ref {
        description
          "Route filter.";
        uses route-filter-type;
      }
    }
  }

  grouping network-route-ipv6 {
    description
      "BGP network routes.";
    leaf address {
      type inet:ipv6-address-no-zone;
      description
        "Specify the IP address advertised by BGP. An IPv6 routes can be configured in the IPv6 address family. Note: During the configuration of a network route, the IP address is adjusted based on the mask. It is recommended that you click Synchronize All after creating a network route.";
    }
    leaf mask-length {
      type uint8 {
        range "1..128";
      }
      description
        "Specify the mask length of an IP address.";
    }
    choice policy-type {
      description
        "Specify the route-policy or filter for route advertisement.";
      case rtp-ref {
        description
          "Specify the route policy.";
        leaf policy-name {
          type leafref {
            path "/ncs:devices/ncs:device/ncs:config/rtp:routing-policy/rtp:policy-definitions/rtp:policy-definition/rtp:name" {
              tailf:xpath-root 3;
            }
          }
          description
            "Specify the route policy.";
        }
      }
      case xpl-ref {
        description
          "Route filter.";
        uses route-filter-type;
      }
    }
  }

  grouping advertise-route-to-evpn-type {
    description
      "Advertise-routes-type configuration.";
    list advertise-route-to-evpn {
      key "protocol";
      description
        "Configure the advertise route protocol.";
      leaf protocol {
        type enumeration {
          enum "all" {
            value 0;
            description
              "Advertise all the types of route protocol.";
          }
        }
        description
          "Route protocol.";
      }
      leaf import-multipath {
        type boolean;
        default "false";
        description
          "Enable/disable route import from multiple paths.";
      }
      leaf include-local-cross {
        type boolean;
        default "false";
        description
          "Enable/disable local cross route to advertise l2vpn evpn.";
      }
      leaf advertise-route-mode {
        type enumeration {
          enum "all" {
            value 0;
            description
              "All:";
          }
          enum "best" {
            value 1;
            description
              "Best:";
          }
          enum "valid" {
            value 2;
            description
              "Valid:";
          }
        }
        default "all";
        description
          "VPN advertise route mode to evrf.";
      }
    }
  }

  grouping vpn-target-type {
    description
      "BGP IPv4/IPv6 VPN target.";
    leaf policy-vpntarget {
      type boolean;
      default "true";
      description
        "Enable/disable VPN target-based filtering for the received VPN routes. Only the VPN route whose Export RT attribute matches the local Import RT attribute can be added to the routing table. This option can be used in the inter-AS VPN Option B solution and the ASBR MP-EBGP inter-AS L2VPN solution in Kompella mode.";
    }
  }

  grouping reflector-cluster-type {
    description
      "BGP reflector cluster-id.";
    choice reflector-type {
      description
        "Set IPv4 address or id.";
      case address {
        description
          "IPv4 address.";
        leaf reflector-cluster-ipv4 {
          type inet:ipv4-address-no-zone;
          description
            "Set a cluster ID. The value is expressed in the format of an IPv4 address. Configuring multiple RRs in a cluster can enhance the stability of the network. If a cluster has more than one RR, select this option to set the same cluster ID for all the RRs to avoid routing loops. To allow clients to receive routes from RRs, ensure that the cluster ID of the RRs is different from the router ID of any client. If the cluster ID of the RRs is the same as the router ID of a client, the client will discard received routes.";
        }
      }
      case id {
        description
          "Set value.";
        leaf reflector-cluster-id {
          type uint32 {
            range "1..4294967295";
          }
          description
            "Set a cluster ID. Configuring multiple RRs in a cluster can enhance the stability of the network. If a cluster has more than one RR, select this option to set the same cluster ID for all the RRs to avoid routing loops. To allow clients to receive routes from RRs, ensure that the cluster ID of the RRs is different from the router ID of any client. If the cluster ID of the RRs is the same as the router ID of a client, the client will discard received routes.";
        }
      }
    }
  }

  grouping reflect-type {
    description
      "Set reflect client or change path-attribute.";
    leaf reflect-change-path {
      type boolean;
      default "false";
      description
        "Enable/disable an RR to use an export policy to change route AS_Path.";
    }
  }

  grouping group-entropy-label-type {
    description
      "Entropy label parameter configuration in a peer group.";
    leaf advertise-entropy-label {
      type boolean;
      default "false";
      description
        "Enable/disable the capability of advertising entropy labels.";
    }
    leaf padding {
      when "../advertise-entropy-label='true'" {
        tailf:xpath-root 3;
      }
      type string {
        length "1..32";
        pattern '(([0-9A-F])*)';
      }
      description
        "Padding format. The value is a hexadecimal string containing 1 to 32 characters (16 hexadecimal numbers). It cannot contain spaces, and can only contain uppercase letters (A to F) and digits (0 to 9), and the length must be an even number.";
    }
    leaf attribute-type {
      when "../advertise-entropy-label='true'" {
        tailf:xpath-root 3;
      }
      type entropy-label-attribute-type;
      mandatory true;
      description
        "The attribute-type of advertising entropy labels.";
    }
    leaf entropy-label {
      type boolean;
      default "false";
      description
        "Enable/disable the function of delivering the entropy label capability to the forwarding plane.";
    }
  }

  grouping peer-entropy-label-type {
    description
      "Entropy label parameter configuration in a peer.";
    leaf advertise-entropy-label {
      type peer-comm-config-type;
      default "default";
      description
        "Enable the capability of advertising entropy labels.";
    }
    leaf padding {
      when "../advertise-entropy-label='enable'" {
        tailf:xpath-root 3;
      }
      type string {
        length "1..32";
        pattern '(([0-9A-F])*)';
      }
      description
        "Padding format. The value is a hexadecimal string containing 1 to 32 characters (16 hexadecimal numbers). It cannot contain spaces, and can only contain uppercase letters (A to F) and digits (0 to 9), and the length must be an even number.";
    }
    leaf attribute-type {
      when "../advertise-entropy-label='enable'" {
        tailf:xpath-root 3;
      }
      type entropy-label-attribute-type;
      mandatory true;
      description
        "The attribute-type of advertising entropy labels.";
    }
    leaf entropy-label {
      type peer-comm-config-type;
      default "default";
      description
        "Enable the function of delivering the entropy label capability to the forwarding plane.";
    }
    // NCS drop config false leaf 'effect-advertise-entropy-label'
    // NCS drop config false leaf 'effect-padding'
    // NCS drop config false leaf 'effect-attribute-type'
    // NCS drop config false leaf 'effect-entropy-label'
  }

  augment "/ncs:devices/ncs:device/ncs:config" {
    container bgp {
      tailf:ncs-device-type "netconf";
      tailf:display-when "not(../../ncs:module) or ../../ncs:module[ncs:name='huawei-bgp']";
      description
        "Inter-AS routing protocol that exchanges Network Layer Reachability Information (NLRI) with other BGP systems,
         Universal BGP configurations that contain the basic BGP configurations and the query information.";
      container global {
        description
          "Configure the router for BGP globally.";
        leaf yang-enable {
          type boolean;
          default "false";
          description
            "Enable/disable BGP yang mode. To use NETCONF YANG to manage BGP VPN instances in huawei-bgp.yang, enable YANG management for the BGP VPN instances on the device or enable the leaf node globally in the huawei-bgp.yang file.";
        }
        leaf memory-overload-exception-discard-route {
          type boolean;
          default "false";
          description
            "Enable/disable BGP to discard routes received from all peers if the memory usage of a device is abnormal.";
        }
      }
      container paf-controls {
        description
          "List of PAF-based limiting disabled for some features.";
        list paf-control {
          key "feature-name";
          description
            "Configure PAF-based limiting disabled for some features.";
          leaf feature-name {
            type paf-control-feature-type;
            description
              "Feature name.";
          }
        }
      }
      container base-process {
        description
          "Configure the global BGP information, such as the protocol version, AS number, and system identifier.";
        leaf enable {
          type boolean;
          must "(../enable='true' and ../as) or (../enable='false' and not(../as))" {
            tailf:xpath-root 3;
          }
          default "false";
          description
            "Enable/disable BGP function.";
        }
        leaf as {
          when "../enable='true'" {
            tailf:xpath-root 3;
          }
          type as-number-validate;
          description
            "Local AS number, which can be in either of the two formats:
             The two-byte format is X. X is an integer ranging from 1 to 65535.
             The four-byte format is X.Y and X. When the format is X.Y, X and Y are both integers, with the value of X ranging from 1 to 65535, and the value of Y ranging from 0 to 65535; when the format is X, X is an interger, with the value ranging from 1 to 4294967295.
             An AS consists of multiple routers managed based on the same techniques. Interior Gateway Protocol (IGP) and universal routing metric packets are used inside an AS, and Exterior Gateway Protocol (EGP) is used outside to send packets to other ASs. With the development of this definition, one AS usually uses multiple IGPs and metrics. Even though multiple IGPs and metrics are used, the routing plan and destination reachability of an AS are consistent with those of another AS. The local AS number cannot be configured same as the confederation sub-ASs. The object cannot be deleted or modified.";
          ext:operation-exclude "update" {
            description
              "The node cannot be modified when BGP is enabled.";
          }
        }
        leaf keep-all-routes {
          when "../enable='true'" {
            tailf:xpath-root 3;
          }
          type boolean;
          default "false";
          description
            "Enable/disable saving all the updated information about BGP routes from a peer or peer group after a BGP connection is established, even though these BGP routes fail to match the routing policy on the ingress. Save all the updated information about BGP routes from a peer or peer group after a BGP connection is established, even though these BGP routes fail to match the routing policy on the ingress. By default, only the updated information about BGP routes from a specified peer is saved on condition that the routes match the routing policy on the ingress. If a router supports route refreshing, this option is not required.";
        }
        leaf check-first-as {
          when "../enable='true'" {
            tailf:xpath-root 3;
          }
          type boolean;
          default "true";
          description
            "Enable/disable checking the first AS in the AS_Path of the update messages from EBGP peers.";
        }
        leaf router-id-auto-select {
          when "../enable='true'" {
            tailf:xpath-root 3;
          }
          type boolean;
          default "false";
          description
            "Enable/disable router ID auto select. If a BGP VPN instance is not enabled to select a router ID, a router ID can be configured for the BGP VPN instance. If no router ID is configured for the BGP VPN instance, the BGP VPN instance inherits the router ID of the public network instance. If a BGP VPN instance is enabled to select a router ID, it uses the address of an interface bound to a VPN as the router ID based on the following rules:
             1. If Loopback interfaces configured with IP addresses exist, the largest IP address among the IP addresses of the Loopback interfaces is selected as the router ID.
             2. If there is no Loopback interface configured with an IP address, the largest IP address among the IP addresses of other interfaces is selected as the router ID, regardless of whether the interface is Up.";
        }
        leaf shutdown {
          when "../enable='true'" {
            tailf:xpath-root 3;
          }
          type boolean;
          default "false";
          description
            "Enable/disable interrupting BGP all neighbour.";
        }
        leaf local-ifnet-mtu {
          when "../enable='true'" {
            tailf:xpath-root 3;
          }
          type uint16 {
            range "46..65535";
          }
          default "1500";
          description
            "BGP LOCALIFNET MTU.";
        }
        leaf private-4byte-as {
          when "../enable='true'" {
            tailf:xpath-root 3;
          }
          type boolean;
          default "false";
          description
            "Enable/disable BGP private 4 byte AS. With BGP private-4-byte-as, BGP private as is from 64512 to 65535 and from 4200000000 to 4294967294.";
        }
        leaf local-cross-no-med {
          when "../enable='true'" {
            tailf:xpath-root 3;
          }
          type boolean;
          default "false";
          description
            "Enable/disable local cross routing non-med.";
        }
        leaf as-path-limit {
          when "../enable='true'" {
            tailf:xpath-root 3;
          }
          type uint16 {
            range "1..2000";
          }
          description
            "Maximum number of AS numbers in the AS_Path attribute.";
        }
        leaf dynamic-session-limit {
          when "../enable='true'" {
            tailf:xpath-root 3;
          }
          ext:dynamic-default;
          type uint32 {
            range "1..4294967295";
          }
          description
            "Upper limit on the number of dynamic peer sessions.";
        }
        leaf peer-up-route-lowest-priority {
          when "../enable='true'" {
            tailf:xpath-root 3;
          }
          type boolean;
          default "false";
          description
            "Enable/disable reducing route priority to lowest.";
        }
        leaf delay-time {
          when "../peer-up-route-lowest-priority='true'" {
            tailf:xpath-root 3;
          }
          type uint32 {
            range "1..864000";
          }
          units "s";
          description
            "Specifies the delay time.";
        }
        container confederation {
          when "../enable='true'" {
            tailf:xpath-root 3;
          }
          description
            "Configure confederation.";
          leaf id {
            type as-number-validate;
            description
              "Configure the confederation ID.";
          }
          leaf nonstanded {
            type boolean;
            default "false";
            description
              "Enable/disable nonstanded. Configure the device to be compatible with devices in a nonstandard confederation.";
          }
          leaf-list as {
            when '../id' {
              tailf:xpath-root 3;
            }
            type as-number-validate;
            max-elements 32;
            description
              "Configure the confederation AS number. The confederation AS number can be in either of the two formats:
               The two-byte format is X. X is an integer ranging from 1 to 65535.
               The four-byte format is X.Y and X. When the format is X.Y, X and Y are both integers, with the value of X ranging from 1 to 65535, and the value of Y ranging from 0 to 65535; when the format is X, X is an interger, with the value of X ranging from 1 to 4294967295. The confederation sub-ASs cannot be configured same as the local AS number.";
          }
        }
        container graceful-restart {
          when "../enable='true'" {
            tailf:xpath-root 3;
          }
          description
            "Configure the graceful-restart.";
          uses graceful-restart-type;
        }
        uses remote-prefix-sid-states-type;
        container reference-period {
          when "../enable='true'" {
            tailf:xpath-root 3;
          }
          must 'hold-interval>suppress-interval' {
            tailf:xpath-root 3;
          }
          must 'clear-interval>hold-interval' {
            tailf:xpath-root 3;
          }
          description
            "Configure the reference period.";
          uses reference-period-type;
        }
        container timer {
          when "../enable='true'" {
            tailf:xpath-root 3;
          }
          description
            "Configure BGP global timer parameters.";
          uses global-timer-para-type;
        }
        uses graceful-restart-status-type;
        uses error-discard-info-type;
        uses vpn-brief-infos-type;
        // NCS drop config false container 'default-parameter'
      }
      container instance-processs {
        description
          "List of the global BGP information for the list of all BGP instances, such as the protocol version, AS number, and system identifier.";
        list instance-process {
          key "name";
          max-elements 1;
          description
            "Configure the global BGP information for the BGP instances, such as the protocol version, AS number, and system identifier.";
          leaf name {
            type string {
              length "1..31";
            }
            must "../name != 'default'" {
              tailf:xpath-root 3;
            }
            description
              "Name of BGP Site.";
          }
          leaf as-number {
            type as-number-validate;
            mandatory true;
            description
              "Local AS number, which can be in either of the two formats:
               The two-byte format is X. X is an integer ranging from 1 to 65535.
               The four-byte format is X.Y and X. When the format is X.Y, X and Y are both integers, with the value of X ranging from 1 to 65535, and the value of Y ranging from 0 to 65535; when the format is X, X is an interger, with the value ranging from 1 to 4294967295.
               An AS consists of instance routers managed based on the same techniques. Interior Gateway Protocol (IGP) and universal routing metric packets are used inside an AS, and Exterior Gateway Protocol (EGP) is used outside to send packets to other ASs. With the development of this definition, one AS usually uses instance IGPs and metrics. Even though instance IGPs and metrics are used, the routing plan and destination reachability of an AS are consistent with those of another AS. The local AS number cannot be configured same as the confederation sub-ASs.";
            ext:operation-exclude "update" {
              description
                "The node cannot be modified when BGP is enabled.";
            }
          }
          leaf check-first-as {
            type boolean;
            default "true";
            description
              "Enable/disable checking the first AS in the AS_Path of the update messages from EBGP peers.";
          }
          leaf shutdown {
            type boolean;
            default "false";
            description
              "Enable/disable interrupting BGP all neighbour.";
          }
          leaf private-4byte-as {
            type boolean;
            default "false";
            description
              "Enable/disable BGP private 4 byte AS. With BGP private-4-byte-as, BGP private as is from 64512 to 65535 and from 4200000000 to 4294967294.";
          }
          leaf peer-up-route-lowest-priority {
            type boolean;
            default "false";
            description
              "Enable/disable reducing route priority to lowest.";
          }
          leaf delay-time {
            when "../peer-up-route-lowest-priority='true'" {
              tailf:xpath-root 3;
            }
            type uint32 {
              range "1..864000";
            }
            units "s";
            description
              "Specifies the delay time.";
          }
          leaf memory-limit {
            type boolean;
            default "false";
            description
              "Enable/disable using the prefix memory-limit command, you can configure the capability of BGP about memory limit when the system memory usage exceeded.";
          }
          container graceful-restart {
            description
              "Configure the graceful-restart.";
            uses graceful-restart-type;
          }
          container reference-period {
            must 'hold-interval>suppress-interval' {
              tailf:xpath-root 3;
            }
            must 'clear-interval>hold-interval' {
              tailf:xpath-root 3;
            }
            description
              "Configure the reference period.";
            uses reference-period-type;
          }
          container timer {
            description
              "Configure BGP global timer parameters.";
            uses global-timer-para-type;
          }
        }
      }
    }
  }
  augment "/ncs:devices/ncs:device/ncs:live-status" {
    container bgp {
      tailf:ncs-device-type "netconf";
      tailf:display-when "not(../../ncs:module) or ../../ncs:module[ncs:name='huawei-bgp'] or (../../ncs:live-status-protocol[not(ncs:capability)]) or (../../ncs:live-status-protocol/ncs:capability/ncs:module[.='huawei-bgp'])";
      description
        "Inter-AS routing protocol that exchanges Network Layer Reachability Information (NLRI) with other BGP systems,
         Universal BGP configurations that contain the basic BGP configurations and the query information.";
      container global {
        description
          "Configure the router for BGP globally.";
        leaf yang-enable {
          type boolean;
          // NCS drop default statement
          description
            "Enable/disable BGP yang mode. To use NETCONF YANG to manage BGP VPN instances in huawei-bgp.yang, enable YANG management for the BGP VPN instances on the device or enable the leaf node globally in the huawei-bgp.yang file.";
        }
        leaf memory-overload-exception-discard-route {
          type boolean;
          // NCS drop default statement
          description
            "Enable/disable BGP to discard routes received from all peers if the memory usage of a device is abnormal.";
        }
      }
      container paf-controls {
        description
          "List of PAF-based limiting disabled for some features.";
        list paf-control {
          key "feature-name";
          description
            "Configure PAF-based limiting disabled for some features.";
          leaf feature-name {
            type live_ncs_paf-control-feature-type;
            description
              "Feature name.";
          }
        }
      }
      container base-process {
        description
          "Configure the global BGP information, such as the protocol version, AS number, and system identifier.";
        leaf enable {
          type boolean;
          // NCS drop must statement
          // NCS drop default statement
          description
            "Enable/disable BGP function.";
        }
        leaf as {
          // NCS drop when statement
          type live_ncs_as-number-validate;
          description
            "Local AS number, which can be in either of the two formats:
             The two-byte format is X. X is an integer ranging from 1 to 65535.
             The four-byte format is X.Y and X. When the format is X.Y, X and Y are both integers, with the value of X ranging from 1 to 65535, and the value of Y ranging from 0 to 65535; when the format is X, X is an interger, with the value ranging from 1 to 4294967295.
             An AS consists of multiple routers managed based on the same techniques. Interior Gateway Protocol (IGP) and universal routing metric packets are used inside an AS, and Exterior Gateway Protocol (EGP) is used outside to send packets to other ASs. With the development of this definition, one AS usually uses multiple IGPs and metrics. Even though multiple IGPs and metrics are used, the routing plan and destination reachability of an AS are consistent with those of another AS. The local AS number cannot be configured same as the confederation sub-ASs. The object cannot be deleted or modified.";
          ext:operation-exclude "update" {
            description
              "The node cannot be modified when BGP is enabled.";
          }
        }
        leaf keep-all-routes {
          // NCS drop when statement
          type boolean;
          // NCS drop default statement
          description
            "Enable/disable saving all the updated information about BGP routes from a peer or peer group after a BGP connection is established, even though these BGP routes fail to match the routing policy on the ingress. Save all the updated information about BGP routes from a peer or peer group after a BGP connection is established, even though these BGP routes fail to match the routing policy on the ingress. By default, only the updated information about BGP routes from a specified peer is saved on condition that the routes match the routing policy on the ingress. If a router supports route refreshing, this option is not required.";
        }
        leaf check-first-as {
          // NCS drop when statement
          type boolean;
          // NCS drop default statement
          description
            "Enable/disable checking the first AS in the AS_Path of the update messages from EBGP peers.";
        }
        leaf router-id-auto-select {
          // NCS drop when statement
          type boolean;
          // NCS drop default statement
          description
            "Enable/disable router ID auto select. If a BGP VPN instance is not enabled to select a router ID, a router ID can be configured for the BGP VPN instance. If no router ID is configured for the BGP VPN instance, the BGP VPN instance inherits the router ID of the public network instance. If a BGP VPN instance is enabled to select a router ID, it uses the address of an interface bound to a VPN as the router ID based on the following rules:
             1. If Loopback interfaces configured with IP addresses exist, the largest IP address among the IP addresses of the Loopback interfaces is selected as the router ID.
             2. If there is no Loopback interface configured with an IP address, the largest IP address among the IP addresses of other interfaces is selected as the router ID, regardless of whether the interface is Up.";
        }
        leaf shutdown {
          // NCS drop when statement
          type boolean;
          // NCS drop default statement
          description
            "Enable/disable interrupting BGP all neighbour.";
        }
        leaf local-ifnet-mtu {
          // NCS drop when statement
          type uint16 {
            range "46..65535";
          }
          // NCS drop default statement
          description
            "BGP LOCALIFNET MTU.";
        }
        leaf private-4byte-as {
          // NCS drop when statement
          type boolean;
          // NCS drop default statement
          description
            "Enable/disable BGP private 4 byte AS. With BGP private-4-byte-as, BGP private as is from 64512 to 65535 and from 4200000000 to 4294967294.";
        }
        leaf local-cross-no-med {
          // NCS drop when statement
          type boolean;
          // NCS drop default statement
          description
            "Enable/disable local cross routing non-med.";
        }
        leaf as-path-limit {
          // NCS drop when statement
          type uint16 {
            range "1..2000";
          }
          description
            "Maximum number of AS numbers in the AS_Path attribute.";
        }
        leaf dynamic-session-limit {
          // NCS drop when statement
          ext:dynamic-default;
          type uint32 {
            range "1..4294967295";
          }
          description
            "Upper limit on the number of dynamic peer sessions.";
        }
        leaf peer-up-route-lowest-priority {
          // NCS drop when statement
          type boolean;
          // NCS drop default statement
          description
            "Enable/disable reducing route priority to lowest.";
        }
        leaf delay-time {
          // NCS drop when statement
          type uint32 {
            range "1..864000";
          }
          units "s";
          description
            "Specifies the delay time.";
        }
        container confederation {
          // NCS drop when statement
          description
            "Configure confederation.";
          leaf id {
            type live_ncs_as-number-validate;
            description
              "Configure the confederation ID.";
          }
          leaf nonstanded {
            type boolean;
            // NCS drop default statement
            description
              "Enable/disable nonstanded. Configure the device to be compatible with devices in a nonstandard confederation.";
          }
          leaf-list as {
            // NCS drop when statement
            type live_ncs_as-number-validate;
            // NCS drop max-elements statement
            description
              "Configure the confederation AS number. The confederation AS number can be in either of the two formats:
               The two-byte format is X. X is an integer ranging from 1 to 65535.
               The four-byte format is X.Y and X. When the format is X.Y, X and Y are both integers, with the value of X ranging from 1 to 65535, and the value of Y ranging from 0 to 65535; when the format is X, X is an interger, with the value of X ranging from 1 to 4294967295. The confederation sub-ASs cannot be configured same as the local AS number.";
          }
        }
        container graceful-restart {
          // NCS drop when statement
          description
            "Configure the graceful-restart.";
          uses live_ncs_graceful-restart-type;
        }
        uses live_ncs_remote-prefix-sid-states-type;
        container reference-period {
          // NCS drop when statement
          // NCS drop must statement
          // NCS drop must statement
          description
            "Configure the reference period.";
          uses live_ncs_reference-period-type;
        }
        container timer {
          // NCS drop when statement
          description
            "Configure BGP global timer parameters.";
          uses live_ncs_global-timer-para-type;
        }
        uses live_ncs_graceful-restart-status-type;
        uses live_ncs_error-discard-info-type;
        uses live_ncs_vpn-brief-infos-type;
        container default-parameter {
          description
            "Statistics of default parameter of BGP.";
          leaf version {
            type uint8;
            description
              "BGP protocol version.";
          }
          leaf connect-retry-time {
            type uint16;
            units "s";
            description
              "Value of connect retry timer.";
          }
          leaf hold-time {
            type uint32;
            units "s";
            description
              "The holdtime interval.";
          }
          leaf keepalive-time {
            type uint32;
            units "s";
            description
              "The keepalive interval.";
          }
        }
      }
      container instance-processs {
        description
          "List of the global BGP information for the list of all BGP instances, such as the protocol version, AS number, and system identifier.";
        list instance-process {
          key "name";
          // NCS drop max-elements statement
          description
            "Configure the global BGP information for the BGP instances, such as the protocol version, AS number, and system identifier.";
          leaf name {
            type string {
              length "1..31";
            }
            // NCS drop must statement
            description
              "Name of BGP Site.";
          }
          leaf as-number {
            type live_ncs_as-number-validate;
            // NCS drop mandatory statement
            description
              "Local AS number, which can be in either of the two formats:
               The two-byte format is X. X is an integer ranging from 1 to 65535.
               The four-byte format is X.Y and X. When the format is X.Y, X and Y are both integers, with the value of X ranging from 1 to 65535, and the value of Y ranging from 0 to 65535; when the format is X, X is an interger, with the value ranging from 1 to 4294967295.
               An AS consists of instance routers managed based on the same techniques. Interior Gateway Protocol (IGP) and universal routing metric packets are used inside an AS, and Exterior Gateway Protocol (EGP) is used outside to send packets to other ASs. With the development of this definition, one AS usually uses instance IGPs and metrics. Even though instance IGPs and metrics are used, the routing plan and destination reachability of an AS are consistent with those of another AS. The local AS number cannot be configured same as the confederation sub-ASs.";
            ext:operation-exclude "update" {
              description
                "The node cannot be modified when BGP is enabled.";
            }
          }
          leaf check-first-as {
            type boolean;
            // NCS drop default statement
            description
              "Enable/disable checking the first AS in the AS_Path of the update messages from EBGP peers.";
          }
          leaf shutdown {
            type boolean;
            // NCS drop default statement
            description
              "Enable/disable interrupting BGP all neighbour.";
          }
          leaf private-4byte-as {
            type boolean;
            // NCS drop default statement
            description
              "Enable/disable BGP private 4 byte AS. With BGP private-4-byte-as, BGP private as is from 64512 to 65535 and from 4200000000 to 4294967294.";
          }
          leaf peer-up-route-lowest-priority {
            type boolean;
            // NCS drop default statement
            description
              "Enable/disable reducing route priority to lowest.";
          }
          leaf delay-time {
            // NCS drop when statement
            type uint32 {
              range "1..864000";
            }
            units "s";
            description
              "Specifies the delay time.";
          }
          leaf memory-limit {
            type boolean;
            // NCS drop default statement
            description
              "Enable/disable using the prefix memory-limit command, you can configure the capability of BGP about memory limit when the system memory usage exceeded.";
          }
          container graceful-restart {
            description
              "Configure the graceful-restart.";
            uses live_ncs_graceful-restart-type;
          }
          container reference-period {
            // NCS drop must statement
            // NCS drop must statement
            description
              "Configure the reference period.";
            uses live_ncs_reference-period-type;
          }
          container timer {
            description
              "Configure BGP global timer parameters.";
            uses live_ncs_global-timer-para-type;
          }
        }
      }
    }
  }
  augment "/ncs:devices/ncs:template/ncs:ned-id/ncs:config" {
    container bgp {
      description
        "Inter-AS routing protocol that exchanges Network Layer Reachability Information (NLRI) with other BGP systems,
         Universal BGP configurations that contain the basic BGP configurations and the query information.";
      container global {
        description
          "Configure the router for BGP globally.";
        leaf yang-enable {
          type string;
          // NCS drop default statement
          description
            "Enable/disable BGP yang mode. To use NETCONF YANG to manage BGP VPN instances in huawei-bgp.yang, enable YANG management for the BGP VPN instances on the device or enable the leaf node globally in the huawei-bgp.yang file.";
        }
        leaf memory-overload-exception-discard-route {
          type string;
          // NCS drop default statement
          description
            "Enable/disable BGP to discard routes received from all peers if the memory usage of a device is abnormal.";
        }
      }
      container paf-controls {
        description
          "List of PAF-based limiting disabled for some features.";
        list paf-control {
          // NCS patched for predictable order
          ordered-by user;
          key "feature-name";
          description
            "Configure PAF-based limiting disabled for some features.";
          leaf feature-name {
            type ncs_template_paf-control-feature-type;
            description
              "Feature name.";
          }
        }
      }
      container base-process {
        description
          "Configure the global BGP information, such as the protocol version, AS number, and system identifier.";
        leaf enable {
          type string;
          // NCS drop must statement
          // NCS drop default statement
          description
            "Enable/disable BGP function.";
        }
        leaf as {
          // NCS drop when statement
          type ncs_template_as-number-validate;
          description
            "Local AS number, which can be in either of the two formats:
             The two-byte format is X. X is an integer ranging from 1 to 65535.
             The four-byte format is X.Y and X. When the format is X.Y, X and Y are both integers, with the value of X ranging from 1 to 65535, and the value of Y ranging from 0 to 65535; when the format is X, X is an interger, with the value ranging from 1 to 4294967295.
             An AS consists of multiple routers managed based on the same techniques. Interior Gateway Protocol (IGP) and universal routing metric packets are used inside an AS, and Exterior Gateway Protocol (EGP) is used outside to send packets to other ASs. With the development of this definition, one AS usually uses multiple IGPs and metrics. Even though multiple IGPs and metrics are used, the routing plan and destination reachability of an AS are consistent with those of another AS. The local AS number cannot be configured same as the confederation sub-ASs. The object cannot be deleted or modified.";
          ext:operation-exclude "update" {
            description
              "The node cannot be modified when BGP is enabled.";
          }
        }
        leaf keep-all-routes {
          // NCS drop when statement
          type string;
          // NCS drop default statement
          description
            "Enable/disable saving all the updated information about BGP routes from a peer or peer group after a BGP connection is established, even though these BGP routes fail to match the routing policy on the ingress. Save all the updated information about BGP routes from a peer or peer group after a BGP connection is established, even though these BGP routes fail to match the routing policy on the ingress. By default, only the updated information about BGP routes from a specified peer is saved on condition that the routes match the routing policy on the ingress. If a router supports route refreshing, this option is not required.";
        }
        leaf check-first-as {
          // NCS drop when statement
          type string;
          // NCS drop default statement
          description
            "Enable/disable checking the first AS in the AS_Path of the update messages from EBGP peers.";
        }
        leaf router-id-auto-select {
          // NCS drop when statement
          type string;
          // NCS drop default statement
          description
            "Enable/disable router ID auto select. If a BGP VPN instance is not enabled to select a router ID, a router ID can be configured for the BGP VPN instance. If no router ID is configured for the BGP VPN instance, the BGP VPN instance inherits the router ID of the public network instance. If a BGP VPN instance is enabled to select a router ID, it uses the address of an interface bound to a VPN as the router ID based on the following rules:
             1. If Loopback interfaces configured with IP addresses exist, the largest IP address among the IP addresses of the Loopback interfaces is selected as the router ID.
             2. If there is no Loopback interface configured with an IP address, the largest IP address among the IP addresses of other interfaces is selected as the router ID, regardless of whether the interface is Up.";
        }
        leaf shutdown {
          // NCS drop when statement
          type string;
          // NCS drop default statement
          description
            "Enable/disable interrupting BGP all neighbour.";
        }
        leaf local-ifnet-mtu {
          // NCS drop when statement
          type string;
          // NCS drop default statement
          description
            "BGP LOCALIFNET MTU.";
        }
        leaf private-4byte-as {
          // NCS drop when statement
          type string;
          // NCS drop default statement
          description
            "Enable/disable BGP private 4 byte AS. With BGP private-4-byte-as, BGP private as is from 64512 to 65535 and from 4200000000 to 4294967294.";
        }
        leaf local-cross-no-med {
          // NCS drop when statement
          type string;
          // NCS drop default statement
          description
            "Enable/disable local cross routing non-med.";
        }
        leaf as-path-limit {
          // NCS drop when statement
          type string;
          description
            "Maximum number of AS numbers in the AS_Path attribute.";
        }
        leaf dynamic-session-limit {
          // NCS drop when statement
          ext:dynamic-default;
          type string;
          description
            "Upper limit on the number of dynamic peer sessions.";
        }
        leaf peer-up-route-lowest-priority {
          // NCS drop when statement
          type string;
          // NCS drop default statement
          description
            "Enable/disable reducing route priority to lowest.";
        }
        leaf delay-time {
          // NCS drop when statement
          type string;
          units "s";
          description
            "Specifies the delay time.";
        }
        container confederation {
          // NCS drop when statement
          description
            "Configure confederation.";
          leaf id {
            type ncs_template_as-number-validate;
            description
              "Configure the confederation ID.";
          }
          leaf nonstanded {
            type string;
            // NCS drop default statement
            description
              "Enable/disable nonstanded. Configure the device to be compatible with devices in a nonstandard confederation.";
          }
          leaf-list as {
            // NCS patched for predictable order
            ordered-by user;
            // NCS drop when statement
            type ncs_template_as-number-validate;
            // NCS drop max-elements statement
            description
              "Configure the confederation AS number. The confederation AS number can be in either of the two formats:
               The two-byte format is X. X is an integer ranging from 1 to 65535.
               The four-byte format is X.Y and X. When the format is X.Y, X and Y are both integers, with the value of X ranging from 1 to 65535, and the value of Y ranging from 0 to 65535; when the format is X, X is an interger, with the value of X ranging from 1 to 4294967295. The confederation sub-ASs cannot be configured same as the local AS number.";
          }
        }
        container graceful-restart {
          // NCS drop when statement
          description
            "Configure the graceful-restart.";
          uses ncs_template_graceful-restart-type;
        }
        uses ncs_template_remote-prefix-sid-states-type;
        container reference-period {
          // NCS drop when statement
          // NCS drop must statement
          // NCS drop must statement
          description
            "Configure the reference period.";
          uses ncs_template_reference-period-type;
        }
        container timer {
          // NCS drop when statement
          description
            "Configure BGP global timer parameters.";
          uses ncs_template_global-timer-para-type;
        }
        uses ncs_template_graceful-restart-status-type;
        uses ncs_template_error-discard-info-type;
        uses ncs_template_vpn-brief-infos-type;
        // NCS drop config false container 'default-parameter'
      }
      container instance-processs {
        description
          "List of the global BGP information for the list of all BGP instances, such as the protocol version, AS number, and system identifier.";
        list instance-process {
          // NCS patched for predictable order
          ordered-by user;
          key "name";
          // NCS drop max-elements statement
          description
            "Configure the global BGP information for the BGP instances, such as the protocol version, AS number, and system identifier.";
          leaf name {
            type string;
            // NCS drop must statement
            description
              "Name of BGP Site.";
          }
          leaf as-number {
            type ncs_template_as-number-validate;
            // NCS drop mandatory statement
            description
              "Local AS number, which can be in either of the two formats:
               The two-byte format is X. X is an integer ranging from 1 to 65535.
               The four-byte format is X.Y and X. When the format is X.Y, X and Y are both integers, with the value of X ranging from 1 to 65535, and the value of Y ranging from 0 to 65535; when the format is X, X is an interger, with the value ranging from 1 to 4294967295.
               An AS consists of instance routers managed based on the same techniques. Interior Gateway Protocol (IGP) and universal routing metric packets are used inside an AS, and Exterior Gateway Protocol (EGP) is used outside to send packets to other ASs. With the development of this definition, one AS usually uses instance IGPs and metrics. Even though instance IGPs and metrics are used, the routing plan and destination reachability of an AS are consistent with those of another AS. The local AS number cannot be configured same as the confederation sub-ASs.";
            ext:operation-exclude "update" {
              description
                "The node cannot be modified when BGP is enabled.";
            }
          }
          leaf check-first-as {
            type string;
            // NCS drop default statement
            description
              "Enable/disable checking the first AS in the AS_Path of the update messages from EBGP peers.";
          }
          leaf shutdown {
            type string;
            // NCS drop default statement
            description
              "Enable/disable interrupting BGP all neighbour.";
          }
          leaf private-4byte-as {
            type string;
            // NCS drop default statement
            description
              "Enable/disable BGP private 4 byte AS. With BGP private-4-byte-as, BGP private as is from 64512 to 65535 and from 4200000000 to 4294967294.";
          }
          leaf peer-up-route-lowest-priority {
            type string;
            // NCS drop default statement
            description
              "Enable/disable reducing route priority to lowest.";
          }
          leaf delay-time {
            // NCS drop when statement
            type string;
            units "s";
            description
              "Specifies the delay time.";
          }
          leaf memory-limit {
            type string;
            // NCS drop default statement
            description
              "Enable/disable using the prefix memory-limit command, you can configure the capability of BGP about memory limit when the system memory usage exceeded.";
          }
          container graceful-restart {
            description
              "Configure the graceful-restart.";
            uses ncs_template_graceful-restart-type;
          }
          container reference-period {
            // NCS drop must statement
            // NCS drop must statement
            description
              "Configure the reference period.";
            uses ncs_template_reference-period-type;
          }
          container timer {
            description
              "Configure BGP global timer parameters.";
            uses ncs_template_global-timer-para-type;
          }
        }
      }
    }
  }
  augment "/ncs:devices/ncs:template/ncs:ned-id/ncs:config/ni:network-instance/ni:instances/ni:instance" {
    description
      "BGP network instance configuration.";
    container bgp {
      description
        "Configure BGP network instance. All nodes of private VPN Instance in this container can be used only when the value of the global BGP enabling node (/bgp:bgp/bgp:global/bgp:yang-enable) is set to true.";
      container base-process {
        // NCS drop when statement
        presence "Create vrf session.";
        description
          "Enable/disable BGP instances.";
        ext:generated-by "system" {
          // NCS drop when statement
          description
            "The BGP public instance is generated automatically when BGP is enabled.";
        }
        leaf router-id {
          type string;
          description
            "ID of a router that is in IPv4 address format. Certain dynamic routing protocols require a router ID. If no router ID is specified for a router when these protocols are enabled, the router ID in the RM module is used by default. The default router ID in the RM module is 0.0.0.0 when the router is not configured with any interface.
             The rules for selecting a router ID are as follows:
             1. If you set a router ID through this configuration, the set router ID is used. If the router ID is not set, you need to select a router ID according to the following rules:
             (1) If loopback interfaces configured with IP addresses exist, the largest IP address among the IP addresses of the loopback interfaces is selected as the router ID.
             (2) If no loopback interface configured with an IP address exists, the largest IP address among the IP addresses of other interfaces is selected as the router ID, regardless of whether the interface is Up.
             The router ID is reselected only when the interface address that is selected as the router ID is deleted or changed. The router ID is not reselected in any of the following cases:
             a. The interface is Down.
             b. A loopback interface is configured when the IP address of a non-loopback interface is selected as the router ID.
             c. A larger IP address of an interface is configured.
             2. Each VPN instance selects the router ID from the addresses of the interfaces of the VPN instance according to the preceding rules.
             3. When both the AMB and SMB exist on the router, the system backs up the router ID set through the related command and the router ID that is selected from IP addresses of the interfaces. After the active/standby switchover is performed, the system checks the validity of the router ID selected from the interface addresses. If the router ID is invalid, the system reselects a router ID.";
        }
        leaf router-id-auto-select {
          // NCS drop when statement
          type string;
          // NCS drop must statement
          // NCS drop default statement
          description
            "Enable/disable router ID auto select. If a BGP VPN instance is not enabled to select a router ID, a router ID can be configured for the BGP VPN instance. If no router ID is configured for the BGP VPN instance, the BGP VPN instance inherits the router ID of the public network instance. If a BGP VPN instance is enabled to select a router ID, it uses the address of an interface bound to a VPN as the router ID based on the following rules:

             1. If Loopback interfaces configured with IP addresses exist, the largest IP address among the IP addresses of the Loopback interfaces is selected as the router ID.

             2. If there is no Loopback interface configured with an IP address, the largest IP address among the IP addresses of other interfaces is selected as the router ID, regardless of whether the interface is Up.";
        }
        // NCS drop config false leaf 'effect-router-id'
        container afs {
          description
            "List of BGP address family instances.";
          list af {
            // NCS patched for predictable order
            ordered-by user;
            key "type";
            description
              "Configure BGP address family instance. In public network instances, all types of address families can be configured. In IPv4 VPN instances, the IPv4 unicast, IPv4 flow, and IPv4 labeled unicast address families can be configured. In IPv6 VPN instances, the IPv6 unicast and IPv6 flow address families can be configured. The IPv4 address family in the BGP _public_ VPN instance cannot be deleted.";
            ext:generated-by "system" {
              // NCS drop when statement
              ext:filter "type = 'ipv4uni'";
              description
                "The IPv4 unicast of the BGP public instance is generated automatically when BGP is enabled.";
            }
            leaf type {
              type bgp:ncs_template_af-type;
              description
                "Address family type of a BGP instance.";
            }
            container ipv4-unicast {
              // NCS drop when statement
              description
                "Configure IPv4 unicast options.";
              container common {
                description
                  "Configure IPv4 unicast common options.";
                leaf auto-frr {
                  type string;
                  // NCS drop default statement
                  description
                    "Enable/disable BGP Auto FRR. If IP FRR, VPN FRR, and Auto FRR are all enabled, IP FRR and VPN FRR take precedence over Auto FRR. If a route fails to match the routing policy of IP FRR or VPN FRR, Auto FRR takes effect.";
                }
                leaf tunnel-selector-name {
                  // NCS drop when statement
                  type string;
                  description
                    "Configure a tunnel selector and apply it to the BGP IPv4 unicast, BGP VPNv4 address families and BGP VPNv6 address families so that IPv4,VPNv4 and VPNv6 labeled routes can be iterated to tunnels based on the tunnel selector. By default, no tunnel selector is configured.";
                }
                leaf tunnel-selector-all {
                  // NCS drop when statement
                  type string;
                  // NCS drop default statement
                  description
                    "Enable/disable tunnel selector for labeled, imported, and network segment routes.";
                }
                leaf route-select-delay {
                  type string;
                  units "s";
                  // NCS drop default statement
                  description
                    "Route selection delay.";
                }
                uses ncs_template_reflector-cluster-type;
                uses ncs_template_reflect-type;
                leaf maximum-load-balancing-ibgp {
                  type string;
                  // NCS drop must statement
                  // NCS drop default statement
                  description
                    "Specify the maximum number of equal-cost IBGP routes.";
                }
                leaf maximum-load-balancing-ebgp {
                  type string;
                  // NCS drop must statement
                  // NCS drop default statement
                  description
                    "Specify the maximum number of equal-cost EBGP routes.";
                }
                leaf nexthop-select-depend-type {
                  // NCS drop when statement
                  type ncs_template_select-depend-type;
                  // NCS drop default statement
                  description
                    "Specify the route iteration mode: IP or tunnel. In tunnel mode, the labeled BGP IPv4 route can participate in route selection only after its next hop is iterated to an LSP. In IP
                     mode, the labeled BGP IPv4 route can participate in route selection only after its next hop is iterated to an IP address. By default, the labeled BGP IPv4 route can participate in route selection
                     if its next hop can be iterated to an IP address, regardless of whether the LSP of the next hop exists. This allows the RR that is not enabled with MPLS to forward labeled routes. In non-RR
                     networking or RR networking where the BGP next hop is changed, BGP needs to check whether there is an LSP destined for the next hop. If such an LSP is not found, BGP needs to establish an LSP in
                     advance. If the default setting is adopted, a labeled BGP IPv4 unicast route may be selected prior to LSP establishment. As a result, services are incorrectly switched before LSP establishment and
                     service stability is affected. Therefore, allow route selection only after the labeled BGP IPv4 route is iterated to an LSP.";
                }
                leaf nexthop-inherit-ip-cost {
                  // NCS drop when statement
                  type string;
                  // NCS drop default statement
                  description
                    "Enable/disable next hop iteration mode to IP. Specify the route iteration mode: IP or tunnel. In tunnel mode, the labeled BGP IPv4 route can participate in route selection only after its next hop is iterated to an LSP.";
                }
                leaf nexthop-resolve-aigp {
                  // NCS drop when statement
                  type string;
                  // NCS drop default statement
                  description
                    "Enable/disable route with AIGP attribute for route selection.";
                }
                leaf always-compare-med {
                  type string;
                  // NCS drop default statement
                  description
                    "Enable/disable BGP to compare the MEDs of routes from peers in different ASs in route selection. If
                     there are multiple reachable routes to the same destination, the route with the smallest MED is preferred. Do not use this option unless different ASs use the same IGP and route selection mode.";
                }
                leaf default-med {
                  type string;
                  // NCS drop default statement
                  description
                    "Specify the Multi-Exit-Discriminator (MED) of BGP routes. The value is an integer. This value is valid only for the imported routes and BGP summarized routes on the local router.";
                }
                leaf summary-automatic {
                  type string;
                  // NCS drop default statement
                  description
                    "Enable/disable automatic summarization for imported routes. Manual summarization takes precedence over automatic summarization. After automatic summarization is enabled, BGP summarizes routes based on the natural network segment (for example, 10.1.1.1/24 and 10.2.1.1/24 are summarized into 10.0.0.0/8, a Class A address), and sends only the summarized route to peers. This reduces the number of routes.";
                }
                leaf nexthop-third-party {
                  type string;
                  // NCS drop default statement
                  description
                    "Enable/disable BGP third-party next hop.";
                }
                leaf best-route-bit-error-detection {
                  // NCS drop when statement
                  type string;
                  // NCS drop default statement
                  description
                    "Enable/disable the function to reroute traffic when a bit error event occurs.";
                }
                leaf supernet-unicast-advertise {
                  type string;
                  // NCS drop default statement
                  description
                    "Enable/disable the function to advertise supernet unicast routes.";
                }
                leaf supernet-label-advertise {
                  type string;
                  // NCS drop default statement
                  description
                    "Enable/disable the function to advertise supernet labeled routes.";
                }
                leaf lsp-mtu {
                  type string;
                  // NCS drop default statement
                  description
                    "BGP LSP MTU.";
                }
                leaf label-free-delay {
                  type string;
                  units "s";
                  // NCS drop default statement
                  description
                    "Label Free Delay.";
                }
                leaf bestroute-med-confederation {
                  // NCS drop when statement
                  type string;
                  // NCS drop default statement
                  description
                    "Enable/disable BGP to compare MED value only within the federation.";
                }
                leaf bestroute-as-path-ignore {
                  type string;
                  // NCS drop must statement
                  // NCS drop default statement
                  description
                    "Enable/disable BGP to ignore the AS_Path attribute when selecting the optimal route. By default, BGP uses the AS_Path attribute as one of route selection rules, and a route with a shorter AS_Path is preferred. After bestroute-as-path-ignore is selected, BGP does not compare the AS_Path length.";
                }
                leaf determin-med {
                  type string;
                  // NCS drop default statement
                  description
                    "Enable/disable deterministic MED so that the route selection result is relevant to the sequence in which routes are received.";
                }
                leaf best-external {
                  // NCS drop when statement
                  type string;
                  // NCS drop must statement
                  // NCS drop default statement
                  description
                    "Enable/disable best external route selection.";
                }
                leaf attribute-set-enable {
                  // NCS drop when statement
                  type string;
                  // NCS drop default statement
                  description
                    "Enable/disable the capability of processing attribute set.";
                }
                leaf attribute-set-mode {
                  // NCS drop when statement
                  type bgp:ncs_template_attribute-set-type;
                  // NCS drop default statement
                  description
                    "The processing mode of attribute set.";
                }
                leaf add-path-select-num {
                  // NCS drop when statement
                  type string;
                  // NCS drop must statement
                  description
                    "Number of Add-Path routes.";
                }
                leaf load-balanc-igp-metric-ignore {
                  type string;
                  // NCS drop default statement
                  description
                    "Enable/disable BGP to ignore the IGP cost of each BGP route to the next hop when selecting routes for load balancing. By default, only the routes with the same IGP cost can participate in load balancing.";
                }
                leaf load-balanc-as-path-ignore {
                  type string;
                  // NCS drop must statement
                  // NCS drop default statement
                  description
                    "Enable/disable BGP to ignore the AS_Path of each BGP route to the next hop when selecting routes for load balancing. By default, only the routes with the same AS_Path can participate in load balancing.";
                }
                leaf load-balanc-as-path-relax {
                  type string;
                  // NCS drop must statement
                  // NCS drop default statement
                  description
                    "Enable/disable BGP to ignore comparison of AS_Path attributes with the same length. By default, only the routes with the same AS_Path can participate in load balancing.";
                }
                leaf default-local-preference {
                  type string;
                  // NCS drop default statement
                  description
                    "The local preference of BGP routes.";
                }
                leaf default-route-import {
                  type string;
                  // NCS drop default statement
                  description
                    "Enable/disable the function to import default routes into the BGP routing table. Default-route-imported must be used with import-routes so that default routes can be imported to the BGP routing table. If only import-routes is used, no default routes can be added to the BGP routing table. In addition, default-route-imported can only import the default routes in the routing table into the BGP routing table.";
                }
                leaf routerid-neglect {
                  type string;
                  // NCS drop default statement
                  description
                    "Enable/disable BGP to ignore router IDs when selecting the optimal route. Comparing router IDs is the last resort in route selection. This means that if one optimal route must be selected and no other parameters can be used to break the tie, router IDs can be used. If this option is selected, the first received route will be selected as the optimal route, and BGP will ignore the router ID and peer address in route selection.";
                }
                leaf maximum-load-balancing {
                  type string;
                  // NCS drop must statement
                  // NCS drop default statement
                  description
                    "Specify the maximum number of equal-cost routes in the BGP routing table. The value can be 1 or an integer greater than 1. The value depends on the associated license. Equal-cost BGP routes can be generated for load balancing only when the BGP routes meet the first nine rules of the route-selection policy and have the same AS-Path attribute.";
                }
                leaf reflect-between-client {
                  type string;
                  // NCS drop default statement
                  description
                    "Enable/disable route reflection between clients. If clients of a route reflector (RR) are fully meshed, you can disable route reflection among clients to reduce the cost.";
                }
                leaf import-rib-nexthop-invariable {
                  // NCS drop when statement
                  type string;
                  // NCS drop default statement
                  description
                    "Enable/disable the function to advertise the route without modifying the next-hop.";
                }
                leaf route-relay-tunnel {
                  type string;
                  // NCS drop must statement
                  // NCS drop default statement
                  description
                    "Enable/disable unicast route recursive-lookup tunnel.";
                }
                leaf route-relay-tunnel-selector {
                  // NCS drop when statement
                  type string;
                  description
                    "Unicast route tunnel selector name.";
                }
                leaf route-relay-tunnel-v6-selector {
                  // NCS drop when statement
                  type string;
                  description
                    "Enable/disable unicast route recursive-lookup IPv6 tunnel by tunnel selector name.";
                }
                uses ncs_template_bestroute-med-plus-igp-type;
                uses ncs_template_bestroute-router-id-prior-clusterlist-type;
                leaf bestroute-med-none-as-maximum {
                  type string;
                  // NCS drop default statement
                  description
                    "Enable/disable BGP considers its MED as the largest MED value (4294967295). If a route does not carry MED, BGP considers its MED as the default value (0) during route selection.";
                }
                leaf bestroute-rd-large-first {
                  // NCS drop when statement
                  type string;
                  // NCS drop default statement
                  description
                    "Enable/disable a BGP device to select the route with the largest route distinguisher (RD) during route selection.";
                }
                leaf ebgp-ecmp-nexthop-changed {
                  // NCS drop when statement
                  type string;
                  // NCS drop default statement
                  description
                    "Enable/disable next hop of equal-cost EBGP routes is changed. When equal-cost EBGP routes are load-balancing traffic, the next hop of these routes is changed to a local interface before these routes are advertised. This function can be enabled only when the maximum number of equal-cost EBGP routes is greater than 1.";
                }
                leaf ibgp-ecmp-nexthop-changed {
                  // NCS drop when statement
                  type string;
                  // NCS drop default statement
                  description
                    "Enable/disable next hop of equal-cost IBGP routes is changed. When equal-cost IBGP routes are load-balancing traffic, the next hop of these routes is changed to a local interface before these routes are advertised. This function can be enabled only when the maximum number of equal-cost IBGP routes is greater than 1.";
                }
                leaf ecmp-nexthop-changed {
                  // NCS drop when statement
                  type string;
                  // NCS drop default statement
                  description
                    "Enable/disable next hop of equal-cost routes is changed. When equal-cost BGP routes are load-balancing traffic, the next hop of these routes is changed to a local interface before these routes are advertised. This function can be enabled only when the maximum number of equal-cost BGP routes is greater than 1.";
                }
                leaf maximum-load-balancing-eibgp {
                  // NCS drop when statement
                  type string;
                  // NCS drop must statement
                  description
                    "Specify the maximum number of equal-cost EBGP routes and IBGP routes. After the attribute is set, load balancing is performed among equal-cost BGP VPN routes, regardless of the route type, EBGP or IBGP.";
                }
                leaf eibgp-ecmp-nexthop-changed {
                  // NCS drop when statement
                  type string;
                  // NCS drop default statement
                  description
                    "Enable/disable next hop of equal-cost EBGP and IBGP routes is changed. When equal-cost EBGP and IBGP routes are load-balancing traffic, the next hop of these routes is changed to a local interface before these routes are advertised.";
                }
                leaf load-balancing-eibgp-enable {
                  // NCS drop when statement
                  type string;
                  // NCS drop must statement
                  // NCS drop default statement
                  description
                    "Enable/disable EIBGP route load balancing.";
                }
                leaf ext-community-change {
                  type string;
                  // NCS drop default statement
                  description
                    "Enable/disable the function to change the extended community attribute.";
                }
                leaf active-route-advertise {
                  type string;
                  // NCS drop default statement
                  description
                    "Enable/disable the function to advertise the optimal routes in the RM module to peers.";
                }
                leaf nexthop-priority {
                  type ncs_template_nexthop-priority-address-type;
                  description
                    "Routes with next-hop IPv4 addresses and routes with next-hop IPv6 addresses coexist. If the next-hop address type is set to IPv4, routes with next-hop IPv4 addresses have a higher priority. If the next-hop address type is set to IPv6, routes with next-hop IPv6 addresses have a higher priority.";
                }
                leaf ebgp-interface-sensitive {
                  type string;
                  // NCS drop default statement
                  description
                    "Enable/disable the function of EBGP interface fast sensing. If this function is enabled, the sessions of directly connected EBGP peers are immediately cleared from the associated interface when the interface becomes down.";
                }
                uses ncs_template_group-origin-as-validation-type;
                leaf advertise-route-mode {
                  // NCS drop when statement
                  type ncs_template_bgp-advertise-route-mode;
                  // NCS drop default statement
                  description
                    "VPN advertise route mode.";
                }
                leaf reoriginate-route {
                  // NCS drop when statement
                  type string;
                  // NCS drop default statement
                  description
                    "Enable/disable route reorigination.";
                }
                leaf rpd-policy-change-delay {
                  // NCS drop when statement
                  type string;
                  // NCS drop default statement
                  description
                    "Specify the delay time of RPD policy's change.";
                }
              }
              uses ncs_template_bgp-route-preference-options;
              container nexthop-recursive-lookup {
                description
                  "Configure next hop iteration.";
                container common {
                  description
                    "Configure next hop iteration common options.";
                  uses ncs_template_nexthop-recursive-lookup-restrain;
                  uses ncs_template_nexthop-recursive-lookup-default-route;
                }
                uses ncs_template_nexthop-recursive-lookup-delay;
              }
              container import-routes {
                description
                  "List of imported routes.";
                list import-route {
                  // NCS patched for predictable order
                  ordered-by user;
                  key "protocol process-id";
                  description
                    "Configure route import. Routes of other protocol types can be imported by BGP. By default, BGP does not import routes of other protocol types.";
                  leaf protocol {
                    type bgp:ncs_template_ipv4-import-route-protocol-type;
                    description
                      "Routing protocol from which routes can be imported.";
                  }
                  leaf process-id {
                    type string;
                    description
                      "Process ID of an imported routing protocol. The process ID is 0, if the imported routing protocol is direct routes, static routes, UNRs, or OP-routes. The process ID must be specified range from 1 to 4294967295, if the imported routing protocol is RIP, OSPF, ISIS.";
                  }
                  leaf med {
                    type string;
                    description
                      "Specifies the MED metric of the imported route.";
                  }
                  choice policy-type {
                    description
                      "Set route policy or filter.";
                    case rtp-ref {
                      description
                        "Route policy.";
                      leaf policy-name {
                        type string;
                        description
                          "When routes are imported from other routing protocols, the route-policy filter can be used to filter the routes and change route attributes.";
                      }
                    }
                    case xpl-ref {
                      description
                        "Route filter.";
                      uses ncs_template_route-filter-type;
                    }
                  }
                  leaf non-relay-tunnel {
                    // NCS drop when statement
                    type string;
                    // NCS drop default statement
                    description
                      "Enable/disable imported route relay a tunnel.";
                  }
                }
              }
              container aggregate-routes {
                description
                  "List of summarized routes.";
                list aggregate-route {
                  // NCS patched for predictable order
                  ordered-by user;
                  key "address mask-length";
                  description
                    "Configure a summarized route in the BGP routing table. The local outbound interface of the summarized route is Null0. When another router receives the route, the route adds an outbound interface to the route. If the Origin attributes of the specific routes for the route summarization are different, the Origin attribute of the summarized route is that with the highest priority. Origin attributes are arranged in the priority order of complete > egp > igp. A summarized route carries the community attribute of each specific route.";
                  // NCS expand uses statement
                  leaf address {
                    type string;
                    description
                      "Specify the IPv4 address or IPv6 address of a summarized route. Only IPv4 summarized routes can be configured in the IPv4 address family and only IPv6 summarized routes can be configured in the IPv6 address family.";
                    // NCS drop must statement
                  }
                  leaf mask-length {
                    type string;
                    description
                      "Specify the mask length of a summarized address.";
                    // NCS drop must statement
                  }
                  leaf as-set {
                    type string;
                    // NCS drop default statement
                    description
                      "Enable/disable the generation of routes with the AS-SET attribute. This option can be used to create a summarized route. The AS_Path attribute of the summarized route contains the AS-Path attributes of the specific routes for the route summarization. Exercise caution when using this option if multiple AS_Paths need to be summarized to prevent route flapping.";
                  }
                  leaf detail-suppressed {
                    type string;
                    // NCS drop default statement
                    description
                      "Enable/disable detail-suppressed. Suppress the advertisement of specific routes for the route summarization. Only the summarized route is advertised.";
                  }
                  choice policy-type {
                    description
                      "Set route policy or filter.";
                    case rtp-ref {
                      description
                        "Route policy.";
                      leaf attribute-policy {
                        type string;
                        description
                          "Specify an attribute of summarized routes. If apply as-path is used to configure the AS_Path attribute that is used in the route Summarization policy, and the as-set keyword is set, the AS_Path attribute in the policy does not take effect. This parameter and any of the following parameters overwrite each other: suppressFilter, originFilter, and attributeFilter.";
                      }
                      leaf origin-policy {
                        type string;
                        description
                          "Specify the name of a policy for generating summarized routes. Summarized routes are generated only when the routes match route-policy. This parameter and any of the following parameters overwrite each other: suppressFilter, originFilter, and attributeFilter.";
                      }
                      leaf suppress-policy {
                        type string;
                        description
                          "Specify a policy for suppressing the advertisement of specified routes. The routes matching the policy are not advertised, and other routes are advertised. This parameter and any of the following parameters overwrite each other: suppressFilter, originFilter, and attributeFilter.";
                      }
                    }
                    case xpl-ref {
                      description
                        "Route filter.";
                      leaf attribute-filter-name {
                        type string;
                        description
                          "Specify a route-filter name.";
                      }
                      leaf attribute-filter-parameter {
                        // NCS drop when statement
                        type xpl:ncs_template_filter-parameter-type;
                        description
                          "Specify a route-filter parameter.";
                      }
                      leaf origin-filter-name {
                        type string;
                        description
                          "Specify a route-filter name.";
                      }
                      leaf origin-filter-parameter {
                        // NCS drop when statement
                        type xpl:ncs_template_filter-parameter-type;
                        description
                          "Specify a route-filter parameter.";
                      }
                      leaf suppress-filter-name {
                        type string;
                        description
                          "Specify a route-filter name.";
                      }
                      leaf suppress-filter-parameter {
                        // NCS drop when statement
                        type xpl:ncs_template_filter-parameter-type;
                        description
                          "Specify a route-filter parameter.";
                      }
                    }
                  }
                }
              }
              container aggregate-default-route {
                description
                  "Configure aggregate default route.";
                leaf origin-ip-prefix {
                  type string;
                  description
                    "Specify the name of an IPv4 prefix list for a summary default route. Only the name of an IPv4 prefix list can be configured in a BGP IPv4 address family.";
                }
                leaf attribute-policy {
                  // NCS drop when statement
                  type string;
                  description
                    "Specify an attribute policy of a summary default route.";
                }
              }
              container network-routes {
                description
                  "List of network routes.";
                list network-route {
                  // NCS patched for predictable order
                  ordered-by user;
                  key "address mask-length";
                  description
                    "Configure a network route in the BGP routing table.";
                  uses ncs_template_network-route-ipv4;
                  leaf non-relay-tunnel {
                    // NCS drop when statement
                    type string;
                    // NCS drop default statement
                    description
                      "Enable/disable imported route relay a tunnel.";
                  }
                }
              }
              container advertise-route-to-evpns {
                // NCS drop when statement
                description
                  "Configure advertise route protocol.";
                uses ncs_template_advertise-route-to-evpn-type;
              }
              container import-ribs {
                description
                  "List of imported RIBs configuration.";
                list import-rib {
                  // NCS patched for predictable order
                  ordered-by user;
                  key "source-vpn source-address-family";
                  description
                    "Configure imported RIBs.";
                  leaf source-vpn {
                    type string;
                    // NCS drop must statement
                    description
                      "Source VPN name.";
                  }
                  leaf source-address-family {
                    type bgp:ncs_template_import-rib-ipv4-safi-type;
                    description
                      "Source address family type.";
                  }
                  leaf valid-route {
                    type string;
                    // NCS drop default statement
                    description
                      "Enable/disable imported valid route.";
                  }
                  leaf include-label-route {
                    // NCS drop when statement
                    type string;
                    // NCS drop default statement
                    description
                      "Enable/disable imported include label route.";
                  }
                  // NCS expand uses statement
                  choice policy-type {
                    case rtp-ref {
                      description
                        "Specify the route policy.";
                      leaf policy-name {
                        type string;
                        description
                          "Specify the route policy.";
                      }
                    }
                    case xpl-ref {
                      description
                        "Route filter.";
                      uses ncs_template_route-filter-type;
                    }
                    description
                      "Specify the route-policy or filter for imported RIBs.";
                  }
                }
              }
              uses ncs_template_ipv4-import-filter-protocol-type;
              container export-filter-policys {
                description
                  "List of filtering policies.";
                list export-filter-policy {
                  // NCS patched for predictable order
                  ordered-by user;
                  key "protocol process-id";
                  description
                    "Apply a filtering policy. It is used to filter the routes to be advertised to the peer. By default, routes are not filtered.";
                  leaf protocol {
                    type bgp:ncs_template_ipv4-export-filter-protocol-type;
                    description
                      "Specify the name of a routing protocol. The routing protocol takes effect only on the routes to be advertised. The IPv4 address family supports the direct, IS-IS, OSPF, RIP, and static routing protocols. The IPv6 unicast address family of a public network instance supports the direct, IS-IS, OSPFv3, RIPng, and static routing protocols. The IPv6 address family of a VPNv6 instance supports the direct, IS-IS, RIPng, and static routing protocols.";
                  }
                  leaf process-id {
                    type string;
                    description
                      "Specify the process ID required to be matched. The value is an integer ranging from 0 to 4294967295. If direct or static routes need to be filtered, no process ID is required.";
                  }
                  uses ncs_template_ipv4-filter-protocol-policy-choice-type;
                }
              }
              container lsp-options {
                description
                  "Configure parameters for lsp.";
                uses ncs_template_safi-lsp-options;
                leaf maximum-load-balancing-transit {
                  // NCS drop when statement
                  type string;
                  // NCS drop default statement
                  description
                    "Maximum number of transit LSPs for load balancing.";
                }
                leaf unicast-rt-label-advertise {
                  // NCS drop when statement
                  type string;
                  // NCS drop default statement
                  description
                    "Enable/disable a device to convert received IPv4 public network unicast routes to labeled routes by allocating one BGP label to each route and advertise the labeled routes to peers with the labeled route exchange capability.";
                }
                leaf unicast-rt-label-advertise-popgo {
                  // NCS drop when statement
                  type string;
                  // NCS drop default statement
                  description
                    "Enable/disable a device to convert received IPv4 public network unicast routes to labeled routes by adding a BGP label to each route and advertise the labeled routes to peers with the labeled route exchange capability. If the IP address of an outbound interface is reachable but no LSP is reachable, traffic is forwarded through the outbound interface and a specific next hop, during which the label POPGO action is performed.";
                }
                leaf lsp-operation {
                  // NCS drop when statement
                  type ncs_template_lsp-operation-type;
                  // NCS drop default statement
                  description
                    "Label operation type.";
                }
                uses ncs_template_ingress-choice-policy-set;
              }
              container segment-routing-ipv6 {
                description
                  "Configure BGP segment-routing IPv6.";
                leaf srv6-best-effort-enable {
                  type empty;
                  description
                    "Enable SRv6 BE iteration.";
                }
                leaf srv6-traffic-engineer-enable {
                  type empty;
                  description
                    "Enable SRv6 TE iteration.";
                }
              }
              uses ncs_template_vrf-af-dampening-routes;
              uses bgp:ncs_template_slow-peer-type;
              // NCS expand uses statement
              container routing-table-rib-only {
                description
                  "Configure disable route delivery to the IP routing table.";
                leaf enable {
                  type string;
                  // NCS drop default statement
                  description
                    "Enable/disable prevent BGP routes from being added to the IP routing table.";
                  // NCS drop must statement
                }
                choice policy-type {
                  description
                    "Set route policy or filter.";
                  case rtp-ref {
                    description
                      "Route policy.";
                    leaf policy-name {
                      // NCS drop when statement
                      type string;
                      description
                        "When routes are imported from other routing protocols, the route-policy filter can be used to filter the routes and change route attributes.";
                    }
                  }
                  case xpl-ref {
                    description
                      "Route filter.";
                    leaf filter-name {
                      // NCS drop when statement
                      type string;
                      description
                        "Specify a route-filter name.";
                    }
                    leaf filter-parameter {
                      // NCS drop when statement
                      type xpl:ncs_template_filter-parameter-type;
                      description
                        "Specify a route-filter parameter.";
                    }
                  }
                }
              }
              uses ncs_template_qos-local-id-type;
            }
            container ipv6-unicast {
              // NCS drop when statement
              description
                "Configure IPv6 unicast options.";
              container common {
                description
                  "Configure IPv6 unicast common options.";
                leaf auto-frr {
                  type string;
                  // NCS drop default statement
                  description
                    "Enable/disable BGP auto FRR. If IP FRR, VPN FRR, and Auto FRR are all enabled, IP FRR and VPN FRR take precedence over Auto FRR. If a route fails to match the routing policy of IP FRR or VPN FRR, Auto FRR takes effect.";
                }
                leaf route-select-delay {
                  type string;
                  units "s";
                  // NCS drop default statement
                  description
                    "Route selection delay.";
                }
                uses ncs_template_reflector-cluster-type;
                uses ncs_template_reflect-type;
                leaf maximum-load-balancing-ibgp {
                  type string;
                  // NCS drop default statement
                  description
                    "Specify the maximum number of equal-cost IBGP routes.";
                }
                leaf maximum-load-balancing-ebgp {
                  type string;
                  // NCS drop default statement
                  description
                    "Specify the maximum number of equal-cost EBGP routes.";
                }
                leaf explicit-null {
                  // NCS drop when statement
                  type string;
                  // NCS drop must statement
                  // NCS drop default statement
                  description
                    "Enable/disable the function to explicit null. After 6PE routes are enabled to share a single label, all routes share the explicit-null label 2 when the 6PE sends IPv6 routes to its 6PE peer. This can save label resources on the 6PE. Therefore, when there are a large number of IPv6 routes that need to be sent, the problem that the IPv6 routes cannot be forwarded due to the shortage of labels can be avoided.";
                }
                leaf lsp-operation {
                  // NCS drop when statement
                  type ncs_template_lsp-operation-type;
                  // NCS drop must statement
                  // NCS drop default statement
                  description
                    "Label operation mode.";
                }
                leaf nexthop-select-depend-type {
                  // NCS drop when statement
                  type ncs_template_select-depend-type;
                  // NCS drop default statement
                  description
                    "Specify the route iteration mode: IP or tunnel. In tunnel mode, the labeled BGP IPv4 route can participate in route selection only after its next hop is iterated to an LSP. In IP
                     mode, the labeled BGP IPv4 route can participate in route selection only after its next hop is iterated to an IP address. By default, the labeled BGP IPv4 route can participate in route selection
                     if its next hop can be iterated to an IP address, regardless of whether the LSP of the next hop exists. This allows the RR that is not enabled with MPLS to forward labeled routes. In non-RR
                     networking or RR networking where the BGP next hop is changed, BGP needs to check whether there is an LSP destined for the next hop. If such an LSP is not found, BGP needs to establish an LSP in
                     advance. If the default setting is adopted, a labeled BGP IPv4 unicast route may be selected prior to LSP establishment. As a result, services are incorrectly switched before LSP establishment and
                     service stability is affected. Therefore, allow route selection only after the labeled BGP IPv4 route is iterated to an LSP.";
                }
                leaf nexthop-inherit-ip-cost {
                  // NCS drop when statement
                  type string;
                  // NCS drop default statement
                  description
                    "Enable/disable next hop iteration mode to IP. Specify the route iteration mode: IP or tunnel. In tunnel mode, the labeled BGP IPv4 route can participate in route selection only after its next hop is iterated to an LSP.";
                }
                leaf nexthop-resolve-aigp {
                  // NCS drop when statement
                  type string;
                  // NCS drop default statement
                  description
                    "Enable/disable route with AIGP attribute for route selection.";
                }
                leaf always-compare-med {
                  type string;
                  // NCS drop default statement
                  description
                    "Enable/disable BGP to compare the MEDs of routes from peers in different ASs in route selection. If
                     there are multiple reachable routes to the same destination, the route with the smallest MED is preferred. Do not use this option unless different ASs use the same IGP and route selection mode.";
                }
                leaf default-med {
                  type string;
                  // NCS drop default statement
                  description
                    "Specify the Multi-Exit-Discriminator (MED) of BGP routes. The value is an integer. This value is valid only for the imported routes and BGP summarized routes on the local router.";
                }
                leaf nexthop-third-party {
                  type string;
                  // NCS drop default statement
                  description
                    "Enable/disable BGP third-party next hop.";
                }
                leaf supernet-unicast-advertise {
                  type string;
                  // NCS drop default statement
                  description
                    "Enable/disable advertise supernet unicast routes.";
                }
                leaf bestroute-med-confederation {
                  // NCS drop when statement
                  type string;
                  // NCS drop default statement
                  description
                    "Enable/disable BGP to compare Med value only within the federation.";
                }
                leaf bestroute-as-path-ignore {
                  type string;
                  // NCS drop must statement
                  // NCS drop default statement
                  description
                    "Enable/disable BGP to ignore the AS_Path attribute when selecting the optimal route. By default, BGP uses the AS_Path attribute as one of route selection rules, and a route with a shorter AS_Path is preferred. After bestroute-as-path-ignore is selected, BGP does not compare the AS_Path length.";
                }
                leaf determin-med {
                  type string;
                  // NCS drop default statement
                  description
                    "Enable/disable deterministic MED so that the route selection result is relevant to the sequence in which routes are received.";
                }
                leaf best-external {
                  // NCS drop when statement
                  type string;
                  // NCS drop must statement
                  // NCS drop default statement
                  description
                    "Enable/disable best external route selection.";
                }
                leaf attribute-set-enable {
                  // NCS drop when statement
                  type string;
                  // NCS drop default statement
                  description
                    "Enable/disable the capability of processing attribute set.";
                }
                leaf attribute-set-mode {
                  // NCS drop when statement
                  type bgp:ncs_template_attribute-set-type;
                  // NCS drop default statement
                  description
                    "The processing mode of attribute set.";
                }
                leaf add-path-select-num {
                  // NCS drop when statement
                  type string;
                  // NCS drop must statement
                  description
                    "Number of add-path routes.";
                }
                leaf load-balanc-igp-metric-ignore {
                  type string;
                  // NCS drop default statement
                  description
                    "Enable/disable BGP to ignore the IGP cost of each BGP route to the next hop when selecting routes for load balancing. By default, only the routes with the same IGP cost can participate in load balancing.";
                }
                leaf load-balanc-as-path-ignore {
                  type string;
                  // NCS drop must statement
                  // NCS drop default statement
                  description
                    "Enable/disable BGP to ignore the AS_Path of each BGP route to the next hop when selecting routes for load balancing. By default, only the routes with the same AS_Path can participate in load balancing.";
                }
                leaf load-balanc-as-path-relax {
                  type string;
                  // NCS drop must statement
                  // NCS drop default statement
                  description
                    "Enable/disable BGP to ignore comparison of AS_Path attributes with the same length. By default, only the routes with the same AS_Path can participate in load balancing.";
                }
                leaf default-local-preference {
                  type string;
                  // NCS drop default statement
                  description
                    "The local preference of BGP routes.";
                }
                leaf default-route-import {
                  type string;
                  // NCS drop default statement
                  description
                    "Enable/disable the function to import default routes into the BGP routing table. Default-route-imported must be used with import-routes so that default routes can be imported to the BGP routing table. If only import-routes is used, no default routes can be added to the BGP routing table. In addition, default-route-imported can only import the default routes in the routing table into the BGP routing table.";
                }
                leaf routerid-neglect {
                  type string;
                  // NCS drop default statement
                  description
                    "Enable/disable BGP to ignore router IDs when selecting the optimal route. Comparing router IDs is the last resort in route selection. This means that if one optimal route must be selected and no other parameters can be used to break the tie, router IDs can be used. If this option is selected, the first received route will be selected as the optimal route, and BGP will ignore the router ID and peer address in route selection.";
                }
                leaf maximum-load-balancing {
                  type string;
                  // NCS drop default statement
                  description
                    "Specify the maximum number of equal-cost routes in the BGP routing table. The value depends on the associated license. Equal-cost BGP routes can be generated for load balancing only when the BGP routes meet the first nine rules of the route-selection policy and have the same AS-Path attribute.";
                }
                leaf reflect-between-client {
                  type string;
                  // NCS drop default statement
                  description
                    "Enable/disable route reflection between clients. If clients of a route reflector (RR) are fully meshed, you can disable route reflection among clients to reduce the cost.";
                }
                leaf best-route-bit-error-detection {
                  // NCS drop when statement
                  type string;
                  // NCS drop default statement
                  description
                    "Enable/disable the function to reroute traffic when a bit error event occurs.";
                }
                leaf import-rib-nexthop-invariable {
                  // NCS drop when statement
                  type string;
                  // NCS drop default statement
                  description
                    "Enable/disable advertise the route without modifying the next-hop.";
                }
                leaf route-relay-tunnel-v4 {
                  type string;
                  // NCS drop default statement
                  description
                    "Enable/disable unicast-route recursive-lookup tunnel.";
                }
                leaf route-relay-tunnel-v4-selector {
                  // NCS drop when statement
                  type string;
                  description
                    "Unicast route tunnel selector name.";
                }
                leaf route-relay-tunnel-v6-selector {
                  // NCS drop when statement
                  type string;
                  description
                    "Enable/disable unicast route recursive-lookup IPv6 tunnel by tunnel selector name.";
                }
                uses ncs_template_bestroute-med-plus-igp-type;
                uses ncs_template_bestroute-router-id-prior-clusterlist-type;
                leaf bestroute-med-none-as-maximum {
                  type string;
                  // NCS drop default statement
                  description
                    "Enable/disable BGP considers its MED as the largest MED value (4294967295). If a route does not carry MED, BGP considers its MED as the default value (0) during route selection.";
                }
                leaf bestroute-rd-large-first {
                  // NCS drop when statement
                  type string;
                  // NCS drop default statement
                  description
                    "Enable/disable a BGP device to select the route with the largest route distinguisher (RD) during route selection.";
                }
                leaf nexthop-priority {
                  // NCS drop when statement
                  type ncs_template_nexthop-priority-address-type;
                  description
                    "In the VRF instance, routes with next-hop IPv4 addresses and routes with next-hop IPv6 addresses coexist. If the next-hop address type is set to IPv4, routes with next-hop IPv4 addresses have a higher priority. If the next-hop address type is set to IPv6, routes with next-hop IPv6 addresses have a higher priority.";
                }
                leaf ebgp-ecmp-nexthop-changed {
                  // NCS drop when statement
                  type string;
                  // NCS drop default statement
                  description
                    "Enable/disable next hop of equal-cost EBGP routes is changed. Enable/disable next hop of equal-cost EBGP routes is changed. When equal-cost EBGP routes are load-balancing traffic, the next hop of these routes is changed to a local interface before these routes are advertised. This function can be enabled only when the maximum number of equal-cost EBGP routes is greater than 1.";
                }
                leaf ibgp-ecmp-nexthop-changed {
                  // NCS drop when statement
                  type string;
                  // NCS drop default statement
                  description
                    "Enable/disable next hop of equal-cost IBGP routes is changed. When equal-cost IBGP routes are load-balancing traffic, the next hop of these routes is changed to a local interface before these routes are advertised. This function can be enabled only when the maximum number of equal-cost IBGP routes is greater than 1.";
                }
                leaf ecmp-nexthop-changed {
                  // NCS drop when statement
                  type string;
                  // NCS drop default statement
                  description
                    "Enable/disable next hop of equal-cost routes is changed. When equal-cost BGP routes are load-balancing traffic, the next hop of these routes is changed to a local interface before these routes are advertised. This function can be enabled only when the maximum number of equal-cost BGP routes is greater than 1.";
                }
                leaf maximum-load-balancing-eibgp {
                  // NCS drop when statement
                  type string;
                  // NCS drop must statement
                  description
                    "Specify the maximum number of equal-cost EBGP routes and IBGP routes. After the attribute is set, load balancing is performed among equal-cost BGP VPN routes, regardless of the route type, EBGP or IBGP.";
                }
                leaf eibgp-ecmp-nexthop-changed {
                  // NCS drop when statement
                  type string;
                  // NCS drop default statement
                  description
                    "Enable/disable next hop of equal-cost EBGP and IBGP routes is changed. When equal-cost EBGP and IBGP routes are load-balancing traffic, the next hop of these routes is changed to a local interface before these routes are advertised.";
                }
                leaf load-balancing-eibgp-enable {
                  // NCS drop when statement
                  type string;
                  // NCS drop must statement
                  // NCS drop default statement
                  description
                    "Enable/disable EIBGP route load balancing.";
                }
                leaf ext-community-change {
                  type string;
                  // NCS drop default statement
                  description
                    "Enable/disable the function to change the extended community attribute.";
                }
                leaf active-route-advertise {
                  type string;
                  // NCS drop default statement
                  description
                    "Enable/disable the function to advertise the optimal routes in the RM module to peers.";
                }
                leaf ebgp-interface-sensitive {
                  type string;
                  // NCS drop default statement
                  description
                    "Enable/disable the function of EBGP interface fast sensing. If this function is enabled, the sessions of directly connected EBGP peers are immediately cleared from the associated interface when the interface becomes down.";
                }
                uses ncs_template_group-origin-as-validation-type;
                leaf advertise-route-mode {
                  // NCS drop when statement
                  type ncs_template_bgp-advertise-route-mode;
                  // NCS drop default statement
                  description
                    "VPN advertise route mode.";
                }
              }
              uses ncs_template_bgp-route-preference-options;
              container nexthop-recursive-lookup {
                description
                  "Configure next hop iteration.";
                container common {
                  description
                    "Configure next hop iteration common options.";
                  uses ncs_template_nexthop-recursive-lookup-restrain;
                  uses ncs_template_nexthop-recursive-lookup-default-route;
                }
                uses ncs_template_nexthop-recursive-lookup-delay;
              }
              container import-routes {
                description
                  "List of imported routes.";
                list import-route {
                  // NCS patched for predictable order
                  ordered-by user;
                  key "protocol process-id";
                  description
                    "Configure route import. Routes of other protocol types can be imported by BGP. By default, BGP does not import routes of other protocol types.";
                  leaf protocol {
                    type bgp:ncs_template_ipv6-import-route-protocol-type;
                    description
                      "Routing protocol from which routes can be imported.";
                  }
                  leaf process-id {
                    type string;
                    description
                      "Process ID of an imported routing protocol. The process ID is 0, if the imported routing protocol is direct routes, static routes, UNRs, or OP-routes. The process ID must be specified range from 1 to 4294967295, if the imported routing protocol is ISIS, RIPng, or OSPFv3.";
                  }
                  leaf med {
                    type string;
                    description
                      "Specifies the MED metric of the imported route.";
                  }
                  choice policy-type {
                    description
                      "Set route policy or filter.";
                    case rtp-ref {
                      description
                        "Route policy.";
                      leaf policy-name {
                        type string;
                        description
                          "When routes are imported from other routing protocols, the route-policy filter can be used to filter the routes and change route attributes.";
                      }
                    }
                    case xpl-ref {
                      description
                        "Route filter.";
                      uses ncs_template_route-filter-type;
                    }
                  }
                }
              }
              container aggregate-routes {
                description
                  "List of summarized routes.";
                list aggregate-route {
                  // NCS patched for predictable order
                  ordered-by user;
                  key "address mask-length";
                  description
                    "Configure a summarized route in the BGP routing table. The local outbound interface of the summarized route is Null0. When another router receives the route, the route adds an outbound interface to the route. By default, route summarization is not performed. If the Origin attributes of the specific routes for the route summarization are different, the Origin attribute of the summarized route is that with the highest priority. Origin attributes are arranged in the priority order of complete > egp > igp. A summarized route carries the community attribute of each specific route.";
                  // NCS expand uses statement
                  leaf address {
                    type string;
                    description
                      "Specify the IPv4 address or IPv6 address of a summarized route. Only IPv4 summarized routes can be configured in the IPv4 address family and only IPv6 summarized routes can be configured in the IPv6 address family.";
                    // NCS drop must statement
                  }
                  leaf mask-length {
                    type string;
                    description
                      "Specify the mask length of a summarized address.";
                    // NCS drop must statement
                  }
                  leaf as-set {
                    type string;
                    // NCS drop default statement
                    description
                      "Enable/disable the generation of routes with the AS-SET attribute. This option can be used to create a summarized route. The AS_Path attribute of the summarized route contains the AS-Path attributes of the specific routes for the route summarization. Exercise caution when using this option if multiple AS_Paths need to be summarized to prevent route flapping.";
                  }
                  leaf detail-suppressed {
                    type string;
                    // NCS drop default statement
                    description
                      "Enable/disable detail-suppressed. Suppress the advertisement of specific routes for the route summarization. Only the summarized route is advertised.";
                  }
                  choice policy-type {
                    description
                      "Set route policy or filter.";
                    case rtp-ref {
                      description
                        "Route policy.";
                      leaf attribute-policy {
                        type string;
                        description
                          "Specify an attribute of summarized routes. If apply as-path is used to configure the AS_Path attribute that is used in the route Summarization policy, and the as-set keyword is set, the AS_Path attribute in the policy does not take effect. This parameter and any of the following parameters overwrite each other: suppressFilter, originFilter, and attributeFilter.";
                      }
                      leaf origin-policy {
                        type string;
                        description
                          "Specify the name of a policy for generating summarized routes. Summarized routes are generated only when the routes match route-policy. This parameter and any of the following parameters overwrite each other: suppressFilter, originFilter, and attributeFilter.";
                      }
                      leaf suppress-policy {
                        type string;
                        description
                          "Specify a policy for suppressing the advertisement of specified routes. The routes matching the policy are not advertised, and other routes are advertised. This parameter and any of the following parameters overwrite each other: suppressFilter, originFilter, and attributeFilter.";
                      }
                    }
                    case xpl-ref {
                      description
                        "Route filter.";
                      leaf attribute-filter-name {
                        type string;
                        description
                          "Specify a route-filter name.";
                      }
                      leaf attribute-filter-parameter {
                        // NCS drop when statement
                        type xpl:ncs_template_filter-parameter-type;
                        description
                          "Specify a route-filter parameter.";
                      }
                      leaf origin-filter-name {
                        type string;
                        description
                          "Specify a route-filter name.";
                      }
                      leaf origin-filter-parameter {
                        // NCS drop when statement
                        type xpl:ncs_template_filter-parameter-type;
                        description
                          "Specify a route-filter parameter.";
                      }
                      leaf suppress-filter-name {
                        type string;
                        description
                          "Specify a route-filter name.";
                      }
                      leaf suppress-filter-parameter {
                        // NCS drop when statement
                        type xpl:ncs_template_filter-parameter-type;
                        description
                          "Specify a route-filter parameter.";
                      }
                    }
                  }
                }
              }
              container aggregate-default-route {
                description
                  "Configure aggregate default route.";
                leaf origin-ipv6-prefix {
                  type string;
                  description
                    "Specify the name of an IPv6 prefix list for a summary default route. Only the name of an IPv6 prefix list can be configured in a BGP IPv6 address family.";
                }
                leaf attribute-policy {
                  // NCS drop when statement
                  type string;
                  description
                    "Specify an attribute policy of a summary default route.";
                }
              }
              container network-routes {
                description
                  "List of network routes.";
                list network-route {
                  // NCS patched for predictable order
                  ordered-by user;
                  key "address mask-length";
                  description
                    "Configure a network route in the BGP routing table.";
                  uses ncs_template_network-route-ipv6;
                }
              }
              container advertise-route-to-evpns {
                // NCS drop when statement
                description
                  "Configure advertise route protocol.";
                uses ncs_template_advertise-route-to-evpn-type;
              }
              container import-ribs {
                description
                  "List of imported RIBs configuration.";
                list import-rib {
                  // NCS patched for predictable order
                  ordered-by user;
                  key "source-vpn source-address-family";
                  description
                    "Configure imported RIBs.";
                  leaf source-vpn {
                    type string;
                    // NCS drop must statement
                    description
                      "Source VPN name for imported RIBs.";
                  }
                  leaf source-address-family {
                    type bgp:ncs_template_import-rib-ipv6-safi-type;
                    description
                      "Source address family type for imported RIBs.";
                  }
                  leaf valid-route {
                    type string;
                    // NCS drop default statement
                    description
                      "Enable/disable imported valid route.";
                  }
                  leaf include-label-route {
                    type string;
                    // NCS drop default statement
                    description
                      "Enable/disable imported include label route.";
                  }
                  // NCS expand uses statement
                  choice policy-type {
                    case rtp-ref {
                      description
                        "Specify the route policy.";
                      leaf policy-name {
                        type string;
                        description
                          "Specify the route policy.";
                      }
                    }
                    case xpl-ref {
                      description
                        "Route filter.";
                      uses ncs_template_route-filter-type;
                    }
                    description
                      "Specify the route-policy or filter for imported RIBs.";
                  }
                }
              }
              container segment-routing-ipv6 {
                // NCS drop when statement
                description
                  "Configure BGP segment-routing IPv6.";
                leaf srv6-best-effort-enable {
                  type empty;
                  description
                    "Enable SRv6 BE iteration.";
                }
                leaf srv6-traffic-engineer-enable {
                  type empty;
                  description
                    "Enable SRv6 TE iteration.";
                }
              }
              uses ncs_template_vrf-af-dampening-routes;
              uses ncs_template_ipv6-import-filter-protocol-type;
              uses ncs_template_ipv6-export-filter-protocol-type;
              uses bgp:ncs_template_slow-peer-type;
              // NCS expand uses statement
              container routing-table-rib-only {
                description
                  "Configure disable route delivery to the IP routing table.";
                leaf enable {
                  type string;
                  // NCS drop default statement
                  description
                    "Enable/disable prevent BGP routes from being added to the IP routing table.";
                  // NCS drop must statement
                }
                choice policy-type {
                  description
                    "Set route policy or filter.";
                  case rtp-ref {
                    description
                      "Route policy.";
                    leaf policy-name {
                      // NCS drop when statement
                      type string;
                      description
                        "When routes are imported from other routing protocols, the route-policy filter can be used to filter the routes and change route attributes.";
                    }
                  }
                  case xpl-ref {
                    description
                      "Route filter.";
                    leaf filter-name {
                      // NCS drop when statement
                      type string;
                      description
                        "Specify a route-filter name.";
                    }
                    leaf filter-parameter {
                      // NCS drop when statement
                      type xpl:ncs_template_filter-parameter-type;
                      description
                        "Specify a route-filter parameter.";
                    }
                  }
                }
              }
              uses ncs_template_ipv6-qos-local-id-type;
            }
            container ipv4-vpn {
              // NCS drop when statement
              description
                "Configure IPv4 VPNv4 options.";
              uses ncs_template_vpn-target-type;
              uses ncs_template_reflector-cluster-type;
              uses ncs_template_reflect-type;
              leaf auto-frr {
                type string;
                // NCS drop default statement
                description
                  "Enable/disable BGP Auto FRR. If IP FRR, VPN FRR, and Auto FRR are all enabled, IP FRR and VPN FRR take precedence over Auto FRR. If a route fails to match the routing policy of IP FRR or VPN FRR, Auto FRR takes effect.";
              }
              leaf tunnel-selector-name {
                type string;
                description
                  "Configure a tunnel selector and apply it to the BGP IPv4 unicast, BGP VPNv4 address families and BGP VPNv6 address families so that IPv4,VPNv4 and VPNv6 labeled routes can be iterated to tunnels based on the tunnel selector.";
              }
              leaf route-select-delay {
                type string;
                units "s";
                // NCS drop default statement
                description
                  "Route selection delay.";
              }
              leaf apply-label-mode {
                type ncs_template_apply-label-type;
                // NCS drop default statement
                description
                  "Method of distributing labels to VPNV4 and VPNV6 routes. The way which assigns the label depends on the paf value. If there are a large number of routes, assign a label for the routes that have same nexthop and out-label. This allows all routes which have same nexthop and out-label to use one label.";
              }
              leaf nexthop-select-depend-type {
                type ncs_template_select-depend-type-ext;
                // NCS drop default statement
                description
                  "In none mode, route selection does not depend on whether the next hop is reachable. In tunnel mode, the labeled BGP IPv4 route can participate in route selection only after its next hop is iterated to an LSP. In IP
                   mode, the labeled BGP IPv4 route can participate in route selection only after its next hop is iterated to an IP address. By default, the labeled BGP IPv4 route can participate in route selection
                   if its next hop can be iterated to an IP address, regardless of whether the LSP of the next hop exists. This allows the RR that is not enabled with MPLS to forward labeled routes. In non-RR
                   networking or RR networking where the BGP next hop is changed, BGP needs to check whether there is an LSP destined for the next hop. If such an LSP is not found, BGP needs to establish an LSP in
                   advance. If the default setting is adopted, a labeled BGP IPv4 unicast route may be selected prior to LSP establishment. As a result, services are incorrectly switched before LSP establishment and
                   service stability is affected. Therefore, allow route selection only after the labeled BGP IPv4 route is iterated to an LSP.";
              }
              leaf default-med {
                type string;
                // NCS drop default statement
                description
                  "Specify the Multi-Exit-Discriminator (MED) of BGP routes. The value is an integer. This value is valid only for the imported routes and BGP summarized routes on the local router.";
              }
              leaf best-external {
                // NCS drop when statement
                type string;
                // NCS drop default statement
                description
                  "Enable/disable best external route selection.";
              }
              leaf label-free-delay {
                type string;
                units "s";
                // NCS drop default statement
                description
                  "Label free delay.";
              }
              leaf add-path-select-num {
                // NCS drop when statement
                type string;
                description
                  "Number of Add-Path routes.";
              }
              leaf default-local-preference {
                type string;
                // NCS drop default statement
                description
                  "The local preference of BGP routes.";
              }
              uses ncs_template_bestroute-med-plus-igp-type;
              uses ncs_template_bestroute-router-id-prior-clusterlist-type;
              leaf reflect-between-client {
                type string;
                // NCS drop default statement
                description
                  "Enable/disable route reflection between clients. If clients of a route reflector (RR) are fully meshed, you can disable route reflection among clients to reduce the cost.";
              }
              leaf activate-route-tag {
                type string;
                // NCS drop default statement
                description
                  "Enable/disable tag-based filtering.";
              }
              uses ncs_template_route-reflector-ext-community-filter-type;
              uses ncs_template_vrf-af-dampening-routes-ext;
              container nexthop-recursive-lookup {
                description
                  "Configure next hop iteration.";
                container common {
                  description
                    "Configure next hop iteration common options.";
                  uses ncs_template_nexthop-recursive-lookup-restrain;
                  uses ncs_template_nexthop-recursive-lookup-default-route;
                }
                uses ncs_template_nexthop-recursive-lookup-delay;
                uses ncs_template_bit-error-detection-type;
              }
              uses ncs_template_ipv4-import-filter-protocol-type;
              uses ncs_template_ipv4vpn-export-filter-protocol-type;
              uses bgp:ncs_template_slow-peer-type;
            }
            container ipv6-vpn {
              // NCS drop when statement
              description
                "Configure IPv6 VPNv6 options.";
              uses ncs_template_vpn-target-type;
              uses ncs_template_reflector-cluster-type;
              uses ncs_template_reflect-type;
              leaf auto-frr {
                type string;
                // NCS drop default statement
                description
                  "Enable/disable BGP Auto FRR. If IP FRR, VPN FRR, and Auto FRR are all enabled, IP FRR and VPN FRR take precedence over Auto FRR. If a route fails to match the routing policy of IP FRR or VPN FRR, Auto FRR takes effect.";
              }
              leaf tunnel-selector-name {
                type string;
                description
                  "Configure a tunnel selector and apply it to the BGP IPv4 unicast, BGP VPNv4 address families and BGP VPNv6 address families so that IPv4,VPNv4 and VPNv6 labeled routes can be iterated to tunnels based on the tunnel selector. By default, no tunnel selector is configured.";
              }
              leaf route-select-delay {
                type string;
                units "s";
                // NCS drop default statement
                description
                  "Route selection delay.";
              }
              leaf apply-label-mode {
                type ncs_template_apply-label-type;
                // NCS drop default statement
                description
                  "Method of distributing labels to VPNV4 and VPNV6 routes. The way which assigns the label depends on the paf value. If there are a large number of routes, assign a label for the routes that have same nexthop and out-label. This allows all routes which have same nexthop and out-label to use one label.";
              }
              leaf nexthop-select-depend-type {
                type ncs_template_select-depend-type-ext;
                // NCS drop default statement
                description
                  "In none mode, route selection does not depend on whether the next hop is reachable. In tunnel mode, the labeled BGP IPv4 route can participate in route selection only after its next hop is iterated to an LSP. In IP
                   mode, the labeled BGP IPv4 route can participate in route selection only after its next hop is iterated to an IP address. By default, the labeled BGP IPv4 route can participate in route selection
                   if its next hop can be iterated to an IP address, regardless of whether the LSP of the next hop exists. This allows the RR that is not enabled with MPLS to forward labeled routes. In non-RR
                   networking or RR networking where the BGP next hop is changed, BGP needs to check whether there is an LSP destined for the next hop. If such an LSP is not found, BGP needs to establish an LSP in
                   advance. If the default setting is adopted, a labeled BGP IPv4 unicast route may be selected prior to LSP establishment. As a result, services are incorrectly switched before LSP establishment and
                   service stability is affected. Therefore, allow route selection only after the labeled BGP IPv4 route is iterated to an LSP.";
              }
              leaf default-med {
                type string;
                // NCS drop default statement
                description
                  "Specify the Multi-Exit-Discriminator (MED) of BGP routes. The value is an integer. This value is valid only for the imported routes and BGP summarized routes on the local router.";
              }
              leaf best-external {
                // NCS drop when statement
                type string;
                // NCS drop default statement
                description
                  "Enable/disable best external route selection.";
              }
              leaf add-path-select-num {
                // NCS drop when statement
                type string;
                description
                  "Number of add-path routes.";
              }
              leaf default-local-preference {
                type string;
                // NCS drop default statement
                description
                  "The local preference of BGP routes.";
              }
              uses ncs_template_bestroute-med-plus-igp-type;
              uses ncs_template_bestroute-router-id-prior-clusterlist-type;
              leaf reflect-between-client {
                type string;
                // NCS drop default statement
                description
                  "Enable/disable route reflection between clients. If clients of a route reflector (RR) are fully meshed, you can disable route reflection among clients to reduce the cost.";
              }
              leaf label-free-delay {
                type string;
                units "s";
                // NCS drop default statement
                description
                  "Label free delay.";
              }
              uses ncs_template_route-reflector-ext-community-filter-type;
              container nexthop-recursive-lookup {
                description
                  "Configure next hop iteration.";
                container common {
                  description
                    "Configure next hop iteration common options.";
                  uses ncs_template_nexthop-recursive-lookup-restrain;
                  uses ncs_template_nexthop-recursive-lookup-default-route;
                }
                uses ncs_template_nexthop-recursive-lookup-delay;
                uses ncs_template_bit-error-detection-type;
              }
              uses ncs_template_ipv6-import-filter-protocol-type;
              uses ncs_template_ipv6vpn-export-filter-protocol-type;
              uses bgp:ncs_template_slow-peer-type;
              uses ncs_template_vrf-af-dampening-routes-ext;
            }
            container ipv4-labeluni {
              // NCS drop when statement
              description
                "Configure IPv4 label unicast options.";
              container common {
                description
                  "Configure IPv4 label unicast common options.";
                leaf auto-frr {
                  type string;
                  // NCS drop default statement
                  description
                    "Enable/disable BGP Auto FRR. If IP FRR, VPN FRR, and Auto FRR are all enabled, IP FRR and VPN FRR take precedence over Auto FRR. If a route fails to match the routing policy of IP FRR or VPN FRR, Auto FRR takes effect.";
                }
                leaf tunnel-selector-name {
                  // NCS drop when statement
                  type string;
                  description
                    "Configure a tunnel selector and apply it to the BGP IPv4 unicast, BGP VPNv4 address families and BGP VPNv6 address families so that IPv4,VPNv4 and VPNv6 labeled routes can be iterated to tunnels based on the tunnel selector. By default, no tunnel selector is configured.";
                }
                leaf tunnel-selector-all {
                  // NCS drop when statement
                  type string;
                  // NCS drop default statement
                  description
                    "Enable/disable tunnel selector for labeled, imported, and network segment routes.";
                }
                leaf nexthop-select-depend-type {
                  // NCS drop when statement
                  type ncs_template_select-depend-type;
                  // NCS drop default statement
                  description
                    "Specify the route iteration mode: IP or tunnel. In tunnel mode, the labeled BGP IPv4 route can participate in route selection only after its next hop is iterated to an LSP. In IP
                     mode, the labeled BGP IPv4 route can participate in route selection only after its next hop is iterated to an IP address. By default, the labeled BGP IPv4 route can participate in route selection
                     if its next hop can be iterated to an IP address, regardless of whether the LSP of the next hop exists. This allows the RR that is not enabled with MPLS to forward labeled routes. In non-RR
                     networking or RR networking where the BGP next hop is changed, BGP needs to check whether there is an LSP destined for the next hop. If such an LSP is not found, BGP needs to establish an LSP in
                     advance. If the default setting is adopted, a labeled BGP IPv4 unicast route may be selected prior to LSP establishment. As a result, services are incorrectly switched before LSP establishment and
                     service stability is affected. Therefore, allow route selection only after the labeled BGP IPv4 route is iterated to an LSP.";
                }
                leaf nexthop-inherit-ip-cost {
                  // NCS drop when statement
                  type string;
                  // NCS drop default statement
                  description
                    "Enable/disable next hop iteration mode to IP. Specify the route iteration mode: IP or tunnel. In tunnel mode, the labeled BGP IPv4 route can participate in route selection only after its next hop is iterated to an LSP.";
                }
                leaf always-compare-med {
                  type string;
                  // NCS drop default statement
                  description
                    "Enable/disable BGP to compare the MEDs of routes from peers in different ASs in route selection. If
                     there are multiple reachable routes to the same destination, the route with the smallest MED is preferred. Do not use this option unless different ASs use the same IGP and route selection mode.";
                }
                leaf default-med {
                  type string;
                  // NCS drop default statement
                  description
                    "Specify the Multi-Exit-Discriminator (MED) of BGP routes. The value is an integer. This value is valid only for the imported routes and BGP summarized routes on the local router.";
                }
                leaf best-route-bit-error-detection {
                  // NCS drop when statement
                  type string;
                  // NCS drop default statement
                  description
                    "Enable/disable the function to reroute traffic when a bit error event occurs.";
                }
                leaf supernet-label-advertise {
                  type string;
                  // NCS drop default statement
                  description
                    "Enable/disable the function to advertise supernet labeled routes.";
                }
                leaf lsp-mtu {
                  type string;
                  // NCS drop default statement
                  description
                    "BGP LSP MTU.";
                }
                leaf label-free-delay {
                  type string;
                  units "s";
                  // NCS drop default statement
                  description
                    "Label free delay.";
                }
                leaf bestroute-med-confederation {
                  // NCS drop when statement
                  type string;
                  // NCS drop default statement
                  description
                    "Enable/disable BGP to compare Med value only within the federation.";
                }
                leaf bestroute-as-path-ignore {
                  type string;
                  // NCS drop must statement
                  // NCS drop default statement
                  description
                    "Enable/disable BGP to ignore the AS_Path attribute when selecting the optimal route. By default, BGP uses the AS_Path attribute as one of route selection rules, and a route with a shorter AS_Path is preferred. After bestroute-as-path-ignore is selected, BGP does not compare the AS_Path length.";
                }
                leaf determin-med {
                  type string;
                  // NCS drop must statement
                  // NCS drop default statement
                  description
                    "Enable/disable deterministic MED so that the route selection result is relevant to the sequence in which routes are received.";
                }
                leaf best-external {
                  // NCS drop when statement
                  type string;
                  // NCS drop must statement
                  // NCS drop default statement
                  description
                    "Enable/disable best external route selection.";
                }
                leaf add-path-select-num {
                  // NCS drop when statement
                  type string;
                  // NCS drop must statement
                  description
                    "Number of add-path routes.";
                }
                leaf load-balanc-igp-metric-ignore {
                  // NCS drop when statement
                  type string;
                  // NCS drop default statement
                  description
                    "Enable/disable BGP to ignore the IGP cost of each BGP route to the next hop when selecting routes for load balancing. By default, only the routes with the same IGP cost can participate in load balancing.";
                }
                leaf load-balanc-as-path-ignore {
                  // NCS drop when statement
                  type string;
                  // NCS drop must statement
                  // NCS drop default statement
                  description
                    "Enable/disable BGP to ignore the AS_Path of each BGP route to the next hop when selecting routes for load balancing. By default, only the routes with the same AS_Path can participate in load balancing.";
                }
                leaf load-balanc-as-path-relax {
                  // NCS drop when statement
                  type string;
                  // NCS drop must statement
                  // NCS drop default statement
                  description
                    "Enable/disable BGP to ignore comparison of AS_Path attributes with the same length. By default, only the routes with the same AS_Path can participate in load balancing.";
                }
                leaf default-local-preference {
                  type string;
                  // NCS drop default statement
                  description
                    "The local preference of BGP routes.";
                }
                leaf default-route-import {
                  type string;
                  // NCS drop default statement
                  description
                    "Enable/disable the function to import default routes into the BGP routing table. Default-route-imported must be used with import-routes so that default routes can be imported to the BGP routing table. If only import-routes is used, no default routes can be added to the BGP routing table. In addition, default-route-imported can only import the default routes in the routing table into the BGP routing table.";
                }
                leaf routerid-neglect {
                  type string;
                  // NCS drop default statement
                  description
                    "Enable/disable BGP to ignore router IDs when selecting the optimal route. Comparing router IDs is the last resort in route selection. This means that if one optimal route must be selected and no other parameters can be used to break the tie, router IDs can be used. If this option is selected, the first received route will be selected as the optimal route, and BGP will ignore the router ID and peer address in route selection.";
                }
                leaf route-select-delay {
                  type string;
                  units "s";
                  // NCS drop default statement
                  description
                    "Route selection delay.";
                }
                leaf import-rib-nexthop-invariable {
                  // NCS drop when statement
                  type string;
                  // NCS drop default statement
                  description
                    "Enable/disable the command to enable advertise the route without modifying the next-hop.";
                }
                uses ncs_template_reflect-type;
                uses ncs_template_reflector-cluster-type;
                leaf reflect-between-client {
                  type string;
                  // NCS drop default statement
                  description
                    "Enable/disable route reflection between clients. If clients of a route reflector (RR) are fully meshed, you can disable route reflection among clients to reduce the cost.";
                }
                uses ncs_template_bestroute-med-plus-igp-type;
                uses ncs_template_bestroute-router-id-prior-clusterlist-type;
                leaf bestroute-med-none-as-maximum {
                  type string;
                  // NCS drop default statement
                  description
                    "Enable/disable BGP considers its MED as the largest MED value (4294967295). If a route does not carry MED, BGP considers its MED as the default value (0) during route selection.";
                }
                leaf ext-community-change {
                  type string;
                  // NCS drop default statement
                  description
                    "Enable/disable the function to change the extended community attribute.";
                }
              }
              container nexthop-recursive-lookup {
                description
                  "Configure next hop iteration.";
                container common {
                  description
                    "Configure next hop iteration common options.";
                  uses ncs_template_nexthop-recursive-lookup-restrain;
                }
              }
              container import-routes {
                description
                  "List of imported routes.";
                list import-route {
                  // NCS patched for predictable order
                  ordered-by user;
                  key "protocol process-id";
                  description
                    "Apply route import policy. Routes of other protocol types can be imported by BGP. By default, BGP does not import routes of other protocol types.";
                  uses ncs_template_import-routes-type;
                  leaf non-relay-tunnel {
                    // NCS drop when statement
                    type string;
                    // NCS drop default statement
                    description
                      "Enable/disable imported route relay a tunnel.";
                  }
                }
              }
              container network-routes {
                description
                  "List of network routes.";
                list network-route {
                  // NCS patched for predictable order
                  ordered-by user;
                  key "address mask-length";
                  description
                    "Configure a network route in the BGP routing table.";
                  uses ncs_template_network-route-ipv4;
                  leaf non-relay-tunnel {
                    // NCS drop when statement
                    type string;
                    // NCS drop default statement
                    description
                      "Enable/disable imported route relay a tunnel.";
                  }
                }
              }
              container import-ribs {
                description
                  "List of imported RIBs configuration.";
                list import-rib {
                  // NCS patched for predictable order
                  ordered-by user;
                  key "source-vpn source-address-family";
                  description
                    "Configure imported RIBs.";
                  leaf source-vpn {
                    type string;
                    // NCS drop must statement
                    description
                      "Source VPN name.";
                  }
                  leaf source-address-family {
                    type bgp:ncs_template_import-rib-ipv4-safi-type;
                    description
                      "Source address family type.";
                  }
                  leaf valid-route {
                    type string;
                    // NCS drop default statement
                    description
                      "Enable/disable imported valid route.";
                  }
                  leaf include-label-route {
                    // NCS drop when statement
                    type string;
                    // NCS drop default statement
                    description
                      "Enable/disable imported include label route.";
                  }
                  // NCS expand uses statement
                  choice policy-type {
                    case rtp-ref {
                      description
                        "Specify the route policy.";
                      leaf policy-name {
                        type string;
                        description
                          "Specify the route policy.";
                      }
                    }
                    case xpl-ref {
                      description
                        "Route filter.";
                      uses ncs_template_route-filter-type;
                    }
                    description
                      "Specify the route-policy or filter for imported RIBs.";
                  }
                }
              }
              container lsp-options {
                description
                  "Configure BGP ingress-lsp.";
                uses ncs_template_safi-lsp-options;
                leaf maximum-load-balancing-transit {
                  // NCS drop when statement
                  type string;
                  // NCS drop default statement
                  description
                    "Maximum number of transit LSPs for load balancing.";
                }
                leaf unicast-rt-label-advertise-popgo {
                  // NCS drop when statement
                  type string;
                  // NCS drop default statement
                  description
                    "Enable/disable a device to convert received IPv4 public network unicast routes to labeled routes by adding a BGP label to each route and advertise the labeled routes to peers with the labeled route exchange capability. If the IP address of an outbound interface is reachable but no LSP is reachable, traffic is forwarded through the outbound interface and a specific next hop, during which the label POPGO action is performed.";
                }
                leaf lsp-operation {
                  // NCS drop when statement
                  type ncs_template_lsp-operation-type;
                  // NCS drop default statement
                  description
                    "Label operation type.";
                }
                uses ncs_template_ingress-choice-policy-set;
              }
              uses ncs_template_vrf-af-dampening-routes;
              uses bgp:ncs_template_slow-peer-type;
            }
            container ipv4-multicast {
              // NCS drop when statement
              description
                "Configure IPv4 multicast options.";
              container common {
                description
                  "Configure BGP IPv4-multicast address family options.";
                leaf always-compare-med {
                  type string;
                  // NCS drop default statement
                  description
                    "Enable/disable BGP to compare the MEDs of routes from peers in different ASs in route selection. If
                     there are multiple reachable routes to the same destination, the route with the smallest MED is preferred. Do not use this option unless different ASs use the same IGP and route selection mode.";
                }
                leaf default-med {
                  type string;
                  // NCS drop default statement
                  description
                    "Specify the Multi-Exit-Discriminator (MED) of BGP routes. The value is an integer. This value is valid only for the imported routes and BGP summarized routes on the local router.";
                }
                leaf summary-automatic {
                  type string;
                  // NCS drop default statement
                  description
                    "Enable/disable automatic summarization for imported routes. Manual summarization takes precedence over automatic summarization. After automatic summarization is enabled, BGP summarizes routes based on the natural network segment (for example, 10.1.1.1/24 and 10.2.1.1/24 are summarized into 10.0.0.0/8, a Class A address), and sends only the summarized route to peers. This reduces the number of routes.";
                }
                leaf bestroute-med-confederation {
                  type string;
                  // NCS drop default statement
                  description
                    "Enable/disable BGP to compare Med value only within the federation.";
                }
                leaf default-local-preference {
                  type string;
                  // NCS drop default statement
                  description
                    "The local preference of BGP routes.";
                }
                leaf default-route-import {
                  type string;
                  // NCS drop default statement
                  description
                    "Enable/disable the function to import default routes into the BGP routing table. Default-route-imported must be used with import-routes so that default routes can be imported to the BGP routing table. If only import-routes is used, no default routes can be added to the BGP routing table. In addition, default-route-imported can only import the default routes in the routing table into the BGP routing table.";
                }
                leaf routerid-neglect {
                  type string;
                  // NCS drop default statement
                  description
                    "Enable/disable BGP to ignore router IDs when selecting the optimal route. Comparing router IDs is the last resort in route selection. This means that if one optimal route must be selected and no other parameters can be used to break the tie, router IDs can be used. If this option is selected, the first received route will be selected as the optimal route, and BGP will ignore the router ID and peer address in route selection.";
                }
                leaf route-select-delay {
                  type string;
                  units "s";
                  // NCS drop default statement
                  description
                    "Route selection delay.";
                }
                uses ncs_template_reflect-type;
                uses ncs_template_reflector-cluster-type;
                leaf reflect-between-client {
                  type string;
                  // NCS drop default statement
                  description
                    "Enable/disable route reflection between clients. If clients of a route reflector (RR) are fully meshed, you can disable route reflection among clients to reduce the cost.";
                }
                leaf determin-med {
                  type string;
                  // NCS drop default statement
                  description
                    "Enable/disable deterministic MED so that the route selection result is relevant to the sequence in which routes are received.";
                }
                uses ncs_template_bestroute-med-plus-igp-type;
                uses ncs_template_bestroute-router-id-prior-clusterlist-type;
                leaf bestroute-as-path-ignore {
                  type string;
                  // NCS drop default statement
                  description
                    "Enable/disable BGP to ignore the AS_Path attribute when selecting the optimal route. By default, BGP uses the AS_Path attribute as one of route selection rules, and a route with a shorter AS_Path is preferred. After bestroute-as-path-ignore is selected, BGP does not compare the AS_Path length.";
                }
                leaf bestroute-med-none-as-maximum {
                  type string;
                  // NCS drop default statement
                  description
                    "Enable/disable BGP considers its MED as the largest MED value (4294967295). If a route does not carry MED, BGP considers its MED as the default value (0) during route selection.";
                }
                leaf maximum-load-balancing {
                  type string;
                  // NCS drop must statement
                  // NCS drop default statement
                  description
                    "Specify the maximum number of equal-cost routes in the BGP routing table. The value can be 1 or an integer greater than 1. The value depends on the associated license. By default, the maximum number of equal-cost routes is 1. Equal-cost BGP routes can be generated for load balancing only when the BGP routes meet the first nine rules of the route-selection policy and have the same AS-Path attribute.";
                }
                leaf maximum-load-balancing-ibgp {
                  type string;
                  // NCS drop must statement
                  // NCS drop default statement
                  description
                    "Specify the maximum number of equal-cost IBGP routes.";
                }
                leaf maximum-load-balancing-ebgp {
                  type string;
                  // NCS drop must statement
                  // NCS drop default statement
                  description
                    "Specify the maximum number of equal-cost EBGP routes.";
                }
                leaf ext-community-change {
                  type string;
                  // NCS drop default statement
                  description
                    "Enable/disable the function to change the extended community attribute.";
                }
              }
              container nexthop-recursive-lookup {
                description
                  "Configure next hop iteration.";
                container common {
                  description
                    "Configure next hop iteration common options.";
                  choice policy-type {
                    description
                      "Set route-policy or route-filter.";
                    case rtp-ref {
                      description
                        "Route policy.";
                      leaf route-policy {
                        type string;
                        description
                          "Specify the name of a routing policy.";
                      }
                    }
                    case xpl-ref {
                      description
                        "Route filter.";
                      uses ncs_template_route-filter-type;
                    }
                  }
                }
                uses ncs_template_nexthop-recursive-lookup-delay;
              }
              uses ncs_template_bgp-route-preference-options;
              uses ncs_template_vrf-af-dampening-routes;
              container network-routes {
                description
                  "List of network routes.";
                list network-route {
                  // NCS patched for predictable order
                  ordered-by user;
                  key "address mask-length";
                  description
                    "Configure a network route in the BGP routing table.";
                  uses ncs_template_network-route-ipv4;
                }
              }
              container import-routes {
                description
                  "List of imported routes.";
                list import-route {
                  // NCS patched for predictable order
                  ordered-by user;
                  key "protocol process-id";
                  description
                    "Configure route import. Routes of other protocol types can be imported by BGP. By default, BGP does not import routes of other protocol types.";
                  leaf protocol {
                    type bgp:ncs_template_ipv4multi-import-route-protocol-type;
                    description
                      "Routing protocol from which routes can be imported.";
                  }
                  leaf process-id {
                    type string;
                    // NCS drop must statement
                    description
                      "Process ID of an imported routing protocol. The process ID is 0, if the imported routing protocol is direct routes, static routes, UNRs, or OP-routes. The process ID must be specified range from 1 to 4294967295, if the imported routing protocol is RIP, OSPF, ISIS.";
                  }
                  leaf med {
                    type string;
                    description
                      "Specifies the MED metric of the imported route.";
                  }
                  choice policy-type {
                    description
                      "Set route policy or filter.";
                    case rtp-ref {
                      description
                        "Route policy.";
                      leaf policy-name {
                        type string;
                        description
                          "When routes are imported from other routing protocols, the route-policy filter can be used to filter the routes and change route attributes.";
                      }
                    }
                    case xpl-ref {
                      description
                        "Route filter.";
                      uses ncs_template_route-filter-type;
                    }
                  }
                }
              }
              container aggregate-routes {
                description
                  "List of summarized routes.";
                list aggregate-route {
                  // NCS patched for predictable order
                  ordered-by user;
                  key "address mask-length";
                  description
                    "Configure a summarized route in the BGP routing table. The local outbound interface of the summarized route is Null0. When another router receives the route, the route adds an outbound interface to the route. By default, route summarization is not performed. If the Origin attributes of the specific routes for the route summarization are different, the Origin attribute of the summarized route is that with the highest priority. Origin attributes are arranged in the priority order of complete > egp > igp. A summarized route carries the community attribute of each specific route.";
                  // NCS expand uses statement
                  leaf address {
                    type string;
                    description
                      "Specify the IPv4 address or IPv6 address of a summarized route. Only IPv4 summarized routes can be configured in the IPv4 address family and only IPv6 summarized routes can be configured in the IPv6 address family.";
                    // NCS drop must statement
                  }
                  leaf mask-length {
                    type string;
                    description
                      "Specify the mask length of a summarized address.";
                    // NCS drop must statement
                  }
                  leaf as-set {
                    type string;
                    // NCS drop default statement
                    description
                      "Enable/disable the generation of routes with the AS-SET attribute. This option can be used to create a summarized route. The AS_Path attribute of the summarized route contains the AS-Path attributes of the specific routes for the route summarization. Exercise caution when using this option if multiple AS_Paths need to be summarized to prevent route flapping.";
                  }
                  leaf detail-suppressed {
                    type string;
                    // NCS drop default statement
                    description
                      "Enable/disable detail-suppressed. Suppress the advertisement of specific routes for the route summarization. Only the summarized route is advertised.";
                  }
                  choice policy-type {
                    description
                      "Set route policy or filter.";
                    case rtp-ref {
                      description
                        "Route policy.";
                      leaf attribute-policy {
                        type string;
                        description
                          "Specify an attribute of summarized routes. If apply as-path is used to configure the AS_Path attribute that is used in the route Summarization policy, and the as-set keyword is set, the AS_Path attribute in the policy does not take effect. This parameter and any of the following parameters overwrite each other: suppressFilter, originFilter, and attributeFilter.";
                      }
                      leaf origin-policy {
                        type string;
                        description
                          "Specify the name of a policy for generating summarized routes. Summarized routes are generated only when the routes match route-policy. This parameter and any of the following parameters overwrite each other: suppressFilter, originFilter, and attributeFilter.";
                      }
                      leaf suppress-policy {
                        type string;
                        description
                          "Specify a policy for suppressing the advertisement of specified routes. The routes matching the policy are not advertised, and other routes are advertised. This parameter and any of the following parameters overwrite each other: suppressFilter, originFilter, and attributeFilter.";
                      }
                    }
                    case xpl-ref {
                      description
                        "Route filter.";
                      leaf attribute-filter-name {
                        type string;
                        description
                          "Specify a route-filter name.";
                      }
                      leaf attribute-filter-parameter {
                        // NCS drop when statement
                        type xpl:ncs_template_filter-parameter-type;
                        description
                          "Specify a route-filter parameter.";
                      }
                      leaf origin-filter-name {
                        type string;
                        description
                          "Specify a route-filter name.";
                      }
                      leaf origin-filter-parameter {
                        // NCS drop when statement
                        type xpl:ncs_template_filter-parameter-type;
                        description
                          "Specify a route-filter parameter.";
                      }
                      leaf suppress-filter-name {
                        type string;
                        description
                          "Specify a route-filter name.";
                      }
                      leaf suppress-filter-parameter {
                        // NCS drop when statement
                        type xpl:ncs_template_filter-parameter-type;
                        description
                          "Specify a route-filter parameter.";
                      }
                    }
                  }
                }
              }
              uses ncs_template_ipv4-import-filter-protocol-type;
              container export-filter-policys {
                description
                  "List of filtering policies.";
                list export-filter-policy {
                  // NCS patched for predictable order
                  ordered-by user;
                  key "protocol process-id";
                  description
                    "Apply a filtering policy. It is used to filter the routes to be advertised to the peer. By default, routes are not filtered.";
                  leaf protocol {
                    type bgp:ncs_template_ipv4-export-filter-protocol-type;
                    description
                      "Specify the name of a routing protocol. The routing protocol takes effect only on the routes to be advertised. The IPv4 address family supports the direct, IS-IS, OSPF, RIP, and static routing protocols. The IPv6 unicast address family of a public network instance supports the direct, IS-IS, OSPFv3, RIPng, and static routing protocols. The IPv6 address family of a VPNv6 instance supports the direct, IS-IS, RIPng, and static routing protocols.";
                  }
                  leaf process-id {
                    type string;
                    // NCS drop must statement
                    description
                      "Specify the process ID required to be matched. The value is an integer ranging from 0 to 4294967295. If direct or static routes need to be filtered, no process ID is required.";
                  }
                  uses ncs_template_ipv4-filter-protocol-policy-choice-type;
                }
              }
              uses bgp:ncs_template_slow-peer-type;
              uses ncs_template_qos-local-id-type;
            }
          }
        }
        container dynamic-peer-prefixes {
          description
            "List of IP prefixes from which a dynamic BGP peer group listens for BGP connection requests.";
          list dynamic-peer-prefix {
            // NCS patched for predictable order
            ordered-by user;
            key "address mask-length peer-group";
            description
              "Configure an IP prefix from which a dynamic BGP peer group listens for BGP connection requests.";
            leaf address {
              type string;
              // NCS drop must statement
              description
                "Network segment address for a dynamic peer connection.";
            }
            leaf mask-length {
              type string;
              description
                "Mask length of a network segment. For an IPv4 network address, the value ranges from 0 to 32.";
            }
            leaf peer-group {
              type string;
              // NCS drop must statement
              // NCS drop must statement
              description
                "The peer-group within which the dynamic neighbor will be configured.";
            }
          }
        }
        container peer-groups {
          description
            "List of BGP peer groups. The BGP peer groups can help you simplify the configurations. If you want to perform the same configuration for several peers, you can create a peer group and then configure the peer group. After you add these peers to the peer group, all these peers will have the same configurations as the peer group.";
          list peer-group {
            // NCS patched for predictable order
            ordered-by user;
            key "name";
            description
              "Configure information about a BGP peer group.";
            leaf name {
              type string;
              description
                "Specify the name of a peer group. The value is a string of characters, spaces not supported.";
            }
            leaf type {
              type ncs_template_group-type;
              // NCS drop mandatory statement
              description
                "Specify the type of a peer group. The value can be IBGP or EBGP.The object cannot be modified.";
              ext:operation-exclude "update" {
                description
                  "The node cannot be modified, when node is already configured.";
              }
            }
            uses ncs_template_peer-local-if-type;
            uses ncs_template_authentication-attr-type;
            leaf description {
              type string;
              description
                "Specify the description of a peer group. The value is a string, which can be letters or digits, spaces supported. By default, no description is configured.";
            }
            leaf group-as {
              // NCS drop when statement
              type ncs_template_as-number-validate;
              description
                "Specify the AS number of a peer group. The AS number is in either a 2-byte or 4-byte format.
                 The two-byte format is X. X is an integer ranging from 1 to 65535.
                 The four-byte format is X.Y and X. When the format is X.Y, X and Y are both integers, with the value of X ranging from 1 to 65535, and the value of Y ranging from 0 to 65535; when the format is X, X is an interger, with the value of X ranging from 1 to 4294967295.";
            }
            leaf tcp-mss {
              type string;
              description
                "Maximum TCP MSS value used for TCP connection establishment for a peer group.";
            }
            leaf ebgp-max-hop {
              // NCS drop when statement
              type string;
              // NCS drop must statement
              // NCS drop default statement
              description
                "Maximum number of hops in an indirect EBGP connection. By default, EBGP connections can be established only between directly connected peers. The function must be configured on both ends.";
            }
            leaf valid-ttl-hops {
              type string;
              // NCS drop must statement
              description
                "Enable GTSM on a peer or peer group. The valid-TTL-Value parameter is used to specify the number of TTL hops to be detected. If the value is configured as hops, the valid TTL range of the detected packet is [255-hops+1, 255].";
            }
            uses ncs_template_peer-tracking-type;
            leaf conventional {
              type string;
              // NCS drop default statement
              description
                "Enable/disable general router functions on peers. In conventional mode, not all the extended router functions, such as, route refreshing, GR, and multi-address family negotiation, are available. Therefore, the router of a new version can be compatible with the routers of earlier versions.";
            }
            leaf route-refresh {
              type string;
              // NCS drop default statement
              description
                "Enable/disable BGP to advertise Refresh messages to peers.";
            }
            leaf four-byte-as {
              type string;
              // NCS drop default statement
              description
                "Enable/disable BGP to advertise routes carrying 4-byte AS numbers to peers. After the 4-byte AS number function is disabled, Open packets will not carry 4-byte AS number capability flag, and peer ends will not know that local ends have the 4-byte AS number function. The 4-byte AS number function cannot be disabled from peers (peer groups) if a 4-byte AS number, fake AS number, or confederation ID is configured on a router and the AS number of a peer is 4-byte. If the 4-byte AS number function is disabled in such a situation, BGP sessions may fail to be established, and route transmission may be affected.";
            }
            leaf ignore {
              type string;
              // NCS drop default statement
              description
                "Enable/disable the function to tear down sessions between peers and clear all related routing information.";
            }
            leaf connect-mode {
              // NCS drop when statement
              type ncs_template_connect-mode;
              // NCS drop default statement
              description
                "The value can be Connect-only, Listen-only, or Both. If the value is Connect-only, the specified peer or peer group only initiatively sends connection requests, instead of listening to connection requests. If the value is Listen-only, the specified peer or peer group only listens to connection requests, instead of initiatively sending connection requests. If the value is Both, the specified peer or peer group not only initiatively sends connection requests, but also listens to connection requests. The default value is Both.";
            }
            leaf log-change {
              type string;
              // NCS drop default statement
              description
                "Enable/disable BGP to record the session status and events of the specified peer or peer group.";
            }
            leaf path-mtu-auto-discovery {
              // NCS drop when statement
              type string;
              // NCS drop default statement
              description
                "Enable/disable path mtu auto discovery.";
            }
            leaf local-ifnet-disable {
              type string;
              description
                "Enable/disable MPLS local IFNET tunnel creation on a BGP peer. By default, MPLS local IFNET tunnels can be created on an EBGP peer,but such tunnels cannot be created on an IBGP peer.";
              ext:dynamic-default;
            }
            leaf check-first-as {
              // NCS drop when statement
              type ncs_template_peer-cap-config-state;
              // NCS drop default statement
              description
                "Check the first AS in the AS_Path of the update messages from EBGP peers.";
            }
            leaf memory-priority {
              type ncs_template_memory-priority;
              // NCS drop default statement
              description
                "Set a priority that determines the disconnection order of each BGP peer relationship in a peer group if memory overload occurs.";
            }
            leaf oscillation-dampening {
              // NCS drop when statement
              type string;
              // NCS drop default statement
              description
                "Enable/disable BGP to suppress the establishment of a specified peer group's peer relationships that flap continuously. By default, the capability is enabled.";
            }
            leaf peer-establish-mode {
              type ncs_template_peer-establish-mode;
              // NCS drop default statement
              description
                "Specify mode in which a BGP peer is established. The value can be static or dynamic.";
              ext:operation-exclude "update|delete" {
                description
                  "The node cannot be modified, deleted when node is already configured.";
              }
            }
            leaf as-number-type {
              // NCS drop when statement
              type ncs_template_as-number-type;
              // NCS drop must statement
              // NCS drop default statement
              description
                "Specify the type of the AS number that is used to establish a BGP peer relationship dynamically. The value can be dynamic-neighbor or confederation.";
              ext:operation-exclude "update|delete" {
                description
                  "The node cannot be modified, deleted when node is already configured.";
              }
            }
            leaf-list listen-as {
              // NCS patched for predictable order
              ordered-by user;
              // NCS drop when statement
              type ncs_template_as-number-validate;
              // NCS drop must statement
              // NCS drop max-elements statement
              description
                "Specify the peer AS from which a dynamic EBGP peer group listens for BGP connection requests.";
            }
            container listen-as-segments {
              // NCS drop when statement
              description
                "List of AS number ranges for listening.";
              list listen-as-segment {
                // NCS patched for predictable order
                ordered-by user;
                // NCS drop must statement
                key "begin-as end-as";
                // NCS drop max-elements statement
                description
                  "Specify an AS number range from which a dynamic EBGP peer group listens for connection requests. The value of begin-as must be smaller than that of end-as. The value of As-Segment cannot contain the value of LocalAS or the value of fake-as. An AS number range cannot contain a confederation AS number, and any two AS number ranges cannot contain each other.";
                leaf begin-as {
                  type ncs_template_as-number-validate;
                  description
                    "Specify the start AS number in an AS range.";
                }
                leaf end-as {
                  type ncs_template_as-number-validate;
                  description
                    "Specify the end AS number in an AS range.";
                }
              }
            }
            container fake-as-parameter {
              description
                "Configure BGP fake-as parameters.";
              leaf fake-as {
                // NCS drop when statement
                type bgp:ncs_template_as-number-validate;
                description
                  "Fake AS number that is specified for a local peer. By default, a peer uses the actual AS number of the local end.
                   An AS number can be in either two-byte format or four-byte format:
                   The two-byte format is X. X is an integer ranging from 1 to 65535.
                   The four-byte format is X.Y and X. When the format is X.Y, X and Y are both integers, with the value of X ranging from 1 to 65535, and the value of Y ranging from 0 to 65535; when the format is X, X is an interger, with the value of X ranging from 1 to 4294967295.";
              }
              leaf dual-as {
                // NCS drop when statement
                type string;
                // NCS drop default statement
                description
                  "Enable/disable the function to the remote EBGP peer can use the actual or fake AS number when specifying the AS number for a local peer. The local peer uses the fake and actual AS numbers to establish a BGP peer relationship with the remote end and identifies the AS number configured by the remote end through the error code (OPEN Message Error) and sub-error code (Bad Peer AS) of the Notification message from the remote end.";
              }
              leaf prepend-global-as {
                // NCS drop when statement
                type string;
                // NCS drop default statement
                description
                  "Enable/disable the function to add the global AS number to the Update packets to be advertised.";
              }
              leaf prepend-fake-as {
                // NCS drop when statement
                type string;
                // NCS drop default statement
                description
                  "Enable/disable the function to add the Fake AS number to received Update packets.";
              }
            }
            uses ncs_template_peer-timer-para-type;
            uses ncs_template_group-bfd-parameter-type;
            container graceful-restart {
              // NCS drop when statement
              description
                "Configure graceful restart.";
              uses ncs_template_group-graceful-restart-type;
              leaf peer-reset {
                type string;
                // NCS drop default statement
                description
                  "Enable/disable reseting BGP peer graceful.";
              }
            }
            container local-graceful-restart {
              // NCS drop when statement
              description
                "Configure local graceful restart.";
              uses ncs_template_group-graceful-restart-type;
            }
            // NCS drop config false container members
            container afs {
              description
                "List of all peer groups that are enabled in a specified address family.";
              list af {
                // NCS patched for predictable order
                ordered-by user;
                key "type";
                description
                  "Configure peer group enabled in a specified address family.";
                leaf type {
                  type bgp:ncs_template_group-af-type;
                  // NCS drop must statement
                  description
                    "Address family type of a BGP instance.";
                }
                container ipv4-unicast {
                  // NCS drop when statement
                  description
                    "Configure IPv4 unicast options.";
                  leaf advertise-community {
                    type string;
                    // NCS drop default statement
                    description
                      "Enable/disable advertise the community attribute to a peer or a peer group.";
                  }
                  leaf reflect-client {
                    // NCS drop when statement
                    type string;
                    // NCS drop default statement
                    description
                      "Enable/disable the local device as a route reflector (RR) and a peer or peer group as its client. This configuration is applicable between IBGP peers only. The configurations of RRs and its clients in an address family are valid only in this address family. Therefore, it is recommended to configure RRs and its clients in the specified address family that is required.";
                  }
                  leaf orf-type {
                    // NCS drop when statement
                    type bgp:ncs_template_bgp-orf-type;
                    // NCS drop must statement
                    // NCS drop default statement
                    description
                      "ORF Type.";
                  }
                  leaf orf-mode {
                    // NCS drop when statement
                    type bgp:ncs_template_bgp-orf-mode-type;
                    // NCS drop must statement
                    // NCS drop default statement
                    description
                      "Configure an outbound route filtering (ORF) mode, which can be Receive, Send, or Both, and the default ORF mode is Both.";
                  }
                  leaf label-route-capability {
                    type string;
                    // NCS drop default statement
                    description
                      "Enable/disable a device to exchange labeled routes.";
                  }
                  leaf check-tunnel-reachable {
                    // NCS drop when statement
                    type string;
                    // NCS drop default statement
                    description
                      "Enable/disable tunnel reachability check.";
                  }
                  leaf check-withdraw-type {
                    // NCS drop when statement
                    type string;
                    // NCS drop default statement
                    status obsolete;
                    description
                      "Enable/disable withdraw type check.";
                  }
                  leaf nexthop-configure {
                    type ncs_template_nexthop-configuration-type;
                    description
                      "Both the next-hop-local mode and next-hop-invariable mode are available when the peer address family is the VPNv4/VPNv6/L2VPN AD address family. Only the next-hop-local mode is available when the peer address family is not VPNv4/VPNV6/L2VPN AD address family. In next-hop-local mode, you can configure a BGP speaker to set its IP address of as the next hop of the routes to be advertised to IBGP peers or IBGP peer groups. In next-hop-invariable mode, you can configure PEs in different ASs not to change the next hop of routes when the PEs advertise the routes to their EBGP peers and use the next hop addresses of IGP routes to advertise imported IGP routes to IBGP peers. By default, when a BGP speaker advertises routes to EBGP peers and imported IGP routes to IBGP peers, the BGP speaker changes the next hop to its interface address.";
                  }
                  uses ncs_template_peer-policy-filter-type;
                  leaf advertise-ext-community {
                    type string;
                    // NCS drop default statement
                    description
                      "Enable/disable advertise the extended community attribute to a peer or peer group.";
                  }
                  leaf origin-as-validation {
                    // NCS drop when statement
                    type string;
                    // NCS drop default statement
                    description
                      "Enable/disable the BGP peer origin validation.";
                  }
                  leaf discard-ext-community {
                    type string;
                    // NCS drop default statement
                    description
                      "Enable/disable discard the extended community attribute in the routing information about a specified peer.";
                  }
                  leaf allow-as-loop {
                    type string;
                    description
                      "Allow repetitive local AS numbers. By default, repetitive local AS numbers are not allowed.";
                  }
                  leaf aigp {
                    // NCS drop when statement
                    type string;
                    // NCS drop default statement
                    description
                      "Enable/disable route with AIGP attribute advertisement to or from a peer.";
                  }
                  leaf add-path-mode {
                    // NCS drop when statement
                    type ncs_template_add-path-cap-type;
                    // NCS drop default statement
                    description
                      "Enable Add-Path route advertisement to a peer.";
                  }
                  uses ncs_template_ip-prefix-filter-type;
                  uses ncs_template_as-path-filter-type;
                  uses ncs_template_peer-group-acl-name-or-num-type;
                  uses ncs_template_default-route-advertise-type;
                  leaf default-route-match-mode {
                    // NCS drop when statement
                    type ncs_template_cra-match-mode;
                    // NCS drop default statement
                    description
                      "Configure the matching mode of default route advertisement, which can be disabling of route advertisement conditions, enabling of all route advertisement conditions, and enabling of part route advertisement conditions. Enabling of all route advertisement conditions indicates that a default route can be advertised only when it matches all the conditions. Enabling of part route advertisement conditions indicates that a default route can be advertised only when it matches one condition.";
                  }
                  uses ncs_template_rt-update-interval-type;
                  uses ncs_template_preferred-value-type;
                  leaf add-path-number {
                    // NCS drop when statement
                    type string;
                    description
                      "Number of Add-Path routes that can be advertised to a peer.";
                  }
                  leaf substitute-as-enable {
                    // NCS drop when statement
                    type string;
                    // NCS drop default statement
                    description
                      "Enable/disable replace the AS number of a specified peer in the AS_Path attribute with the local AS number. On a PE where AS number replacement is enabled, if an AS number in the AS_Path attribute of a route is same as that of the CE to which the PE advertises the route, the PE replaces the AS number with its own AS number before advertising the route.";
                  }
                  leaf soo {
                    // NCS drop when statement
                    type string;
                    description
                      "Configure the Site-of-Origin (SoO) extended community attribute. This attribute can be expressed in the following formats: X.X.X.X:number<0-65535>, number<0-65535>:number<0-4294967295>, or number<0-65535>.number<0-65535>:number<0-65535> or <65536-4294967295>:<0-65535>. 0:0 or 0.0:0 is not supported.
                       Two CEs are in the same site and can advertise routes to each other, and they are connected to a VPN through PEs. If the local routes of a CE are advertised to the other CE over the VPN, a routing loop may occur.
                       The SoO feature can prevent a route advertised by a site from being sent back to the site, preventing routing loops. After SoO is enabled and a PE receives a route from a CE, the specified SoO attribute will be added to the route. Before advertising the route to the other CE, the PE checks the SoO attribute. If the SoO attribute is the same as the locally configured SoO attribute, the PE does not advertise the route, preventing routing loops.";
                  }
                  leaf keep-all-routes {
                    // NCS drop when statement
                    type string;
                    // NCS drop default statement
                    description
                      "Enable/disable saving all the updated information about BGP routes from a specified peer or peer group after a BGP connection is established, even though these BGP routes fail to match the routing policy on the ingress. By default, the updated information about BGP routes from a specified peer is saved only when the routes match the routing policy on the ingress. If a router supports route refreshing, this option is not required.";
                  }
                  leaf exp-mode {
                    type ncs_template_exp-mode-type;
                    // NCS drop default statement
                    description
                      "Specify the ASs in which a BGP label can inherit the QoS priority carried in the outer label of public tunnel in the Core AS and the ASs in which the priorities of BGP LSPs must be restored before the LSPs are advertised to a non-core AS.";
                  }
                  leaf advertise-best-external {
                    // NCS drop when statement
                    type string;
                    // NCS drop must statement
                    // NCS drop must statement
                    // NCS drop must statement
                    // NCS drop default statement
                    description
                      "Enable/disable the device to advertise Best External routes to peers.";
                  }
                  leaf load-balancing-enable {
                    type string;
                    // NCS drop default statement
                    description
                      "Enable/disable a neighbour to participate in load balancing.";
                  }
                  choice load-balancing-ignore-as-type {
                    description
                      "Set load balancing as path type.";
                    case as-attribute {
                      description
                        "Ignore the as-path attribute.";
                      leaf load-balancing-as-path-ignore {
                        // NCS drop when statement
                        type empty;
                        description
                          "Configure BGP to ignore the AS_Path attribute when selecting the equal route. After as-path-neglect is selected, BGP does not compare the AS_Path length.";
                      }
                    }
                    case same-length-as-attribute {
                      description
                        "Ignore comparison of as-path attributes with the same length.";
                      leaf load-balancing-as-path-relax {
                        // NCS drop when statement
                        type empty;
                        description
                          "Configure BGP to ignore comparison of AS_Path attributes with the same length when selecting the equal route. After as-path-neglect is selected, BGP does not compare the AS_Path length.";
                      }
                    }
                  }
                  leaf prefix-sid {
                    // NCS drop when statement
                    type string;
                    // NCS drop default statement
                    description
                      "Enable/disable a device to exchange IPv4 prefix SIDs with a specified IPv6 peer group.";
                  }
                  choice prefix-sid-packet {
                    description
                      "Prefix-sid packet method.";
                    case sid-type5 {
                      description
                        "Packet by type5.";
                      leaf advertise-srv6-locator {
                        // NCS drop when statement
                        type empty;
                        description
                          "Advertise SRv6 locators.";
                      }
                    }
                  }
                  uses ncs_template_group-independent-peer-group-type;
                  uses ncs_template_advertise-large-community-group-type;
                  uses ncs_template_ipv4-default-route-match-conditions-type;
                  uses ncs_template_route-limit-accept-type;
                  uses ncs_template_public-as-only-type;
                  uses ncs_template_group-public-as-only-import-type;
                  uses ncs_template_advertise-dependent-filter-group-type;
                  container entropy-label-parameter {
                    // NCS drop when statement
                    description
                      "Configure information about entropy label parameter in a peer group.";
                    uses ncs_template_group-entropy-label-type;
                  }
                }
                container ipv6-unicast {
                  // NCS drop when statement
                  description
                    "Configure IPv6 unicast options.";
                  leaf advertise-community {
                    type string;
                    // NCS drop default statement
                    description
                      "Enable/disable advertise the community attribute to a peer or a peer group.";
                  }
                  leaf reflect-client {
                    // NCS drop when statement
                    type string;
                    // NCS drop default statement
                    description
                      "Enable/disable the local device as a route reflector (RR) and a peer or peer group as its client. This configuration is applicable between IBGP peers only. The configurations of RRs and its clients in an address family are valid only in this address family. Therefore, it is recommended to configure RRs and its clients in the specified address family that is required.";
                  }
                  leaf label-route-capability {
                    type string;
                    // NCS drop default statement
                    description
                      "Enable/disable a device to exchange labeled routes.";
                  }
                  leaf nexthop-configure {
                    type ncs_template_nexthop-configuration-type;
                    description
                      "Both the next-hop-local mode and next-hop-invariable mode are available when the peer address family is the VPNv4/VPNV6/L2VPN AD address family. Only the next-hop-local mode is available when the peer address family is not VPNv4/VPNV6/L2VPN AD address family. In next-hop-local mode, you can configure a BGP speaker to set its IP address of as the next hop of the routes to be advertised to IBGP peers or IBGP peer groups. In next-hop-invariable mode, you can configure PEs in different ASs not to change the next hop of routes when the PEs advertise the routes to their EBGP peers and use the next hop addresses of IGP routes to advertise imported IGP routes to IBGP peers. By default, when a BGP speaker advertises routes to EBGP peers and imported IGP routes to IBGP peers, the BGP speaker changes the next hop to its interface address.";
                  }
                  uses ncs_template_peer-policy-filter-type;
                  leaf advertise-ext-community {
                    type string;
                    // NCS drop default statement
                    description
                      "Enable/disable advertise the extended community attribute to a peer or peer group.";
                  }
                  leaf origin-as-validation {
                    // NCS drop when statement
                    type string;
                    // NCS drop default statement
                    description
                      "Enable/disable the BGP peer origin validation.";
                  }
                  leaf discard-ext-community {
                    type string;
                    // NCS drop default statement
                    description
                      "Enable/disable discard the extended community attribute in the routing information about a specified peer.";
                  }
                  leaf allow-as-loop {
                    type string;
                    description
                      "Allow repetitive local AS numbers. By default, repetitive local AS numbers are not allowed.";
                  }
                  leaf aigp {
                    // NCS drop when statement
                    type string;
                    // NCS drop default statement
                    description
                      "Enable/disable route with AIGP attribute advertisement to or from a peer.";
                  }
                  uses ncs_template_default-route-advertise-type;
                  leaf default-route-match-mode {
                    // NCS drop when statement
                    type ncs_template_cra-match-mode;
                    // NCS drop default statement
                    description
                      "Configure the matching mode of default route advertisement, which can be disabling of route advertisement conditions, enabling of all route advertisement conditions, and enabling of part route advertisement conditions. Enabling of all route advertisement conditions indicates that a default route can be advertised only when it matches all the conditions. Enabling of part route advertisement conditions indicates that a default route can be advertised only when it matches one condition.";
                  }
                  leaf add-path-mode {
                    // NCS drop when statement
                    type ncs_template_add-path-cap-type;
                    // NCS drop default statement
                    description
                      "Enable Add-Path route advertisement to a peer.";
                  }
                  uses ncs_template_ipv6-prefix-filter-type;
                  uses ncs_template_as-path-filter-type;
                  uses ncs_template_peer-group-acl6-name-or-num-type;
                  uses ncs_template_rt-update-interval-type;
                  uses ncs_template_preferred-value-type;
                  leaf add-path-number {
                    // NCS drop when statement
                    type string;
                    description
                      "Number of Add-Path routes that can be advertised to a peer.";
                  }
                  leaf substitute-as-enable {
                    // NCS drop when statement
                    type string;
                    // NCS drop default statement
                    description
                      "Enable/disable replace the AS number of a specified peer in the AS_Path attribute with the local AS number. On a PE where AS number replacement is enabled, if an AS number in the AS_Path attribute of a route is same as that of the CE to which the PE advertises the route, the PE replaces the AS number with its own AS number before advertising the route.";
                  }
                  leaf soo {
                    // NCS drop when statement
                    type string;
                    description
                      "Configure the Site-of-Origin (SoO) extended community attribute. This attribute can be expressed in the following formats: X.X.X.X:number<0-65535>, number<0-65535>:number<0-4294967295>, or number<0-65535>.number<0-65535>:number<0-65535> or <65536-4294967295>:<0-65535>. 0:0 or 0.0:0 is not supported.
                       Two CEs are in the same site and can advertise routes to each other, and they are connected to a VPN through PEs. If the local routes of a CE are advertised to the other CE over the VPN, a routing loop may occur.
                       The SoO feature can prevent a route advertised by a site from being sent back to the site, preventing routing loops. After SoO is enabled and a PE receives a route from a CE, the specified SoO attribute will be added to the route. Before advertising the route to the other CE, the PE checks the SoO attribute. If the SoO attribute is the same as the locally configured SoO attribute, the PE does not advertise the route, preventing routing loops.";
                  }
                  leaf keep-all-routes {
                    // NCS drop when statement
                    type string;
                    // NCS drop default statement
                    description
                      "Enable/disable saving all the updated information about BGP routes from a specified peer or peer group after a BGP connection is established, even though these BGP routes fail to match the routing policy on the ingress. By default, the updated information about BGP routes from a specified peer is saved only when the routes match the routing policy on the ingress. If a router supports route refreshing, this option is not required.";
                  }
                  leaf advertise-best-external {
                    // NCS drop when statement
                    type string;
                    // NCS drop must statement
                    // NCS drop must statement
                    // NCS drop must statement
                    // NCS drop default statement
                    description
                      "Enable/disable the device to advertise Best External routes to peers.";
                  }
                  leaf load-balancing-enable {
                    type string;
                    // NCS drop default statement
                    description
                      "Enable/disable a neighbour to participate in load balancing.";
                  }
                  choice load-balancing-ignore-as-type {
                    description
                      "Set load balancing as path type.";
                    case as-attribute {
                      description
                        "Ignore the as-path attribute.";
                      leaf load-balancing-as-path-ignore {
                        // NCS drop when statement
                        type empty;
                        description
                          "Configure BGP to ignore the AS_Path attribute when selecting the equal route. After as-path-neglect is selected, BGP does not compare the AS_Path length.";
                      }
                    }
                    case same-length-as-attribute {
                      description
                        "Ignore comparison of as-path attributes with the same length.";
                      leaf load-balancing-as-path-relax {
                        // NCS drop when statement
                        type empty;
                        description
                          "Configure BGP to ignore comparison of AS_Path attributes with the same length when selecting the equal route. After as-path-neglect is selected, BGP does not compare the AS_Path length.";
                      }
                    }
                  }
                  leaf prefix-sid {
                    // NCS drop when statement
                    type string;
                    // NCS drop default statement
                    description
                      "Enable/disable a device to exchange IPv4 prefix SIDs with a specified IPv6 peer group.";
                  }
                  choice prefix-sid-packet {
                    description
                      "Prefix-sid packet method.";
                    case sid-type5 {
                      description
                        "Packet by type5.";
                      leaf advertise-srv6-locator {
                        // NCS drop when statement
                        type empty;
                        description
                          "Advertise SRv6 locators.";
                      }
                    }
                  }
                  uses ncs_template_advertise-large-community-group-type;
                  uses ncs_template_group-independent-peer-group-type;
                  uses ncs_template_ipv6-default-route-match-conditions-type;
                  uses ncs_template_route-limit-accept-type;
                  uses ncs_template_public-as-only-type;
                  uses ncs_template_group-public-as-only-import-type;
                  uses ncs_template_advertise-dependent-filter6-group-type;
                }
                container ipv4-vpn {
                  // NCS drop when statement
                  description
                    "Configure IPv4 vpnv4 options.";
                  leaf advertise-community {
                    type string;
                    // NCS drop default statement
                    description
                      "Enable/disable advertise the community attribute to a peer or a peer group.";
                  }
                  leaf reflect-client {
                    // NCS drop when statement
                    type string;
                    // NCS drop default statement
                    description
                      "Enable/disable the local device as a route reflector (RR) and a peer or peer group as its client. This configuration is applicable between IBGP peers only. The configurations of RRs and its clients in an address family are valid only in this address family. Therefore, it is recommended to configure RRs and its clients in the specified address family that is required.";
                  }
                  leaf nexthop-configure {
                    type ncs_template_nexthop-configuration-type;
                    description
                      "Both the next-hop-local mode and next-hop-invariable mode are available when the peer address family is the VPNv4/VPNV6/L2VPN AD address family. Only the next-hop-local mode is available when the peer address family is not VPNv4/VPNV6/L2VPN AD address family. In next-hop-local mode, you can configure a BGP speaker to set its IP address of as the next hop of the routes to be advertised to IBGP peers or IBGP peer groups. In next-hop-invariable mode, you can configure PEs in different ASs not to change the next hop of routes when the PEs advertise the routes to their EBGP peers and use the next hop addresses of IGP routes to advertise imported IGP routes to IBGP peers. By default, when a BGP speaker advertises routes to EBGP peers and imported IGP routes to IBGP peers, the BGP speaker changes the next hop to its interface address.";
                  }
                  uses ncs_template_peer-policy-filter-type;
                  leaf ignore-bit-error {
                    // NCS drop when statement
                    type string;
                    // NCS drop default statement
                    description
                      "Enable/disable the peer to ignore bit error detection results.";
                  }
                  leaf allow-as-loop {
                    type string;
                    description
                      "Allow repetitive local AS numbers. By default, repetitive local AS numbers are not allowed.";
                  }
                  leaf aigp {
                    type string;
                    // NCS drop default statement
                    description
                      "Enable/disable route with AIGP attribute advertisement to or from a peer.";
                  }
                  leaf add-path-mode {
                    // NCS drop when statement
                    type ncs_template_add-path-cap-type;
                    // NCS drop default statement
                    description
                      "Enable Add-Path route advertisement to a peer.";
                  }
                  uses ncs_template_ip-prefix-filter-type;
                  uses ncs_template_peer-ipv4-reoriginate-type;
                  uses ncs_template_as-path-filter-type;
                  uses ncs_template_peer-group-acl-name-or-num-type;
                  uses ncs_template_rt-update-interval-type;
                  uses ncs_template_preferred-value-type;
                  leaf add-path-number {
                    // NCS drop when statement
                    type string;
                    description
                      "Number of Add-Path routes that can be advertised to a peer.";
                  }
                  leaf upe {
                    type string;
                    // NCS drop default statement
                    description
                      "Enable/disable the peer as an underlayer PE (UPE).";
                  }
                  leaf advertise-best-external {
                    // NCS drop when statement
                    type string;
                    // NCS drop must statement
                    // NCS drop must statement
                    // NCS drop must statement
                    // NCS drop default statement
                    description
                      "Enable/disable the device to advertise Best External routes to peers.";
                  }
                  uses ncs_template_advertise-large-community-group-type;
                  leaf keep-all-routes {
                    // NCS drop when statement
                    type string;
                    // NCS drop default statement
                    description
                      "Enable/disable saving all the updated information about BGP routes from a specified peer or peer group after a BGP connection is established, even though these BGP routes fail to match the routing policy on the ingress. By default, the updated information about BGP routes from a specified peer is saved only when the routes match the routing policy on the ingress. If a router supports route refreshing, this option is not required.";
                  }
                  uses ncs_template_group-independent-peer-group-type;
                  leaf origin-as-validation {
                    // NCS drop when statement
                    type string;
                    // NCS drop default statement
                    description
                      "Enable/disable the BGP peer origin validation.";
                  }
                  container default-route-originates {
                    description
                      "Configure advertised default VPNv4 routes.";
                    uses ncs_template_default-route-originate-type;
                  }
                  uses ncs_template_route-limit-type;
                  uses ncs_template_public-as-only-type;
                  uses ncs_template_group-public-as-only-import-type;
                }
                container ipv6-vpn {
                  // NCS drop when statement
                  description
                    "Configure IPv6 vpn options.";
                  leaf advertise-community {
                    type string;
                    // NCS drop default statement
                    description
                      "Enable/disable advertise the community attribute to a peer or a peer group.";
                  }
                  leaf reflect-client {
                    // NCS drop when statement
                    type string;
                    // NCS drop default statement
                    description
                      "Enable/disable the local device as a route reflector (RR) and a peer or peer group as its client. This configuration is applicable between IBGP peers only. The configurations of RRs and its clients in an address family are valid only in this address family. Therefore, it is recommended to configure RRs and its clients in the specified address family that is required.";
                  }
                  leaf nexthop-configure {
                    type ncs_template_nexthop-configuration-type;
                    description
                      "Both the next-hop-local mode and next-hop-invariable mode are available when the peer address family is the VPNv4/VPNV6/L2VPN AD address family. Only the next-hop-local mode is available when the peer address family is not VPNv4/VPNV6/L2VPN AD address family. In next-hop-local mode, you can configure a BGP speaker to set its IP address of as the next hop of the routes to be advertised to IBGP peers or IBGP peer groups. In next-hop-invariable mode, you can configure PEs in different ASs not to change the next hop of routes when the PEs advertise the routes to their EBGP peers and use the next hop addresses of IGP routes to advertise imported IGP routes to IBGP peers. By default, when a BGP speaker advertises routes to EBGP peers and imported IGP routes to IBGP peers, the BGP speaker changes the next hop to its interface address.";
                  }
                  uses ncs_template_peer-policy-filter-type;
                  leaf ignore-bit-error {
                    // NCS drop when statement
                    type string;
                    // NCS drop default statement
                    description
                      "Enable/disable the peer to ignore bit error detection results.";
                  }
                  leaf allow-as-loop {
                    type string;
                    description
                      "Allow repetitive local AS numbers. By default, repetitive local AS numbers are not allowed.";
                  }
                  leaf aigp {
                    type string;
                    // NCS drop default statement
                    description
                      "Enable/disable route with AIGP attribute advertisement to or from a peer.";
                  }
                  leaf add-path-mode {
                    // NCS drop when statement
                    type ncs_template_add-path-cap-type;
                    // NCS drop default statement
                    description
                      "Enable Add-Path route advertisement to a peer.";
                  }
                  uses ncs_template_ipv6-prefix-filter-type;
                  leaf reoriginate-route-enable {
                    type string;
                    // NCS drop default statement
                    description
                      "Enable/disable route regeneration.";
                  }
                  leaf reoriginate-ipv6-enable {
                    type string;
                    // NCS drop default statement
                    description
                      "Enable/disable IP route regeneration and advertisement.";
                  }
                  leaf reoriginate-mac-ipv6-enable {
                    type string;
                    // NCS drop default statement
                    description
                      "Enable/disable MAC-IP route regeneration and advertisement.";
                  }
                  uses ncs_template_as-path-filter-type;
                  uses ncs_template_peer-group-acl6-name-or-num-type;
                  uses ncs_template_rt-update-interval-type;
                  uses ncs_template_preferred-value-type;
                  leaf add-path-number {
                    // NCS drop when statement
                    type string;
                    description
                      "Number of Add-Path routes that can be advertised to a peer.";
                  }
                  leaf advertise-best-external {
                    // NCS drop when statement
                    type string;
                    // NCS drop must statement
                    // NCS drop must statement
                    // NCS drop must statement
                    // NCS drop default statement
                    description
                      "Enable/disable the device to advertise Best External routes to peers.";
                  }
                  uses ncs_template_advertise-large-community-group-type;
                  leaf keep-all-routes {
                    // NCS drop when statement
                    type string;
                    // NCS drop default statement
                    description
                      "Enable/disable saving all the updated information about BGP routes from a specified peer or peer group after a BGP connection is established, even though these BGP routes fail to match the routing policy on the ingress. By default, the updated information about BGP routes from a specified peer is saved only when the routes match the routing policy on the ingress. If a router supports route refreshing, this option is not required.";
                  }
                  uses ncs_template_group-independent-peer-group-type;
                  leaf origin-as-validation {
                    // NCS drop when statement
                    type string;
                    // NCS drop default statement
                    description
                      "Enable/disable the BGP peer origin validation.";
                  }
                  uses ncs_template_route-limit-type;
                  uses ncs_template_public-as-only-type;
                  uses ncs_template_group-public-as-only-import-type;
                }
                container ipv4-labeluni {
                  // NCS drop when statement
                  description
                    "Configure IPv4 label unicast options.";
                  leaf advertise-community {
                    type string;
                    // NCS drop default statement
                    description
                      "Enable/disable advertise the community attribute to a peer or a peer group.";
                  }
                  leaf reflect-client {
                    // NCS drop when statement
                    type string;
                    // NCS drop default statement
                    description
                      "Enable/disable the local device as a route reflector (RR) and a peer or peer group as its client. This configuration is applicable between IBGP peers only. The configurations of RRs and its clients in an address family are valid only in this address family. Therefore, it is recommended to configure RRs and its clients in the specified address family that is required.";
                  }
                  leaf check-tunnel-reachable {
                    type string;
                    // NCS drop default statement
                    description
                      "Enable/disable tunnel reachability check.";
                  }
                  uses ncs_template_peer-policy-filter-type;
                  leaf advertise-ext-community {
                    type string;
                    // NCS drop default statement
                    description
                      "Enable/disable advertise the extended community attribute to a peer or peer group.";
                  }
                  leaf discard-ext-community {
                    type string;
                    // NCS drop default statement
                    description
                      "Enable/disable discard the extended community attribute in the routing information about a specified peer.";
                  }
                  leaf allow-as-loop {
                    type string;
                    description
                      "Allow repetitive local AS numbers. By default, repetitive local AS numbers are not allowed.";
                  }
                  leaf aigp {
                    // NCS drop when statement
                    type string;
                    // NCS drop default statement
                    description
                      "Enable/disable route with AIGP attribute advertisement to or from a peer.";
                  }
                  leaf add-path-mode {
                    // NCS drop when statement
                    type ncs_template_add-path-cap-type;
                    // NCS drop default statement
                    description
                      "Enable Add-Path route advertisement to a peer.";
                  }
                  uses ncs_template_ip-prefix-filter-type;
                  uses ncs_template_as-path-filter-type;
                  uses ncs_template_peer-group-acl-name-or-num-type;
                  uses ncs_template_rt-update-interval-type;
                  leaf nexthop-configure {
                    type ncs_template_nexthop-configuration-type;
                    description
                      "Both the next-hop-local mode and next-hop-invariable mode are available when the peer address family is the VPNv4/VPNV6/L2VPN AD address family. Only the next-hop-local mode is available when the peer address family is not VPNv4/VPNV6/L2VPN AD address family. In next-hop-local mode, you can configure a BGP speaker to set its IP address of as the next hop of the routes to be advertised to IBGP peers or IBGP peer groups. In next-hop-invariable mode, you can configure PEs in different ASs not to change the next hop of routes when the PEs advertise the routes to their EBGP peers and use the next hop addresses of IGP routes to advertise imported IGP routes to IBGP peers. By default, when a BGP speaker advertises routes to EBGP peers and imported IGP routes to IBGP peers, the BGP speaker changes the next hop to its interface address.";
                  }
                  uses ncs_template_preferred-value-type;
                  leaf exp-mode {
                    // NCS drop when statement
                    type ncs_template_exp-mode-type;
                    // NCS drop default statement
                    description
                      "Specify the ASs in which a BGP label can inherit the QoS priority carried in the outer label of public tunnel in the Core AS and the ASs in which the priorities of BGP LSPs must be restored before the LSPs are advertised to a non-core AS.";
                  }
                  leaf add-path-number {
                    // NCS drop when statement
                    type string;
                    description
                      "Number of Add-Path routes that can be advertised to a peer.";
                  }
                  leaf substitute-as-enable {
                    // NCS drop when statement
                    type string;
                    // NCS drop default statement
                    description
                      "Enable/disable replace the AS number of a specified peer in the AS_Path attribute with the local AS number. On a PE where AS number replacement is enabled, if an AS number in the AS_Path attribute of a route is same as that of the CE to which the PE advertises the route, the PE replaces the AS number with its own AS number before advertising the route.";
                  }
                  leaf soo {
                    // NCS drop when statement
                    type string;
                    description
                      "Configure the Site-of-Origin (SoO) extended community attribute. This attribute can be expressed in the following formats: X.X.X.X:number<0-65535>, number<0-65535>:number<0-4294967295>, or number<0-65535>.number<0-65535>:number<0-65535> or <65536-4294967295>:<0-65535>. 0:0 or 0.0:0 is not supported.
                       Two CEs are in the same site and can advertise routes to each other, and they are connected to a VPN through PEs. If the local routes of a CE are advertised to the other CE over the VPN, a routing loop may occur.
                       The SoO feature can prevent a route advertised by a site from being sent back to the site, preventing routing loops. After SoO is enabled and a PE receives a route from a CE, the specified SoO attribute will be added to the route. Before advertising the route to the other CE, the PE checks the SoO attribute. If the SoO attribute is the same as the locally configured SoO attribute, the PE does not advertise the route, preventing routing loops.";
                  }
                  leaf advertise-best-external {
                    // NCS drop when statement
                    type string;
                    // NCS drop must statement
                    // NCS drop must statement
                    // NCS drop must statement
                    // NCS drop default statement
                    description
                      "Enable/disable the device to advertise Best External routes to peers.";
                  }
                  leaf load-balancing-enable {
                    // NCS drop when statement
                    type string;
                    // NCS drop default statement
                    description
                      "Enable/disable a neighbour to participate in load balancing.";
                  }
                  choice load-balancing-ignore-as-type {
                    description
                      "Set load balancing as path type.";
                    case as-attribute {
                      description
                        "Ignore the as-path attribute.";
                      leaf load-balancing-as-path-ignore {
                        // NCS drop when statement
                        type empty;
                        description
                          "Configure BGP to ignore the AS_Path attribute when selecting the equal route. After as-path-neglect is selected, BGP does not compare the AS_Path length.";
                      }
                    }
                    case same-length-as-attribute {
                      description
                        "Ignore comparison of as-path attributes with the same length.";
                      leaf load-balancing-as-path-relax {
                        // NCS drop when statement
                        type empty;
                        description
                          "Configure BGP to ignore comparison of AS_Path attributes with the same length when selecting the equal route. After as-path-neglect is selected, BGP does not compare the AS_Path length.";
                      }
                    }
                  }
                  uses ncs_template_advertise-large-community-group-type;
                  uses ncs_template_group-independent-peer-group-type;
                  uses ncs_template_route-limit-accept-type;
                  uses ncs_template_public-as-only-type;
                  uses ncs_template_group-public-as-only-import-type;
                  container entropy-label-parameter {
                    // NCS drop when statement
                    description
                      "Configure information about entropy label parameter in a peer group.";
                    uses ncs_template_group-entropy-label-type;
                  }
                }
                container ipv4-multicast {
                  // NCS drop when statement
                  description
                    "Configure IPv4 multicast options.";
                  uses ncs_template_default-route-advertise-type;
                  uses ncs_template_ip-prefix-filter-type;
                  uses ncs_template_as-path-filter-type;
                  uses ncs_template_peer-group-acl-name-or-num-type;
                  leaf advertise-ext-community {
                    type string;
                    // NCS drop default statement
                    description
                      "Enable/disable advertise the extended community attribute to a peer or peer group.";
                  }
                  leaf discard-ext-community {
                    type string;
                    // NCS drop default statement
                    description
                      "Enable/disable discard the extended community attribute in the routing information about a specified peer.";
                  }
                  leaf allow-as-loop {
                    type string;
                    description
                      "Allow repetitive local AS numbers. By default, repetitive local AS numbers are not allowed.";
                  }
                  leaf nexthop-configure {
                    type ncs_template_nexthop-configuration-type;
                    // NCS drop must statement
                    description
                      "Both the next-hop-local mode and next-hop-invariable mode are available when the peer address family is the VPNv4/VPNV6/L2VPN AD address family. Only the next-hop-local mode is available when the peer address family is not VPNv4/VPNV6/L2VPN AD address family. In next-hop-local mode, you can configure a BGP speaker to set its IP address of as the next hop of the routes to be advertised to IBGP peers or IBGP peer groups. In next-hop-invariable mode, you can configure PEs in different ASs not to change the next hop of routes when the PEs advertise the routes to their EBGP peers and use the next hop addresses of IGP routes to advertise imported IGP routes to IBGP peers. By default, when a BGP speaker advertises routes to EBGP peers and imported IGP routes to IBGP peers, the BGP speaker changes the next hop to its interface address.";
                  }
                  leaf advertise-community {
                    type string;
                    // NCS drop default statement
                    description
                      "Enable/disable advertise the community attribute to a peer or a peer group.";
                  }
                  leaf keep-all-routes {
                    // NCS drop when statement
                    type string;
                    // NCS drop default statement
                    description
                      "Enable/disable saving all the updated information about BGP routes from a specified peer or peer group after a BGP connection is established, even though these BGP routes fail to match the routing policy on the ingress. By default, the updated information about BGP routes from a specified peer is saved only when the routes match the routing policy on the ingress. If a router supports route refreshing, this option is not required.";
                  }
                  uses ncs_template_peer-policy-filter-type;
                  leaf reflect-client {
                    // NCS drop when statement
                    type string;
                    // NCS drop default statement
                    description
                      "Enable/disable the local device as a route reflector (RR) and a peer or peer group as its client. This configuration is applicable between IBGP peers only. The configurations of RRs and its clients in an address family are valid only in this address family. Therefore, it is recommended to configure RRs and its clients in the specified address family that is required.";
                  }
                  leaf load-balancing-enable {
                    type string;
                    // NCS drop default statement
                    description
                      "Enable/disable a neighbour to participate in load balancing.";
                  }
                  choice load-balancing-ignore-as-type {
                    description
                      "Set load balancing as path type.";
                    case as-attribute {
                      description
                        "Ignore the as-path attribute.";
                      leaf load-balancing-as-path-ignore {
                        // NCS drop when statement
                        type empty;
                        description
                          "Configure BGP to ignore the AS_Path attribute when selecting the equal route. After as-path-neglect is selected, BGP does not compare the AS_Path length.";
                      }
                    }
                    case same-length-as-attribute {
                      description
                        "Ignore comparison of as-path attributes with the same length.";
                      leaf load-balancing-as-path-relax {
                        // NCS drop when statement
                        type empty;
                        description
                          "Configure BGP to ignore comparison of AS_Path attributes with the same length when selecting the equal route. After as-path-neglect is selected, BGP does not compare the AS_Path length.";
                      }
                    }
                  }
                  uses ncs_template_advertise-large-community-group-type;
                  uses ncs_template_rt-update-interval-type;
                  uses bgp:ncs_template_preferred-value-type;
                  uses ncs_template_group-independent-peer-group-type;
                  uses ncs_template_route-limit-type;
                  uses ncs_template_public-as-only-type;
                  uses ncs_template_group-public-as-only-import-type;
                }
              }
            }
          }
        }
        container peers {
          description
            "List of BGP peers.";
          list peer {
            // NCS patched for predictable order
            ordered-by user;
            key "address";
            description
              "Configure a single BGP peer.";
            leaf address {
              type string;
              description
                "Connection address of a peer, which can be an IPv4 or IPv6 address.";
            }
            leaf remote-as {
              type ncs_template_as-number-validate;
              // NCS drop mandatory statement
              description
                "AS number of a peer, which must be selected or group name when creating, and which can be in either two-byte format or four-byte format:
                 The two-byte format is X. X is an integer ranging from 1 to 65535.
                 The four-byte format is X.Y and X. When the format is X.Y, X and Y are both integers, with the value of X ranging from 1 to 65535, and the value of Y ranging from 0 to 65535; when the format is X, X is an interger, with the value of X ranging from 1 to 4294967295.
                 The object cannot be modified.";
              ext:operation-exclude "update" {
                description
                  "The node cannot be modified, when node is already configured.";
              }
            }
            leaf group-name {
              type string;
              // NCS drop must statement
              description
                "Specify the name of a peer group that BGP peers need to join. That must be selected group name or AS when creating, and the value is a string, spaces not supported. By default, BGP peers join no peer group. BGP peers distinguish the peer group type when joining a peer group. IBGP peers cannot join an EBGP peer group. BGP peers will be deleted when they leave a peer group. The object cannot be modified.";
              ext:operation-exclude "update" {
                description
                  "The node cannot be modified, when the peer already belongs to a peer-group.";
              }
            }
            uses ncs_template_peer-local-if-type;
            uses ncs_template_authentication-attr-type;
            leaf description {
              type string;
              description
                "Description of a peer, which can be letters or digits. The description is a string, spaces supported. By default, no description is configured for a peer.";
            }
            leaf ebgp-max-hop {
              type string;
              // NCS drop must statement
              description
                "Maximum number of hops in an indirect EBGP connection. By default, EBGP connections can be established only between directly connected peers. The function must be configured on both ends. By default, value is determined by the neighbor type, the default value of EBGP is 1 and the default value of IBGP is 0.";
            }
            uses ncs_template_peer-tracking-type;
            leaf conventional {
              type string;
              // NCS drop default statement
              description
                "Enable/disable general router functions on peers. In conventional mode, not all the extended router functions, such as, route refreshing, GR, and multi-address family negotiation, are available. Therefore, the router of a new version can be compatible with the routers of earlier versions.";
            }
            leaf route-refresh {
              type string;
              // NCS drop default statement
              description
                "Enable/disable BGP to advertise Refresh messages to peers.";
            }
            leaf four-byte-as {
              type string;
              // NCS drop default statement
              description
                "Enable/disable BGP to advertise routes carrying 4-byte AS numbers to peers. After the 4-byte AS number function is disabled, Open packets will not carry 4-byte AS number capability flag, and peer ends will not know that local ends have the 4-byte AS number function. The 4-byte AS number function cannot be disabled from peers (peer groups) if a 4-byte AS number, fake AS number, or confederation ID is configured on a router and the AS number of a peer is 4-byte. If the 4-byte AS number function is disabled in such a situation, BGP sessions may fail to be established, and route transmission may be affected.";
            }
            leaf ignore {
              type string;
              // NCS drop default statement
              description
                "Enable/disable the function to tear down sessions between peers and clear all related routing information.";
            }
            leaf valid-ttl-hops {
              type string;
              // NCS drop must statement
              description
                "Enable GTSM on a peer or peer group. The valid-TTL-Value parameter is used to specify the number of TTL hops to be detected. If the value is configured as hops, the valid TTL range of the detected packet is [255-hops+1, 255].";
            }
            leaf connect-mode {
              type ncs_template_connect-mode;
              // NCS drop default statement
              description
                "The value can be Connect-only, Listen-only, or Both. If the value is Connect-only, the specified peer or peer group only initiatively sends connection requests, instead of listening to connection requests. If the value is Listen-only, the specified peer or peer group only listens to connection requests, instead of initiatively sending connection requests. If the value is Both, the specified peer or peer group not only initiatively sends connection requests, but also listens to connection requests. The default value is Both.";
            }
            leaf log-change {
              type string;
              // NCS drop default statement
              description
                "Enable/disable BGP to record the session status and events of the specified peer or peer group.";
            }
            leaf path-mtu-auto-discovery {
              type string;
              // NCS drop default statement
              description
                "Enable/disable path mtu auto discovery.";
            }
            leaf local-ifnet-disable {
              type string;
              description
                "Enable/disable MPLS local IFNET tunnel creation on a BGP IPv4 peer. By default, MPLS local IFNET tunnels can be created on an EBGP peer,but such tunnels cannot be created on an IBGP peer.";
              ext:dynamic-default;
            }
            leaf check-first-as {
              type ncs_template_peer-cap-config-state;
              // NCS drop default statement
              description
                "Check the first AS in the AS_Path of the update messages from EBGP peers.";
            }
            leaf egress-engineer {
              // NCS drop when statement
              type ncs_template_epe-state;
              // NCS drop default statement
              description
                "BGP Egress Peer Engineering (BGP-EPE) is enable or disable. The default value is default (The function is disable, If the neighbour joins the group, the function is Inheritance group).";
            }
            leaf tcp-mss {
              type string;
              description
                "Maximum TCP MSS value used for TCP connection establishment for a peer.";
            }
            leaf memory-priority {
              type ncs_template_peer-memory-priority;
              // NCS drop default statement
              description
                "Set a priority that determines the disconnection order of a BGP peer relationship if memory overload occurs.";
            }
            // NCS drop config false leaf 'memory-priority-capability'
            leaf oscillation-dampening {
              type ncs_template_peer-attr-enable-type;
              description
                "Enable/disable BGP to suppress the establishment of a specified peer relationship that flaps continuously. By default, the capability is enabled.";
            }
            // NCS drop config false container 'effect-state'
            uses ncs_template_fake-as-type;
            uses ncs_template_peer-timer-para-type;
            uses ncs_template_peer-bfd-parameter-type;
            // NCS drop config false container 'bfd-parameter-state'
            container egress-engineer-parameter {
              // NCS drop when statement
              description
                "Configure BGP peer egress engineering information.";
              leaf static-label {
                type string;
                description
                  "The static label for BGP EPE.";
              }
              leaf label-pop {
                // NCS drop when statement
                type string;
                // NCS drop must statement
                // NCS drop default statement
                description
                  "Enable/disable the BGP-EPE label popping function.";
              }
              leaf relate-bfd {
                type string;
                // NCS drop must statement
                // NCS drop default statement
                description
                  "Enable/disable association between the BGP-EPE label and BFD status.";
              }
              leaf peer-set-name {
                type string;
                description
                  "Add peer to peer set.";
              }
            }
            container graceful-restart {
              description
                "Configure graceful restart.";
              uses ncs_template_peer-graceful-restart-type;
              leaf peer-reset {
                type ncs_template_peer-comm-config-type;
                // NCS drop default statement
                description
                  "Enable/disable reseting BGP peer graceful.";
              }
              // NCS drop config false leaf 'effect-peer-reset'
            }
            container local-graceful-restart {
              description
                "Configure local graceful restart.";
              uses ncs_template_peer-graceful-restart-type;
            }
            container afs {
              description
                "List of peers in a specified address family.";
              list af {
                // NCS patched for predictable order
                ordered-by user;
                key "type";
                description
                  "Configure peer in a specified address family.";
                leaf type {
                  type bgp:ncs_template_af-type;
                  // NCS drop must statement
                  description
                    "Specify the address family type to set the peer enable.";
                }
                container ipv4-unicast {
                  // NCS drop when statement
                  description
                    "Configure IPv4 unicast options.";
                  leaf group-name {
                    type string;
                    // NCS drop must statement
                    // NCS drop must statement
                    description
                      "Configure a name for a peer group. After a peer is deleted from the peer group, the peer is disabled from the address family. The object cannot be modified.";
                    ext:operation-exclude "update" {
                      description
                        "The node cannot be modified, when the peer already belongs to a peer-group.";
                    }
                  }
                  leaf advertise-community {
                    type string;
                    // NCS drop default statement
                    description
                      "Enable/disable advertise the community attribute to a peer or a peer group.";
                  }
                  leaf reflect-client {
                    type string;
                    // NCS drop default statement
                    description
                      "Enable/disable the local device as a route reflector (RR) and a peer or peer group as its client. This configuration is applicable between IBGP peers only. The configurations of RRs and its clients in an address family are valid only in this address family. Therefore, it is recommended to configure RRs and its clients in the specified address family that is required.";
                  }
                  leaf orf-type {
                    // NCS drop when statement
                    type bgp:ncs_template_bgp-orf-type;
                    // NCS drop must statement
                    // NCS drop default statement
                    description
                      "ORF Type.";
                  }
                  leaf orf-mode {
                    // NCS drop when statement
                    type bgp:ncs_template_bgp-orf-mode-type;
                    // NCS drop must statement
                    // NCS drop default statement
                    description
                      "Configure an outbound route filtering (ORF) mode, which can be Receive, Send, or Both, and the default ORF mode is Both.";
                  }
                  leaf label-route-capability {
                    type string;
                    // NCS drop default statement
                    description
                      "Enable/disable a device to exchange labeled routes.";
                  }
                  leaf check-tunnel-reachable {
                    // NCS drop when statement
                    type string;
                    // NCS drop default statement
                    description
                      "Enable/disable tunnel reachability check.";
                  }
                  leaf check-withdraw-type {
                    // NCS drop when statement
                    type string;
                    // NCS drop default statement
                    status obsolete;
                    description
                      "Enable/disable withdraw type check.";
                  }
                  leaf nexthop-configure {
                    type ncs_template_nexthop-configuration-type;
                    description
                      "Both the next-hop-local mode and next-hop-invariable mode are available when the peer address family is the VPNv4/VPNV6/L2VPN AD address family. Only the next-hop-local mode is available when the peer address family is not VPNv4/VPNV6/L2VPN AD address family. In next-hop-local mode, you can configure a BGP speaker to set its IP address of as the next hop of the routes to be advertised to IBGP peers or IBGP peer groups. In next-hop-invariable mode, you can configure PEs in different ASs not to change the next hop of routes when the PEs advertise the routes to their EBGP peers and use the next hop addresses of IGP routes to advertise imported IGP routes to IBGP peers. By default, when a BGP speaker advertises routes to EBGP peers and imported IGP routes to IBGP peers, the BGP speaker changes the next hop to its interface address.";
                  }
                  uses ncs_template_peer-policy-filter-type;
                  leaf advertise-ext-community {
                    type string;
                    // NCS drop default statement
                    description
                      "Enable/disable advertise the extended community attribute to a peer or peer group.";
                  }
                  leaf origin-as-validation {
                    // NCS drop when statement
                    type string;
                    // NCS drop default statement
                    description
                      "Enable/disable the BGP peer origin validation.";
                  }
                  leaf discard-ext-community {
                    type string;
                    // NCS drop default statement
                    description
                      "Enable/disable discard the extended community attribute in the routing information about a specified peer.";
                  }
                  leaf allow-as-loop {
                    type string;
                    description
                      "Allow repetitive local AS numbers. By default, repetitive local AS numbers are not allowed.";
                  }
                  leaf aigp {
                    // NCS drop when statement
                    type string;
                    // NCS drop default statement
                    description
                      "Enable/disable route with AIGP attribute advertisement to or from a peer.";
                  }
                  uses ncs_template_default-route-advertise-type;
                  leaf default-route-match-mode {
                    // NCS drop when statement
                    type ncs_template_cra-match-mode;
                    // NCS drop default statement
                    description
                      "Configure the matching mode of default route advertisement, which can be disabling of route advertisement conditions, enabling of all route advertisement conditions, and enabling of part route advertisement conditions. Enabling of all route advertisement conditions indicates that a default route can be advertised only when it matches all the conditions. Enabling of part route advertisement conditions indicates that a default route can be advertised only when it matches one condition.";
                  }
                  leaf add-path-mode {
                    // NCS drop when statement
                    type ncs_template_add-path-cap-type;
                    // NCS drop default statement
                    description
                      "Enable add-path route advertisement to a peer.";
                  }
                  uses ncs_template_ip-prefix-filter-type;
                  uses ncs_template_as-path-filter-type;
                  uses ncs_template_peer-group-acl-name-or-num-type;
                  uses ncs_template_rt-update-interval-type;
                  uses ncs_template_preferred-value-type;
                  leaf add-path-number {
                    // NCS drop when statement
                    type string;
                    description
                      "Number of add-path routes that can be advertised to a peer.";
                  }
                  leaf substitute-as-enable {
                    type string;
                    // NCS drop default statement
                    description
                      "Enable/disable replace the AS number of a specified peer in the AS_Path attribute with the local AS number. On a PE where AS number replacement is enabled, if an AS number in the AS_Path attribute of a route is same as that of the CE to which the PE advertises the route, the PE replaces the AS number with its own AS number before advertising the route.";
                  }
                  leaf soo {
                    // NCS drop when statement
                    type string;
                    description
                      "Configure the Site-of-Origin (SoO) extended community attribute. This attribute can be expressed in the following formats: X.X.X.X:number<0-65535>, number<0-65535>:number<0-4294967295>, or number<0-65535>.number<0-65535>:number<0-65535> or <65536-4294967295>:<0-65535>. 0:0 or 0.0:0 is not supported.
                       Two CEs are in the same site and can advertise routes to each other, and they are connected to a VPN through PEs. If the local routes of a CE are advertised to the other CE over the VPN, a routing loop may occur.
                       The SoO feature can prevent a route advertised by a site from being sent back to the site, preventing routing loops. After SoO is enabled and a PE receives a route from a CE, the specified SoO attribute will be added to the route. Before advertising the route to the other CE, the PE checks the SoO attribute. If the SoO attribute is the same as the locally configured SoO attribute, the PE does not advertise the route, preventing routing loops.";
                  }
                  leaf keep-all-routes {
                    // NCS drop when statement
                    type string;
                    // NCS drop default statement
                    description
                      "Enable/disable saving all the updated information about BGP routes from a specified peer or peer group after a BGP connection is established, even though these BGP routes fail to match the routing policy on the ingress. By default, the updated information about BGP routes from a specified peer is saved only when the routes match the routing policy on the ingress. If a router supports route refreshing, this option is not required.";
                  }
                  leaf exp-mode {
                    type ncs_template_exp-mode-type;
                    // NCS drop default statement
                    description
                      "Specify the ASs in which a BGP label can inherit the QoS priority carried in the outer label of public tunnel in the Core AS and the ASs in which the priorities of BGP LSPs must be restored before the LSPs are advertised to a non-core AS.";
                  }
                  leaf advertise-best-external {
                    // NCS drop when statement
                    type string;
                    // NCS drop must statement
                    // NCS drop must statement
                    // NCS drop must statement
                    // NCS drop default statement
                    description
                      "Enable/disable the device to advertise Best External routes to peers.";
                  }
                  leaf load-balancing-enable {
                    type string;
                    // NCS drop default statement
                    description
                      "Enable/disable a neighbour to participate in load balancing.";
                  }
                  choice load-balancing-ignore-as-type {
                    description
                      "Set load balancing as path type.";
                    case as-attribute {
                      description
                        "Ignore the as-path attribute.";
                      leaf load-balancing-as-path-ignore {
                        // NCS drop when statement
                        type empty;
                        description
                          "Configure BGP to ignore the AS_Path attribute when selecting the equal route. After as-path-neglect is selected, BGP does not compare the AS_Path length.";
                      }
                    }
                    case same-length-as-attribute {
                      description
                        "Ignore comparison of as-path attributes with the same length.";
                      leaf load-balancing-as-path-relax {
                        // NCS drop when statement
                        type empty;
                        description
                          "Configure BGP to ignore comparison of AS_Path attributes with the same length when selecting the equal route. After as-path-neglect is selected, BGP does not compare the AS_Path length.";
                      }
                    }
                  }
                  leaf prefix-sid {
                    // NCS drop when statement
                    type bgp:ncs_template_peer-comm-config-type;
                    // NCS drop default statement
                    description
                      "Enable/disable a device to exchange IPv4 prefix SIDs with a specified IPv6 peer.";
                  }
                  // NCS drop config false leaf 'prefix-sid-state'
                  choice prefix-sid-packet {
                    description
                      "Prefix-sid packet method.";
                    case sid-type5 {
                      description
                        "Packet by type5.";
                      leaf advertise-srv6-locator {
                        // NCS drop when statement
                        type empty;
                        description
                          "Advertise SRv6 locators.";
                      }
                    }
                  }
                  // NCS drop config false container 'effect-state'
                  uses ncs_template_advertise-large-community-type;
                  uses ncs_template_peer-independent-peer-group-type;
                  leaf rpd-policy-export {
                    // NCS drop when statement
                    type bgp:ncs_template_peer-enable-config-type;
                    // NCS drop default statement
                    description
                      "Enable/disable RPD export policy.";
                  }
                  uses ncs_template_ipv4-default-route-match-conditions-type;
                  uses ncs_template_route-limit-accept-type;
                  uses ncs_template_public-as-only-type;
                  uses ncs_template_peer-public-as-only-import-type;
                  container entropy-label-parameter {
                    // NCS drop when statement
                    description
                      "Configure information about entropy label parameter configuration in a peer.";
                    uses ncs_template_peer-entropy-label-type;
                  }
                  uses ncs_template_path-attr-map-type;
                  uses ncs_template_advertise-dependent-filter-type;
                }
                container ipv6-unicast {
                  // NCS drop when statement
                  description
                    "Configure IPv6 unicast options.";
                  leaf group-name {
                    type string;
                    // NCS drop must statement
                    // NCS drop must statement
                    description
                      "Configure a name for a peer group. After a peer is deleted from the peer group, the peer is disabled from the address family. The object cannot be modified.";
                    ext:operation-exclude "update" {
                      description
                        "The node cannot be modified, when the peer already belongs to a peer-group.";
                    }
                  }
                  leaf advertise-community {
                    type string;
                    // NCS drop default statement
                    description
                      "Enable/disable advertise the community attribute to a peer or a peer group.";
                  }
                  leaf reflect-client {
                    type string;
                    // NCS drop default statement
                    description
                      "Enable/disable the local device as a route reflector (RR) and a peer or peer group as its client. This configuration is applicable between IBGP peers only. The configurations of RRs and its clients in an address family are valid only in this address family. Therefore, it is recommended to configure RRs and its clients in the specified address family that is required.";
                  }
                  leaf label-route-capability {
                    type string;
                    // NCS drop default statement
                    description
                      "Enable/disable a device to exchange labeled routes.";
                  }
                  leaf nexthop-configure {
                    type ncs_template_nexthop-configuration-type;
                    // NCS drop must statement
                    description
                      "Both the next-hop-local mode and next-hop-invariable mode are available when the peer address family is the VPNv4/VPNV6/L2VPN AD address family. Only the next-hop-local mode is available when the peer address family is not VPNv4/VPNV6/L2VPN AD address family. In next-hop-local mode, you can configure a BGP speaker to set its IP address of as the next hop of the routes to be advertised to IBGP peers or IBGP peer groups. In next-hop-invariable mode, you can configure PEs in different ASs not to change the next hop of routes when the PEs advertise the routes to their EBGP peers and use the next hop addresses of IGP routes to advertise imported IGP routes to IBGP peers. By default, when a BGP speaker advertises routes to EBGP peers and imported IGP routes to IBGP peers, the BGP speaker changes the next hop to its interface address.";
                  }
                  uses ncs_template_peer-policy-filter-type;
                  leaf advertise-ext-community {
                    type string;
                    // NCS drop default statement
                    description
                      "Enable/disable advertise the extended community attribute to a peer or peer group.";
                  }
                  leaf origin-as-validation {
                    // NCS drop when statement
                    type string;
                    // NCS drop default statement
                    description
                      "Enable/disable the BGP peer origin validation.";
                  }
                  leaf discard-ext-community {
                    type string;
                    // NCS drop default statement
                    description
                      "Enable/disable discard the extended community attribute in the routing information about a specified peer.";
                  }
                  leaf allow-as-loop {
                    type string;
                    description
                      "Allow repetitive local AS numbers. By default, repetitive local AS numbers are not allowed.";
                  }
                  leaf aigp {
                    // NCS drop when statement
                    type string;
                    // NCS drop default statement
                    description
                      "Enable/disable route with AIGP attribute advertisement to or from a peer.";
                  }
                  uses ncs_template_default-route-advertise-type;
                  leaf default-route-match-mode {
                    // NCS drop when statement
                    type ncs_template_cra-match-mode;
                    // NCS drop default statement
                    description
                      "Configure the matching mode of default route advertisement, which can be disabling of route advertisement conditions, enabling of all route advertisement conditions, and enabling of part route advertisement conditions. Enabling of all route advertisement conditions indicates that a default route can be advertised only when it matches all the conditions. Enabling of part route advertisement conditions indicates that a default route can be advertised only when it matches one condition.";
                  }
                  leaf add-path-mode {
                    // NCS drop when statement
                    type ncs_template_add-path-cap-type;
                    // NCS drop default statement
                    description
                      "Enable Add-Path route advertisement to a peer.";
                  }
                  uses ncs_template_ipv6-prefix-filter-type;
                  uses ncs_template_as-path-filter-type;
                  uses ncs_template_peer-group-acl6-name-or-num-type;
                  uses ncs_template_rt-update-interval-type;
                  uses ncs_template_preferred-value-type;
                  leaf add-path-number {
                    // NCS drop when statement
                    type string;
                    description
                      "Number of Add-Path routes that can be advertised to a peer.";
                  }
                  leaf substitute-as-enable {
                    type string;
                    // NCS drop default statement
                    description
                      "Enable/disable replace the AS number of a specified peer in the AS_Path attribute with the local AS number. On a PE where AS number replacement is enabled, if an AS number in the AS_Path attribute of a route is same as that of the CE to which the PE advertises the route, the PE replaces the AS number with its own AS number before advertising the route.";
                  }
                  leaf soo {
                    // NCS drop when statement
                    type string;
                    description
                      "Configure the Site-of-Origin (SoO) extended community attribute. This attribute can be expressed in the following formats: X.X.X.X:number<0-65535>, number<0-65535>:number<0-4294967295>, or number<0-65535>.number<0-65535>:number<0-65535> or <65536-4294967295>:<0-65535>. 0:0 or 0.0:0 is not supported.
                       Two CEs are in the same site and can advertise routes to each other, and they are connected to a VPN through PEs. If the local routes of a CE are advertised to the other CE over the VPN, a routing loop may occur.
                       The SoO feature can prevent a route advertised by a site from being sent back to the site, preventing routing loops. After SoO is enabled and a PE receives a route from a CE, the specified SoO attribute will be added to the route. Before advertising the route to the other CE, the PE checks the SoO attribute. If the SoO attribute is the same as the locally configured SoO attribute, the PE does not advertise the route, preventing routing loops.";
                  }
                  leaf keep-all-routes {
                    // NCS drop when statement
                    type string;
                    // NCS drop default statement
                    description
                      "Enable/disable saving all the updated information about BGP routes from a specified peer or peer group after a BGP connection is established, even though these BGP routes fail to match the routing policy on the ingress. By default, the updated information about BGP routes from a specified peer is saved only when the routes match the routing policy on the ingress. If a router supports route refreshing, this option is not required.";
                  }
                  leaf advertise-best-external {
                    // NCS drop when statement
                    type string;
                    // NCS drop must statement
                    // NCS drop must statement
                    // NCS drop must statement
                    // NCS drop default statement
                    description
                      "Enable/disable the device to advertise Best External routes to peers.";
                  }
                  leaf load-balancing-enable {
                    type string;
                    // NCS drop default statement
                    description
                      "Enable/disable a neighbour to participate in load balancing.";
                  }
                  choice load-balancing-ignore-as-type {
                    description
                      "Set load balancing as path type.";
                    case as-attribute {
                      description
                        "Ignore the as-path attribute.";
                      leaf load-balancing-as-path-ignore {
                        // NCS drop when statement
                        type empty;
                        description
                          "Configure BGP to ignore the AS_Path attribute when selecting the equal route. After as-path-neglect is selected, BGP does not compare the AS_Path length.";
                      }
                    }
                    case same-length-as-attribute {
                      description
                        "Ignore comparison of as-path attributes with the same length.";
                      leaf load-balancing-as-path-relax {
                        // NCS drop when statement
                        type empty;
                        description
                          "Configure BGP to ignore comparison of AS_Path attributes with the same length when selecting the equal route. After as-path-neglect is selected, BGP does not compare the AS_Path length.";
                      }
                    }
                  }
                  leaf tunnel-policy {
                    // NCS drop when statement
                    type string;
                    description
                      "Apply a tunnel policy for a 6PE peer. By default, no tunnel policy is configured.";
                  }
                  leaf prefix-sid {
                    // NCS drop when statement
                    type bgp:ncs_template_peer-comm-config-type;
                    // NCS drop default statement
                    description
                      "Enable/disable a device to exchange prefix SIDs with a specified IPv6 peer.";
                  }
                  // NCS drop config false leaf 'prefix-sid-state'
                  choice prefix-sid-packet {
                    description
                      "Prefix-sid packet method.";
                    case sid-type5 {
                      description
                        "Packet by type5.";
                      leaf advertise-srv6-locator {
                        // NCS drop when statement
                        type empty;
                        description
                          "Advertise SRv6 locators.";
                      }
                    }
                  }
                  // NCS drop config false container 'effect-state'
                  uses ncs_template_advertise-large-community-type;
                  uses ncs_template_peer-independent-peer-group-type;
                  uses ncs_template_ipv6-default-route-match-conditions-type;
                  uses ncs_template_route-limit-accept-type;
                  uses ncs_template_public-as-only-type;
                  uses ncs_template_peer-public-as-only-import-type;
                  uses ncs_template_path-attr-map-type;
                  uses ncs_template_advertise-dependent-filter6-type;
                }
                container ipv4-vpn {
                  // NCS drop when statement
                  description
                    "Configure IPv4 VPNv4 options.";
                  leaf group-name {
                    type string;
                    // NCS drop must statement
                    // NCS drop must statement
                    description
                      "Configure a name for a peer group. After a peer is deleted from the peer group, the peer is disabled from the address family. The object cannot be modified.";
                    ext:operation-exclude "update" {
                      description
                        "The node cannot be modified, when the peer already belongs to a peer-group.";
                    }
                  }
                  leaf advertise-community {
                    type string;
                    // NCS drop default statement
                    description
                      "Enable/disable advertise the community attribute to a peer or a peer group.";
                  }
                  leaf reflect-client {
                    type string;
                    // NCS drop default statement
                    description
                      "Enable/disable the local device as a route reflector (RR) and a peer or peer group as its client. This configuration is applicable between IBGP peers only. The configurations of RRs and its clients in an address family are valid only in this address family. Therefore, it is recommended to configure RRs and its clients in the specified address family that is required.";
                  }
                  leaf nexthop-configure {
                    type ncs_template_nexthop-configuration-type;
                    description
                      "Both the next-hop-local mode and next-hop-invariable mode are available when the peer address family is the VPNv4/VPNV6/L2VPN AD address family. Only the next-hop-local mode is available when the peer address family is not VPNv4/VPNV6/L2VPN AD address family. In next-hop-local mode, you can configure a BGP speaker to set its IP address of as the next hop of the routes to be advertised to IBGP peers or IBGP peer groups. In next-hop-invariable mode, you can configure PEs in different ASs not to change the next hop of routes when the PEs advertise the routes to their EBGP peers and use the next hop addresses of IGP routes to advertise imported IGP routes to IBGP peers. By default, when a BGP speaker advertises routes to EBGP peers and imported IGP routes to IBGP peers, the BGP speaker changes the next hop to its interface address.";
                  }
                  uses ncs_template_peer-policy-filter-type;
                  leaf ignore-bit-error {
                    // NCS drop when statement
                    type string;
                    // NCS drop default statement
                    description
                      "Enable/disable the peer to ignore bit error detection results.";
                  }
                  leaf allow-as-loop {
                    type string;
                    description
                      "Allow repetitive local AS numbers. By default, repetitive local AS numbers are not allowed.";
                  }
                  leaf aigp {
                    type string;
                    // NCS drop default statement
                    description
                      "Enable/disable route with AIGP attribute advertisement to or from a peer.";
                  }
                  uses ncs_template_peer-add-path-type;
                  uses ncs_template_ip-prefix-filter-type;
                  uses ncs_template_peer-ipv4-reoriginate-type;
                  uses ncs_template_as-path-filter-type;
                  uses ncs_template_peer-group-acl-name-or-num-type;
                  uses ncs_template_rt-update-interval-type;
                  uses ncs_template_preferred-value-type;
                  leaf upe {
                    type string;
                    // NCS drop default statement
                    description
                      "Enable/disable the peer as an underlayer PE (UPE).";
                  }
                  leaf high-priority {
                    type ncs_template_peer-enable-config-type;
                    // NCS drop default statement
                    description
                      "Enable vpn-router high priority.";
                  }
                  leaf prefix-sid {
                    type bgp:ncs_template_peer-enable-config-type;
                    // NCS drop default statement
                    description
                      "Specify a SID mode relay for peer.";
                  }
                  choice prefix-sid-packet {
                    description
                      "Prefix-sid packet method.";
                    case sid-type5 {
                      description
                        "Packet by type5.";
                      leaf sid-type5 {
                        // NCS drop when statement
                        type empty;
                        description
                          "Packet by type5.";
                      }
                      leaf advertise-srv6-locator {
                        // NCS drop when statement
                        type empty;
                        description
                          "Advertise SRv6 locators.";
                      }
                    }
                  }
                  leaf advertise-best-external {
                    type string;
                    // NCS drop must statement
                    // NCS drop must statement
                    // NCS drop must statement
                    // NCS drop default statement
                    description
                      "Enable/disable the device to advertise Best External routes to peers.";
                  }
                  uses ncs_template_advertise-large-community-type;
                  leaf keep-all-routes {
                    // NCS drop when statement
                    type string;
                    // NCS drop default statement
                    description
                      "Enable/disable saving all the updated information about BGP routes from a specified peer or peer group after a BGP connection is established, even though these BGP routes fail to match the routing policy on the ingress. By default, the updated information about BGP routes from a specified peer is saved only when the routes match the routing policy on the ingress. If a router supports route refreshing, this option is not required.";
                  }
                  uses ncs_template_peer-independent-peer-group-type;
                  uses ncs_template_peer-origin-as-validation-type;
                  container default-route-originates {
                    description
                      "Configure advertised default VPNv4 routes.";
                    uses ncs_template_default-route-originate-type;
                  }
                  uses ncs_template_route-limit-type;
                  uses ncs_template_public-as-only-type;
                  uses ncs_template_peer-public-as-only-import-type;
                  uses ncs_template_path-attr-map-type;
                }
                container ipv6-vpn {
                  // NCS drop when statement
                  description
                    "Configure IPv6 vpn options.";
                  leaf group-name {
                    type string;
                    // NCS drop must statement
                    // NCS drop must statement
                    description
                      "Configure a name for a peer group. After a peer is deleted from the peer group, the peer is disabled from the address family. The object cannot be modified.";
                    ext:operation-exclude "update" {
                      description
                        "The node cannot be modified, when the peer already belongs to a peer-group.";
                    }
                  }
                  leaf advertise-community {
                    type string;
                    // NCS drop default statement
                    description
                      "Enable/disable advertise the community attribute to a peer or a peer group.";
                  }
                  leaf reflect-client {
                    type string;
                    // NCS drop default statement
                    description
                      "Enable/disable the local device as a route reflector (RR) and a peer or peer group as its client. This configuration is applicable between IBGP peers only. The configurations of RRs and its clients in an address family are valid only in this address family. Therefore, it is recommended to configure RRs and its clients in the specified address family that is required.";
                  }
                  leaf nexthop-configure {
                    type ncs_template_nexthop-configuration-type;
                    description
                      "Both the next-hop-local mode and next-hop-invariable mode are available when the peer address family is the VPNv4/VPNV6/L2VPN AD address family. Only the next-hop-local mode is available when the peer address family is not VPNv4/VPNV6/L2VPN AD address family. In next-hop-local mode, you can configure a BGP speaker to set its IP address of as the next hop of the routes to be advertised to IBGP peers or IBGP peer groups. In next-hop-invariable mode, you can configure PEs in different ASs not to change the next hop of routes when the PEs advertise the routes to their EBGP peers and use the next hop addresses of IGP routes to advertise imported IGP routes to IBGP peers. By default, when a BGP speaker advertises routes to EBGP peers and imported IGP routes to IBGP peers, the BGP speaker changes the next hop to its interface address.";
                  }
                  uses ncs_template_peer-policy-filter-type;
                  leaf ignore-bit-error {
                    // NCS drop when statement
                    type string;
                    // NCS drop default statement
                    description
                      "Enable/disable the peer to ignore bit error detection results.";
                  }
                  leaf allow-as-loop {
                    type string;
                    description
                      "Allow repetitive local AS numbers. By default, repetitive local AS numbers are not allowed.";
                  }
                  leaf aigp {
                    type string;
                    // NCS drop default statement
                    description
                      "Enable/disable route with AIGP attribute advertisement to or from a peer.";
                  }
                  uses ncs_template_peer-add-path-type;
                  uses ncs_template_ipv6-prefix-filter-type;
                  leaf reoriginate-route-enable {
                    type string;
                    // NCS drop default statement
                    description
                      "Enable/disable route regeneration.";
                  }
                  leaf reoriginate-ipv6-enable {
                    type string;
                    // NCS drop default statement
                    description
                      "Enable/disable IP route regeneration and advertisement.";
                  }
                  leaf reoriginate-mac-ipv6-enable {
                    type string;
                    // NCS drop default statement
                    description
                      "Enable/disable MAC-IP route regeneration and advertisement.";
                  }
                  uses ncs_template_as-path-filter-type;
                  uses ncs_template_peer-group-acl6-name-or-num-type;
                  uses ncs_template_rt-update-interval-type;
                  uses ncs_template_preferred-value-type;
                  leaf advertise-best-external {
                    type string;
                    // NCS drop must statement
                    // NCS drop must statement
                    // NCS drop must statement
                    // NCS drop default statement
                    description
                      "Enable/disable the device to advertise Best External routes to peers.";
                  }
                  uses ncs_template_advertise-large-community-type;
                  leaf keep-all-routes {
                    // NCS drop when statement
                    type string;
                    // NCS drop default statement
                    description
                      "Enable/disable saving all the updated information about BGP routes from a specified peer or peer group after a BGP connection is established, even though these BGP routes fail to match the routing policy on the ingress. By default, the updated information about BGP routes from a specified peer is saved only when the routes match the routing policy on the ingress. If a router supports route refreshing, this option is not required.";
                  }
                  uses ncs_template_peer-independent-peer-group-type;
                  uses ncs_template_peer-origin-as-validation-type;
                  uses ncs_template_route-limit-type;
                  uses ncs_template_public-as-only-type;
                  uses ncs_template_peer-public-as-only-import-type;
                  uses ncs_template_path-attr-map-type;
                }
                container ipv4-labeluni {
                  // NCS drop when statement
                  description
                    "Configure IPv4 label unicast options.";
                  leaf group-name {
                    type string;
                    // NCS drop must statement
                    // NCS drop must statement
                    description
                      "Configure a name for a peer group. After a peer is deleted from the peer group, the peer is disabled from the address family. The object cannot be modified.";
                    ext:operation-exclude "update" {
                      description
                        "The node cannot be modified, when the peer already belongs to a peer-group.";
                    }
                  }
                  leaf advertise-community {
                    type string;
                    // NCS drop default statement
                    description
                      "Enable/disable advertise the community attribute to a peer or a peer group.";
                  }
                  leaf reflect-client {
                    type string;
                    // NCS drop default statement
                    description
                      "Enable/disable the local device as a route reflector (RR) and a peer or peer group as its client. This configuration is applicable between IBGP peers only. The configurations of RRs and its clients in an address family are valid only in this address family. Therefore, it is recommended to configure RRs and its clients in the specified address family that is required.";
                  }
                  leaf check-tunnel-reachable {
                    type string;
                    // NCS drop default statement
                    description
                      "Enable/disable tunnel reachability check.";
                  }
                  uses ncs_template_peer-policy-filter-type;
                  leaf advertise-ext-community {
                    type string;
                    // NCS drop default statement
                    description
                      "Enable/disable advertise the extended community attribute to a peer or peer group.";
                  }
                  leaf discard-ext-community {
                    type string;
                    // NCS drop default statement
                    description
                      "Enable/disable discard the extended community attribute in the routing information about a specified peer.";
                  }
                  leaf allow-as-loop {
                    type string;
                    description
                      "Allow repetitive local AS numbers. By default, repetitive local AS numbers are not allowed.";
                  }
                  leaf aigp {
                    // NCS drop when statement
                    type string;
                    // NCS drop default statement
                    description
                      "Enable/disable route with AIGP attribute advertisement to or from a peer.";
                  }
                  leaf add-path-mode {
                    // NCS drop when statement
                    type ncs_template_add-path-cap-type;
                    // NCS drop default statement
                    description
                      "Enable add-path route advertisement to a peer.";
                  }
                  uses ncs_template_ip-prefix-filter-type;
                  uses ncs_template_as-path-filter-type;
                  uses ncs_template_peer-group-acl-name-or-num-type;
                  uses ncs_template_rt-update-interval-type;
                  leaf nexthop-configure {
                    type ncs_template_nexthop-configuration-type;
                    description
                      "Both the next-hop-local mode and next-hop-invariable mode are available when the peer address family is the VPNv4/VPNV6/L2VPN AD address family. Only the next-hop-local mode is available when the peer address family is not VPNv4/VPNV6/L2VPN AD address family. In next-hop-local mode, you can configure a BGP speaker to set its IP address of as the next hop of the routes to be advertised to IBGP peers or IBGP peer groups. In next-hop-invariable mode, you can configure PEs in different ASs not to change the next hop of routes when the PEs advertise the routes to their EBGP peers and use the next hop addresses of IGP routes to advertise imported IGP routes to IBGP peers. By default, when a BGP speaker advertises routes to EBGP peers and imported IGP routes to IBGP peers, the BGP speaker changes the next hop to its interface address.";
                  }
                  uses ncs_template_preferred-value-type;
                  leaf exp-mode {
                    // NCS drop when statement
                    type ncs_template_exp-mode-type;
                    // NCS drop default statement
                    description
                      "Specify the ASs in which a BGP label can inherit the QoS priority carried in the outer label of public tunnel in the Core AS and the ASs in which the priorities of BGP LSPs must be restored before the LSPs are advertised to a non-core AS.";
                  }
                  leaf add-path-number {
                    // NCS drop when statement
                    type string;
                    description
                      "Number of Add-Path routes that can be advertised to a peer.";
                  }
                  leaf substitute-as-enable {
                    type string;
                    // NCS drop default statement
                    description
                      "Enable/disable replace the AS number of a specified peer in the AS_Path attribute with the local AS number. On a PE where AS number replacement is enabled, if an AS number in the AS_Path attribute of a route is same as that of the CE to which the PE advertises the route, the PE replaces the AS number with its own AS number before advertising the route.";
                  }
                  leaf soo {
                    // NCS drop when statement
                    type string;
                    description
                      "Configure the Site-of-Origin (SoO) extended community attribute. This attribute can be expressed in the following formats: X.X.X.X:number<0-65535>, number<0-65535>:number<0-4294967295>, or number<0-65535>.number<0-65535>:number<0-65535> or <65536-4294967295>:<0-65535>. 0:0 or 0.0:0 is not supported.
                       Two CEs are in the same site and can advertise routes to each other, and they are connected to a VPN through PEs. If the local routes of a CE are advertised to the other CE over the VPN, a routing loop may occur.
                       The SoO feature can prevent a route advertised by a site from being sent back to the site, preventing routing loops. After SoO is enabled and a PE receives a route from a CE, the specified SoO attribute will be added to the route. Before advertising the route to the other CE, the PE checks the SoO attribute. If the SoO attribute is the same as the locally configured SoO attribute, the PE does not advertise the route, preventing routing loops.";
                  }
                  leaf advertise-best-external {
                    // NCS drop when statement
                    type string;
                    // NCS drop must statement
                    // NCS drop must statement
                    // NCS drop must statement
                    // NCS drop default statement
                    description
                      "Enable/disable the device to advertise Best External routes to peers.";
                  }
                  leaf load-balancing-enable {
                    // NCS drop when statement
                    type string;
                    // NCS drop default statement
                    description
                      "Enable/disable a neighbour to participate in load balancing.";
                  }
                  choice load-balancing-ignore-as-type {
                    description
                      "Set load balancing as path type.";
                    case as-attribute {
                      description
                        "Ignore the as-path attribute.";
                      leaf load-balancing-as-path-ignore {
                        // NCS drop when statement
                        type empty;
                        description
                          "Configure BGP to ignore the AS_Path attribute when selecting the equal route. After as-path-neglect is selected, BGP does not compare the AS_Path length.";
                      }
                    }
                    case same-length-as-attribute {
                      description
                        "Ignore comparison of as-path attributes with the same length.";
                      leaf load-balancing-as-path-relax {
                        // NCS drop when statement
                        type empty;
                        description
                          "Configure BGP to ignore comparison of AS_Path attributes with the same length when selecting the equal route. After as-path-neglect is selected, BGP does not compare the AS_Path length.";
                      }
                    }
                  }
                  uses ncs_template_advertise-large-community-type;
                  uses ncs_template_peer-independent-peer-group-type;
                  uses ncs_template_route-limit-accept-type;
                  uses ncs_template_public-as-only-type;
                  uses ncs_template_peer-public-as-only-import-type;
                  container entropy-label-parameter {
                    // NCS drop when statement
                    description
                      "Configure information about entropy label parameter configuration in a peer.";
                    uses ncs_template_peer-entropy-label-type;
                  }
                  uses ncs_template_path-attr-map-type;
                }
                container ipv4-multicast {
                  // NCS drop when statement
                  description
                    "Configure IPv4 multicast options.";
                  leaf group-name {
                    type string;
                    // NCS drop must statement
                    // NCS drop must statement
                    description
                      "Configure a name for a peer group. After a peer is deleted from the peer group, the peer is disabled from the address family. The object cannot be modified.";
                    ext:operation-exclude "update" {
                      description
                        "The node cannot be modified, when the peer already belongs to a peer-group.";
                    }
                  }
                  uses ncs_template_default-route-advertise-type;
                  uses ncs_template_ip-prefix-filter-type;
                  uses ncs_template_as-path-filter-type;
                  uses ncs_template_peer-group-acl-name-or-num-type;
                  leaf advertise-ext-community {
                    type string;
                    // NCS drop default statement
                    description
                      "Enable/disable advertise the extended community attribute to a peer or peer group.";
                  }
                  leaf discard-ext-community {
                    type string;
                    // NCS drop default statement
                    description
                      "Enable/disable discard the extended community attribute in the routing information about a specified peer.";
                  }
                  leaf allow-as-loop {
                    type string;
                    description
                      "Allow repetitive local AS numbers. By default, repetitive local AS numbers are not allowed.";
                  }
                  leaf nexthop-configure {
                    type ncs_template_nexthop-configuration-type;
                    // NCS drop must statement
                    description
                      "Both the next-hop-local mode and next-hop-invariable mode are available when the peer address family is the VPNv4/VPNV6/L2VPN AD address family. Only the next-hop-local mode is available when the peer address family is not VPNv4/VPNV6/L2VPN AD address family. In next-hop-local mode, you can configure a BGP speaker to set its IP address of as the next hop of the routes to be advertised to IBGP peers or IBGP peer groups. In next-hop-invariable mode, you can configure PEs in different ASs not to change the next hop of routes when the PEs advertise the routes to their EBGP peers and use the next hop addresses of IGP routes to advertise imported IGP routes to IBGP peers. By default, when a BGP speaker advertises routes to EBGP peers and imported IGP routes to IBGP peers, the BGP speaker changes the next hop to its interface address.";
                  }
                  leaf advertise-community {
                    type string;
                    // NCS drop default statement
                    description
                      "Enable/disable advertise the community attribute to a peer or a peer group.";
                  }
                  leaf keep-all-routes {
                    // NCS drop when statement
                    type string;
                    // NCS drop default statement
                    description
                      "Enable/disable saving all the updated information about BGP routes from a specified peer or peer group after a BGP connection is established, even though these BGP routes fail to match the routing policy on the ingress. By default, the updated information about BGP routes from a specified peer is saved only when the routes match the routing policy on the ingress. If a router supports route refreshing, this option is not required.";
                  }
                  uses ncs_template_peer-policy-filter-type;
                  leaf reflect-client {
                    type string;
                    // NCS drop default statement
                    description
                      "Enable/disable the local device as a route reflector (RR) and a peer or peer group as its client. This configuration is applicable between IBGP peers only. The configurations of RRs and its clients in an address family are valid only in this address family. Therefore, it is recommended to configure RRs and its clients in the specified address family that is required.";
                  }
                  leaf load-balancing-enable {
                    type string;
                    // NCS drop default statement
                    description
                      "Enable/disable a neighbour to participate in load balancing.";
                  }
                  choice load-balancing-ignore-as-type {
                    description
                      "Set load balancing as path type.";
                    case as-attribute {
                      description
                        "Ignore the as-path attribute.";
                      leaf load-balancing-as-path-ignore {
                        // NCS drop when statement
                        type empty;
                        description
                          "Configure BGP to ignore the AS_Path attribute when selecting the equal route. After as-path-neglect is selected, BGP does not compare the AS_Path length.";
                      }
                    }
                    case same-length-as-attribute {
                      description
                        "Ignore comparison of as-path attributes with the same length.";
                      leaf load-balancing-as-path-relax {
                        // NCS drop when statement
                        type empty;
                        description
                          "Configure BGP to ignore comparison of AS_Path attributes with the same length when selecting the equal route. After as-path-neglect is selected, BGP does not compare the AS_Path length.";
                      }
                    }
                  }
                  uses ncs_template_advertise-large-community-type;
                  uses ncs_template_rt-update-interval-type;
                  uses bgp:ncs_template_preferred-value-type;
                  uses ncs_template_peer-independent-peer-group-type;
                  uses ncs_template_route-limit-type;
                  uses ncs_template_public-as-only-type;
                  uses ncs_template_peer-public-as-only-import-type;
                  uses ncs_template_path-attr-map-type;
                }
                // NCS drop config false container state
              }
            }
          }
        }
        // NCS drop config false container 'peer-bfd-session-states'
        container egress-engineer-peer-sets {
          // NCS drop when statement
          description
            "List of peer set information under BGP instance.";
          list egress-engineer-peer-set {
            // NCS patched for predictable order
            ordered-by user;
            key "peer-set-name";
            description
              "Configure peer set information.";
            leaf peer-set-name {
              type string;
              description
                "The name for peer set.";
            }
            leaf static-label {
              type string;
              description
                "The static label for peer set.";
            }
            leaf label-pop {
              // NCS drop when statement
              type string;
              // NCS drop must statement
              // NCS drop default statement
              description
                "Enable/disable the BGP-EPE label popping function.";
            }
            leaf relate-bfd {
              type string;
              // NCS drop must statement
              // NCS drop default statement
              description
                "Enable/disable association between the BGP-EPE label and BFD status.";
            }
          }
        }
      }
      container instance-processs {
        // NCS drop when statement
        description
          "List of all BGP instances.";
        list instance-process {
          // NCS patched for predictable order
          ordered-by user;
          key "name";
          // NCS drop max-elements statement
          description
            "Configure a BGP instance.";
          ext:generated-by "system" {
            // NCS drop when statement
            description
              "The BGP public instance is generated automatically when BGP instances is enabled.";
          }
          leaf name {
            type string;
            description
              "Name of BGP Site.";
          }
          leaf router-id {
            type string;
            description
              "ID of a router that is in IPv4 address format. Certain dynamic routing protocols require a router ID. If no router ID is specified for a router when these protocols are enabled, the router ID in the RM module is used by default. The default router ID in the RM module is 0.0.0.0 when the router is not configured with any interface.
               The rules for selecting a router ID are as follows:
               1. If you set a router ID through this configuration, the set router ID is used. If the router ID is not set, you need to select a router ID according to the following rules:
               (1) If loopback interfaces configured with IP addresses exist, the largest IP address among the IP addresses of the loopback interfaces is selected as the router ID.
               (2) If no loopback interface configured with an IP address exists, the largest IP address among the IP addresses of other interfaces is selected as the router ID, regardless of whether the interface is Up.
               The router ID is reselected only when the interface address that is selected as the router ID is deleted or changed. The router ID is not reselected in any of the following cases:
               a. The interface is Down.
               b. A loopback interface is configured when the IP address of a non-loopback interface is selected as the router ID.
               c. A larger IP address of an interface is configured.
               2. Each VPN instance selects the router ID from the addresses of the interfaces of the VPN instance according to the preceding rules.
               3. When both the AMB and SMB exist on the router, the system backs up the router ID set through the related command and the router ID that is selected from IP addresses of the interfaces. After the active/standby switchover is performed, the system checks the validity of the router ID selected from the interface addresses. If the router ID is invalid, the system reselects a router ID.";
          }
          // NCS drop config false leaf 'effect-router-id'
          container afs {
            description
              "List of BGP address family instances.";
            list af {
              // NCS patched for predictable order
              ordered-by user;
              key "type";
              description
                "Configure BGP address family instance.";
              leaf type {
                type bgp:ncs_template_instance-af-type;
                description
                  "Address family type of a BGP instance.";
              }
              container ipv4-vpn {
                // NCS drop when statement
                description
                  "Configure IPv4 VPNv4 options.";
                uses ncs_template_vpn-target-type;
                uses ncs_template_reflector-cluster-type;
                uses ncs_template_reflect-type;
                leaf auto-frr {
                  type string;
                  // NCS drop default statement
                  description
                    "Enable/disable BGP Auto FRR. If IP FRR, VPN FRR, and Auto FRR are all enabled, IP FRR and VPN FRR take precedence over Auto FRR. If a route fails to match the routing policy of IP FRR or VPN FRR, Auto FRR takes effect.";
                }
                leaf tunnel-selector-name {
                  type string;
                  description
                    "Configure a tunnel selector and apply it to the BGP IPv4 unicast, BGP VPNv4 address families and BGP VPNv6 address families so that IPv4,VPNv4 and VPNv6 labeled routes can be iterated to tunnels based on the tunnel selector.";
                }
                leaf route-select-delay {
                  type string;
                  units "s";
                  // NCS drop default statement
                  description
                    "Route selection delay.";
                }
                leaf apply-label-mode {
                  type ncs_template_apply-label-type;
                  // NCS drop default statement
                  description
                    "Method of distributing labels to VPNV4 and VPNV6 routes. The way which assigns the label depends on the paf value. If there are a large number of routes, assign a label for the routes that have same nexthop and out-label. This allows all routes which have same nexthop and out-label to use one label.";
                }
                leaf nexthop-select-depend-type {
                  type ncs_template_select-depend-type-ext;
                  // NCS drop default statement
                  description
                    "Specify the route iteration mode: IP or tunnel. In tunnel mode, the labeled BGP IPv4 route can participate in route selection only after its next hop is iterated to an LSP. In IP
                     mode, the labeled BGP IPv4 route can participate in route selection only after its next hop is iterated to an IP address. By default, the labeled BGP IPv4 route can participate in route selection
                     if its next hop can be iterated to an IP address, regardless of whether the LSP of the next hop exists. This allows the RR that is not enabled with MPLS to forward labeled routes. In non-RR
                     networking or RR networking where the BGP next hop is changed, BGP needs to check whether there is an LSP destined for the next hop. If such an LSP is not found, BGP needs to establish an LSP in
                     advance. If the default setting is adopted, a labeled BGP IPv4 unicast route may be selected prior to LSP establishment. As a result, services are incorrectly switched before LSP establishment and
                     service stability is affected. Therefore, allow route selection only after the labeled BGP IPv4 route is iterated to an LSP.";
                }
                leaf default-med {
                  type string;
                  // NCS drop default statement
                  description
                    "Specify the Multi-Exit-Discriminator (MED) of BGP routes. The value is an integer. This value is valid only for the imported routes and BGP summarized routes on the local router.";
                }
                leaf best-external {
                  type string;
                  // NCS drop default statement
                  description
                    "Enable/disable best external route selection.";
                }
                leaf label-free-delay {
                  type string;
                  units "s";
                  // NCS drop default statement
                  description
                    "Label free delay.";
                }
                leaf add-path-select-num {
                  type string;
                  description
                    "Number of Add-Path routes.";
                }
                leaf default-local-preference {
                  type string;
                  // NCS drop default statement
                  description
                    "The local preference of BGP routes.";
                }
                uses ncs_template_bestroute-med-plus-igp-type;
                uses ncs_template_bestroute-router-id-prior-clusterlist-type;
                leaf reflect-between-client {
                  type string;
                  // NCS drop default statement
                  description
                    "Enable/disable route reflection between clients. If clients of a route reflector (RR) are fully meshed, you can disable route reflection among clients to reduce the cost.";
                }
                leaf activate-route-tag {
                  type string;
                  // NCS drop default statement
                  description
                    "Enable/disable tag-based filtering.";
                }
                uses ncs_template_route-reflector-ext-community-filter-type;
                uses ncs_template_vrf-af-dampening-routes-ext;
                container nexthop-recursive-lookup {
                  description
                    "Configure next hop iteration.";
                  container common {
                    description
                      "Configure next hop iteration common options.";
                    uses ncs_template_nexthop-recursive-lookup-restrain;
                  }
                  uses ncs_template_nexthop-recursive-lookup-delay;
                  uses ncs_template_bit-error-detection-type;
                }
                uses ncs_template_ipv4-import-filter-protocol-type;
                uses ncs_template_ipv4vpn-export-filter-protocol-type;
                uses ncs_template_slow-peer-type;
              }
            }
          }
        }
      }
    }
  }
  augment "/ncs:devices/ncs:device/ncs:live-status/ni:network-instance/ni:instances/ni:instance" {
    description
      "BGP network instance configuration.";
    container bgp {
      tailf:ncs-device-type "netconf";
      tailf:display-when "not(../../../../../ncs:module) or ../../../../../ncs:module[ncs:name='huawei-bgp'] or (../../../../../ncs:live-status-protocol[not(ncs:capability)]) or (../../../../../ncs:live-status-protocol/ncs:capability/ncs:module[.='huawei-bgp'])";
      description
        "Configure BGP network instance. All nodes of private VPN Instance in this container can be used only when the value of the global BGP enabling node (/bgp:bgp/bgp:global/bgp:yang-enable) is set to true.";
      container base-process {
        // NCS drop when statement
        presence "Create vrf session.";
        description
          "Enable/disable BGP instances.";
        ext:generated-by "system" {
          // NCS drop when statement
          description
            "The BGP public instance is generated automatically when BGP is enabled.";
        }
        leaf router-id {
          type inet:ipv4-address-no-zone;
          description
            "ID of a router that is in IPv4 address format. Certain dynamic routing protocols require a router ID. If no router ID is specified for a router when these protocols are enabled, the router ID in the RM module is used by default. The default router ID in the RM module is 0.0.0.0 when the router is not configured with any interface.
             The rules for selecting a router ID are as follows:
             1. If you set a router ID through this configuration, the set router ID is used. If the router ID is not set, you need to select a router ID according to the following rules:
             (1) If loopback interfaces configured with IP addresses exist, the largest IP address among the IP addresses of the loopback interfaces is selected as the router ID.
             (2) If no loopback interface configured with an IP address exists, the largest IP address among the IP addresses of other interfaces is selected as the router ID, regardless of whether the interface is Up.
             The router ID is reselected only when the interface address that is selected as the router ID is deleted or changed. The router ID is not reselected in any of the following cases:
             a. The interface is Down.
             b. A loopback interface is configured when the IP address of a non-loopback interface is selected as the router ID.
             c. A larger IP address of an interface is configured.
             2. Each VPN instance selects the router ID from the addresses of the interfaces of the VPN instance according to the preceding rules.
             3. When both the AMB and SMB exist on the router, the system backs up the router ID set through the related command and the router ID that is selected from IP addresses of the interfaces. After the active/standby switchover is performed, the system checks the validity of the router ID selected from the interface addresses. If the router ID is invalid, the system reselects a router ID.";
        }
        leaf router-id-auto-select {
          // NCS drop when statement
          type boolean;
          // NCS drop must statement
          // NCS drop default statement
          description
            "Enable/disable router ID auto select. If a BGP VPN instance is not enabled to select a router ID, a router ID can be configured for the BGP VPN instance. If no router ID is configured for the BGP VPN instance, the BGP VPN instance inherits the router ID of the public network instance. If a BGP VPN instance is enabled to select a router ID, it uses the address of an interface bound to a VPN as the router ID based on the following rules:

             1. If Loopback interfaces configured with IP addresses exist, the largest IP address among the IP addresses of the Loopback interfaces is selected as the router ID.

             2. If there is no Loopback interface configured with an IP address, the largest IP address among the IP addresses of other interfaces is selected as the router ID, regardless of whether the interface is Up.";
        }
        leaf effect-router-id {
          type inet:ipv4-address-no-zone;
          // NCS drop default statement
          description
            "Router ID that takes effect.";
        }
        container afs {
          description
            "List of BGP address family instances.";
          list af {
            key "type";
            description
              "Configure BGP address family instance. In public network instances, all types of address families can be configured. In IPv4 VPN instances, the IPv4 unicast, IPv4 flow, and IPv4 labeled unicast address families can be configured. In IPv6 VPN instances, the IPv6 unicast and IPv6 flow address families can be configured. The IPv4 address family in the BGP _public_ VPN instance cannot be deleted.";
            ext:generated-by "system" {
              // NCS drop when statement
              ext:filter "type = 'ipv4uni'";
              description
                "The IPv4 unicast of the BGP public instance is generated automatically when BGP is enabled.";
            }
            leaf type {
              type bgp:live_ncs_af-type;
              description
                "Address family type of a BGP instance.";
            }
            container ipv4-unicast {
              // NCS drop when statement
              description
                "Configure IPv4 unicast options.";
              container common {
                description
                  "Configure IPv4 unicast common options.";
                leaf auto-frr {
                  type boolean;
                  // NCS drop default statement
                  description
                    "Enable/disable BGP Auto FRR. If IP FRR, VPN FRR, and Auto FRR are all enabled, IP FRR and VPN FRR take precedence over Auto FRR. If a route fails to match the routing policy of IP FRR or VPN FRR, Auto FRR takes effect.";
                }
                leaf tunnel-selector-name {
                  // NCS drop when statement
                  type leafref {
                    path "/ncs:devices/ncs:device/ncs:live-status/rtp:routing-policy/rtp:tunnel-selectors/rtp:tunnel-selector/rtp:name" {
                      tailf:xpath-root 3;
                    }
                  }
                  description
                    "Configure a tunnel selector and apply it to the BGP IPv4 unicast, BGP VPNv4 address families and BGP VPNv6 address families so that IPv4,VPNv4 and VPNv6 labeled routes can be iterated to tunnels based on the tunnel selector. By default, no tunnel selector is configured.";
                }
                leaf tunnel-selector-all {
                  // NCS drop when statement
                  type boolean;
                  // NCS drop default statement
                  description
                    "Enable/disable tunnel selector for labeled, imported, and network segment routes.";
                }
                leaf route-select-delay {
                  type uint16 {
                    range "0..3600";
                  }
                  units "s";
                  // NCS drop default statement
                  description
                    "Route selection delay.";
                }
                uses live_ncs_reflector-cluster-type;
                uses live_ncs_reflect-type;
                leaf maximum-load-balancing-ibgp {
                  type uint16 {
                    range "1..65535";
                  }
                  // NCS drop must statement
                  // NCS drop default statement
                  description
                    "Specify the maximum number of equal-cost IBGP routes.";
                }
                leaf maximum-load-balancing-ebgp {
                  type uint16 {
                    range "1..65535";
                  }
                  // NCS drop must statement
                  // NCS drop default statement
                  description
                    "Specify the maximum number of equal-cost EBGP routes.";
                }
                leaf nexthop-select-depend-type {
                  // NCS drop when statement
                  type live_ncs_select-depend-type;
                  // NCS drop default statement
                  description
                    "Specify the route iteration mode: IP or tunnel. In tunnel mode, the labeled BGP IPv4 route can participate in route selection only after its next hop is iterated to an LSP. In IP
                     mode, the labeled BGP IPv4 route can participate in route selection only after its next hop is iterated to an IP address. By default, the labeled BGP IPv4 route can participate in route selection
                     if its next hop can be iterated to an IP address, regardless of whether the LSP of the next hop exists. This allows the RR that is not enabled with MPLS to forward labeled routes. In non-RR
                     networking or RR networking where the BGP next hop is changed, BGP needs to check whether there is an LSP destined for the next hop. If such an LSP is not found, BGP needs to establish an LSP in
                     advance. If the default setting is adopted, a labeled BGP IPv4 unicast route may be selected prior to LSP establishment. As a result, services are incorrectly switched before LSP establishment and
                     service stability is affected. Therefore, allow route selection only after the labeled BGP IPv4 route is iterated to an LSP.";
                }
                leaf nexthop-inherit-ip-cost {
                  // NCS drop when statement
                  type boolean;
                  // NCS drop default statement
                  description
                    "Enable/disable next hop iteration mode to IP. Specify the route iteration mode: IP or tunnel. In tunnel mode, the labeled BGP IPv4 route can participate in route selection only after its next hop is iterated to an LSP.";
                }
                leaf nexthop-resolve-aigp {
                  // NCS drop when statement
                  type boolean;
                  // NCS drop default statement
                  description
                    "Enable/disable route with AIGP attribute for route selection.";
                }
                leaf always-compare-med {
                  type boolean;
                  // NCS drop default statement
                  description
                    "Enable/disable BGP to compare the MEDs of routes from peers in different ASs in route selection. If
                     there are multiple reachable routes to the same destination, the route with the smallest MED is preferred. Do not use this option unless different ASs use the same IGP and route selection mode.";
                }
                leaf default-med {
                  type uint32;
                  // NCS drop default statement
                  description
                    "Specify the Multi-Exit-Discriminator (MED) of BGP routes. The value is an integer. This value is valid only for the imported routes and BGP summarized routes on the local router.";
                }
                leaf summary-automatic {
                  type boolean;
                  // NCS drop default statement
                  description
                    "Enable/disable automatic summarization for imported routes. Manual summarization takes precedence over automatic summarization. After automatic summarization is enabled, BGP summarizes routes based on the natural network segment (for example, 10.1.1.1/24 and 10.2.1.1/24 are summarized into 10.0.0.0/8, a Class A address), and sends only the summarized route to peers. This reduces the number of routes.";
                }
                leaf nexthop-third-party {
                  type boolean;
                  // NCS drop default statement
                  description
                    "Enable/disable BGP third-party next hop.";
                }
                leaf best-route-bit-error-detection {
                  // NCS drop when statement
                  type boolean;
                  // NCS drop default statement
                  description
                    "Enable/disable the function to reroute traffic when a bit error event occurs.";
                }
                leaf supernet-unicast-advertise {
                  type boolean;
                  // NCS drop default statement
                  description
                    "Enable/disable the function to advertise supernet unicast routes.";
                }
                leaf supernet-label-advertise {
                  type boolean;
                  // NCS drop default statement
                  description
                    "Enable/disable the function to advertise supernet labeled routes.";
                }
                leaf lsp-mtu {
                  type uint16 {
                    range "46..65535";
                  }
                  // NCS drop default statement
                  description
                    "BGP LSP MTU.";
                }
                leaf label-free-delay {
                  type uint8 {
                    range "0..180";
                  }
                  units "s";
                  // NCS drop default statement
                  description
                    "Label Free Delay.";
                }
                leaf bestroute-med-confederation {
                  // NCS drop when statement
                  type boolean;
                  // NCS drop default statement
                  description
                    "Enable/disable BGP to compare MED value only within the federation.";
                }
                leaf bestroute-as-path-ignore {
                  type boolean;
                  // NCS drop must statement
                  // NCS drop default statement
                  description
                    "Enable/disable BGP to ignore the AS_Path attribute when selecting the optimal route. By default, BGP uses the AS_Path attribute as one of route selection rules, and a route with a shorter AS_Path is preferred. After bestroute-as-path-ignore is selected, BGP does not compare the AS_Path length.";
                }
                leaf determin-med {
                  type boolean;
                  // NCS drop default statement
                  description
                    "Enable/disable deterministic MED so that the route selection result is relevant to the sequence in which routes are received.";
                }
                leaf best-external {
                  // NCS drop when statement
                  type boolean;
                  // NCS drop must statement
                  // NCS drop default statement
                  description
                    "Enable/disable best external route selection.";
                }
                leaf attribute-set-enable {
                  // NCS drop when statement
                  type boolean;
                  // NCS drop default statement
                  description
                    "Enable/disable the capability of processing attribute set.";
                }
                leaf attribute-set-mode {
                  // NCS drop when statement
                  type bgp:live_ncs_attribute-set-type;
                  // NCS drop default statement
                  description
                    "The processing mode of attribute set.";
                }
                leaf add-path-select-num {
                  // NCS drop when statement
                  type uint8 {
                    range "2..64";
                  }
                  // NCS drop must statement
                  description
                    "Number of Add-Path routes.";
                }
                leaf load-balanc-igp-metric-ignore {
                  type boolean;
                  // NCS drop default statement
                  description
                    "Enable/disable BGP to ignore the IGP cost of each BGP route to the next hop when selecting routes for load balancing. By default, only the routes with the same IGP cost can participate in load balancing.";
                }
                leaf load-balanc-as-path-ignore {
                  type boolean;
                  // NCS drop must statement
                  // NCS drop default statement
                  description
                    "Enable/disable BGP to ignore the AS_Path of each BGP route to the next hop when selecting routes for load balancing. By default, only the routes with the same AS_Path can participate in load balancing.";
                }
                leaf load-balanc-as-path-relax {
                  type boolean;
                  // NCS drop must statement
                  // NCS drop default statement
                  description
                    "Enable/disable BGP to ignore comparison of AS_Path attributes with the same length. By default, only the routes with the same AS_Path can participate in load balancing.";
                }
                leaf default-local-preference {
                  type uint32 {
                    range "0..4294967295";
                  }
                  // NCS drop default statement
                  description
                    "The local preference of BGP routes.";
                }
                leaf default-route-import {
                  type boolean;
                  // NCS drop default statement
                  description
                    "Enable/disable the function to import default routes into the BGP routing table. Default-route-imported must be used with import-routes so that default routes can be imported to the BGP routing table. If only import-routes is used, no default routes can be added to the BGP routing table. In addition, default-route-imported can only import the default routes in the routing table into the BGP routing table.";
                }
                leaf routerid-neglect {
                  type boolean;
                  // NCS drop default statement
                  description
                    "Enable/disable BGP to ignore router IDs when selecting the optimal route. Comparing router IDs is the last resort in route selection. This means that if one optimal route must be selected and no other parameters can be used to break the tie, router IDs can be used. If this option is selected, the first received route will be selected as the optimal route, and BGP will ignore the router ID and peer address in route selection.";
                }
                leaf maximum-load-balancing {
                  type uint16 {
                    range "1..65535";
                  }
                  // NCS drop must statement
                  // NCS drop default statement
                  description
                    "Specify the maximum number of equal-cost routes in the BGP routing table. The value can be 1 or an integer greater than 1. The value depends on the associated license. Equal-cost BGP routes can be generated for load balancing only when the BGP routes meet the first nine rules of the route-selection policy and have the same AS-Path attribute.";
                }
                leaf reflect-between-client {
                  type boolean;
                  // NCS drop default statement
                  description
                    "Enable/disable route reflection between clients. If clients of a route reflector (RR) are fully meshed, you can disable route reflection among clients to reduce the cost.";
                }
                leaf import-rib-nexthop-invariable {
                  // NCS drop when statement
                  type boolean;
                  // NCS drop default statement
                  description
                    "Enable/disable the function to advertise the route without modifying the next-hop.";
                }
                leaf route-relay-tunnel {
                  type boolean;
                  // NCS drop must statement
                  // NCS drop default statement
                  description
                    "Enable/disable unicast route recursive-lookup tunnel.";
                }
                leaf route-relay-tunnel-selector {
                  // NCS drop when statement
                  type leafref {
                    path "/ncs:devices/ncs:device/ncs:live-status/rtp:routing-policy/rtp:tunnel-selectors/rtp:tunnel-selector/rtp:name" {
                      tailf:xpath-root 3;
                    }
                  }
                  description
                    "Unicast route tunnel selector name.";
                }
                leaf route-relay-tunnel-v6-selector {
                  // NCS drop when statement
                  type leafref {
                    path "/ncs:devices/ncs:device/ncs:live-status/rtp:routing-policy/rtp:tunnel-selectors/rtp:tunnel-selector/rtp:name" {
                      tailf:xpath-root 3;
                    }
                  }
                  description
                    "Enable/disable unicast route recursive-lookup IPv6 tunnel by tunnel selector name.";
                }
                uses live_ncs_bestroute-med-plus-igp-type;
                uses live_ncs_bestroute-router-id-prior-clusterlist-type;
                leaf bestroute-med-none-as-maximum {
                  type boolean;
                  // NCS drop default statement
                  description
                    "Enable/disable BGP considers its MED as the largest MED value (4294967295). If a route does not carry MED, BGP considers its MED as the default value (0) during route selection.";
                }
                leaf bestroute-rd-large-first {
                  // NCS drop when statement
                  type boolean;
                  // NCS drop default statement
                  description
                    "Enable/disable a BGP device to select the route with the largest route distinguisher (RD) during route selection.";
                }
                leaf ebgp-ecmp-nexthop-changed {
                  // NCS drop when statement
                  type boolean;
                  // NCS drop default statement
                  description
                    "Enable/disable next hop of equal-cost EBGP routes is changed. When equal-cost EBGP routes are load-balancing traffic, the next hop of these routes is changed to a local interface before these routes are advertised. This function can be enabled only when the maximum number of equal-cost EBGP routes is greater than 1.";
                }
                leaf ibgp-ecmp-nexthop-changed {
                  // NCS drop when statement
                  type boolean;
                  // NCS drop default statement
                  description
                    "Enable/disable next hop of equal-cost IBGP routes is changed. When equal-cost IBGP routes are load-balancing traffic, the next hop of these routes is changed to a local interface before these routes are advertised. This function can be enabled only when the maximum number of equal-cost IBGP routes is greater than 1.";
                }
                leaf ecmp-nexthop-changed {
                  // NCS drop when statement
                  type boolean;
                  // NCS drop default statement
                  description
                    "Enable/disable next hop of equal-cost routes is changed. When equal-cost BGP routes are load-balancing traffic, the next hop of these routes is changed to a local interface before these routes are advertised. This function can be enabled only when the maximum number of equal-cost BGP routes is greater than 1.";
                }
                leaf maximum-load-balancing-eibgp {
                  // NCS drop when statement
                  type uint16 {
                    range "1..65535";
                  }
                  // NCS drop must statement
                  description
                    "Specify the maximum number of equal-cost EBGP routes and IBGP routes. After the attribute is set, load balancing is performed among equal-cost BGP VPN routes, regardless of the route type, EBGP or IBGP.";
                }
                leaf eibgp-ecmp-nexthop-changed {
                  // NCS drop when statement
                  type boolean;
                  // NCS drop default statement
                  description
                    "Enable/disable next hop of equal-cost EBGP and IBGP routes is changed. When equal-cost EBGP and IBGP routes are load-balancing traffic, the next hop of these routes is changed to a local interface before these routes are advertised.";
                }
                leaf load-balancing-eibgp-enable {
                  // NCS drop when statement
                  type boolean;
                  // NCS drop must statement
                  // NCS drop default statement
                  description
                    "Enable/disable EIBGP route load balancing.";
                }
                leaf ext-community-change {
                  type boolean;
                  // NCS drop default statement
                  description
                    "Enable/disable the function to change the extended community attribute.";
                }
                leaf active-route-advertise {
                  type boolean;
                  // NCS drop default statement
                  description
                    "Enable/disable the function to advertise the optimal routes in the RM module to peers.";
                }
                leaf nexthop-priority {
                  type live_ncs_nexthop-priority-address-type;
                  description
                    "Routes with next-hop IPv4 addresses and routes with next-hop IPv6 addresses coexist. If the next-hop address type is set to IPv4, routes with next-hop IPv4 addresses have a higher priority. If the next-hop address type is set to IPv6, routes with next-hop IPv6 addresses have a higher priority.";
                }
                leaf ebgp-interface-sensitive {
                  type boolean;
                  // NCS drop default statement
                  description
                    "Enable/disable the function of EBGP interface fast sensing. If this function is enabled, the sessions of directly connected EBGP peers are immediately cleared from the associated interface when the interface becomes down.";
                }
                uses live_ncs_group-origin-as-validation-type;
                leaf advertise-route-mode {
                  // NCS drop when statement
                  type live_ncs_bgp-advertise-route-mode;
                  // NCS drop default statement
                  description
                    "VPN advertise route mode.";
                }
                leaf reoriginate-route {
                  // NCS drop when statement
                  type boolean;
                  // NCS drop default statement
                  description
                    "Enable/disable route reorigination.";
                }
                leaf rpd-policy-change-delay {
                  // NCS drop when statement
                  type uint16 {
                    range "0..180";
                  }
                  // NCS drop default statement
                  description
                    "Specify the delay time of RPD policy's change.";
                }
              }
              uses live_ncs_bgp-route-preference-options;
              container nexthop-recursive-lookup {
                description
                  "Configure next hop iteration.";
                container common {
                  description
                    "Configure next hop iteration common options.";
                  uses live_ncs_nexthop-recursive-lookup-restrain;
                  uses live_ncs_nexthop-recursive-lookup-default-route;
                }
                uses live_ncs_nexthop-recursive-lookup-delay;
              }
              container import-routes {
                description
                  "List of imported routes.";
                list import-route {
                  key "protocol process-id";
                  description
                    "Configure route import. Routes of other protocol types can be imported by BGP. By default, BGP does not import routes of other protocol types.";
                  leaf protocol {
                    type bgp:live_ncs_ipv4-import-route-protocol-type;
                    description
                      "Routing protocol from which routes can be imported.";
                  }
                  leaf process-id {
                    type uint32 {
                      range "0..4294967295";
                    }
                    description
                      "Process ID of an imported routing protocol. The process ID is 0, if the imported routing protocol is direct routes, static routes, UNRs, or OP-routes. The process ID must be specified range from 1 to 4294967295, if the imported routing protocol is RIP, OSPF, ISIS.";
                  }
                  leaf med {
                    type uint32;
                    description
                      "Specifies the MED metric of the imported route.";
                  }
                  choice policy-type {
                    description
                      "Set route policy or filter.";
                    case rtp-ref {
                      description
                        "Route policy.";
                      leaf policy-name {
                        type leafref {
                          path "/ncs:devices/ncs:device/ncs:live-status/rtp:routing-policy/rtp:policy-definitions/rtp:policy-definition/rtp:name" {
                            tailf:xpath-root 3;
                          }
                        }
                        description
                          "When routes are imported from other routing protocols, the route-policy filter can be used to filter the routes and change route attributes.";
                      }
                    }
                    case xpl-ref {
                      description
                        "Route filter.";
                      uses live_ncs_route-filter-type;
                    }
                  }
                  leaf non-relay-tunnel {
                    // NCS drop when statement
                    type boolean;
                    // NCS drop default statement
                    description
                      "Enable/disable imported route relay a tunnel.";
                  }
                }
              }
              container aggregate-routes {
                description
                  "List of summarized routes.";
                list aggregate-route {
                  key "address mask-length";
                  description
                    "Configure a summarized route in the BGP routing table. The local outbound interface of the summarized route is Null0. When another router receives the route, the route adds an outbound interface to the route. If the Origin attributes of the specific routes for the route summarization are different, the Origin attribute of the summarized route is that with the highest priority. Origin attributes are arranged in the priority order of complete > egp > igp. A summarized route carries the community attribute of each specific route.";
                  // NCS expand uses statement
                  leaf address {
                    type inet:ip-address-no-zone;
                    description
                      "Specify the IPv4 address or IPv6 address of a summarized route. Only IPv4 summarized routes can be configured in the IPv4 address family and only IPv6 summarized routes can be configured in the IPv6 address family.";
                    // NCS drop must statement
                  }
                  leaf mask-length {
                    type uint8 {
                      range "1..128";
                    }
                    description
                      "Specify the mask length of a summarized address.";
                    // NCS drop must statement
                  }
                  leaf as-set {
                    type boolean;
                    // NCS drop default statement
                    description
                      "Enable/disable the generation of routes with the AS-SET attribute. This option can be used to create a summarized route. The AS_Path attribute of the summarized route contains the AS-Path attributes of the specific routes for the route summarization. Exercise caution when using this option if multiple AS_Paths need to be summarized to prevent route flapping.";
                  }
                  leaf detail-suppressed {
                    type boolean;
                    // NCS drop default statement
                    description
                      "Enable/disable detail-suppressed. Suppress the advertisement of specific routes for the route summarization. Only the summarized route is advertised.";
                  }
                  choice policy-type {
                    description
                      "Set route policy or filter.";
                    case rtp-ref {
                      description
                        "Route policy.";
                      leaf attribute-policy {
                        type leafref {
                          path "/ncs:devices/ncs:device/ncs:live-status/rtp:routing-policy/rtp:policy-definitions/rtp:policy-definition/rtp:name" {
                            tailf:xpath-root 3;
                          }
                        }
                        description
                          "Specify an attribute of summarized routes. If apply as-path is used to configure the AS_Path attribute that is used in the route Summarization policy, and the as-set keyword is set, the AS_Path attribute in the policy does not take effect. This parameter and any of the following parameters overwrite each other: suppressFilter, originFilter, and attributeFilter.";
                      }
                      leaf origin-policy {
                        type leafref {
                          path "/ncs:devices/ncs:device/ncs:live-status/rtp:routing-policy/rtp:policy-definitions/rtp:policy-definition/rtp:name" {
                            tailf:xpath-root 3;
                          }
                        }
                        description
                          "Specify the name of a policy for generating summarized routes. Summarized routes are generated only when the routes match route-policy. This parameter and any of the following parameters overwrite each other: suppressFilter, originFilter, and attributeFilter.";
                      }
                      leaf suppress-policy {
                        type leafref {
                          path "/ncs:devices/ncs:device/ncs:live-status/rtp:routing-policy/rtp:policy-definitions/rtp:policy-definition/rtp:name" {
                            tailf:xpath-root 3;
                          }
                        }
                        description
                          "Specify a policy for suppressing the advertisement of specified routes. The routes matching the policy are not advertised, and other routes are advertised. This parameter and any of the following parameters overwrite each other: suppressFilter, originFilter, and attributeFilter.";
                      }
                    }
                    case xpl-ref {
                      description
                        "Route filter.";
                      leaf attribute-filter-name {
                        type leafref {
                          path "/ncs:devices/ncs:device/ncs:live-status/xpl:xpl/xpl:route-filters/xpl:route-filter/xpl:name" {
                            tailf:xpath-root 3;
                          }
                        }
                        description
                          "Specify a route-filter name.";
                      }
                      leaf attribute-filter-parameter {
                        // NCS drop when statement
                        type xpl:live_ncs_filter-parameter-type;
                        description
                          "Specify a route-filter parameter.";
                      }
                      leaf origin-filter-name {
                        type leafref {
                          path "/ncs:devices/ncs:device/ncs:live-status/xpl:xpl/xpl:route-filters/xpl:route-filter/xpl:name" {
                            tailf:xpath-root 3;
                          }
                        }
                        description
                          "Specify a route-filter name.";
                      }
                      leaf origin-filter-parameter {
                        // NCS drop when statement
                        type xpl:live_ncs_filter-parameter-type;
                        description
                          "Specify a route-filter parameter.";
                      }
                      leaf suppress-filter-name {
                        type leafref {
                          path "/ncs:devices/ncs:device/ncs:live-status/xpl:xpl/xpl:route-filters/xpl:route-filter/xpl:name" {
                            tailf:xpath-root 3;
                          }
                        }
                        description
                          "Specify a route-filter name.";
                      }
                      leaf suppress-filter-parameter {
                        // NCS drop when statement
                        type xpl:live_ncs_filter-parameter-type;
                        description
                          "Specify a route-filter parameter.";
                      }
                    }
                  }
                }
              }
              container aggregate-default-route {
                description
                  "Configure aggregate default route.";
                leaf origin-ip-prefix {
                  type leafref {
                    path "/ncs:devices/ncs:device/ncs:live-status/rtp:routing-policy/rtp:ipv4-prefix-filters/rtp:ipv4-prefix-filter/rtp:name" {
                      tailf:xpath-root 3;
                    }
                  }
                  description
                    "Specify the name of an IPv4 prefix list for a summary default route. Only the name of an IPv4 prefix list can be configured in a BGP IPv4 address family.";
                }
                leaf attribute-policy {
                  // NCS drop when statement
                  type leafref {
                    path "/ncs:devices/ncs:device/ncs:live-status/rtp:routing-policy/rtp:policy-definitions/rtp:policy-definition/rtp:name" {
                      tailf:xpath-root 3;
                    }
                  }
                  description
                    "Specify an attribute policy of a summary default route.";
                }
              }
              container network-routes {
                description
                  "List of network routes.";
                list network-route {
                  key "address mask-length";
                  description
                    "Configure a network route in the BGP routing table.";
                  uses live_ncs_network-route-ipv4;
                  leaf non-relay-tunnel {
                    // NCS drop when statement
                    type boolean;
                    // NCS drop default statement
                    description
                      "Enable/disable imported route relay a tunnel.";
                  }
                }
              }
              container advertise-route-to-evpns {
                // NCS drop when statement
                description
                  "Configure advertise route protocol.";
                uses live_ncs_advertise-route-to-evpn-type;
              }
              container import-ribs {
                description
                  "List of imported RIBs configuration.";
                list import-rib {
                  key "source-vpn source-address-family";
                  description
                    "Configure imported RIBs.";
                  leaf source-vpn {
                    type leafref {
                      path "/ncs:devices/ncs:device/ncs:live-status/ni:network-instance/ni:instances/ni:instance/ni:name" {
                        tailf:xpath-root 3;
                      }
                    }
                    // NCS drop must statement
                    description
                      "Source VPN name.";
                  }
                  leaf source-address-family {
                    type bgp:live_ncs_import-rib-ipv4-safi-type;
                    description
                      "Source address family type.";
                  }
                  leaf valid-route {
                    type boolean;
                    // NCS drop default statement
                    description
                      "Enable/disable imported valid route.";
                  }
                  leaf include-label-route {
                    // NCS drop when statement
                    type boolean;
                    // NCS drop default statement
                    description
                      "Enable/disable imported include label route.";
                  }
                  // NCS expand uses statement
                  choice policy-type {
                    case rtp-ref {
                      description
                        "Specify the route policy.";
                      leaf policy-name {
                        type leafref {
                          path "/ncs:devices/ncs:device/ncs:live-status/rtp:routing-policy/rtp:policy-definitions/rtp:policy-definition/rtp:name" {
                            tailf:xpath-root 3;
                          }
                        }
                        description
                          "Specify the route policy.";
                      }
                    }
                    case xpl-ref {
                      description
                        "Route filter.";
                      uses live_ncs_route-filter-type;
                    }
                    description
                      "Specify the route-policy or filter for imported RIBs.";
                  }
                }
              }
              uses live_ncs_ipv4-import-filter-protocol-type;
              container export-filter-policys {
                description
                  "List of filtering policies.";
                list export-filter-policy {
                  key "protocol process-id";
                  description
                    "Apply a filtering policy. It is used to filter the routes to be advertised to the peer. By default, routes are not filtered.";
                  leaf protocol {
                    type bgp:live_ncs_ipv4-export-filter-protocol-type;
                    description
                      "Specify the name of a routing protocol. The routing protocol takes effect only on the routes to be advertised. The IPv4 address family supports the direct, IS-IS, OSPF, RIP, and static routing protocols. The IPv6 unicast address family of a public network instance supports the direct, IS-IS, OSPFv3, RIPng, and static routing protocols. The IPv6 address family of a VPNv6 instance supports the direct, IS-IS, RIPng, and static routing protocols.";
                  }
                  leaf process-id {
                    type uint32 {
                      range "0..4294967295";
                    }
                    description
                      "Specify the process ID required to be matched. The value is an integer ranging from 0 to 4294967295. If direct or static routes need to be filtered, no process ID is required.";
                  }
                  uses live_ncs_ipv4-filter-protocol-policy-choice-type;
                }
              }
              container lsp-options {
                description
                  "Configure parameters for lsp.";
                uses live_ncs_safi-lsp-options;
                leaf maximum-load-balancing-transit {
                  // NCS drop when statement
                  type uint16 {
                    range "1..65535";
                  }
                  // NCS drop default statement
                  description
                    "Maximum number of transit LSPs for load balancing.";
                }
                leaf unicast-rt-label-advertise {
                  // NCS drop when statement
                  type boolean;
                  // NCS drop default statement
                  description
                    "Enable/disable a device to convert received IPv4 public network unicast routes to labeled routes by allocating one BGP label to each route and advertise the labeled routes to peers with the labeled route exchange capability.";
                }
                leaf unicast-rt-label-advertise-popgo {
                  // NCS drop when statement
                  type boolean;
                  // NCS drop default statement
                  description
                    "Enable/disable a device to convert received IPv4 public network unicast routes to labeled routes by adding a BGP label to each route and advertise the labeled routes to peers with the labeled route exchange capability. If the IP address of an outbound interface is reachable but no LSP is reachable, traffic is forwarded through the outbound interface and a specific next hop, during which the label POPGO action is performed.";
                }
                leaf lsp-operation {
                  // NCS drop when statement
                  type live_ncs_lsp-operation-type;
                  // NCS drop default statement
                  description
                    "Label operation type.";
                }
                uses live_ncs_ingress-choice-policy-set;
              }
              container segment-routing-ipv6 {
                description
                  "Configure BGP segment-routing IPv6.";
                leaf srv6-best-effort-enable {
                  type empty;
                  description
                    "Enable SRv6 BE iteration.";
                }
                leaf srv6-traffic-engineer-enable {
                  type empty;
                  description
                    "Enable SRv6 TE iteration.";
                }
              }
              uses live_ncs_vrf-af-dampening-routes;
              uses bgp:live_ncs_slow-peer-type;
              // NCS expand uses statement
              container routing-table-rib-only {
                description
                  "Configure disable route delivery to the IP routing table.";
                leaf enable {
                  type boolean;
                  // NCS drop default statement
                  description
                    "Enable/disable prevent BGP routes from being added to the IP routing table.";
                  // NCS drop must statement
                }
                choice policy-type {
                  description
                    "Set route policy or filter.";
                  case rtp-ref {
                    description
                      "Route policy.";
                    leaf policy-name {
                      // NCS drop when statement
                      type leafref {
                        path "/ncs:devices/ncs:device/ncs:live-status/rtp:routing-policy/rtp:policy-definitions/rtp:policy-definition/rtp:name" {
                          tailf:xpath-root 3;
                        }
                      }
                      description
                        "When routes are imported from other routing protocols, the route-policy filter can be used to filter the routes and change route attributes.";
                    }
                  }
                  case xpl-ref {
                    description
                      "Route filter.";
                    leaf filter-name {
                      // NCS drop when statement
                      type leafref {
                        path "/ncs:devices/ncs:device/ncs:live-status/xpl:xpl/xpl:route-filters/xpl:route-filter/xpl:name" {
                          tailf:xpath-root 3;
                        }
                      }
                      description
                        "Specify a route-filter name.";
                    }
                    leaf filter-parameter {
                      // NCS drop when statement
                      type xpl:live_ncs_filter-parameter-type;
                      description
                        "Specify a route-filter parameter.";
                    }
                  }
                }
              }
              uses live_ncs_qos-local-id-type;
            }
            container ipv6-unicast {
              // NCS drop when statement
              description
                "Configure IPv6 unicast options.";
              container common {
                description
                  "Configure IPv6 unicast common options.";
                leaf auto-frr {
                  type boolean;
                  // NCS drop default statement
                  description
                    "Enable/disable BGP auto FRR. If IP FRR, VPN FRR, and Auto FRR are all enabled, IP FRR and VPN FRR take precedence over Auto FRR. If a route fails to match the routing policy of IP FRR or VPN FRR, Auto FRR takes effect.";
                }
                leaf route-select-delay {
                  type uint16 {
                    range "0..3600";
                  }
                  units "s";
                  // NCS drop default statement
                  description
                    "Route selection delay.";
                }
                uses live_ncs_reflector-cluster-type;
                uses live_ncs_reflect-type;
                leaf maximum-load-balancing-ibgp {
                  type uint16 {
                    range "1..65535";
                  }
                  // NCS drop default statement
                  description
                    "Specify the maximum number of equal-cost IBGP routes.";
                }
                leaf maximum-load-balancing-ebgp {
                  type uint16 {
                    range "1..65535";
                  }
                  // NCS drop default statement
                  description
                    "Specify the maximum number of equal-cost EBGP routes.";
                }
                leaf explicit-null {
                  // NCS drop when statement
                  type boolean;
                  // NCS drop must statement
                  // NCS drop default statement
                  description
                    "Enable/disable the function to explicit null. After 6PE routes are enabled to share a single label, all routes share the explicit-null label 2 when the 6PE sends IPv6 routes to its 6PE peer. This can save label resources on the 6PE. Therefore, when there are a large number of IPv6 routes that need to be sent, the problem that the IPv6 routes cannot be forwarded due to the shortage of labels can be avoided.";
                }
                leaf lsp-operation {
                  // NCS drop when statement
                  type live_ncs_lsp-operation-type;
                  // NCS drop must statement
                  // NCS drop default statement
                  description
                    "Label operation mode.";
                }
                leaf nexthop-select-depend-type {
                  // NCS drop when statement
                  type live_ncs_select-depend-type;
                  // NCS drop default statement
                  description
                    "Specify the route iteration mode: IP or tunnel. In tunnel mode, the labeled BGP IPv4 route can participate in route selection only after its next hop is iterated to an LSP. In IP
                     mode, the labeled BGP IPv4 route can participate in route selection only after its next hop is iterated to an IP address. By default, the labeled BGP IPv4 route can participate in route selection
                     if its next hop can be iterated to an IP address, regardless of whether the LSP of the next hop exists. This allows the RR that is not enabled with MPLS to forward labeled routes. In non-RR
                     networking or RR networking where the BGP next hop is changed, BGP needs to check whether there is an LSP destined for the next hop. If such an LSP is not found, BGP needs to establish an LSP in
                     advance. If the default setting is adopted, a labeled BGP IPv4 unicast route may be selected prior to LSP establishment. As a result, services are incorrectly switched before LSP establishment and
                     service stability is affected. Therefore, allow route selection only after the labeled BGP IPv4 route is iterated to an LSP.";
                }
                leaf nexthop-inherit-ip-cost {
                  // NCS drop when statement
                  type boolean;
                  // NCS drop default statement
                  description
                    "Enable/disable next hop iteration mode to IP. Specify the route iteration mode: IP or tunnel. In tunnel mode, the labeled BGP IPv4 route can participate in route selection only after its next hop is iterated to an LSP.";
                }
                leaf nexthop-resolve-aigp {
                  // NCS drop when statement
                  type boolean;
                  // NCS drop default statement
                  description
                    "Enable/disable route with AIGP attribute for route selection.";
                }
                leaf always-compare-med {
                  type boolean;
                  // NCS drop default statement
                  description
                    "Enable/disable BGP to compare the MEDs of routes from peers in different ASs in route selection. If
                     there are multiple reachable routes to the same destination, the route with the smallest MED is preferred. Do not use this option unless different ASs use the same IGP and route selection mode.";
                }
                leaf default-med {
                  type uint32;
                  // NCS drop default statement
                  description
                    "Specify the Multi-Exit-Discriminator (MED) of BGP routes. The value is an integer. This value is valid only for the imported routes and BGP summarized routes on the local router.";
                }
                leaf nexthop-third-party {
                  type boolean;
                  // NCS drop default statement
                  description
                    "Enable/disable BGP third-party next hop.";
                }
                leaf supernet-unicast-advertise {
                  type boolean;
                  // NCS drop default statement
                  description
                    "Enable/disable advertise supernet unicast routes.";
                }
                leaf bestroute-med-confederation {
                  // NCS drop when statement
                  type boolean;
                  // NCS drop default statement
                  description
                    "Enable/disable BGP to compare Med value only within the federation.";
                }
                leaf bestroute-as-path-ignore {
                  type boolean;
                  // NCS drop must statement
                  // NCS drop default statement
                  description
                    "Enable/disable BGP to ignore the AS_Path attribute when selecting the optimal route. By default, BGP uses the AS_Path attribute as one of route selection rules, and a route with a shorter AS_Path is preferred. After bestroute-as-path-ignore is selected, BGP does not compare the AS_Path length.";
                }
                leaf determin-med {
                  type boolean;
                  // NCS drop default statement
                  description
                    "Enable/disable deterministic MED so that the route selection result is relevant to the sequence in which routes are received.";
                }
                leaf best-external {
                  // NCS drop when statement
                  type boolean;
                  // NCS drop must statement
                  // NCS drop default statement
                  description
                    "Enable/disable best external route selection.";
                }
                leaf attribute-set-enable {
                  // NCS drop when statement
                  type boolean;
                  // NCS drop default statement
                  description
                    "Enable/disable the capability of processing attribute set.";
                }
                leaf attribute-set-mode {
                  // NCS drop when statement
                  type bgp:live_ncs_attribute-set-type;
                  // NCS drop default statement
                  description
                    "The processing mode of attribute set.";
                }
                leaf add-path-select-num {
                  // NCS drop when statement
                  type uint8 {
                    range "2..64";
                  }
                  // NCS drop must statement
                  description
                    "Number of add-path routes.";
                }
                leaf load-balanc-igp-metric-ignore {
                  type boolean;
                  // NCS drop default statement
                  description
                    "Enable/disable BGP to ignore the IGP cost of each BGP route to the next hop when selecting routes for load balancing. By default, only the routes with the same IGP cost can participate in load balancing.";
                }
                leaf load-balanc-as-path-ignore {
                  type boolean;
                  // NCS drop must statement
                  // NCS drop default statement
                  description
                    "Enable/disable BGP to ignore the AS_Path of each BGP route to the next hop when selecting routes for load balancing. By default, only the routes with the same AS_Path can participate in load balancing.";
                }
                leaf load-balanc-as-path-relax {
                  type boolean;
                  // NCS drop must statement
                  // NCS drop default statement
                  description
                    "Enable/disable BGP to ignore comparison of AS_Path attributes with the same length. By default, only the routes with the same AS_Path can participate in load balancing.";
                }
                leaf default-local-preference {
                  type uint32 {
                    range "0..4294967295";
                  }
                  // NCS drop default statement
                  description
                    "The local preference of BGP routes.";
                }
                leaf default-route-import {
                  type boolean;
                  // NCS drop default statement
                  description
                    "Enable/disable the function to import default routes into the BGP routing table. Default-route-imported must be used with import-routes so that default routes can be imported to the BGP routing table. If only import-routes is used, no default routes can be added to the BGP routing table. In addition, default-route-imported can only import the default routes in the routing table into the BGP routing table.";
                }
                leaf routerid-neglect {
                  type boolean;
                  // NCS drop default statement
                  description
                    "Enable/disable BGP to ignore router IDs when selecting the optimal route. Comparing router IDs is the last resort in route selection. This means that if one optimal route must be selected and no other parameters can be used to break the tie, router IDs can be used. If this option is selected, the first received route will be selected as the optimal route, and BGP will ignore the router ID and peer address in route selection.";
                }
                leaf maximum-load-balancing {
                  type uint16 {
                    range "1..65535";
                  }
                  // NCS drop default statement
                  description
                    "Specify the maximum number of equal-cost routes in the BGP routing table. The value depends on the associated license. Equal-cost BGP routes can be generated for load balancing only when the BGP routes meet the first nine rules of the route-selection policy and have the same AS-Path attribute.";
                }
                leaf reflect-between-client {
                  type boolean;
                  // NCS drop default statement
                  description
                    "Enable/disable route reflection between clients. If clients of a route reflector (RR) are fully meshed, you can disable route reflection among clients to reduce the cost.";
                }
                leaf best-route-bit-error-detection {
                  // NCS drop when statement
                  type boolean;
                  // NCS drop default statement
                  description
                    "Enable/disable the function to reroute traffic when a bit error event occurs.";
                }
                leaf import-rib-nexthop-invariable {
                  // NCS drop when statement
                  type boolean;
                  // NCS drop default statement
                  description
                    "Enable/disable advertise the route without modifying the next-hop.";
                }
                leaf route-relay-tunnel-v4 {
                  type boolean;
                  // NCS drop default statement
                  description
                    "Enable/disable unicast-route recursive-lookup tunnel.";
                }
                leaf route-relay-tunnel-v4-selector {
                  // NCS drop when statement
                  type leafref {
                    path "/ncs:devices/ncs:device/ncs:live-status/rtp:routing-policy/rtp:tunnel-selectors/rtp:tunnel-selector/rtp:name" {
                      tailf:xpath-root 3;
                    }
                  }
                  description
                    "Unicast route tunnel selector name.";
                }
                leaf route-relay-tunnel-v6-selector {
                  // NCS drop when statement
                  type leafref {
                    path "/ncs:devices/ncs:device/ncs:live-status/rtp:routing-policy/rtp:tunnel-selectors/rtp:tunnel-selector/rtp:name" {
                      tailf:xpath-root 3;
                    }
                  }
                  description
                    "Enable/disable unicast route recursive-lookup IPv6 tunnel by tunnel selector name.";
                }
                uses live_ncs_bestroute-med-plus-igp-type;
                uses live_ncs_bestroute-router-id-prior-clusterlist-type;
                leaf bestroute-med-none-as-maximum {
                  type boolean;
                  // NCS drop default statement
                  description
                    "Enable/disable BGP considers its MED as the largest MED value (4294967295). If a route does not carry MED, BGP considers its MED as the default value (0) during route selection.";
                }
                leaf bestroute-rd-large-first {
                  // NCS drop when statement
                  type boolean;
                  // NCS drop default statement
                  description
                    "Enable/disable a BGP device to select the route with the largest route distinguisher (RD) during route selection.";
                }
                leaf nexthop-priority {
                  // NCS drop when statement
                  type live_ncs_nexthop-priority-address-type;
                  description
                    "In the VRF instance, routes with next-hop IPv4 addresses and routes with next-hop IPv6 addresses coexist. If the next-hop address type is set to IPv4, routes with next-hop IPv4 addresses have a higher priority. If the next-hop address type is set to IPv6, routes with next-hop IPv6 addresses have a higher priority.";
                }
                leaf ebgp-ecmp-nexthop-changed {
                  // NCS drop when statement
                  type boolean;
                  // NCS drop default statement
                  description
                    "Enable/disable next hop of equal-cost EBGP routes is changed. Enable/disable next hop of equal-cost EBGP routes is changed. When equal-cost EBGP routes are load-balancing traffic, the next hop of these routes is changed to a local interface before these routes are advertised. This function can be enabled only when the maximum number of equal-cost EBGP routes is greater than 1.";
                }
                leaf ibgp-ecmp-nexthop-changed {
                  // NCS drop when statement
                  type boolean;
                  // NCS drop default statement
                  description
                    "Enable/disable next hop of equal-cost IBGP routes is changed. When equal-cost IBGP routes are load-balancing traffic, the next hop of these routes is changed to a local interface before these routes are advertised. This function can be enabled only when the maximum number of equal-cost IBGP routes is greater than 1.";
                }
                leaf ecmp-nexthop-changed {
                  // NCS drop when statement
                  type boolean;
                  // NCS drop default statement
                  description
                    "Enable/disable next hop of equal-cost routes is changed. When equal-cost BGP routes are load-balancing traffic, the next hop of these routes is changed to a local interface before these routes are advertised. This function can be enabled only when the maximum number of equal-cost BGP routes is greater than 1.";
                }
                leaf maximum-load-balancing-eibgp {
                  // NCS drop when statement
                  type uint16 {
                    range "1..65535";
                  }
                  // NCS drop must statement
                  description
                    "Specify the maximum number of equal-cost EBGP routes and IBGP routes. After the attribute is set, load balancing is performed among equal-cost BGP VPN routes, regardless of the route type, EBGP or IBGP.";
                }
                leaf eibgp-ecmp-nexthop-changed {
                  // NCS drop when statement
                  type boolean;
                  // NCS drop default statement
                  description
                    "Enable/disable next hop of equal-cost EBGP and IBGP routes is changed. When equal-cost EBGP and IBGP routes are load-balancing traffic, the next hop of these routes is changed to a local interface before these routes are advertised.";
                }
                leaf load-balancing-eibgp-enable {
                  // NCS drop when statement
                  type boolean;
                  // NCS drop must statement
                  // NCS drop default statement
                  description
                    "Enable/disable EIBGP route load balancing.";
                }
                leaf ext-community-change {
                  type boolean;
                  // NCS drop default statement
                  description
                    "Enable/disable the function to change the extended community attribute.";
                }
                leaf active-route-advertise {
                  type boolean;
                  // NCS drop default statement
                  description
                    "Enable/disable the function to advertise the optimal routes in the RM module to peers.";
                }
                leaf ebgp-interface-sensitive {
                  type boolean;
                  // NCS drop default statement
                  description
                    "Enable/disable the function of EBGP interface fast sensing. If this function is enabled, the sessions of directly connected EBGP peers are immediately cleared from the associated interface when the interface becomes down.";
                }
                uses live_ncs_group-origin-as-validation-type;
                leaf advertise-route-mode {
                  // NCS drop when statement
                  type live_ncs_bgp-advertise-route-mode;
                  // NCS drop default statement
                  description
                    "VPN advertise route mode.";
                }
              }
              uses live_ncs_bgp-route-preference-options;
              container nexthop-recursive-lookup {
                description
                  "Configure next hop iteration.";
                container common {
                  description
                    "Configure next hop iteration common options.";
                  uses live_ncs_nexthop-recursive-lookup-restrain;
                  uses live_ncs_nexthop-recursive-lookup-default-route;
                }
                uses live_ncs_nexthop-recursive-lookup-delay;
              }
              container import-routes {
                description
                  "List of imported routes.";
                list import-route {
                  key "protocol process-id";
                  description
                    "Configure route import. Routes of other protocol types can be imported by BGP. By default, BGP does not import routes of other protocol types.";
                  leaf protocol {
                    type bgp:live_ncs_ipv6-import-route-protocol-type;
                    description
                      "Routing protocol from which routes can be imported.";
                  }
                  leaf process-id {
                    type uint32 {
                      range "0..4294967295";
                    }
                    description
                      "Process ID of an imported routing protocol. The process ID is 0, if the imported routing protocol is direct routes, static routes, UNRs, or OP-routes. The process ID must be specified range from 1 to 4294967295, if the imported routing protocol is ISIS, RIPng, or OSPFv3.";
                  }
                  leaf med {
                    type uint32;
                    description
                      "Specifies the MED metric of the imported route.";
                  }
                  choice policy-type {
                    description
                      "Set route policy or filter.";
                    case rtp-ref {
                      description
                        "Route policy.";
                      leaf policy-name {
                        type leafref {
                          path "/ncs:devices/ncs:device/ncs:live-status/rtp:routing-policy/rtp:policy-definitions/rtp:policy-definition/rtp:name" {
                            tailf:xpath-root 3;
                          }
                        }
                        description
                          "When routes are imported from other routing protocols, the route-policy filter can be used to filter the routes and change route attributes.";
                      }
                    }
                    case xpl-ref {
                      description
                        "Route filter.";
                      uses live_ncs_route-filter-type;
                    }
                  }
                }
              }
              container aggregate-routes {
                description
                  "List of summarized routes.";
                list aggregate-route {
                  key "address mask-length";
                  description
                    "Configure a summarized route in the BGP routing table. The local outbound interface of the summarized route is Null0. When another router receives the route, the route adds an outbound interface to the route. By default, route summarization is not performed. If the Origin attributes of the specific routes for the route summarization are different, the Origin attribute of the summarized route is that with the highest priority. Origin attributes are arranged in the priority order of complete > egp > igp. A summarized route carries the community attribute of each specific route.";
                  // NCS expand uses statement
                  leaf address {
                    type inet:ip-address-no-zone;
                    description
                      "Specify the IPv4 address or IPv6 address of a summarized route. Only IPv4 summarized routes can be configured in the IPv4 address family and only IPv6 summarized routes can be configured in the IPv6 address family.";
                    // NCS drop must statement
                  }
                  leaf mask-length {
                    type uint8 {
                      range "1..128";
                    }
                    description
                      "Specify the mask length of a summarized address.";
                    // NCS drop must statement
                  }
                  leaf as-set {
                    type boolean;
                    // NCS drop default statement
                    description
                      "Enable/disable the generation of routes with the AS-SET attribute. This option can be used to create a summarized route. The AS_Path attribute of the summarized route contains the AS-Path attributes of the specific routes for the route summarization. Exercise caution when using this option if multiple AS_Paths need to be summarized to prevent route flapping.";
                  }
                  leaf detail-suppressed {
                    type boolean;
                    // NCS drop default statement
                    description
                      "Enable/disable detail-suppressed. Suppress the advertisement of specific routes for the route summarization. Only the summarized route is advertised.";
                  }
                  choice policy-type {
                    description
                      "Set route policy or filter.";
                    case rtp-ref {
                      description
                        "Route policy.";
                      leaf attribute-policy {
                        type leafref {
                          path "/ncs:devices/ncs:device/ncs:live-status/rtp:routing-policy/rtp:policy-definitions/rtp:policy-definition/rtp:name" {
                            tailf:xpath-root 3;
                          }
                        }
                        description
                          "Specify an attribute of summarized routes. If apply as-path is used to configure the AS_Path attribute that is used in the route Summarization policy, and the as-set keyword is set, the AS_Path attribute in the policy does not take effect. This parameter and any of the following parameters overwrite each other: suppressFilter, originFilter, and attributeFilter.";
                      }
                      leaf origin-policy {
                        type leafref {
                          path "/ncs:devices/ncs:device/ncs:live-status/rtp:routing-policy/rtp:policy-definitions/rtp:policy-definition/rtp:name" {
                            tailf:xpath-root 3;
                          }
                        }
                        description
                          "Specify the name of a policy for generating summarized routes. Summarized routes are generated only when the routes match route-policy. This parameter and any of the following parameters overwrite each other: suppressFilter, originFilter, and attributeFilter.";
                      }
                      leaf suppress-policy {
                        type leafref {
                          path "/ncs:devices/ncs:device/ncs:live-status/rtp:routing-policy/rtp:policy-definitions/rtp:policy-definition/rtp:name" {
                            tailf:xpath-root 3;
                          }
                        }
                        description
                          "Specify a policy for suppressing the advertisement of specified routes. The routes matching the policy are not advertised, and other routes are advertised. This parameter and any of the following parameters overwrite each other: suppressFilter, originFilter, and attributeFilter.";
                      }
                    }
                    case xpl-ref {
                      description
                        "Route filter.";
                      leaf attribute-filter-name {
                        type leafref {
                          path "/ncs:devices/ncs:device/ncs:live-status/xpl:xpl/xpl:route-filters/xpl:route-filter/xpl:name" {
                            tailf:xpath-root 3;
                          }
                        }
                        description
                          "Specify a route-filter name.";
                      }
                      leaf attribute-filter-parameter {
                        // NCS drop when statement
                        type xpl:live_ncs_filter-parameter-type;
                        description
                          "Specify a route-filter parameter.";
                      }
                      leaf origin-filter-name {
                        type leafref {
                          path "/ncs:devices/ncs:device/ncs:live-status/xpl:xpl/xpl:route-filters/xpl:route-filter/xpl:name" {
                            tailf:xpath-root 3;
                          }
                        }
                        description
                          "Specify a route-filter name.";
                      }
                      leaf origin-filter-parameter {
                        // NCS drop when statement
                        type xpl:live_ncs_filter-parameter-type;
                        description
                          "Specify a route-filter parameter.";
                      }
                      leaf suppress-filter-name {
                        type leafref {
                          path "/ncs:devices/ncs:device/ncs:live-status/xpl:xpl/xpl:route-filters/xpl:route-filter/xpl:name" {
                            tailf:xpath-root 3;
                          }
                        }
                        description
                          "Specify a route-filter name.";
                      }
                      leaf suppress-filter-parameter {
                        // NCS drop when statement
                        type xpl:live_ncs_filter-parameter-type;
                        description
                          "Specify a route-filter parameter.";
                      }
                    }
                  }
                }
              }
              container aggregate-default-route {
                description
                  "Configure aggregate default route.";
                leaf origin-ipv6-prefix {
                  type leafref {
                    path "/ncs:devices/ncs:device/ncs:live-status/rtp:routing-policy/rtp:ipv6-prefix-filters/rtp:ipv6-prefix-filter/rtp:name" {
                      tailf:xpath-root 3;
                    }
                  }
                  description
                    "Specify the name of an IPv6 prefix list for a summary default route. Only the name of an IPv6 prefix list can be configured in a BGP IPv6 address family.";
                }
                leaf attribute-policy {
                  // NCS drop when statement
                  type leafref {
                    path "/ncs:devices/ncs:device/ncs:live-status/rtp:routing-policy/rtp:policy-definitions/rtp:policy-definition/rtp:name" {
                      tailf:xpath-root 3;
                    }
                  }
                  description
                    "Specify an attribute policy of a summary default route.";
                }
              }
              container network-routes {
                description
                  "List of network routes.";
                list network-route {
                  key "address mask-length";
                  description
                    "Configure a network route in the BGP routing table.";
                  uses live_ncs_network-route-ipv6;
                }
              }
              container advertise-route-to-evpns {
                // NCS drop when statement
                description
                  "Configure advertise route protocol.";
                uses live_ncs_advertise-route-to-evpn-type;
              }
              container import-ribs {
                description
                  "List of imported RIBs configuration.";
                list import-rib {
                  key "source-vpn source-address-family";
                  description
                    "Configure imported RIBs.";
                  leaf source-vpn {
                    type leafref {
                      path "/ncs:devices/ncs:device/ncs:live-status/ni:network-instance/ni:instances/ni:instance/ni:name" {
                        tailf:xpath-root 3;
                      }
                    }
                    // NCS drop must statement
                    description
                      "Source VPN name for imported RIBs.";
                  }
                  leaf source-address-family {
                    type bgp:live_ncs_import-rib-ipv6-safi-type;
                    description
                      "Source address family type for imported RIBs.";
                  }
                  leaf valid-route {
                    type boolean;
                    // NCS drop default statement
                    description
                      "Enable/disable imported valid route.";
                  }
                  leaf include-label-route {
                    type boolean;
                    // NCS drop default statement
                    description
                      "Enable/disable imported include label route.";
                  }
                  // NCS expand uses statement
                  choice policy-type {
                    case rtp-ref {
                      description
                        "Specify the route policy.";
                      leaf policy-name {
                        type leafref {
                          path "/ncs:devices/ncs:device/ncs:live-status/rtp:routing-policy/rtp:policy-definitions/rtp:policy-definition/rtp:name" {
                            tailf:xpath-root 3;
                          }
                        }
                        description
                          "Specify the route policy.";
                      }
                    }
                    case xpl-ref {
                      description
                        "Route filter.";
                      uses live_ncs_route-filter-type;
                    }
                    description
                      "Specify the route-policy or filter for imported RIBs.";
                  }
                }
              }
              container segment-routing-ipv6 {
                // NCS drop when statement
                description
                  "Configure BGP segment-routing IPv6.";
                leaf srv6-best-effort-enable {
                  type empty;
                  description
                    "Enable SRv6 BE iteration.";
                }
                leaf srv6-traffic-engineer-enable {
                  type empty;
                  description
                    "Enable SRv6 TE iteration.";
                }
              }
              uses live_ncs_vrf-af-dampening-routes;
              uses live_ncs_ipv6-import-filter-protocol-type;
              uses live_ncs_ipv6-export-filter-protocol-type;
              uses bgp:live_ncs_slow-peer-type;
              // NCS expand uses statement
              container routing-table-rib-only {
                description
                  "Configure disable route delivery to the IP routing table.";
                leaf enable {
                  type boolean;
                  // NCS drop default statement
                  description
                    "Enable/disable prevent BGP routes from being added to the IP routing table.";
                  // NCS drop must statement
                }
                choice policy-type {
                  description
                    "Set route policy or filter.";
                  case rtp-ref {
                    description
                      "Route policy.";
                    leaf policy-name {
                      // NCS drop when statement
                      type leafref {
                        path "/ncs:devices/ncs:device/ncs:live-status/rtp:routing-policy/rtp:policy-definitions/rtp:policy-definition/rtp:name" {
                          tailf:xpath-root 3;
                        }
                      }
                      description
                        "When routes are imported from other routing protocols, the route-policy filter can be used to filter the routes and change route attributes.";
                    }
                  }
                  case xpl-ref {
                    description
                      "Route filter.";
                    leaf filter-name {
                      // NCS drop when statement
                      type leafref {
                        path "/ncs:devices/ncs:device/ncs:live-status/xpl:xpl/xpl:route-filters/xpl:route-filter/xpl:name" {
                          tailf:xpath-root 3;
                        }
                      }
                      description
                        "Specify a route-filter name.";
                    }
                    leaf filter-parameter {
                      // NCS drop when statement
                      type xpl:live_ncs_filter-parameter-type;
                      description
                        "Specify a route-filter parameter.";
                    }
                  }
                }
              }
              uses live_ncs_ipv6-qos-local-id-type;
            }
            container ipv4-vpn {
              // NCS drop when statement
              description
                "Configure IPv4 VPNv4 options.";
              uses live_ncs_vpn-target-type;
              uses live_ncs_reflector-cluster-type;
              uses live_ncs_reflect-type;
              leaf auto-frr {
                type boolean;
                // NCS drop default statement
                description
                  "Enable/disable BGP Auto FRR. If IP FRR, VPN FRR, and Auto FRR are all enabled, IP FRR and VPN FRR take precedence over Auto FRR. If a route fails to match the routing policy of IP FRR or VPN FRR, Auto FRR takes effect.";
              }
              leaf tunnel-selector-name {
                type leafref {
                  path "/ncs:devices/ncs:device/ncs:live-status/rtp:routing-policy/rtp:tunnel-selectors/rtp:tunnel-selector/rtp:name" {
                    tailf:xpath-root 3;
                  }
                }
                description
                  "Configure a tunnel selector and apply it to the BGP IPv4 unicast, BGP VPNv4 address families and BGP VPNv6 address families so that IPv4,VPNv4 and VPNv6 labeled routes can be iterated to tunnels based on the tunnel selector.";
              }
              leaf route-select-delay {
                type uint16 {
                  range "0..3600";
                }
                units "s";
                // NCS drop default statement
                description
                  "Route selection delay.";
              }
              leaf apply-label-mode {
                type live_ncs_apply-label-type;
                // NCS drop default statement
                description
                  "Method of distributing labels to VPNV4 and VPNV6 routes. The way which assigns the label depends on the paf value. If there are a large number of routes, assign a label for the routes that have same nexthop and out-label. This allows all routes which have same nexthop and out-label to use one label.";
              }
              leaf nexthop-select-depend-type {
                type live_ncs_select-depend-type-ext;
                // NCS drop default statement
                description
                  "In none mode, route selection does not depend on whether the next hop is reachable. In tunnel mode, the labeled BGP IPv4 route can participate in route selection only after its next hop is iterated to an LSP. In IP
                   mode, the labeled BGP IPv4 route can participate in route selection only after its next hop is iterated to an IP address. By default, the labeled BGP IPv4 route can participate in route selection
                   if its next hop can be iterated to an IP address, regardless of whether the LSP of the next hop exists. This allows the RR that is not enabled with MPLS to forward labeled routes. In non-RR
                   networking or RR networking where the BGP next hop is changed, BGP needs to check whether there is an LSP destined for the next hop. If such an LSP is not found, BGP needs to establish an LSP in
                   advance. If the default setting is adopted, a labeled BGP IPv4 unicast route may be selected prior to LSP establishment. As a result, services are incorrectly switched before LSP establishment and
                   service stability is affected. Therefore, allow route selection only after the labeled BGP IPv4 route is iterated to an LSP.";
              }
              leaf default-med {
                type uint32;
                // NCS drop default statement
                description
                  "Specify the Multi-Exit-Discriminator (MED) of BGP routes. The value is an integer. This value is valid only for the imported routes and BGP summarized routes on the local router.";
              }
              leaf best-external {
                // NCS drop when statement
                type boolean;
                // NCS drop default statement
                description
                  "Enable/disable best external route selection.";
              }
              leaf label-free-delay {
                type uint8 {
                  range "0..180";
                }
                units "s";
                // NCS drop default statement
                description
                  "Label free delay.";
              }
              leaf add-path-select-num {
                // NCS drop when statement
                type uint8 {
                  range "2..64";
                }
                description
                  "Number of Add-Path routes.";
              }
              leaf default-local-preference {
                type uint32 {
                  range "0..4294967295";
                }
                // NCS drop default statement
                description
                  "The local preference of BGP routes.";
              }
              uses live_ncs_bestroute-med-plus-igp-type;
              uses live_ncs_bestroute-router-id-prior-clusterlist-type;
              leaf reflect-between-client {
                type boolean;
                // NCS drop default statement
                description
                  "Enable/disable route reflection between clients. If clients of a route reflector (RR) are fully meshed, you can disable route reflection among clients to reduce the cost.";
              }
              leaf activate-route-tag {
                type boolean;
                // NCS drop default statement
                description
                  "Enable/disable tag-based filtering.";
              }
              uses live_ncs_route-reflector-ext-community-filter-type;
              uses live_ncs_vrf-af-dampening-routes-ext;
              container nexthop-recursive-lookup {
                description
                  "Configure next hop iteration.";
                container common {
                  description
                    "Configure next hop iteration common options.";
                  uses live_ncs_nexthop-recursive-lookup-restrain;
                  uses live_ncs_nexthop-recursive-lookup-default-route;
                }
                uses live_ncs_nexthop-recursive-lookup-delay;
                uses live_ncs_bit-error-detection-type;
              }
              uses live_ncs_ipv4-import-filter-protocol-type;
              uses live_ncs_ipv4vpn-export-filter-protocol-type;
              uses bgp:live_ncs_slow-peer-type;
            }
            container ipv6-vpn {
              // NCS drop when statement
              description
                "Configure IPv6 VPNv6 options.";
              uses live_ncs_vpn-target-type;
              uses live_ncs_reflector-cluster-type;
              uses live_ncs_reflect-type;
              leaf auto-frr {
                type boolean;
                // NCS drop default statement
                description
                  "Enable/disable BGP Auto FRR. If IP FRR, VPN FRR, and Auto FRR are all enabled, IP FRR and VPN FRR take precedence over Auto FRR. If a route fails to match the routing policy of IP FRR or VPN FRR, Auto FRR takes effect.";
              }
              leaf tunnel-selector-name {
                type leafref {
                  path "/ncs:devices/ncs:device/ncs:live-status/rtp:routing-policy/rtp:tunnel-selectors/rtp:tunnel-selector/rtp:name" {
                    tailf:xpath-root 3;
                  }
                }
                description
                  "Configure a tunnel selector and apply it to the BGP IPv4 unicast, BGP VPNv4 address families and BGP VPNv6 address families so that IPv4,VPNv4 and VPNv6 labeled routes can be iterated to tunnels based on the tunnel selector. By default, no tunnel selector is configured.";
              }
              leaf route-select-delay {
                type uint16 {
                  range "0..3600";
                }
                units "s";
                // NCS drop default statement
                description
                  "Route selection delay.";
              }
              leaf apply-label-mode {
                type live_ncs_apply-label-type;
                // NCS drop default statement
                description
                  "Method of distributing labels to VPNV4 and VPNV6 routes. The way which assigns the label depends on the paf value. If there are a large number of routes, assign a label for the routes that have same nexthop and out-label. This allows all routes which have same nexthop and out-label to use one label.";
              }
              leaf nexthop-select-depend-type {
                type live_ncs_select-depend-type-ext;
                // NCS drop default statement
                description
                  "In none mode, route selection does not depend on whether the next hop is reachable. In tunnel mode, the labeled BGP IPv4 route can participate in route selection only after its next hop is iterated to an LSP. In IP
                   mode, the labeled BGP IPv4 route can participate in route selection only after its next hop is iterated to an IP address. By default, the labeled BGP IPv4 route can participate in route selection
                   if its next hop can be iterated to an IP address, regardless of whether the LSP of the next hop exists. This allows the RR that is not enabled with MPLS to forward labeled routes. In non-RR
                   networking or RR networking where the BGP next hop is changed, BGP needs to check whether there is an LSP destined for the next hop. If such an LSP is not found, BGP needs to establish an LSP in
                   advance. If the default setting is adopted, a labeled BGP IPv4 unicast route may be selected prior to LSP establishment. As a result, services are incorrectly switched before LSP establishment and
                   service stability is affected. Therefore, allow route selection only after the labeled BGP IPv4 route is iterated to an LSP.";
              }
              leaf default-med {
                type uint32;
                // NCS drop default statement
                description
                  "Specify the Multi-Exit-Discriminator (MED) of BGP routes. The value is an integer. This value is valid only for the imported routes and BGP summarized routes on the local router.";
              }
              leaf best-external {
                // NCS drop when statement
                type boolean;
                // NCS drop default statement
                description
                  "Enable/disable best external route selection.";
              }
              leaf add-path-select-num {
                // NCS drop when statement
                type uint8 {
                  range "2..64";
                }
                description
                  "Number of add-path routes.";
              }
              leaf default-local-preference {
                type uint32 {
                  range "0..4294967295";
                }
                // NCS drop default statement
                description
                  "The local preference of BGP routes.";
              }
              uses live_ncs_bestroute-med-plus-igp-type;
              uses live_ncs_bestroute-router-id-prior-clusterlist-type;
              leaf reflect-between-client {
                type boolean;
                // NCS drop default statement
                description
                  "Enable/disable route reflection between clients. If clients of a route reflector (RR) are fully meshed, you can disable route reflection among clients to reduce the cost.";
              }
              leaf label-free-delay {
                type uint8 {
                  range "0..180";
                }
                units "s";
                // NCS drop default statement
                description
                  "Label free delay.";
              }
              uses live_ncs_route-reflector-ext-community-filter-type;
              container nexthop-recursive-lookup {
                description
                  "Configure next hop iteration.";
                container common {
                  description
                    "Configure next hop iteration common options.";
                  uses live_ncs_nexthop-recursive-lookup-restrain;
                  uses live_ncs_nexthop-recursive-lookup-default-route;
                }
                uses live_ncs_nexthop-recursive-lookup-delay;
                uses live_ncs_bit-error-detection-type;
              }
              uses live_ncs_ipv6-import-filter-protocol-type;
              uses live_ncs_ipv6vpn-export-filter-protocol-type;
              uses bgp:live_ncs_slow-peer-type;
              uses live_ncs_vrf-af-dampening-routes-ext;
            }
            container ipv4-labeluni {
              // NCS drop when statement
              description
                "Configure IPv4 label unicast options.";
              container common {
                description
                  "Configure IPv4 label unicast common options.";
                leaf auto-frr {
                  type boolean;
                  // NCS drop default statement
                  description
                    "Enable/disable BGP Auto FRR. If IP FRR, VPN FRR, and Auto FRR are all enabled, IP FRR and VPN FRR take precedence over Auto FRR. If a route fails to match the routing policy of IP FRR or VPN FRR, Auto FRR takes effect.";
                }
                leaf tunnel-selector-name {
                  // NCS drop when statement
                  type leafref {
                    path "/ncs:devices/ncs:device/ncs:live-status/rtp:routing-policy/rtp:tunnel-selectors/rtp:tunnel-selector/rtp:name" {
                      tailf:xpath-root 3;
                    }
                  }
                  description
                    "Configure a tunnel selector and apply it to the BGP IPv4 unicast, BGP VPNv4 address families and BGP VPNv6 address families so that IPv4,VPNv4 and VPNv6 labeled routes can be iterated to tunnels based on the tunnel selector. By default, no tunnel selector is configured.";
                }
                leaf tunnel-selector-all {
                  // NCS drop when statement
                  type boolean;
                  // NCS drop default statement
                  description
                    "Enable/disable tunnel selector for labeled, imported, and network segment routes.";
                }
                leaf nexthop-select-depend-type {
                  // NCS drop when statement
                  type live_ncs_select-depend-type;
                  // NCS drop default statement
                  description
                    "Specify the route iteration mode: IP or tunnel. In tunnel mode, the labeled BGP IPv4 route can participate in route selection only after its next hop is iterated to an LSP. In IP
                     mode, the labeled BGP IPv4 route can participate in route selection only after its next hop is iterated to an IP address. By default, the labeled BGP IPv4 route can participate in route selection
                     if its next hop can be iterated to an IP address, regardless of whether the LSP of the next hop exists. This allows the RR that is not enabled with MPLS to forward labeled routes. In non-RR
                     networking or RR networking where the BGP next hop is changed, BGP needs to check whether there is an LSP destined for the next hop. If such an LSP is not found, BGP needs to establish an LSP in
                     advance. If the default setting is adopted, a labeled BGP IPv4 unicast route may be selected prior to LSP establishment. As a result, services are incorrectly switched before LSP establishment and
                     service stability is affected. Therefore, allow route selection only after the labeled BGP IPv4 route is iterated to an LSP.";
                }
                leaf nexthop-inherit-ip-cost {
                  // NCS drop when statement
                  type boolean;
                  // NCS drop default statement
                  description
                    "Enable/disable next hop iteration mode to IP. Specify the route iteration mode: IP or tunnel. In tunnel mode, the labeled BGP IPv4 route can participate in route selection only after its next hop is iterated to an LSP.";
                }
                leaf always-compare-med {
                  type boolean;
                  // NCS drop default statement
                  description
                    "Enable/disable BGP to compare the MEDs of routes from peers in different ASs in route selection. If
                     there are multiple reachable routes to the same destination, the route with the smallest MED is preferred. Do not use this option unless different ASs use the same IGP and route selection mode.";
                }
                leaf default-med {
                  type uint32;
                  // NCS drop default statement
                  description
                    "Specify the Multi-Exit-Discriminator (MED) of BGP routes. The value is an integer. This value is valid only for the imported routes and BGP summarized routes on the local router.";
                }
                leaf best-route-bit-error-detection {
                  // NCS drop when statement
                  type boolean;
                  // NCS drop default statement
                  description
                    "Enable/disable the function to reroute traffic when a bit error event occurs.";
                }
                leaf supernet-label-advertise {
                  type boolean;
                  // NCS drop default statement
                  description
                    "Enable/disable the function to advertise supernet labeled routes.";
                }
                leaf lsp-mtu {
                  type uint16 {
                    range "46..65535";
                  }
                  // NCS drop default statement
                  description
                    "BGP LSP MTU.";
                }
                leaf label-free-delay {
                  type uint8 {
                    range "0..180";
                  }
                  units "s";
                  // NCS drop default statement
                  description
                    "Label free delay.";
                }
                leaf bestroute-med-confederation {
                  // NCS drop when statement
                  type boolean;
                  // NCS drop default statement
                  description
                    "Enable/disable BGP to compare Med value only within the federation.";
                }
                leaf bestroute-as-path-ignore {
                  type boolean;
                  // NCS drop must statement
                  // NCS drop default statement
                  description
                    "Enable/disable BGP to ignore the AS_Path attribute when selecting the optimal route. By default, BGP uses the AS_Path attribute as one of route selection rules, and a route with a shorter AS_Path is preferred. After bestroute-as-path-ignore is selected, BGP does not compare the AS_Path length.";
                }
                leaf determin-med {
                  type boolean;
                  // NCS drop must statement
                  // NCS drop default statement
                  description
                    "Enable/disable deterministic MED so that the route selection result is relevant to the sequence in which routes are received.";
                }
                leaf best-external {
                  // NCS drop when statement
                  type boolean;
                  // NCS drop must statement
                  // NCS drop default statement
                  description
                    "Enable/disable best external route selection.";
                }
                leaf add-path-select-num {
                  // NCS drop when statement
                  type uint8 {
                    range "2..64";
                  }
                  // NCS drop must statement
                  description
                    "Number of add-path routes.";
                }
                leaf load-balanc-igp-metric-ignore {
                  // NCS drop when statement
                  type boolean;
                  // NCS drop default statement
                  description
                    "Enable/disable BGP to ignore the IGP cost of each BGP route to the next hop when selecting routes for load balancing. By default, only the routes with the same IGP cost can participate in load balancing.";
                }
                leaf load-balanc-as-path-ignore {
                  // NCS drop when statement
                  type boolean;
                  // NCS drop must statement
                  // NCS drop default statement
                  description
                    "Enable/disable BGP to ignore the AS_Path of each BGP route to the next hop when selecting routes for load balancing. By default, only the routes with the same AS_Path can participate in load balancing.";
                }
                leaf load-balanc-as-path-relax {
                  // NCS drop when statement
                  type boolean;
                  // NCS drop must statement
                  // NCS drop default statement
                  description
                    "Enable/disable BGP to ignore comparison of AS_Path attributes with the same length. By default, only the routes with the same AS_Path can participate in load balancing.";
                }
                leaf default-local-preference {
                  type uint32 {
                    range "0..4294967295";
                  }
                  // NCS drop default statement
                  description
                    "The local preference of BGP routes.";
                }
                leaf default-route-import {
                  type boolean;
                  // NCS drop default statement
                  description
                    "Enable/disable the function to import default routes into the BGP routing table. Default-route-imported must be used with import-routes so that default routes can be imported to the BGP routing table. If only import-routes is used, no default routes can be added to the BGP routing table. In addition, default-route-imported can only import the default routes in the routing table into the BGP routing table.";
                }
                leaf routerid-neglect {
                  type boolean;
                  // NCS drop default statement
                  description
                    "Enable/disable BGP to ignore router IDs when selecting the optimal route. Comparing router IDs is the last resort in route selection. This means that if one optimal route must be selected and no other parameters can be used to break the tie, router IDs can be used. If this option is selected, the first received route will be selected as the optimal route, and BGP will ignore the router ID and peer address in route selection.";
                }
                leaf route-select-delay {
                  type uint16 {
                    range "0..3600";
                  }
                  units "s";
                  // NCS drop default statement
                  description
                    "Route selection delay.";
                }
                leaf import-rib-nexthop-invariable {
                  // NCS drop when statement
                  type boolean;
                  // NCS drop default statement
                  description
                    "Enable/disable the command to enable advertise the route without modifying the next-hop.";
                }
                uses live_ncs_reflect-type;
                uses live_ncs_reflector-cluster-type;
                leaf reflect-between-client {
                  type boolean;
                  // NCS drop default statement
                  description
                    "Enable/disable route reflection between clients. If clients of a route reflector (RR) are fully meshed, you can disable route reflection among clients to reduce the cost.";
                }
                uses live_ncs_bestroute-med-plus-igp-type;
                uses live_ncs_bestroute-router-id-prior-clusterlist-type;
                leaf bestroute-med-none-as-maximum {
                  type boolean;
                  // NCS drop default statement
                  description
                    "Enable/disable BGP considers its MED as the largest MED value (4294967295). If a route does not carry MED, BGP considers its MED as the default value (0) during route selection.";
                }
                leaf ext-community-change {
                  type boolean;
                  // NCS drop default statement
                  description
                    "Enable/disable the function to change the extended community attribute.";
                }
              }
              container nexthop-recursive-lookup {
                description
                  "Configure next hop iteration.";
                container common {
                  description
                    "Configure next hop iteration common options.";
                  uses live_ncs_nexthop-recursive-lookup-restrain;
                }
              }
              container import-routes {
                description
                  "List of imported routes.";
                list import-route {
                  key "protocol process-id";
                  description
                    "Apply route import policy. Routes of other protocol types can be imported by BGP. By default, BGP does not import routes of other protocol types.";
                  uses live_ncs_import-routes-type;
                  leaf non-relay-tunnel {
                    // NCS drop when statement
                    type boolean;
                    // NCS drop default statement
                    description
                      "Enable/disable imported route relay a tunnel.";
                  }
                }
              }
              container network-routes {
                description
                  "List of network routes.";
                list network-route {
                  key "address mask-length";
                  description
                    "Configure a network route in the BGP routing table.";
                  uses live_ncs_network-route-ipv4;
                  leaf non-relay-tunnel {
                    // NCS drop when statement
                    type boolean;
                    // NCS drop default statement
                    description
                      "Enable/disable imported route relay a tunnel.";
                  }
                }
              }
              container import-ribs {
                description
                  "List of imported RIBs configuration.";
                list import-rib {
                  key "source-vpn source-address-family";
                  description
                    "Configure imported RIBs.";
                  leaf source-vpn {
                    type leafref {
                      path "/ncs:devices/ncs:device/ncs:live-status/ni:network-instance/ni:instances/ni:instance/ni:name" {
                        tailf:xpath-root 3;
                      }
                    }
                    // NCS drop must statement
                    description
                      "Source VPN name.";
                  }
                  leaf source-address-family {
                    type bgp:live_ncs_import-rib-ipv4-safi-type;
                    description
                      "Source address family type.";
                  }
                  leaf valid-route {
                    type boolean;
                    // NCS drop default statement
                    description
                      "Enable/disable imported valid route.";
                  }
                  leaf include-label-route {
                    // NCS drop when statement
                    type boolean;
                    // NCS drop default statement
                    description
                      "Enable/disable imported include label route.";
                  }
                  // NCS expand uses statement
                  choice policy-type {
                    case rtp-ref {
                      description
                        "Specify the route policy.";
                      leaf policy-name {
                        type leafref {
                          path "/ncs:devices/ncs:device/ncs:live-status/rtp:routing-policy/rtp:policy-definitions/rtp:policy-definition/rtp:name" {
                            tailf:xpath-root 3;
                          }
                        }
                        description
                          "Specify the route policy.";
                      }
                    }
                    case xpl-ref {
                      description
                        "Route filter.";
                      uses live_ncs_route-filter-type;
                    }
                    description
                      "Specify the route-policy or filter for imported RIBs.";
                  }
                }
              }
              container lsp-options {
                description
                  "Configure BGP ingress-lsp.";
                uses live_ncs_safi-lsp-options;
                leaf maximum-load-balancing-transit {
                  // NCS drop when statement
                  type uint16 {
                    range "1..65535";
                  }
                  // NCS drop default statement
                  description
                    "Maximum number of transit LSPs for load balancing.";
                }
                leaf unicast-rt-label-advertise-popgo {
                  // NCS drop when statement
                  type boolean;
                  // NCS drop default statement
                  description
                    "Enable/disable a device to convert received IPv4 public network unicast routes to labeled routes by adding a BGP label to each route and advertise the labeled routes to peers with the labeled route exchange capability. If the IP address of an outbound interface is reachable but no LSP is reachable, traffic is forwarded through the outbound interface and a specific next hop, during which the label POPGO action is performed.";
                }
                leaf lsp-operation {
                  // NCS drop when statement
                  type live_ncs_lsp-operation-type;
                  // NCS drop default statement
                  description
                    "Label operation type.";
                }
                uses live_ncs_ingress-choice-policy-set;
              }
              uses live_ncs_vrf-af-dampening-routes;
              uses bgp:live_ncs_slow-peer-type;
            }
            container ipv4-multicast {
              // NCS drop when statement
              description
                "Configure IPv4 multicast options.";
              container common {
                description
                  "Configure BGP IPv4-multicast address family options.";
                leaf always-compare-med {
                  type boolean;
                  // NCS drop default statement
                  description
                    "Enable/disable BGP to compare the MEDs of routes from peers in different ASs in route selection. If
                     there are multiple reachable routes to the same destination, the route with the smallest MED is preferred. Do not use this option unless different ASs use the same IGP and route selection mode.";
                }
                leaf default-med {
                  type uint32;
                  // NCS drop default statement
                  description
                    "Specify the Multi-Exit-Discriminator (MED) of BGP routes. The value is an integer. This value is valid only for the imported routes and BGP summarized routes on the local router.";
                }
                leaf summary-automatic {
                  type boolean;
                  // NCS drop default statement
                  description
                    "Enable/disable automatic summarization for imported routes. Manual summarization takes precedence over automatic summarization. After automatic summarization is enabled, BGP summarizes routes based on the natural network segment (for example, 10.1.1.1/24 and 10.2.1.1/24 are summarized into 10.0.0.0/8, a Class A address), and sends only the summarized route to peers. This reduces the number of routes.";
                }
                leaf bestroute-med-confederation {
                  type boolean;
                  // NCS drop default statement
                  description
                    "Enable/disable BGP to compare Med value only within the federation.";
                }
                leaf default-local-preference {
                  type uint32 {
                    range "0..4294967295";
                  }
                  // NCS drop default statement
                  description
                    "The local preference of BGP routes.";
                }
                leaf default-route-import {
                  type boolean;
                  // NCS drop default statement
                  description
                    "Enable/disable the function to import default routes into the BGP routing table. Default-route-imported must be used with import-routes so that default routes can be imported to the BGP routing table. If only import-routes is used, no default routes can be added to the BGP routing table. In addition, default-route-imported can only import the default routes in the routing table into the BGP routing table.";
                }
                leaf routerid-neglect {
                  type boolean;
                  // NCS drop default statement
                  description
                    "Enable/disable BGP to ignore router IDs when selecting the optimal route. Comparing router IDs is the last resort in route selection. This means that if one optimal route must be selected and no other parameters can be used to break the tie, router IDs can be used. If this option is selected, the first received route will be selected as the optimal route, and BGP will ignore the router ID and peer address in route selection.";
                }
                leaf route-select-delay {
                  type uint16 {
                    range "0..3600";
                  }
                  units "s";
                  // NCS drop default statement
                  description
                    "Route selection delay.";
                }
                uses live_ncs_reflect-type;
                uses live_ncs_reflector-cluster-type;
                leaf reflect-between-client {
                  type boolean;
                  // NCS drop default statement
                  description
                    "Enable/disable route reflection between clients. If clients of a route reflector (RR) are fully meshed, you can disable route reflection among clients to reduce the cost.";
                }
                leaf determin-med {
                  type boolean;
                  // NCS drop default statement
                  description
                    "Enable/disable deterministic MED so that the route selection result is relevant to the sequence in which routes are received.";
                }
                uses live_ncs_bestroute-med-plus-igp-type;
                uses live_ncs_bestroute-router-id-prior-clusterlist-type;
                leaf bestroute-as-path-ignore {
                  type boolean;
                  // NCS drop default statement
                  description
                    "Enable/disable BGP to ignore the AS_Path attribute when selecting the optimal route. By default, BGP uses the AS_Path attribute as one of route selection rules, and a route with a shorter AS_Path is preferred. After bestroute-as-path-ignore is selected, BGP does not compare the AS_Path length.";
                }
                leaf bestroute-med-none-as-maximum {
                  type boolean;
                  // NCS drop default statement
                  description
                    "Enable/disable BGP considers its MED as the largest MED value (4294967295). If a route does not carry MED, BGP considers its MED as the default value (0) during route selection.";
                }
                leaf maximum-load-balancing {
                  type uint16 {
                    range "1..65535";
                  }
                  // NCS drop must statement
                  // NCS drop default statement
                  description
                    "Specify the maximum number of equal-cost routes in the BGP routing table. The value can be 1 or an integer greater than 1. The value depends on the associated license. By default, the maximum number of equal-cost routes is 1. Equal-cost BGP routes can be generated for load balancing only when the BGP routes meet the first nine rules of the route-selection policy and have the same AS-Path attribute.";
                }
                leaf maximum-load-balancing-ibgp {
                  type uint16 {
                    range "1..65535";
                  }
                  // NCS drop must statement
                  // NCS drop default statement
                  description
                    "Specify the maximum number of equal-cost IBGP routes.";
                }
                leaf maximum-load-balancing-ebgp {
                  type uint16 {
                    range "1..65535";
                  }
                  // NCS drop must statement
                  // NCS drop default statement
                  description
                    "Specify the maximum number of equal-cost EBGP routes.";
                }
                leaf ext-community-change {
                  type boolean;
                  // NCS drop default statement
                  description
                    "Enable/disable the function to change the extended community attribute.";
                }
              }
              container nexthop-recursive-lookup {
                description
                  "Configure next hop iteration.";
                container common {
                  description
                    "Configure next hop iteration common options.";
                  choice policy-type {
                    description
                      "Set route-policy or route-filter.";
                    case rtp-ref {
                      description
                        "Route policy.";
                      leaf route-policy {
                        type leafref {
                          path "/ncs:devices/ncs:device/ncs:live-status/rtp:routing-policy/rtp:policy-definitions/rtp:policy-definition/rtp:name" {
                            tailf:xpath-root 3;
                          }
                        }
                        description
                          "Specify the name of a routing policy.";
                      }
                    }
                    case xpl-ref {
                      description
                        "Route filter.";
                      uses live_ncs_route-filter-type;
                    }
                  }
                }
                uses live_ncs_nexthop-recursive-lookup-delay;
              }
              uses live_ncs_bgp-route-preference-options;
              uses live_ncs_vrf-af-dampening-routes;
              container network-routes {
                description
                  "List of network routes.";
                list network-route {
                  key "address mask-length";
                  description
                    "Configure a network route in the BGP routing table.";
                  uses live_ncs_network-route-ipv4;
                }
              }
              container import-routes {
                description
                  "List of imported routes.";
                list import-route {
                  key "protocol process-id";
                  description
                    "Configure route import. Routes of other protocol types can be imported by BGP. By default, BGP does not import routes of other protocol types.";
                  leaf protocol {
                    type bgp:live_ncs_ipv4multi-import-route-protocol-type;
                    description
                      "Routing protocol from which routes can be imported.";
                  }
                  leaf process-id {
                    type uint32 {
                      range "0..4294967295";
                    }
                    // NCS drop must statement
                    description
                      "Process ID of an imported routing protocol. The process ID is 0, if the imported routing protocol is direct routes, static routes, UNRs, or OP-routes. The process ID must be specified range from 1 to 4294967295, if the imported routing protocol is RIP, OSPF, ISIS.";
                  }
                  leaf med {
                    type uint32;
                    description
                      "Specifies the MED metric of the imported route.";
                  }
                  choice policy-type {
                    description
                      "Set route policy or filter.";
                    case rtp-ref {
                      description
                        "Route policy.";
                      leaf policy-name {
                        type leafref {
                          path "/ncs:devices/ncs:device/ncs:live-status/rtp:routing-policy/rtp:policy-definitions/rtp:policy-definition/rtp:name" {
                            tailf:xpath-root 3;
                          }
                        }
                        description
                          "When routes are imported from other routing protocols, the route-policy filter can be used to filter the routes and change route attributes.";
                      }
                    }
                    case xpl-ref {
                      description
                        "Route filter.";
                      uses live_ncs_route-filter-type;
                    }
                  }
                }
              }
              container aggregate-routes {
                description
                  "List of summarized routes.";
                list aggregate-route {
                  key "address mask-length";
                  description
                    "Configure a summarized route in the BGP routing table. The local outbound interface of the summarized route is Null0. When another router receives the route, the route adds an outbound interface to the route. By default, route summarization is not performed. If the Origin attributes of the specific routes for the route summarization are different, the Origin attribute of the summarized route is that with the highest priority. Origin attributes are arranged in the priority order of complete > egp > igp. A summarized route carries the community attribute of each specific route.";
                  // NCS expand uses statement
                  leaf address {
                    type inet:ip-address-no-zone;
                    description
                      "Specify the IPv4 address or IPv6 address of a summarized route. Only IPv4 summarized routes can be configured in the IPv4 address family and only IPv6 summarized routes can be configured in the IPv6 address family.";
                    // NCS drop must statement
                  }
                  leaf mask-length {
                    type uint8 {
                      range "1..128";
                    }
                    description
                      "Specify the mask length of a summarized address.";
                    // NCS drop must statement
                  }
                  leaf as-set {
                    type boolean;
                    // NCS drop default statement
                    description
                      "Enable/disable the generation of routes with the AS-SET attribute. This option can be used to create a summarized route. The AS_Path attribute of the summarized route contains the AS-Path attributes of the specific routes for the route summarization. Exercise caution when using this option if multiple AS_Paths need to be summarized to prevent route flapping.";
                  }
                  leaf detail-suppressed {
                    type boolean;
                    // NCS drop default statement
                    description
                      "Enable/disable detail-suppressed. Suppress the advertisement of specific routes for the route summarization. Only the summarized route is advertised.";
                  }
                  choice policy-type {
                    description
                      "Set route policy or filter.";
                    case rtp-ref {
                      description
                        "Route policy.";
                      leaf attribute-policy {
                        type leafref {
                          path "/ncs:devices/ncs:device/ncs:live-status/rtp:routing-policy/rtp:policy-definitions/rtp:policy-definition/rtp:name" {
                            tailf:xpath-root 3;
                          }
                        }
                        description
                          "Specify an attribute of summarized routes. If apply as-path is used to configure the AS_Path attribute that is used in the route Summarization policy, and the as-set keyword is set, the AS_Path attribute in the policy does not take effect. This parameter and any of the following parameters overwrite each other: suppressFilter, originFilter, and attributeFilter.";
                      }
                      leaf origin-policy {
                        type leafref {
                          path "/ncs:devices/ncs:device/ncs:live-status/rtp:routing-policy/rtp:policy-definitions/rtp:policy-definition/rtp:name" {
                            tailf:xpath-root 3;
                          }
                        }
                        description
                          "Specify the name of a policy for generating summarized routes. Summarized routes are generated only when the routes match route-policy. This parameter and any of the following parameters overwrite each other: suppressFilter, originFilter, and attributeFilter.";
                      }
                      leaf suppress-policy {
                        type leafref {
                          path "/ncs:devices/ncs:device/ncs:live-status/rtp:routing-policy/rtp:policy-definitions/rtp:policy-definition/rtp:name" {
                            tailf:xpath-root 3;
                          }
                        }
                        description
                          "Specify a policy for suppressing the advertisement of specified routes. The routes matching the policy are not advertised, and other routes are advertised. This parameter and any of the following parameters overwrite each other: suppressFilter, originFilter, and attributeFilter.";
                      }
                    }
                    case xpl-ref {
                      description
                        "Route filter.";
                      leaf attribute-filter-name {
                        type leafref {
                          path "/ncs:devices/ncs:device/ncs:live-status/xpl:xpl/xpl:route-filters/xpl:route-filter/xpl:name" {
                            tailf:xpath-root 3;
                          }
                        }
                        description
                          "Specify a route-filter name.";
                      }
                      leaf attribute-filter-parameter {
                        // NCS drop when statement
                        type xpl:live_ncs_filter-parameter-type;
                        description
                          "Specify a route-filter parameter.";
                      }
                      leaf origin-filter-name {
                        type leafref {
                          path "/ncs:devices/ncs:device/ncs:live-status/xpl:xpl/xpl:route-filters/xpl:route-filter/xpl:name" {
                            tailf:xpath-root 3;
                          }
                        }
                        description
                          "Specify a route-filter name.";
                      }
                      leaf origin-filter-parameter {
                        // NCS drop when statement
                        type xpl:live_ncs_filter-parameter-type;
                        description
                          "Specify a route-filter parameter.";
                      }
                      leaf suppress-filter-name {
                        type leafref {
                          path "/ncs:devices/ncs:device/ncs:live-status/xpl:xpl/xpl:route-filters/xpl:route-filter/xpl:name" {
                            tailf:xpath-root 3;
                          }
                        }
                        description
                          "Specify a route-filter name.";
                      }
                      leaf suppress-filter-parameter {
                        // NCS drop when statement
                        type xpl:live_ncs_filter-parameter-type;
                        description
                          "Specify a route-filter parameter.";
                      }
                    }
                  }
                }
              }
              uses live_ncs_ipv4-import-filter-protocol-type;
              container export-filter-policys {
                description
                  "List of filtering policies.";
                list export-filter-policy {
                  key "protocol process-id";
                  description
                    "Apply a filtering policy. It is used to filter the routes to be advertised to the peer. By default, routes are not filtered.";
                  leaf protocol {
                    type bgp:live_ncs_ipv4-export-filter-protocol-type;
                    description
                      "Specify the name of a routing protocol. The routing protocol takes effect only on the routes to be advertised. The IPv4 address family supports the direct, IS-IS, OSPF, RIP, and static routing protocols. The IPv6 unicast address family of a public network instance supports the direct, IS-IS, OSPFv3, RIPng, and static routing protocols. The IPv6 address family of a VPNv6 instance supports the direct, IS-IS, RIPng, and static routing protocols.";
                  }
                  leaf process-id {
                    type uint32 {
                      range "0..4294967295";
                    }
                    // NCS drop must statement
                    description
                      "Specify the process ID required to be matched. The value is an integer ranging from 0 to 4294967295. If direct or static routes need to be filtered, no process ID is required.";
                  }
                  uses live_ncs_ipv4-filter-protocol-policy-choice-type;
                }
              }
              uses bgp:live_ncs_slow-peer-type;
              uses live_ncs_qos-local-id-type;
            }
          }
        }
        container dynamic-peer-prefixes {
          description
            "List of IP prefixes from which a dynamic BGP peer group listens for BGP connection requests.";
          list dynamic-peer-prefix {
            key "address mask-length peer-group";
            description
              "Configure an IP prefix from which a dynamic BGP peer group listens for BGP connection requests.";
            leaf address {
              type inet:ip-address-no-zone;
              // NCS drop must statement
              description
                "Network segment address for a dynamic peer connection.";
            }
            leaf mask-length {
              type uint8 {
                range "0..32";
              }
              description
                "Mask length of a network segment. For an IPv4 network address, the value ranges from 0 to 32.";
            }
            leaf peer-group {
              type leafref {
                path "../../../peer-groups/peer-group/name";
              }
              // NCS drop must statement
              // NCS drop must statement
              description
                "The peer-group within which the dynamic neighbor will be configured.";
            }
          }
        }
        container peer-groups {
          description
            "List of BGP peer groups. The BGP peer groups can help you simplify the configurations. If you want to perform the same configuration for several peers, you can create a peer group and then configure the peer group. After you add these peers to the peer group, all these peers will have the same configurations as the peer group.";
          list peer-group {
            key "name";
            description
              "Configure information about a BGP peer group.";
            leaf name {
              type string {
                length "1..47";
                pattern '([^\? ]+)';
              }
              description
                "Specify the name of a peer group. The value is a string of characters, spaces not supported.";
            }
            leaf type {
              type live_ncs_group-type;
              // NCS drop mandatory statement
              description
                "Specify the type of a peer group. The value can be IBGP or EBGP.The object cannot be modified.";
              ext:operation-exclude "update" {
                description
                  "The node cannot be modified, when node is already configured.";
              }
            }
            uses live_ncs_peer-local-if-type;
            uses live_ncs_authentication-attr-type;
            leaf description {
              type string {
                length "1..255";
                pattern '([^?]*)';
              }
              description
                "Specify the description of a peer group. The value is a string, which can be letters or digits, spaces supported. By default, no description is configured.";
            }
            leaf group-as {
              // NCS drop when statement
              type live_ncs_as-number-validate;
              description
                "Specify the AS number of a peer group. The AS number is in either a 2-byte or 4-byte format.
                 The two-byte format is X. X is an integer ranging from 1 to 65535.
                 The four-byte format is X.Y and X. When the format is X.Y, X and Y are both integers, with the value of X ranging from 1 to 65535, and the value of Y ranging from 0 to 65535; when the format is X, X is an interger, with the value of X ranging from 1 to 4294967295.";
            }
            leaf tcp-mss {
              type uint16 {
                range "176..4096";
              }
              description
                "Maximum TCP MSS value used for TCP connection establishment for a peer group.";
            }
            leaf ebgp-max-hop {
              // NCS drop when statement
              type uint32 {
                range "1..255";
              }
              // NCS drop must statement
              // NCS drop default statement
              description
                "Maximum number of hops in an indirect EBGP connection. By default, EBGP connections can be established only between directly connected peers. The function must be configured on both ends.";
            }
            leaf valid-ttl-hops {
              type uint16 {
                range "1..255";
              }
              // NCS drop must statement
              description
                "Enable GTSM on a peer or peer group. The valid-TTL-Value parameter is used to specify the number of TTL hops to be detected. If the value is configured as hops, the valid TTL range of the detected packet is [255-hops+1, 255].";
            }
            uses live_ncs_peer-tracking-type;
            leaf conventional {
              type boolean;
              // NCS drop default statement
              description
                "Enable/disable general router functions on peers. In conventional mode, not all the extended router functions, such as, route refreshing, GR, and multi-address family negotiation, are available. Therefore, the router of a new version can be compatible with the routers of earlier versions.";
            }
            leaf route-refresh {
              type boolean;
              // NCS drop default statement
              description
                "Enable/disable BGP to advertise Refresh messages to peers.";
            }
            leaf four-byte-as {
              type boolean;
              // NCS drop default statement
              description
                "Enable/disable BGP to advertise routes carrying 4-byte AS numbers to peers. After the 4-byte AS number function is disabled, Open packets will not carry 4-byte AS number capability flag, and peer ends will not know that local ends have the 4-byte AS number function. The 4-byte AS number function cannot be disabled from peers (peer groups) if a 4-byte AS number, fake AS number, or confederation ID is configured on a router and the AS number of a peer is 4-byte. If the 4-byte AS number function is disabled in such a situation, BGP sessions may fail to be established, and route transmission may be affected.";
            }
            leaf ignore {
              type boolean;
              // NCS drop default statement
              description
                "Enable/disable the function to tear down sessions between peers and clear all related routing information.";
            }
            leaf connect-mode {
              // NCS drop when statement
              type live_ncs_connect-mode;
              // NCS drop default statement
              description
                "The value can be Connect-only, Listen-only, or Both. If the value is Connect-only, the specified peer or peer group only initiatively sends connection requests, instead of listening to connection requests. If the value is Listen-only, the specified peer or peer group only listens to connection requests, instead of initiatively sending connection requests. If the value is Both, the specified peer or peer group not only initiatively sends connection requests, but also listens to connection requests. The default value is Both.";
            }
            leaf log-change {
              type boolean;
              // NCS drop default statement
              description
                "Enable/disable BGP to record the session status and events of the specified peer or peer group.";
            }
            leaf path-mtu-auto-discovery {
              // NCS drop when statement
              type boolean;
              // NCS drop default statement
              description
                "Enable/disable path mtu auto discovery.";
            }
            leaf local-ifnet-disable {
              type boolean;
              description
                "Enable/disable MPLS local IFNET tunnel creation on a BGP peer. By default, MPLS local IFNET tunnels can be created on an EBGP peer,but such tunnels cannot be created on an IBGP peer.";
              ext:dynamic-default;
            }
            leaf check-first-as {
              // NCS drop when statement
              type live_ncs_peer-cap-config-state;
              // NCS drop default statement
              description
                "Check the first AS in the AS_Path of the update messages from EBGP peers.";
            }
            leaf memory-priority {
              type live_ncs_memory-priority;
              // NCS drop default statement
              description
                "Set a priority that determines the disconnection order of each BGP peer relationship in a peer group if memory overload occurs.";
            }
            leaf oscillation-dampening {
              // NCS drop when statement
              type boolean;
              // NCS drop default statement
              description
                "Enable/disable BGP to suppress the establishment of a specified peer group's peer relationships that flap continuously. By default, the capability is enabled.";
            }
            leaf peer-establish-mode {
              type live_ncs_peer-establish-mode;
              // NCS drop default statement
              description
                "Specify mode in which a BGP peer is established. The value can be static or dynamic.";
              ext:operation-exclude "update|delete" {
                description
                  "The node cannot be modified, deleted when node is already configured.";
              }
            }
            leaf as-number-type {
              // NCS drop when statement
              type live_ncs_as-number-type;
              // NCS drop must statement
              // NCS drop default statement
              description
                "Specify the type of the AS number that is used to establish a BGP peer relationship dynamically. The value can be dynamic-neighbor or confederation.";
              ext:operation-exclude "update|delete" {
                description
                  "The node cannot be modified, deleted when node is already configured.";
              }
            }
            leaf-list listen-as {
              // NCS drop when statement
              type live_ncs_as-number-validate;
              // NCS drop must statement
              // NCS drop max-elements statement
              description
                "Specify the peer AS from which a dynamic EBGP peer group listens for BGP connection requests.";
            }
            container listen-as-segments {
              // NCS drop when statement
              description
                "List of AS number ranges for listening.";
              list listen-as-segment {
                // NCS drop must statement
                key "begin-as end-as";
                // NCS drop max-elements statement
                description
                  "Specify an AS number range from which a dynamic EBGP peer group listens for connection requests. The value of begin-as must be smaller than that of end-as. The value of As-Segment cannot contain the value of LocalAS or the value of fake-as. An AS number range cannot contain a confederation AS number, and any two AS number ranges cannot contain each other.";
                leaf begin-as {
                  type live_ncs_as-number-validate;
                  description
                    "Specify the start AS number in an AS range.";
                }
                leaf end-as {
                  type live_ncs_as-number-validate;
                  description
                    "Specify the end AS number in an AS range.";
                }
              }
            }
            container fake-as-parameter {
              description
                "Configure BGP fake-as parameters.";
              leaf fake-as {
                // NCS drop when statement
                type bgp:live_ncs_as-number-validate;
                description
                  "Fake AS number that is specified for a local peer. By default, a peer uses the actual AS number of the local end.
                   An AS number can be in either two-byte format or four-byte format:
                   The two-byte format is X. X is an integer ranging from 1 to 65535.
                   The four-byte format is X.Y and X. When the format is X.Y, X and Y are both integers, with the value of X ranging from 1 to 65535, and the value of Y ranging from 0 to 65535; when the format is X, X is an interger, with the value of X ranging from 1 to 4294967295.";
              }
              leaf dual-as {
                // NCS drop when statement
                type boolean;
                // NCS drop default statement
                description
                  "Enable/disable the function to the remote EBGP peer can use the actual or fake AS number when specifying the AS number for a local peer. The local peer uses the fake and actual AS numbers to establish a BGP peer relationship with the remote end and identifies the AS number configured by the remote end through the error code (OPEN Message Error) and sub-error code (Bad Peer AS) of the Notification message from the remote end.";
              }
              leaf prepend-global-as {
                // NCS drop when statement
                type boolean;
                // NCS drop default statement
                description
                  "Enable/disable the function to add the global AS number to the Update packets to be advertised.";
              }
              leaf prepend-fake-as {
                // NCS drop when statement
                type boolean;
                // NCS drop default statement
                description
                  "Enable/disable the function to add the Fake AS number to received Update packets.";
              }
            }
            uses live_ncs_peer-timer-para-type;
            uses live_ncs_group-bfd-parameter-type;
            container graceful-restart {
              // NCS drop when statement
              description
                "Configure graceful restart.";
              uses live_ncs_group-graceful-restart-type;
              leaf peer-reset {
                type boolean;
                // NCS drop default statement
                description
                  "Enable/disable reseting BGP peer graceful.";
              }
            }
            container local-graceful-restart {
              // NCS drop when statement
              description
                "Configure local graceful restart.";
              uses live_ncs_group-graceful-restart-type;
            }
            container members {
              description
                "List of members in a peer group.";
              list member {
                key "peer-address";
                description
                  "Statistics of member in a peer group.";
                leaf peer-address {
                  type inet:ip-address-no-zone;
                  description
                    "Specify the address of the peer joining the peer group.";
                }
              }
            }
            container afs {
              description
                "List of all peer groups that are enabled in a specified address family.";
              list af {
                key "type";
                description
                  "Configure peer group enabled in a specified address family.";
                leaf type {
                  type bgp:live_ncs_group-af-type;
                  // NCS drop must statement
                  description
                    "Address family type of a BGP instance.";
                }
                container ipv4-unicast {
                  // NCS drop when statement
                  description
                    "Configure IPv4 unicast options.";
                  leaf advertise-community {
                    type boolean;
                    // NCS drop default statement
                    description
                      "Enable/disable advertise the community attribute to a peer or a peer group.";
                  }
                  leaf reflect-client {
                    // NCS drop when statement
                    type boolean;
                    // NCS drop default statement
                    description
                      "Enable/disable the local device as a route reflector (RR) and a peer or peer group as its client. This configuration is applicable between IBGP peers only. The configurations of RRs and its clients in an address family are valid only in this address family. Therefore, it is recommended to configure RRs and its clients in the specified address family that is required.";
                  }
                  leaf orf-type {
                    // NCS drop when statement
                    type bgp:live_ncs_bgp-orf-type;
                    // NCS drop must statement
                    // NCS drop default statement
                    description
                      "ORF Type.";
                  }
                  leaf orf-mode {
                    // NCS drop when statement
                    type bgp:live_ncs_bgp-orf-mode-type;
                    // NCS drop must statement
                    // NCS drop default statement
                    description
                      "Configure an outbound route filtering (ORF) mode, which can be Receive, Send, or Both, and the default ORF mode is Both.";
                  }
                  leaf label-route-capability {
                    type boolean;
                    // NCS drop default statement
                    description
                      "Enable/disable a device to exchange labeled routes.";
                  }
                  leaf check-tunnel-reachable {
                    // NCS drop when statement
                    type boolean;
                    // NCS drop default statement
                    description
                      "Enable/disable tunnel reachability check.";
                  }
                  leaf check-withdraw-type {
                    // NCS drop when statement
                    type boolean;
                    // NCS drop default statement
                    status obsolete;
                    description
                      "Enable/disable withdraw type check.";
                  }
                  leaf nexthop-configure {
                    type live_ncs_nexthop-configuration-type;
                    description
                      "Both the next-hop-local mode and next-hop-invariable mode are available when the peer address family is the VPNv4/VPNv6/L2VPN AD address family. Only the next-hop-local mode is available when the peer address family is not VPNv4/VPNV6/L2VPN AD address family. In next-hop-local mode, you can configure a BGP speaker to set its IP address of as the next hop of the routes to be advertised to IBGP peers or IBGP peer groups. In next-hop-invariable mode, you can configure PEs in different ASs not to change the next hop of routes when the PEs advertise the routes to their EBGP peers and use the next hop addresses of IGP routes to advertise imported IGP routes to IBGP peers. By default, when a BGP speaker advertises routes to EBGP peers and imported IGP routes to IBGP peers, the BGP speaker changes the next hop to its interface address.";
                  }
                  uses live_ncs_peer-policy-filter-type;
                  leaf advertise-ext-community {
                    type boolean;
                    // NCS drop default statement
                    description
                      "Enable/disable advertise the extended community attribute to a peer or peer group.";
                  }
                  leaf origin-as-validation {
                    // NCS drop when statement
                    type boolean;
                    // NCS drop default statement
                    description
                      "Enable/disable the BGP peer origin validation.";
                  }
                  leaf discard-ext-community {
                    type boolean;
                    // NCS drop default statement
                    description
                      "Enable/disable discard the extended community attribute in the routing information about a specified peer.";
                  }
                  leaf allow-as-loop {
                    type uint32 {
                      range "1..10";
                    }
                    description
                      "Allow repetitive local AS numbers. By default, repetitive local AS numbers are not allowed.";
                  }
                  leaf aigp {
                    // NCS drop when statement
                    type boolean;
                    // NCS drop default statement
                    description
                      "Enable/disable route with AIGP attribute advertisement to or from a peer.";
                  }
                  leaf add-path-mode {
                    // NCS drop when statement
                    type live_ncs_add-path-cap-type;
                    // NCS drop default statement
                    description
                      "Enable Add-Path route advertisement to a peer.";
                  }
                  uses live_ncs_ip-prefix-filter-type;
                  uses live_ncs_as-path-filter-type;
                  uses live_ncs_peer-group-acl-name-or-num-type;
                  uses live_ncs_default-route-advertise-type;
                  leaf default-route-match-mode {
                    // NCS drop when statement
                    type live_ncs_cra-match-mode;
                    // NCS drop default statement
                    description
                      "Configure the matching mode of default route advertisement, which can be disabling of route advertisement conditions, enabling of all route advertisement conditions, and enabling of part route advertisement conditions. Enabling of all route advertisement conditions indicates that a default route can be advertised only when it matches all the conditions. Enabling of part route advertisement conditions indicates that a default route can be advertised only when it matches one condition.";
                  }
                  uses live_ncs_rt-update-interval-type;
                  uses live_ncs_preferred-value-type;
                  leaf add-path-number {
                    // NCS drop when statement
                    type uint8 {
                      range "2..64";
                    }
                    description
                      "Number of Add-Path routes that can be advertised to a peer.";
                  }
                  leaf substitute-as-enable {
                    // NCS drop when statement
                    type boolean;
                    // NCS drop default statement
                    description
                      "Enable/disable replace the AS number of a specified peer in the AS_Path attribute with the local AS number. On a PE where AS number replacement is enabled, if an AS number in the AS_Path attribute of a route is same as that of the CE to which the PE advertises the route, the PE replaces the AS number with its own AS number before advertising the route.";
                  }
                  leaf soo {
                    // NCS drop when statement
                    type string {
                      length "3..21";
                    }
                    description
                      "Configure the Site-of-Origin (SoO) extended community attribute. This attribute can be expressed in the following formats: X.X.X.X:number<0-65535>, number<0-65535>:number<0-4294967295>, or number<0-65535>.number<0-65535>:number<0-65535> or <65536-4294967295>:<0-65535>. 0:0 or 0.0:0 is not supported.
                       Two CEs are in the same site and can advertise routes to each other, and they are connected to a VPN through PEs. If the local routes of a CE are advertised to the other CE over the VPN, a routing loop may occur.
                       The SoO feature can prevent a route advertised by a site from being sent back to the site, preventing routing loops. After SoO is enabled and a PE receives a route from a CE, the specified SoO attribute will be added to the route. Before advertising the route to the other CE, the PE checks the SoO attribute. If the SoO attribute is the same as the locally configured SoO attribute, the PE does not advertise the route, preventing routing loops.";
                  }
                  leaf keep-all-routes {
                    // NCS drop when statement
                    type boolean;
                    // NCS drop default statement
                    description
                      "Enable/disable saving all the updated information about BGP routes from a specified peer or peer group after a BGP connection is established, even though these BGP routes fail to match the routing policy on the ingress. By default, the updated information about BGP routes from a specified peer is saved only when the routes match the routing policy on the ingress. If a router supports route refreshing, this option is not required.";
                  }
                  leaf exp-mode {
                    type live_ncs_exp-mode-type;
                    // NCS drop default statement
                    description
                      "Specify the ASs in which a BGP label can inherit the QoS priority carried in the outer label of public tunnel in the Core AS and the ASs in which the priorities of BGP LSPs must be restored before the LSPs are advertised to a non-core AS.";
                  }
                  leaf advertise-best-external {
                    // NCS drop when statement
                    type boolean;
                    // NCS drop must statement
                    // NCS drop must statement
                    // NCS drop must statement
                    // NCS drop default statement
                    description
                      "Enable/disable the device to advertise Best External routes to peers.";
                  }
                  leaf load-balancing-enable {
                    type boolean;
                    // NCS drop default statement
                    description
                      "Enable/disable a neighbour to participate in load balancing.";
                  }
                  choice load-balancing-ignore-as-type {
                    description
                      "Set load balancing as path type.";
                    case as-attribute {
                      description
                        "Ignore the as-path attribute.";
                      leaf load-balancing-as-path-ignore {
                        // NCS drop when statement
                        type empty;
                        description
                          "Configure BGP to ignore the AS_Path attribute when selecting the equal route. After as-path-neglect is selected, BGP does not compare the AS_Path length.";
                      }
                    }
                    case same-length-as-attribute {
                      description
                        "Ignore comparison of as-path attributes with the same length.";
                      leaf load-balancing-as-path-relax {
                        // NCS drop when statement
                        type empty;
                        description
                          "Configure BGP to ignore comparison of AS_Path attributes with the same length when selecting the equal route. After as-path-neglect is selected, BGP does not compare the AS_Path length.";
                      }
                    }
                  }
                  leaf prefix-sid {
                    // NCS drop when statement
                    type boolean;
                    // NCS drop default statement
                    description
                      "Enable/disable a device to exchange IPv4 prefix SIDs with a specified IPv6 peer group.";
                  }
                  choice prefix-sid-packet {
                    description
                      "Prefix-sid packet method.";
                    case sid-type5 {
                      description
                        "Packet by type5.";
                      leaf advertise-srv6-locator {
                        // NCS drop when statement
                        type empty;
                        description
                          "Advertise SRv6 locators.";
                      }
                    }
                  }
                  uses live_ncs_group-independent-peer-group-type;
                  uses live_ncs_advertise-large-community-group-type;
                  uses live_ncs_ipv4-default-route-match-conditions-type;
                  uses live_ncs_route-limit-accept-type;
                  uses live_ncs_public-as-only-type;
                  uses live_ncs_group-public-as-only-import-type;
                  uses live_ncs_advertise-dependent-filter-group-type;
                  container entropy-label-parameter {
                    // NCS drop when statement
                    description
                      "Configure information about entropy label parameter in a peer group.";
                    uses live_ncs_group-entropy-label-type;
                  }
                }
                container ipv6-unicast {
                  // NCS drop when statement
                  description
                    "Configure IPv6 unicast options.";
                  leaf advertise-community {
                    type boolean;
                    // NCS drop default statement
                    description
                      "Enable/disable advertise the community attribute to a peer or a peer group.";
                  }
                  leaf reflect-client {
                    // NCS drop when statement
                    type boolean;
                    // NCS drop default statement
                    description
                      "Enable/disable the local device as a route reflector (RR) and a peer or peer group as its client. This configuration is applicable between IBGP peers only. The configurations of RRs and its clients in an address family are valid only in this address family. Therefore, it is recommended to configure RRs and its clients in the specified address family that is required.";
                  }
                  leaf label-route-capability {
                    type boolean;
                    // NCS drop default statement
                    description
                      "Enable/disable a device to exchange labeled routes.";
                  }
                  leaf nexthop-configure {
                    type live_ncs_nexthop-configuration-type;
                    description
                      "Both the next-hop-local mode and next-hop-invariable mode are available when the peer address family is the VPNv4/VPNV6/L2VPN AD address family. Only the next-hop-local mode is available when the peer address family is not VPNv4/VPNV6/L2VPN AD address family. In next-hop-local mode, you can configure a BGP speaker to set its IP address of as the next hop of the routes to be advertised to IBGP peers or IBGP peer groups. In next-hop-invariable mode, you can configure PEs in different ASs not to change the next hop of routes when the PEs advertise the routes to their EBGP peers and use the next hop addresses of IGP routes to advertise imported IGP routes to IBGP peers. By default, when a BGP speaker advertises routes to EBGP peers and imported IGP routes to IBGP peers, the BGP speaker changes the next hop to its interface address.";
                  }
                  uses live_ncs_peer-policy-filter-type;
                  leaf advertise-ext-community {
                    type boolean;
                    // NCS drop default statement
                    description
                      "Enable/disable advertise the extended community attribute to a peer or peer group.";
                  }
                  leaf origin-as-validation {
                    // NCS drop when statement
                    type boolean;
                    // NCS drop default statement
                    description
                      "Enable/disable the BGP peer origin validation.";
                  }
                  leaf discard-ext-community {
                    type boolean;
                    // NCS drop default statement
                    description
                      "Enable/disable discard the extended community attribute in the routing information about a specified peer.";
                  }
                  leaf allow-as-loop {
                    type uint32 {
                      range "1..10";
                    }
                    description
                      "Allow repetitive local AS numbers. By default, repetitive local AS numbers are not allowed.";
                  }
                  leaf aigp {
                    // NCS drop when statement
                    type boolean;
                    // NCS drop default statement
                    description
                      "Enable/disable route with AIGP attribute advertisement to or from a peer.";
                  }
                  uses live_ncs_default-route-advertise-type;
                  leaf default-route-match-mode {
                    // NCS drop when statement
                    type live_ncs_cra-match-mode;
                    // NCS drop default statement
                    description
                      "Configure the matching mode of default route advertisement, which can be disabling of route advertisement conditions, enabling of all route advertisement conditions, and enabling of part route advertisement conditions. Enabling of all route advertisement conditions indicates that a default route can be advertised only when it matches all the conditions. Enabling of part route advertisement conditions indicates that a default route can be advertised only when it matches one condition.";
                  }
                  leaf add-path-mode {
                    // NCS drop when statement
                    type live_ncs_add-path-cap-type;
                    // NCS drop default statement
                    description
                      "Enable Add-Path route advertisement to a peer.";
                  }
                  uses live_ncs_ipv6-prefix-filter-type;
                  uses live_ncs_as-path-filter-type;
                  uses live_ncs_peer-group-acl6-name-or-num-type;
                  uses live_ncs_rt-update-interval-type;
                  uses live_ncs_preferred-value-type;
                  leaf add-path-number {
                    // NCS drop when statement
                    type uint8 {
                      range "2..64";
                    }
                    description
                      "Number of Add-Path routes that can be advertised to a peer.";
                  }
                  leaf substitute-as-enable {
                    // NCS drop when statement
                    type boolean;
                    // NCS drop default statement
                    description
                      "Enable/disable replace the AS number of a specified peer in the AS_Path attribute with the local AS number. On a PE where AS number replacement is enabled, if an AS number in the AS_Path attribute of a route is same as that of the CE to which the PE advertises the route, the PE replaces the AS number with its own AS number before advertising the route.";
                  }
                  leaf soo {
                    // NCS drop when statement
                    type string {
                      length "3..21";
                    }
                    description
                      "Configure the Site-of-Origin (SoO) extended community attribute. This attribute can be expressed in the following formats: X.X.X.X:number<0-65535>, number<0-65535>:number<0-4294967295>, or number<0-65535>.number<0-65535>:number<0-65535> or <65536-4294967295>:<0-65535>. 0:0 or 0.0:0 is not supported.
                       Two CEs are in the same site and can advertise routes to each other, and they are connected to a VPN through PEs. If the local routes of a CE are advertised to the other CE over the VPN, a routing loop may occur.
                       The SoO feature can prevent a route advertised by a site from being sent back to the site, preventing routing loops. After SoO is enabled and a PE receives a route from a CE, the specified SoO attribute will be added to the route. Before advertising the route to the other CE, the PE checks the SoO attribute. If the SoO attribute is the same as the locally configured SoO attribute, the PE does not advertise the route, preventing routing loops.";
                  }
                  leaf keep-all-routes {
                    // NCS drop when statement
                    type boolean;
                    // NCS drop default statement
                    description
                      "Enable/disable saving all the updated information about BGP routes from a specified peer or peer group after a BGP connection is established, even though these BGP routes fail to match the routing policy on the ingress. By default, the updated information about BGP routes from a specified peer is saved only when the routes match the routing policy on the ingress. If a router supports route refreshing, this option is not required.";
                  }
                  leaf advertise-best-external {
                    // NCS drop when statement
                    type boolean;
                    // NCS drop must statement
                    // NCS drop must statement
                    // NCS drop must statement
                    // NCS drop default statement
                    description
                      "Enable/disable the device to advertise Best External routes to peers.";
                  }
                  leaf load-balancing-enable {
                    type boolean;
                    // NCS drop default statement
                    description
                      "Enable/disable a neighbour to participate in load balancing.";
                  }
                  choice load-balancing-ignore-as-type {
                    description
                      "Set load balancing as path type.";
                    case as-attribute {
                      description
                        "Ignore the as-path attribute.";
                      leaf load-balancing-as-path-ignore {
                        // NCS drop when statement
                        type empty;
                        description
                          "Configure BGP to ignore the AS_Path attribute when selecting the equal route. After as-path-neglect is selected, BGP does not compare the AS_Path length.";
                      }
                    }
                    case same-length-as-attribute {
                      description
                        "Ignore comparison of as-path attributes with the same length.";
                      leaf load-balancing-as-path-relax {
                        // NCS drop when statement
                        type empty;
                        description
                          "Configure BGP to ignore comparison of AS_Path attributes with the same length when selecting the equal route. After as-path-neglect is selected, BGP does not compare the AS_Path length.";
                      }
                    }
                  }
                  leaf prefix-sid {
                    // NCS drop when statement
                    type boolean;
                    // NCS drop default statement
                    description
                      "Enable/disable a device to exchange IPv4 prefix SIDs with a specified IPv6 peer group.";
                  }
                  choice prefix-sid-packet {
                    description
                      "Prefix-sid packet method.";
                    case sid-type5 {
                      description
                        "Packet by type5.";
                      leaf advertise-srv6-locator {
                        // NCS drop when statement
                        type empty;
                        description
                          "Advertise SRv6 locators.";
                      }
                    }
                  }
                  uses live_ncs_advertise-large-community-group-type;
                  uses live_ncs_group-independent-peer-group-type;
                  uses live_ncs_ipv6-default-route-match-conditions-type;
                  uses live_ncs_route-limit-accept-type;
                  uses live_ncs_public-as-only-type;
                  uses live_ncs_group-public-as-only-import-type;
                  uses live_ncs_advertise-dependent-filter6-group-type;
                }
                container ipv4-vpn {
                  // NCS drop when statement
                  description
                    "Configure IPv4 vpnv4 options.";
                  leaf advertise-community {
                    type boolean;
                    // NCS drop default statement
                    description
                      "Enable/disable advertise the community attribute to a peer or a peer group.";
                  }
                  leaf reflect-client {
                    // NCS drop when statement
                    type boolean;
                    // NCS drop default statement
                    description
                      "Enable/disable the local device as a route reflector (RR) and a peer or peer group as its client. This configuration is applicable between IBGP peers only. The configurations of RRs and its clients in an address family are valid only in this address family. Therefore, it is recommended to configure RRs and its clients in the specified address family that is required.";
                  }
                  leaf nexthop-configure {
                    type live_ncs_nexthop-configuration-type;
                    description
                      "Both the next-hop-local mode and next-hop-invariable mode are available when the peer address family is the VPNv4/VPNV6/L2VPN AD address family. Only the next-hop-local mode is available when the peer address family is not VPNv4/VPNV6/L2VPN AD address family. In next-hop-local mode, you can configure a BGP speaker to set its IP address of as the next hop of the routes to be advertised to IBGP peers or IBGP peer groups. In next-hop-invariable mode, you can configure PEs in different ASs not to change the next hop of routes when the PEs advertise the routes to their EBGP peers and use the next hop addresses of IGP routes to advertise imported IGP routes to IBGP peers. By default, when a BGP speaker advertises routes to EBGP peers and imported IGP routes to IBGP peers, the BGP speaker changes the next hop to its interface address.";
                  }
                  uses live_ncs_peer-policy-filter-type;
                  leaf ignore-bit-error {
                    // NCS drop when statement
                    type boolean;
                    // NCS drop default statement
                    description
                      "Enable/disable the peer to ignore bit error detection results.";
                  }
                  leaf allow-as-loop {
                    type uint32 {
                      range "1..10";
                    }
                    description
                      "Allow repetitive local AS numbers. By default, repetitive local AS numbers are not allowed.";
                  }
                  leaf aigp {
                    type boolean;
                    // NCS drop default statement
                    description
                      "Enable/disable route with AIGP attribute advertisement to or from a peer.";
                  }
                  leaf add-path-mode {
                    // NCS drop when statement
                    type live_ncs_add-path-cap-type;
                    // NCS drop default statement
                    description
                      "Enable Add-Path route advertisement to a peer.";
                  }
                  uses live_ncs_ip-prefix-filter-type;
                  uses live_ncs_peer-ipv4-reoriginate-type;
                  uses live_ncs_as-path-filter-type;
                  uses live_ncs_peer-group-acl-name-or-num-type;
                  uses live_ncs_rt-update-interval-type;
                  uses live_ncs_preferred-value-type;
                  leaf add-path-number {
                    // NCS drop when statement
                    type uint8 {
                      range "2..64";
                    }
                    description
                      "Number of Add-Path routes that can be advertised to a peer.";
                  }
                  leaf upe {
                    type boolean;
                    // NCS drop default statement
                    description
                      "Enable/disable the peer as an underlayer PE (UPE).";
                  }
                  leaf advertise-best-external {
                    // NCS drop when statement
                    type boolean;
                    // NCS drop must statement
                    // NCS drop must statement
                    // NCS drop must statement
                    // NCS drop default statement
                    description
                      "Enable/disable the device to advertise Best External routes to peers.";
                  }
                  uses live_ncs_advertise-large-community-group-type;
                  leaf keep-all-routes {
                    // NCS drop when statement
                    type boolean;
                    // NCS drop default statement
                    description
                      "Enable/disable saving all the updated information about BGP routes from a specified peer or peer group after a BGP connection is established, even though these BGP routes fail to match the routing policy on the ingress. By default, the updated information about BGP routes from a specified peer is saved only when the routes match the routing policy on the ingress. If a router supports route refreshing, this option is not required.";
                  }
                  uses live_ncs_group-independent-peer-group-type;
                  leaf origin-as-validation {
                    // NCS drop when statement
                    type boolean;
                    // NCS drop default statement
                    description
                      "Enable/disable the BGP peer origin validation.";
                  }
                  container default-route-originates {
                    description
                      "Configure advertised default VPNv4 routes.";
                    uses live_ncs_default-route-originate-type;
                  }
                  uses live_ncs_route-limit-type;
                  uses live_ncs_public-as-only-type;
                  uses live_ncs_group-public-as-only-import-type;
                }
                container ipv6-vpn {
                  // NCS drop when statement
                  description
                    "Configure IPv6 vpn options.";
                  leaf advertise-community {
                    type boolean;
                    // NCS drop default statement
                    description
                      "Enable/disable advertise the community attribute to a peer or a peer group.";
                  }
                  leaf reflect-client {
                    // NCS drop when statement
                    type boolean;
                    // NCS drop default statement
                    description
                      "Enable/disable the local device as a route reflector (RR) and a peer or peer group as its client. This configuration is applicable between IBGP peers only. The configurations of RRs and its clients in an address family are valid only in this address family. Therefore, it is recommended to configure RRs and its clients in the specified address family that is required.";
                  }
                  leaf nexthop-configure {
                    type live_ncs_nexthop-configuration-type;
                    description
                      "Both the next-hop-local mode and next-hop-invariable mode are available when the peer address family is the VPNv4/VPNV6/L2VPN AD address family. Only the next-hop-local mode is available when the peer address family is not VPNv4/VPNV6/L2VPN AD address family. In next-hop-local mode, you can configure a BGP speaker to set its IP address of as the next hop of the routes to be advertised to IBGP peers or IBGP peer groups. In next-hop-invariable mode, you can configure PEs in different ASs not to change the next hop of routes when the PEs advertise the routes to their EBGP peers and use the next hop addresses of IGP routes to advertise imported IGP routes to IBGP peers. By default, when a BGP speaker advertises routes to EBGP peers and imported IGP routes to IBGP peers, the BGP speaker changes the next hop to its interface address.";
                  }
                  uses live_ncs_peer-policy-filter-type;
                  leaf ignore-bit-error {
                    // NCS drop when statement
                    type boolean;
                    // NCS drop default statement
                    description
                      "Enable/disable the peer to ignore bit error detection results.";
                  }
                  leaf allow-as-loop {
                    type uint32 {
                      range "1..10";
                    }
                    description
                      "Allow repetitive local AS numbers. By default, repetitive local AS numbers are not allowed.";
                  }
                  leaf aigp {
                    type boolean;
                    // NCS drop default statement
                    description
                      "Enable/disable route with AIGP attribute advertisement to or from a peer.";
                  }
                  leaf add-path-mode {
                    // NCS drop when statement
                    type live_ncs_add-path-cap-type;
                    // NCS drop default statement
                    description
                      "Enable Add-Path route advertisement to a peer.";
                  }
                  uses live_ncs_ipv6-prefix-filter-type;
                  leaf reoriginate-route-enable {
                    type boolean;
                    // NCS drop default statement
                    description
                      "Enable/disable route regeneration.";
                  }
                  leaf reoriginate-ipv6-enable {
                    type boolean;
                    // NCS drop default statement
                    description
                      "Enable/disable IP route regeneration and advertisement.";
                  }
                  leaf reoriginate-mac-ipv6-enable {
                    type boolean;
                    // NCS drop default statement
                    description
                      "Enable/disable MAC-IP route regeneration and advertisement.";
                  }
                  uses live_ncs_as-path-filter-type;
                  uses live_ncs_peer-group-acl6-name-or-num-type;
                  uses live_ncs_rt-update-interval-type;
                  uses live_ncs_preferred-value-type;
                  leaf add-path-number {
                    // NCS drop when statement
                    type uint8 {
                      range "2..64";
                    }
                    description
                      "Number of Add-Path routes that can be advertised to a peer.";
                  }
                  leaf advertise-best-external {
                    // NCS drop when statement
                    type boolean;
                    // NCS drop must statement
                    // NCS drop must statement
                    // NCS drop must statement
                    // NCS drop default statement
                    description
                      "Enable/disable the device to advertise Best External routes to peers.";
                  }
                  uses live_ncs_advertise-large-community-group-type;
                  leaf keep-all-routes {
                    // NCS drop when statement
                    type boolean;
                    // NCS drop default statement
                    description
                      "Enable/disable saving all the updated information about BGP routes from a specified peer or peer group after a BGP connection is established, even though these BGP routes fail to match the routing policy on the ingress. By default, the updated information about BGP routes from a specified peer is saved only when the routes match the routing policy on the ingress. If a router supports route refreshing, this option is not required.";
                  }
                  uses live_ncs_group-independent-peer-group-type;
                  leaf origin-as-validation {
                    // NCS drop when statement
                    type boolean;
                    // NCS drop default statement
                    description
                      "Enable/disable the BGP peer origin validation.";
                  }
                  uses live_ncs_route-limit-type;
                  uses live_ncs_public-as-only-type;
                  uses live_ncs_group-public-as-only-import-type;
                }
                container ipv4-labeluni {
                  // NCS drop when statement
                  description
                    "Configure IPv4 label unicast options.";
                  leaf advertise-community {
                    type boolean;
                    // NCS drop default statement
                    description
                      "Enable/disable advertise the community attribute to a peer or a peer group.";
                  }
                  leaf reflect-client {
                    // NCS drop when statement
                    type boolean;
                    // NCS drop default statement
                    description
                      "Enable/disable the local device as a route reflector (RR) and a peer or peer group as its client. This configuration is applicable between IBGP peers only. The configurations of RRs and its clients in an address family are valid only in this address family. Therefore, it is recommended to configure RRs and its clients in the specified address family that is required.";
                  }
                  leaf check-tunnel-reachable {
                    type boolean;
                    // NCS drop default statement
                    description
                      "Enable/disable tunnel reachability check.";
                  }
                  uses live_ncs_peer-policy-filter-type;
                  leaf advertise-ext-community {
                    type boolean;
                    // NCS drop default statement
                    description
                      "Enable/disable advertise the extended community attribute to a peer or peer group.";
                  }
                  leaf discard-ext-community {
                    type boolean;
                    // NCS drop default statement
                    description
                      "Enable/disable discard the extended community attribute in the routing information about a specified peer.";
                  }
                  leaf allow-as-loop {
                    type uint32 {
                      range "1..10";
                    }
                    description
                      "Allow repetitive local AS numbers. By default, repetitive local AS numbers are not allowed.";
                  }
                  leaf aigp {
                    // NCS drop when statement
                    type boolean;
                    // NCS drop default statement
                    description
                      "Enable/disable route with AIGP attribute advertisement to or from a peer.";
                  }
                  leaf add-path-mode {
                    // NCS drop when statement
                    type live_ncs_add-path-cap-type;
                    // NCS drop default statement
                    description
                      "Enable Add-Path route advertisement to a peer.";
                  }
                  uses live_ncs_ip-prefix-filter-type;
                  uses live_ncs_as-path-filter-type;
                  uses live_ncs_peer-group-acl-name-or-num-type;
                  uses live_ncs_rt-update-interval-type;
                  leaf nexthop-configure {
                    type live_ncs_nexthop-configuration-type;
                    description
                      "Both the next-hop-local mode and next-hop-invariable mode are available when the peer address family is the VPNv4/VPNV6/L2VPN AD address family. Only the next-hop-local mode is available when the peer address family is not VPNv4/VPNV6/L2VPN AD address family. In next-hop-local mode, you can configure a BGP speaker to set its IP address of as the next hop of the routes to be advertised to IBGP peers or IBGP peer groups. In next-hop-invariable mode, you can configure PEs in different ASs not to change the next hop of routes when the PEs advertise the routes to their EBGP peers and use the next hop addresses of IGP routes to advertise imported IGP routes to IBGP peers. By default, when a BGP speaker advertises routes to EBGP peers and imported IGP routes to IBGP peers, the BGP speaker changes the next hop to its interface address.";
                  }
                  uses live_ncs_preferred-value-type;
                  leaf exp-mode {
                    // NCS drop when statement
                    type live_ncs_exp-mode-type;
                    // NCS drop default statement
                    description
                      "Specify the ASs in which a BGP label can inherit the QoS priority carried in the outer label of public tunnel in the Core AS and the ASs in which the priorities of BGP LSPs must be restored before the LSPs are advertised to a non-core AS.";
                  }
                  leaf add-path-number {
                    // NCS drop when statement
                    type uint8 {
                      range "2..64";
                    }
                    description
                      "Number of Add-Path routes that can be advertised to a peer.";
                  }
                  leaf substitute-as-enable {
                    // NCS drop when statement
                    type boolean;
                    // NCS drop default statement
                    description
                      "Enable/disable replace the AS number of a specified peer in the AS_Path attribute with the local AS number. On a PE where AS number replacement is enabled, if an AS number in the AS_Path attribute of a route is same as that of the CE to which the PE advertises the route, the PE replaces the AS number with its own AS number before advertising the route.";
                  }
                  leaf soo {
                    // NCS drop when statement
                    type string {
                      length "3..21";
                    }
                    description
                      "Configure the Site-of-Origin (SoO) extended community attribute. This attribute can be expressed in the following formats: X.X.X.X:number<0-65535>, number<0-65535>:number<0-4294967295>, or number<0-65535>.number<0-65535>:number<0-65535> or <65536-4294967295>:<0-65535>. 0:0 or 0.0:0 is not supported.
                       Two CEs are in the same site and can advertise routes to each other, and they are connected to a VPN through PEs. If the local routes of a CE are advertised to the other CE over the VPN, a routing loop may occur.
                       The SoO feature can prevent a route advertised by a site from being sent back to the site, preventing routing loops. After SoO is enabled and a PE receives a route from a CE, the specified SoO attribute will be added to the route. Before advertising the route to the other CE, the PE checks the SoO attribute. If the SoO attribute is the same as the locally configured SoO attribute, the PE does not advertise the route, preventing routing loops.";
                  }
                  leaf advertise-best-external {
                    // NCS drop when statement
                    type boolean;
                    // NCS drop must statement
                    // NCS drop must statement
                    // NCS drop must statement
                    // NCS drop default statement
                    description
                      "Enable/disable the device to advertise Best External routes to peers.";
                  }
                  leaf load-balancing-enable {
                    // NCS drop when statement
                    type boolean;
                    // NCS drop default statement
                    description
                      "Enable/disable a neighbour to participate in load balancing.";
                  }
                  choice load-balancing-ignore-as-type {
                    description
                      "Set load balancing as path type.";
                    case as-attribute {
                      description
                        "Ignore the as-path attribute.";
                      leaf load-balancing-as-path-ignore {
                        // NCS drop when statement
                        type empty;
                        description
                          "Configure BGP to ignore the AS_Path attribute when selecting the equal route. After as-path-neglect is selected, BGP does not compare the AS_Path length.";
                      }
                    }
                    case same-length-as-attribute {
                      description
                        "Ignore comparison of as-path attributes with the same length.";
                      leaf load-balancing-as-path-relax {
                        // NCS drop when statement
                        type empty;
                        description
                          "Configure BGP to ignore comparison of AS_Path attributes with the same length when selecting the equal route. After as-path-neglect is selected, BGP does not compare the AS_Path length.";
                      }
                    }
                  }
                  uses live_ncs_advertise-large-community-group-type;
                  uses live_ncs_group-independent-peer-group-type;
                  uses live_ncs_route-limit-accept-type;
                  uses live_ncs_public-as-only-type;
                  uses live_ncs_group-public-as-only-import-type;
                  container entropy-label-parameter {
                    // NCS drop when statement
                    description
                      "Configure information about entropy label parameter in a peer group.";
                    uses live_ncs_group-entropy-label-type;
                  }
                }
                container ipv4-multicast {
                  // NCS drop when statement
                  description
                    "Configure IPv4 multicast options.";
                  uses live_ncs_default-route-advertise-type;
                  uses live_ncs_ip-prefix-filter-type;
                  uses live_ncs_as-path-filter-type;
                  uses live_ncs_peer-group-acl-name-or-num-type;
                  leaf advertise-ext-community {
                    type boolean;
                    // NCS drop default statement
                    description
                      "Enable/disable advertise the extended community attribute to a peer or peer group.";
                  }
                  leaf discard-ext-community {
                    type boolean;
                    // NCS drop default statement
                    description
                      "Enable/disable discard the extended community attribute in the routing information about a specified peer.";
                  }
                  leaf allow-as-loop {
                    type uint32 {
                      range "1..10";
                    }
                    description
                      "Allow repetitive local AS numbers. By default, repetitive local AS numbers are not allowed.";
                  }
                  leaf nexthop-configure {
                    type live_ncs_nexthop-configuration-type;
                    // NCS drop must statement
                    description
                      "Both the next-hop-local mode and next-hop-invariable mode are available when the peer address family is the VPNv4/VPNV6/L2VPN AD address family. Only the next-hop-local mode is available when the peer address family is not VPNv4/VPNV6/L2VPN AD address family. In next-hop-local mode, you can configure a BGP speaker to set its IP address of as the next hop of the routes to be advertised to IBGP peers or IBGP peer groups. In next-hop-invariable mode, you can configure PEs in different ASs not to change the next hop of routes when the PEs advertise the routes to their EBGP peers and use the next hop addresses of IGP routes to advertise imported IGP routes to IBGP peers. By default, when a BGP speaker advertises routes to EBGP peers and imported IGP routes to IBGP peers, the BGP speaker changes the next hop to its interface address.";
                  }
                  leaf advertise-community {
                    type boolean;
                    // NCS drop default statement
                    description
                      "Enable/disable advertise the community attribute to a peer or a peer group.";
                  }
                  leaf keep-all-routes {
                    // NCS drop when statement
                    type boolean;
                    // NCS drop default statement
                    description
                      "Enable/disable saving all the updated information about BGP routes from a specified peer or peer group after a BGP connection is established, even though these BGP routes fail to match the routing policy on the ingress. By default, the updated information about BGP routes from a specified peer is saved only when the routes match the routing policy on the ingress. If a router supports route refreshing, this option is not required.";
                  }
                  uses live_ncs_peer-policy-filter-type;
                  leaf reflect-client {
                    // NCS drop when statement
                    type boolean;
                    // NCS drop default statement
                    description
                      "Enable/disable the local device as a route reflector (RR) and a peer or peer group as its client. This configuration is applicable between IBGP peers only. The configurations of RRs and its clients in an address family are valid only in this address family. Therefore, it is recommended to configure RRs and its clients in the specified address family that is required.";
                  }
                  leaf load-balancing-enable {
                    type boolean;
                    // NCS drop default statement
                    description
                      "Enable/disable a neighbour to participate in load balancing.";
                  }
                  choice load-balancing-ignore-as-type {
                    description
                      "Set load balancing as path type.";
                    case as-attribute {
                      description
                        "Ignore the as-path attribute.";
                      leaf load-balancing-as-path-ignore {
                        // NCS drop when statement
                        type empty;
                        description
                          "Configure BGP to ignore the AS_Path attribute when selecting the equal route. After as-path-neglect is selected, BGP does not compare the AS_Path length.";
                      }
                    }
                    case same-length-as-attribute {
                      description
                        "Ignore comparison of as-path attributes with the same length.";
                      leaf load-balancing-as-path-relax {
                        // NCS drop when statement
                        type empty;
                        description
                          "Configure BGP to ignore comparison of AS_Path attributes with the same length when selecting the equal route. After as-path-neglect is selected, BGP does not compare the AS_Path length.";
                      }
                    }
                  }
                  uses live_ncs_advertise-large-community-group-type;
                  uses live_ncs_rt-update-interval-type;
                  uses bgp:live_ncs_preferred-value-type;
                  uses live_ncs_group-independent-peer-group-type;
                  uses live_ncs_route-limit-type;
                  uses live_ncs_public-as-only-type;
                  uses live_ncs_group-public-as-only-import-type;
                }
              }
            }
          }
        }
        container peers {
          description
            "List of BGP peers.";
          list peer {
            key "address";
            description
              "Configure a single BGP peer.";
            leaf address {
              type inet:ip-address-no-zone;
              description
                "Connection address of a peer, which can be an IPv4 or IPv6 address.";
            }
            leaf remote-as {
              type live_ncs_as-number-validate;
              // NCS drop mandatory statement
              description
                "AS number of a peer, which must be selected or group name when creating, and which can be in either two-byte format or four-byte format:
                 The two-byte format is X. X is an integer ranging from 1 to 65535.
                 The four-byte format is X.Y and X. When the format is X.Y, X and Y are both integers, with the value of X ranging from 1 to 65535, and the value of Y ranging from 0 to 65535; when the format is X, X is an interger, with the value of X ranging from 1 to 4294967295.
                 The object cannot be modified.";
              ext:operation-exclude "update" {
                description
                  "The node cannot be modified, when node is already configured.";
              }
            }
            leaf group-name {
              type leafref {
                path "../../../peer-groups/peer-group/name";
              }
              // NCS drop must statement
              description
                "Specify the name of a peer group that BGP peers need to join. That must be selected group name or AS when creating, and the value is a string, spaces not supported. By default, BGP peers join no peer group. BGP peers distinguish the peer group type when joining a peer group. IBGP peers cannot join an EBGP peer group. BGP peers will be deleted when they leave a peer group. The object cannot be modified.";
              ext:operation-exclude "update" {
                description
                  "The node cannot be modified, when the peer already belongs to a peer-group.";
              }
            }
            uses live_ncs_peer-local-if-type;
            uses live_ncs_authentication-attr-type;
            leaf description {
              type string {
                length "1..255";
                pattern '([^?]*)';
              }
              description
                "Description of a peer, which can be letters or digits. The description is a string, spaces supported. By default, no description is configured for a peer.";
            }
            leaf ebgp-max-hop {
              type uint32 {
                range "1..255";
              }
              // NCS drop must statement
              description
                "Maximum number of hops in an indirect EBGP connection. By default, EBGP connections can be established only between directly connected peers. The function must be configured on both ends. By default, value is determined by the neighbor type, the default value of EBGP is 1 and the default value of IBGP is 0.";
            }
            uses live_ncs_peer-tracking-type;
            leaf conventional {
              type boolean;
              // NCS drop default statement
              description
                "Enable/disable general router functions on peers. In conventional mode, not all the extended router functions, such as, route refreshing, GR, and multi-address family negotiation, are available. Therefore, the router of a new version can be compatible with the routers of earlier versions.";
            }
            leaf route-refresh {
              type boolean;
              // NCS drop default statement
              description
                "Enable/disable BGP to advertise Refresh messages to peers.";
            }
            leaf four-byte-as {
              type boolean;
              // NCS drop default statement
              description
                "Enable/disable BGP to advertise routes carrying 4-byte AS numbers to peers. After the 4-byte AS number function is disabled, Open packets will not carry 4-byte AS number capability flag, and peer ends will not know that local ends have the 4-byte AS number function. The 4-byte AS number function cannot be disabled from peers (peer groups) if a 4-byte AS number, fake AS number, or confederation ID is configured on a router and the AS number of a peer is 4-byte. If the 4-byte AS number function is disabled in such a situation, BGP sessions may fail to be established, and route transmission may be affected.";
            }
            leaf ignore {
              type boolean;
              // NCS drop default statement
              description
                "Enable/disable the function to tear down sessions between peers and clear all related routing information.";
            }
            leaf valid-ttl-hops {
              type uint16 {
                range "1..255";
              }
              // NCS drop must statement
              description
                "Enable GTSM on a peer or peer group. The valid-TTL-Value parameter is used to specify the number of TTL hops to be detected. If the value is configured as hops, the valid TTL range of the detected packet is [255-hops+1, 255].";
            }
            leaf connect-mode {
              type live_ncs_connect-mode;
              // NCS drop default statement
              description
                "The value can be Connect-only, Listen-only, or Both. If the value is Connect-only, the specified peer or peer group only initiatively sends connection requests, instead of listening to connection requests. If the value is Listen-only, the specified peer or peer group only listens to connection requests, instead of initiatively sending connection requests. If the value is Both, the specified peer or peer group not only initiatively sends connection requests, but also listens to connection requests. The default value is Both.";
            }
            leaf log-change {
              type boolean;
              // NCS drop default statement
              description
                "Enable/disable BGP to record the session status and events of the specified peer or peer group.";
            }
            leaf path-mtu-auto-discovery {
              type boolean;
              // NCS drop default statement
              description
                "Enable/disable path mtu auto discovery.";
            }
            leaf local-ifnet-disable {
              type boolean;
              description
                "Enable/disable MPLS local IFNET tunnel creation on a BGP IPv4 peer. By default, MPLS local IFNET tunnels can be created on an EBGP peer,but such tunnels cannot be created on an IBGP peer.";
              ext:dynamic-default;
            }
            leaf check-first-as {
              type live_ncs_peer-cap-config-state;
              // NCS drop default statement
              description
                "Check the first AS in the AS_Path of the update messages from EBGP peers.";
            }
            leaf egress-engineer {
              // NCS drop when statement
              type live_ncs_epe-state;
              // NCS drop default statement
              description
                "BGP Egress Peer Engineering (BGP-EPE) is enable or disable. The default value is default (The function is disable, If the neighbour joins the group, the function is Inheritance group).";
            }
            leaf tcp-mss {
              type uint16 {
                range "176..4096";
              }
              description
                "Maximum TCP MSS value used for TCP connection establishment for a peer.";
            }
            leaf memory-priority {
              type live_ncs_peer-memory-priority;
              // NCS drop default statement
              description
                "Set a priority that determines the disconnection order of a BGP peer relationship if memory overload occurs.";
            }
            leaf memory-priority-capability {
              type live_ncs_memory-priority;
              description
                "Priority that is used to determine the disconnection order of a BGP peer relationship if memory overload occurs.";
            }
            leaf oscillation-dampening {
              type live_ncs_peer-attr-enable-type;
              description
                "Enable/disable BGP to suppress the establishment of a specified peer relationship that flaps continuously. By default, the capability is enabled.";
            }
            container effect-state {
              description
                "Operational state of a BGP peer. It uses the peer-specific configuration or inherits the configuration of its peer group.";
              leaf oscillation-dampening {
                type boolean;
                description
                  "Whether the capability of suppressing the establishment of a specified peer relationship that flaps continuously is enabled on the BGP peer.";
              }
            }
            uses live_ncs_fake-as-type;
            uses live_ncs_peer-timer-para-type;
            uses live_ncs_peer-bfd-parameter-type;
            container bfd-parameter-state {
              description
                "Statistics of BFD Parameter State.";
              leaf valid-ttl-hops {
                type uint8 {
                  range "1..255";
                }
                description
                  "The valid TTL hops value.";
              }
            }
            container egress-engineer-parameter {
              // NCS drop when statement
              description
                "Configure BGP peer egress engineering information.";
              leaf static-label {
                type uint32 {
                  range "16..1048575";
                }
                description
                  "The static label for BGP EPE.";
              }
              leaf label-pop {
                // NCS drop when statement
                type boolean;
                // NCS drop must statement
                // NCS drop default statement
                description
                  "Enable/disable the BGP-EPE label popping function.";
              }
              leaf relate-bfd {
                type boolean;
                // NCS drop must statement
                // NCS drop default statement
                description
                  "Enable/disable association between the BGP-EPE label and BFD status.";
              }
              leaf peer-set-name {
                type leafref {
                  path "../../../../bgp:egress-engineer-peer-sets/bgp:egress-engineer-peer-set/bgp:peer-set-name";
                }
                description
                  "Add peer to peer set.";
              }
            }
            container graceful-restart {
              description
                "Configure graceful restart.";
              uses live_ncs_peer-graceful-restart-type;
              leaf peer-reset {
                type live_ncs_peer-comm-config-type;
                // NCS drop default statement
                description
                  "Enable/disable reseting BGP peer graceful.";
              }
              leaf effect-peer-reset {
                type boolean;
                description
                  "Whether enable/disable reseting BGP peer graceful.";
              }
            }
            container local-graceful-restart {
              description
                "Configure local graceful restart.";
              uses live_ncs_peer-graceful-restart-type;
            }
            container afs {
              description
                "List of peers in a specified address family.";
              list af {
                key "type";
                description
                  "Configure peer in a specified address family.";
                leaf type {
                  type bgp:live_ncs_af-type;
                  // NCS drop must statement
                  description
                    "Specify the address family type to set the peer enable.";
                }
                container ipv4-unicast {
                  // NCS drop when statement
                  description
                    "Configure IPv4 unicast options.";
                  leaf group-name {
                    type leafref {
                      path "../../../../../../peer-groups/peer-group/name";
                    }
                    // NCS drop must statement
                    // NCS drop must statement
                    description
                      "Configure a name for a peer group. After a peer is deleted from the peer group, the peer is disabled from the address family. The object cannot be modified.";
                    ext:operation-exclude "update" {
                      description
                        "The node cannot be modified, when the peer already belongs to a peer-group.";
                    }
                  }
                  leaf advertise-community {
                    type boolean;
                    // NCS drop default statement
                    description
                      "Enable/disable advertise the community attribute to a peer or a peer group.";
                  }
                  leaf reflect-client {
                    type boolean;
                    // NCS drop default statement
                    description
                      "Enable/disable the local device as a route reflector (RR) and a peer or peer group as its client. This configuration is applicable between IBGP peers only. The configurations of RRs and its clients in an address family are valid only in this address family. Therefore, it is recommended to configure RRs and its clients in the specified address family that is required.";
                  }
                  leaf orf-type {
                    // NCS drop when statement
                    type bgp:live_ncs_bgp-orf-type;
                    // NCS drop must statement
                    // NCS drop default statement
                    description
                      "ORF Type.";
                  }
                  leaf orf-mode {
                    // NCS drop when statement
                    type bgp:live_ncs_bgp-orf-mode-type;
                    // NCS drop must statement
                    // NCS drop default statement
                    description
                      "Configure an outbound route filtering (ORF) mode, which can be Receive, Send, or Both, and the default ORF mode is Both.";
                  }
                  leaf label-route-capability {
                    type boolean;
                    // NCS drop default statement
                    description
                      "Enable/disable a device to exchange labeled routes.";
                  }
                  leaf check-tunnel-reachable {
                    // NCS drop when statement
                    type boolean;
                    // NCS drop default statement
                    description
                      "Enable/disable tunnel reachability check.";
                  }
                  leaf check-withdraw-type {
                    // NCS drop when statement
                    type boolean;
                    // NCS drop default statement
                    status obsolete;
                    description
                      "Enable/disable withdraw type check.";
                  }
                  leaf nexthop-configure {
                    type live_ncs_nexthop-configuration-type;
                    description
                      "Both the next-hop-local mode and next-hop-invariable mode are available when the peer address family is the VPNv4/VPNV6/L2VPN AD address family. Only the next-hop-local mode is available when the peer address family is not VPNv4/VPNV6/L2VPN AD address family. In next-hop-local mode, you can configure a BGP speaker to set its IP address of as the next hop of the routes to be advertised to IBGP peers or IBGP peer groups. In next-hop-invariable mode, you can configure PEs in different ASs not to change the next hop of routes when the PEs advertise the routes to their EBGP peers and use the next hop addresses of IGP routes to advertise imported IGP routes to IBGP peers. By default, when a BGP speaker advertises routes to EBGP peers and imported IGP routes to IBGP peers, the BGP speaker changes the next hop to its interface address.";
                  }
                  uses live_ncs_peer-policy-filter-type;
                  leaf advertise-ext-community {
                    type boolean;
                    // NCS drop default statement
                    description
                      "Enable/disable advertise the extended community attribute to a peer or peer group.";
                  }
                  leaf origin-as-validation {
                    // NCS drop when statement
                    type boolean;
                    // NCS drop default statement
                    description
                      "Enable/disable the BGP peer origin validation.";
                  }
                  leaf discard-ext-community {
                    type boolean;
                    // NCS drop default statement
                    description
                      "Enable/disable discard the extended community attribute in the routing information about a specified peer.";
                  }
                  leaf allow-as-loop {
                    type uint32 {
                      range "1..10";
                    }
                    description
                      "Allow repetitive local AS numbers. By default, repetitive local AS numbers are not allowed.";
                  }
                  leaf aigp {
                    // NCS drop when statement
                    type boolean;
                    // NCS drop default statement
                    description
                      "Enable/disable route with AIGP attribute advertisement to or from a peer.";
                  }
                  uses live_ncs_default-route-advertise-type;
                  leaf default-route-match-mode {
                    // NCS drop when statement
                    type live_ncs_cra-match-mode;
                    // NCS drop default statement
                    description
                      "Configure the matching mode of default route advertisement, which can be disabling of route advertisement conditions, enabling of all route advertisement conditions, and enabling of part route advertisement conditions. Enabling of all route advertisement conditions indicates that a default route can be advertised only when it matches all the conditions. Enabling of part route advertisement conditions indicates that a default route can be advertised only when it matches one condition.";
                  }
                  leaf add-path-mode {
                    // NCS drop when statement
                    type live_ncs_add-path-cap-type;
                    // NCS drop default statement
                    description
                      "Enable add-path route advertisement to a peer.";
                  }
                  uses live_ncs_ip-prefix-filter-type;
                  uses live_ncs_as-path-filter-type;
                  uses live_ncs_peer-group-acl-name-or-num-type;
                  uses live_ncs_rt-update-interval-type;
                  uses live_ncs_preferred-value-type;
                  leaf add-path-number {
                    // NCS drop when statement
                    type uint8 {
                      range "2..64";
                    }
                    description
                      "Number of add-path routes that can be advertised to a peer.";
                  }
                  leaf substitute-as-enable {
                    type boolean;
                    // NCS drop default statement
                    description
                      "Enable/disable replace the AS number of a specified peer in the AS_Path attribute with the local AS number. On a PE where AS number replacement is enabled, if an AS number in the AS_Path attribute of a route is same as that of the CE to which the PE advertises the route, the PE replaces the AS number with its own AS number before advertising the route.";
                  }
                  leaf soo {
                    // NCS drop when statement
                    type string {
                      length "3..21";
                    }
                    description
                      "Configure the Site-of-Origin (SoO) extended community attribute. This attribute can be expressed in the following formats: X.X.X.X:number<0-65535>, number<0-65535>:number<0-4294967295>, or number<0-65535>.number<0-65535>:number<0-65535> or <65536-4294967295>:<0-65535>. 0:0 or 0.0:0 is not supported.
                       Two CEs are in the same site and can advertise routes to each other, and they are connected to a VPN through PEs. If the local routes of a CE are advertised to the other CE over the VPN, a routing loop may occur.
                       The SoO feature can prevent a route advertised by a site from being sent back to the site, preventing routing loops. After SoO is enabled and a PE receives a route from a CE, the specified SoO attribute will be added to the route. Before advertising the route to the other CE, the PE checks the SoO attribute. If the SoO attribute is the same as the locally configured SoO attribute, the PE does not advertise the route, preventing routing loops.";
                  }
                  leaf keep-all-routes {
                    // NCS drop when statement
                    type boolean;
                    // NCS drop default statement
                    description
                      "Enable/disable saving all the updated information about BGP routes from a specified peer or peer group after a BGP connection is established, even though these BGP routes fail to match the routing policy on the ingress. By default, the updated information about BGP routes from a specified peer is saved only when the routes match the routing policy on the ingress. If a router supports route refreshing, this option is not required.";
                  }
                  leaf exp-mode {
                    type live_ncs_exp-mode-type;
                    // NCS drop default statement
                    description
                      "Specify the ASs in which a BGP label can inherit the QoS priority carried in the outer label of public tunnel in the Core AS and the ASs in which the priorities of BGP LSPs must be restored before the LSPs are advertised to a non-core AS.";
                  }
                  leaf advertise-best-external {
                    // NCS drop when statement
                    type boolean;
                    // NCS drop must statement
                    // NCS drop must statement
                    // NCS drop must statement
                    // NCS drop default statement
                    description
                      "Enable/disable the device to advertise Best External routes to peers.";
                  }
                  leaf load-balancing-enable {
                    type boolean;
                    // NCS drop default statement
                    description
                      "Enable/disable a neighbour to participate in load balancing.";
                  }
                  choice load-balancing-ignore-as-type {
                    description
                      "Set load balancing as path type.";
                    case as-attribute {
                      description
                        "Ignore the as-path attribute.";
                      leaf load-balancing-as-path-ignore {
                        // NCS drop when statement
                        type empty;
                        description
                          "Configure BGP to ignore the AS_Path attribute when selecting the equal route. After as-path-neglect is selected, BGP does not compare the AS_Path length.";
                      }
                    }
                    case same-length-as-attribute {
                      description
                        "Ignore comparison of as-path attributes with the same length.";
                      leaf load-balancing-as-path-relax {
                        // NCS drop when statement
                        type empty;
                        description
                          "Configure BGP to ignore comparison of AS_Path attributes with the same length when selecting the equal route. After as-path-neglect is selected, BGP does not compare the AS_Path length.";
                      }
                    }
                  }
                  leaf prefix-sid {
                    // NCS drop when statement
                    type bgp:live_ncs_peer-comm-config-type;
                    // NCS drop default statement
                    description
                      "Enable/disable a device to exchange IPv4 prefix SIDs with a specified IPv6 peer.";
                  }
                  leaf prefix-sid-state {
                    // NCS drop when statement
                    type boolean;
                    // NCS drop default statement
                    description
                      "Whether the prefix-sid to a peer is enabled.";
                  }
                  choice prefix-sid-packet {
                    description
                      "Prefix-sid packet method.";
                    case sid-type5 {
                      description
                        "Packet by type5.";
                      leaf advertise-srv6-locator {
                        // NCS drop when statement
                        type empty;
                        description
                          "Advertise SRv6 locators.";
                      }
                    }
                  }
                  container effect-state {
                    description
                      "Operational state of peer.";
                    leaf advertise-srv6-locator {
                      type boolean;
                      description
                        "Whether to advertise SRv6 locators on the BGP peer.";
                    }
                  }
                  uses live_ncs_advertise-large-community-type;
                  uses live_ncs_peer-independent-peer-group-type;
                  leaf rpd-policy-export {
                    // NCS drop when statement
                    type bgp:live_ncs_peer-enable-config-type;
                    // NCS drop default statement
                    description
                      "Enable/disable RPD export policy.";
                  }
                  uses live_ncs_ipv4-default-route-match-conditions-type;
                  uses live_ncs_route-limit-accept-type;
                  uses live_ncs_public-as-only-type;
                  uses live_ncs_peer-public-as-only-import-type;
                  container entropy-label-parameter {
                    // NCS drop when statement
                    description
                      "Configure information about entropy label parameter configuration in a peer.";
                    uses live_ncs_peer-entropy-label-type;
                  }
                  uses live_ncs_path-attr-map-type;
                  uses live_ncs_advertise-dependent-filter-type;
                }
                container ipv6-unicast {
                  // NCS drop when statement
                  description
                    "Configure IPv6 unicast options.";
                  leaf group-name {
                    type leafref {
                      path "../../../../../../peer-groups/peer-group/name";
                    }
                    // NCS drop must statement
                    // NCS drop must statement
                    description
                      "Configure a name for a peer group. After a peer is deleted from the peer group, the peer is disabled from the address family. The object cannot be modified.";
                    ext:operation-exclude "update" {
                      description
                        "The node cannot be modified, when the peer already belongs to a peer-group.";
                    }
                  }
                  leaf advertise-community {
                    type boolean;
                    // NCS drop default statement
                    description
                      "Enable/disable advertise the community attribute to a peer or a peer group.";
                  }
                  leaf reflect-client {
                    type boolean;
                    // NCS drop default statement
                    description
                      "Enable/disable the local device as a route reflector (RR) and a peer or peer group as its client. This configuration is applicable between IBGP peers only. The configurations of RRs and its clients in an address family are valid only in this address family. Therefore, it is recommended to configure RRs and its clients in the specified address family that is required.";
                  }
                  leaf label-route-capability {
                    type boolean;
                    // NCS drop default statement
                    description
                      "Enable/disable a device to exchange labeled routes.";
                  }
                  leaf nexthop-configure {
                    type live_ncs_nexthop-configuration-type;
                    // NCS drop must statement
                    description
                      "Both the next-hop-local mode and next-hop-invariable mode are available when the peer address family is the VPNv4/VPNV6/L2VPN AD address family. Only the next-hop-local mode is available when the peer address family is not VPNv4/VPNV6/L2VPN AD address family. In next-hop-local mode, you can configure a BGP speaker to set its IP address of as the next hop of the routes to be advertised to IBGP peers or IBGP peer groups. In next-hop-invariable mode, you can configure PEs in different ASs not to change the next hop of routes when the PEs advertise the routes to their EBGP peers and use the next hop addresses of IGP routes to advertise imported IGP routes to IBGP peers. By default, when a BGP speaker advertises routes to EBGP peers and imported IGP routes to IBGP peers, the BGP speaker changes the next hop to its interface address.";
                  }
                  uses live_ncs_peer-policy-filter-type;
                  leaf advertise-ext-community {
                    type boolean;
                    // NCS drop default statement
                    description
                      "Enable/disable advertise the extended community attribute to a peer or peer group.";
                  }
                  leaf origin-as-validation {
                    // NCS drop when statement
                    type boolean;
                    // NCS drop default statement
                    description
                      "Enable/disable the BGP peer origin validation.";
                  }
                  leaf discard-ext-community {
                    type boolean;
                    // NCS drop default statement
                    description
                      "Enable/disable discard the extended community attribute in the routing information about a specified peer.";
                  }
                  leaf allow-as-loop {
                    type uint32 {
                      range "1..10";
                    }
                    description
                      "Allow repetitive local AS numbers. By default, repetitive local AS numbers are not allowed.";
                  }
                  leaf aigp {
                    // NCS drop when statement
                    type boolean;
                    // NCS drop default statement
                    description
                      "Enable/disable route with AIGP attribute advertisement to or from a peer.";
                  }
                  uses live_ncs_default-route-advertise-type;
                  leaf default-route-match-mode {
                    // NCS drop when statement
                    type live_ncs_cra-match-mode;
                    // NCS drop default statement
                    description
                      "Configure the matching mode of default route advertisement, which can be disabling of route advertisement conditions, enabling of all route advertisement conditions, and enabling of part route advertisement conditions. Enabling of all route advertisement conditions indicates that a default route can be advertised only when it matches all the conditions. Enabling of part route advertisement conditions indicates that a default route can be advertised only when it matches one condition.";
                  }
                  leaf add-path-mode {
                    // NCS drop when statement
                    type live_ncs_add-path-cap-type;
                    // NCS drop default statement
                    description
                      "Enable Add-Path route advertisement to a peer.";
                  }
                  uses live_ncs_ipv6-prefix-filter-type;
                  uses live_ncs_as-path-filter-type;
                  uses live_ncs_peer-group-acl6-name-or-num-type;
                  uses live_ncs_rt-update-interval-type;
                  uses live_ncs_preferred-value-type;
                  leaf add-path-number {
                    // NCS drop when statement
                    type uint8 {
                      range "2..64";
                    }
                    description
                      "Number of Add-Path routes that can be advertised to a peer.";
                  }
                  leaf substitute-as-enable {
                    type boolean;
                    // NCS drop default statement
                    description
                      "Enable/disable replace the AS number of a specified peer in the AS_Path attribute with the local AS number. On a PE where AS number replacement is enabled, if an AS number in the AS_Path attribute of a route is same as that of the CE to which the PE advertises the route, the PE replaces the AS number with its own AS number before advertising the route.";
                  }
                  leaf soo {
                    // NCS drop when statement
                    type string {
                      length "3..21";
                    }
                    description
                      "Configure the Site-of-Origin (SoO) extended community attribute. This attribute can be expressed in the following formats: X.X.X.X:number<0-65535>, number<0-65535>:number<0-4294967295>, or number<0-65535>.number<0-65535>:number<0-65535> or <65536-4294967295>:<0-65535>. 0:0 or 0.0:0 is not supported.
                       Two CEs are in the same site and can advertise routes to each other, and they are connected to a VPN through PEs. If the local routes of a CE are advertised to the other CE over the VPN, a routing loop may occur.
                       The SoO feature can prevent a route advertised by a site from being sent back to the site, preventing routing loops. After SoO is enabled and a PE receives a route from a CE, the specified SoO attribute will be added to the route. Before advertising the route to the other CE, the PE checks the SoO attribute. If the SoO attribute is the same as the locally configured SoO attribute, the PE does not advertise the route, preventing routing loops.";
                  }
                  leaf keep-all-routes {
                    // NCS drop when statement
                    type boolean;
                    // NCS drop default statement
                    description
                      "Enable/disable saving all the updated information about BGP routes from a specified peer or peer group after a BGP connection is established, even though these BGP routes fail to match the routing policy on the ingress. By default, the updated information about BGP routes from a specified peer is saved only when the routes match the routing policy on the ingress. If a router supports route refreshing, this option is not required.";
                  }
                  leaf advertise-best-external {
                    // NCS drop when statement
                    type boolean;
                    // NCS drop must statement
                    // NCS drop must statement
                    // NCS drop must statement
                    // NCS drop default statement
                    description
                      "Enable/disable the device to advertise Best External routes to peers.";
                  }
                  leaf load-balancing-enable {
                    type boolean;
                    // NCS drop default statement
                    description
                      "Enable/disable a neighbour to participate in load balancing.";
                  }
                  choice load-balancing-ignore-as-type {
                    description
                      "Set load balancing as path type.";
                    case as-attribute {
                      description
                        "Ignore the as-path attribute.";
                      leaf load-balancing-as-path-ignore {
                        // NCS drop when statement
                        type empty;
                        description
                          "Configure BGP to ignore the AS_Path attribute when selecting the equal route. After as-path-neglect is selected, BGP does not compare the AS_Path length.";
                      }
                    }
                    case same-length-as-attribute {
                      description
                        "Ignore comparison of as-path attributes with the same length.";
                      leaf load-balancing-as-path-relax {
                        // NCS drop when statement
                        type empty;
                        description
                          "Configure BGP to ignore comparison of AS_Path attributes with the same length when selecting the equal route. After as-path-neglect is selected, BGP does not compare the AS_Path length.";
                      }
                    }
                  }
                  leaf tunnel-policy {
                    // NCS drop when statement
                    type leafref {
                      path "/ncs:devices/ncs:device/ncs:live-status/tnlm:tunnel-management/tnlm:tunnel-policys/tnlm:tunnel-policy/tnlm:name" {
                        tailf:xpath-root 3;
                      }
                    }
                    description
                      "Apply a tunnel policy for a 6PE peer. By default, no tunnel policy is configured.";
                  }
                  leaf prefix-sid {
                    // NCS drop when statement
                    type bgp:live_ncs_peer-comm-config-type;
                    // NCS drop default statement
                    description
                      "Enable/disable a device to exchange prefix SIDs with a specified IPv6 peer.";
                  }
                  leaf prefix-sid-state {
                    // NCS drop when statement
                    type boolean;
                    // NCS drop default statement
                    description
                      "Whether the prefix-sid to a peer is enabled.";
                  }
                  choice prefix-sid-packet {
                    description
                      "Prefix-sid packet method.";
                    case sid-type5 {
                      description
                        "Packet by type5.";
                      leaf advertise-srv6-locator {
                        // NCS drop when statement
                        type empty;
                        description
                          "Advertise SRv6 locators.";
                      }
                    }
                  }
                  container effect-state {
                    description
                      "Operational state of peer.";
                    leaf advertise-srv6-locator {
                      type boolean;
                      description
                        "Whether to advertise SRv6 locators on the BGP peer.";
                    }
                  }
                  uses live_ncs_advertise-large-community-type;
                  uses live_ncs_peer-independent-peer-group-type;
                  uses live_ncs_ipv6-default-route-match-conditions-type;
                  uses live_ncs_route-limit-accept-type;
                  uses live_ncs_public-as-only-type;
                  uses live_ncs_peer-public-as-only-import-type;
                  uses live_ncs_path-attr-map-type;
                  uses live_ncs_advertise-dependent-filter6-type;
                }
                container ipv4-vpn {
                  // NCS drop when statement
                  description
                    "Configure IPv4 VPNv4 options.";
                  leaf group-name {
                    type leafref {
                      path "../../../../../../peer-groups/peer-group/name";
                    }
                    // NCS drop must statement
                    // NCS drop must statement
                    description
                      "Configure a name for a peer group. After a peer is deleted from the peer group, the peer is disabled from the address family. The object cannot be modified.";
                    ext:operation-exclude "update" {
                      description
                        "The node cannot be modified, when the peer already belongs to a peer-group.";
                    }
                  }
                  leaf advertise-community {
                    type boolean;
                    // NCS drop default statement
                    description
                      "Enable/disable advertise the community attribute to a peer or a peer group.";
                  }
                  leaf reflect-client {
                    type boolean;
                    // NCS drop default statement
                    description
                      "Enable/disable the local device as a route reflector (RR) and a peer or peer group as its client. This configuration is applicable between IBGP peers only. The configurations of RRs and its clients in an address family are valid only in this address family. Therefore, it is recommended to configure RRs and its clients in the specified address family that is required.";
                  }
                  leaf nexthop-configure {
                    type live_ncs_nexthop-configuration-type;
                    description
                      "Both the next-hop-local mode and next-hop-invariable mode are available when the peer address family is the VPNv4/VPNV6/L2VPN AD address family. Only the next-hop-local mode is available when the peer address family is not VPNv4/VPNV6/L2VPN AD address family. In next-hop-local mode, you can configure a BGP speaker to set its IP address of as the next hop of the routes to be advertised to IBGP peers or IBGP peer groups. In next-hop-invariable mode, you can configure PEs in different ASs not to change the next hop of routes when the PEs advertise the routes to their EBGP peers and use the next hop addresses of IGP routes to advertise imported IGP routes to IBGP peers. By default, when a BGP speaker advertises routes to EBGP peers and imported IGP routes to IBGP peers, the BGP speaker changes the next hop to its interface address.";
                  }
                  uses live_ncs_peer-policy-filter-type;
                  leaf ignore-bit-error {
                    // NCS drop when statement
                    type boolean;
                    // NCS drop default statement
                    description
                      "Enable/disable the peer to ignore bit error detection results.";
                  }
                  leaf allow-as-loop {
                    type uint32 {
                      range "1..10";
                    }
                    description
                      "Allow repetitive local AS numbers. By default, repetitive local AS numbers are not allowed.";
                  }
                  leaf aigp {
                    type boolean;
                    // NCS drop default statement
                    description
                      "Enable/disable route with AIGP attribute advertisement to or from a peer.";
                  }
                  uses live_ncs_peer-add-path-type;
                  uses live_ncs_ip-prefix-filter-type;
                  uses live_ncs_peer-ipv4-reoriginate-type;
                  uses live_ncs_as-path-filter-type;
                  uses live_ncs_peer-group-acl-name-or-num-type;
                  uses live_ncs_rt-update-interval-type;
                  uses live_ncs_preferred-value-type;
                  leaf upe {
                    type boolean;
                    // NCS drop default statement
                    description
                      "Enable/disable the peer as an underlayer PE (UPE).";
                  }
                  leaf high-priority {
                    type live_ncs_peer-enable-config-type;
                    // NCS drop default statement
                    description
                      "Enable vpn-router high priority.";
                  }
                  leaf prefix-sid {
                    type bgp:live_ncs_peer-enable-config-type;
                    // NCS drop default statement
                    description
                      "Specify a SID mode relay for peer.";
                  }
                  choice prefix-sid-packet {
                    description
                      "Prefix-sid packet method.";
                    case sid-type5 {
                      description
                        "Packet by type5.";
                      leaf sid-type5 {
                        // NCS drop when statement
                        type empty;
                        description
                          "Packet by type5.";
                      }
                      leaf advertise-srv6-locator {
                        // NCS drop when statement
                        type empty;
                        description
                          "Advertise SRv6 locators.";
                      }
                    }
                  }
                  leaf advertise-best-external {
                    type boolean;
                    // NCS drop must statement
                    // NCS drop must statement
                    // NCS drop must statement
                    // NCS drop default statement
                    description
                      "Enable/disable the device to advertise Best External routes to peers.";
                  }
                  uses live_ncs_advertise-large-community-type;
                  leaf keep-all-routes {
                    // NCS drop when statement
                    type boolean;
                    // NCS drop default statement
                    description
                      "Enable/disable saving all the updated information about BGP routes from a specified peer or peer group after a BGP connection is established, even though these BGP routes fail to match the routing policy on the ingress. By default, the updated information about BGP routes from a specified peer is saved only when the routes match the routing policy on the ingress. If a router supports route refreshing, this option is not required.";
                  }
                  uses live_ncs_peer-independent-peer-group-type;
                  uses live_ncs_peer-origin-as-validation-type;
                  container default-route-originates {
                    description
                      "Configure advertised default VPNv4 routes.";
                    uses live_ncs_default-route-originate-type;
                  }
                  uses live_ncs_route-limit-type;
                  uses live_ncs_public-as-only-type;
                  uses live_ncs_peer-public-as-only-import-type;
                  uses live_ncs_path-attr-map-type;
                }
                container ipv6-vpn {
                  // NCS drop when statement
                  description
                    "Configure IPv6 vpn options.";
                  leaf group-name {
                    type leafref {
                      path "../../../../../../peer-groups/peer-group/name";
                    }
                    // NCS drop must statement
                    // NCS drop must statement
                    description
                      "Configure a name for a peer group. After a peer is deleted from the peer group, the peer is disabled from the address family. The object cannot be modified.";
                    ext:operation-exclude "update" {
                      description
                        "The node cannot be modified, when the peer already belongs to a peer-group.";
                    }
                  }
                  leaf advertise-community {
                    type boolean;
                    // NCS drop default statement
                    description
                      "Enable/disable advertise the community attribute to a peer or a peer group.";
                  }
                  leaf reflect-client {
                    type boolean;
                    // NCS drop default statement
                    description
                      "Enable/disable the local device as a route reflector (RR) and a peer or peer group as its client. This configuration is applicable between IBGP peers only. The configurations of RRs and its clients in an address family are valid only in this address family. Therefore, it is recommended to configure RRs and its clients in the specified address family that is required.";
                  }
                  leaf nexthop-configure {
                    type live_ncs_nexthop-configuration-type;
                    description
                      "Both the next-hop-local mode and next-hop-invariable mode are available when the peer address family is the VPNv4/VPNV6/L2VPN AD address family. Only the next-hop-local mode is available when the peer address family is not VPNv4/VPNV6/L2VPN AD address family. In next-hop-local mode, you can configure a BGP speaker to set its IP address of as the next hop of the routes to be advertised to IBGP peers or IBGP peer groups. In next-hop-invariable mode, you can configure PEs in different ASs not to change the next hop of routes when the PEs advertise the routes to their EBGP peers and use the next hop addresses of IGP routes to advertise imported IGP routes to IBGP peers. By default, when a BGP speaker advertises routes to EBGP peers and imported IGP routes to IBGP peers, the BGP speaker changes the next hop to its interface address.";
                  }
                  uses live_ncs_peer-policy-filter-type;
                  leaf ignore-bit-error {
                    // NCS drop when statement
                    type boolean;
                    // NCS drop default statement
                    description
                      "Enable/disable the peer to ignore bit error detection results.";
                  }
                  leaf allow-as-loop {
                    type uint32 {
                      range "1..10";
                    }
                    description
                      "Allow repetitive local AS numbers. By default, repetitive local AS numbers are not allowed.";
                  }
                  leaf aigp {
                    type boolean;
                    // NCS drop default statement
                    description
                      "Enable/disable route with AIGP attribute advertisement to or from a peer.";
                  }
                  uses live_ncs_peer-add-path-type;
                  uses live_ncs_ipv6-prefix-filter-type;
                  leaf reoriginate-route-enable {
                    type boolean;
                    // NCS drop default statement
                    description
                      "Enable/disable route regeneration.";
                  }
                  leaf reoriginate-ipv6-enable {
                    type boolean;
                    // NCS drop default statement
                    description
                      "Enable/disable IP route regeneration and advertisement.";
                  }
                  leaf reoriginate-mac-ipv6-enable {
                    type boolean;
                    // NCS drop default statement
                    description
                      "Enable/disable MAC-IP route regeneration and advertisement.";
                  }
                  uses live_ncs_as-path-filter-type;
                  uses live_ncs_peer-group-acl6-name-or-num-type;
                  uses live_ncs_rt-update-interval-type;
                  uses live_ncs_preferred-value-type;
                  leaf advertise-best-external {
                    type boolean;
                    // NCS drop must statement
                    // NCS drop must statement
                    // NCS drop must statement
                    // NCS drop default statement
                    description
                      "Enable/disable the device to advertise Best External routes to peers.";
                  }
                  uses live_ncs_advertise-large-community-type;
                  leaf keep-all-routes {
                    // NCS drop when statement
                    type boolean;
                    // NCS drop default statement
                    description
                      "Enable/disable saving all the updated information about BGP routes from a specified peer or peer group after a BGP connection is established, even though these BGP routes fail to match the routing policy on the ingress. By default, the updated information about BGP routes from a specified peer is saved only when the routes match the routing policy on the ingress. If a router supports route refreshing, this option is not required.";
                  }
                  uses live_ncs_peer-independent-peer-group-type;
                  uses live_ncs_peer-origin-as-validation-type;
                  uses live_ncs_route-limit-type;
                  uses live_ncs_public-as-only-type;
                  uses live_ncs_peer-public-as-only-import-type;
                  uses live_ncs_path-attr-map-type;
                }
                container ipv4-labeluni {
                  // NCS drop when statement
                  description
                    "Configure IPv4 label unicast options.";
                  leaf group-name {
                    type leafref {
                      path "../../../../../../peer-groups/peer-group/name";
                    }
                    // NCS drop must statement
                    // NCS drop must statement
                    description
                      "Configure a name for a peer group. After a peer is deleted from the peer group, the peer is disabled from the address family. The object cannot be modified.";
                    ext:operation-exclude "update" {
                      description
                        "The node cannot be modified, when the peer already belongs to a peer-group.";
                    }
                  }
                  leaf advertise-community {
                    type boolean;
                    // NCS drop default statement
                    description
                      "Enable/disable advertise the community attribute to a peer or a peer group.";
                  }
                  leaf reflect-client {
                    type boolean;
                    // NCS drop default statement
                    description
                      "Enable/disable the local device as a route reflector (RR) and a peer or peer group as its client. This configuration is applicable between IBGP peers only. The configurations of RRs and its clients in an address family are valid only in this address family. Therefore, it is recommended to configure RRs and its clients in the specified address family that is required.";
                  }
                  leaf check-tunnel-reachable {
                    type boolean;
                    // NCS drop default statement
                    description
                      "Enable/disable tunnel reachability check.";
                  }
                  uses live_ncs_peer-policy-filter-type;
                  leaf advertise-ext-community {
                    type boolean;
                    // NCS drop default statement
                    description
                      "Enable/disable advertise the extended community attribute to a peer or peer group.";
                  }
                  leaf discard-ext-community {
                    type boolean;
                    // NCS drop default statement
                    description
                      "Enable/disable discard the extended community attribute in the routing information about a specified peer.";
                  }
                  leaf allow-as-loop {
                    type uint32 {
                      range "1..10";
                    }
                    description
                      "Allow repetitive local AS numbers. By default, repetitive local AS numbers are not allowed.";
                  }
                  leaf aigp {
                    // NCS drop when statement
                    type boolean;
                    // NCS drop default statement
                    description
                      "Enable/disable route with AIGP attribute advertisement to or from a peer.";
                  }
                  leaf add-path-mode {
                    // NCS drop when statement
                    type live_ncs_add-path-cap-type;
                    // NCS drop default statement
                    description
                      "Enable add-path route advertisement to a peer.";
                  }
                  uses live_ncs_ip-prefix-filter-type;
                  uses live_ncs_as-path-filter-type;
                  uses live_ncs_peer-group-acl-name-or-num-type;
                  uses live_ncs_rt-update-interval-type;
                  leaf nexthop-configure {
                    type live_ncs_nexthop-configuration-type;
                    description
                      "Both the next-hop-local mode and next-hop-invariable mode are available when the peer address family is the VPNv4/VPNV6/L2VPN AD address family. Only the next-hop-local mode is available when the peer address family is not VPNv4/VPNV6/L2VPN AD address family. In next-hop-local mode, you can configure a BGP speaker to set its IP address of as the next hop of the routes to be advertised to IBGP peers or IBGP peer groups. In next-hop-invariable mode, you can configure PEs in different ASs not to change the next hop of routes when the PEs advertise the routes to their EBGP peers and use the next hop addresses of IGP routes to advertise imported IGP routes to IBGP peers. By default, when a BGP speaker advertises routes to EBGP peers and imported IGP routes to IBGP peers, the BGP speaker changes the next hop to its interface address.";
                  }
                  uses live_ncs_preferred-value-type;
                  leaf exp-mode {
                    // NCS drop when statement
                    type live_ncs_exp-mode-type;
                    // NCS drop default statement
                    description
                      "Specify the ASs in which a BGP label can inherit the QoS priority carried in the outer label of public tunnel in the Core AS and the ASs in which the priorities of BGP LSPs must be restored before the LSPs are advertised to a non-core AS.";
                  }
                  leaf add-path-number {
                    // NCS drop when statement
                    type uint8 {
                      range "2..64";
                    }
                    description
                      "Number of Add-Path routes that can be advertised to a peer.";
                  }
                  leaf substitute-as-enable {
                    type boolean;
                    // NCS drop default statement
                    description
                      "Enable/disable replace the AS number of a specified peer in the AS_Path attribute with the local AS number. On a PE where AS number replacement is enabled, if an AS number in the AS_Path attribute of a route is same as that of the CE to which the PE advertises the route, the PE replaces the AS number with its own AS number before advertising the route.";
                  }
                  leaf soo {
                    // NCS drop when statement
                    type string {
                      length "3..21";
                    }
                    description
                      "Configure the Site-of-Origin (SoO) extended community attribute. This attribute can be expressed in the following formats: X.X.X.X:number<0-65535>, number<0-65535>:number<0-4294967295>, or number<0-65535>.number<0-65535>:number<0-65535> or <65536-4294967295>:<0-65535>. 0:0 or 0.0:0 is not supported.
                       Two CEs are in the same site and can advertise routes to each other, and they are connected to a VPN through PEs. If the local routes of a CE are advertised to the other CE over the VPN, a routing loop may occur.
                       The SoO feature can prevent a route advertised by a site from being sent back to the site, preventing routing loops. After SoO is enabled and a PE receives a route from a CE, the specified SoO attribute will be added to the route. Before advertising the route to the other CE, the PE checks the SoO attribute. If the SoO attribute is the same as the locally configured SoO attribute, the PE does not advertise the route, preventing routing loops.";
                  }
                  leaf advertise-best-external {
                    // NCS drop when statement
                    type boolean;
                    // NCS drop must statement
                    // NCS drop must statement
                    // NCS drop must statement
                    // NCS drop default statement
                    description
                      "Enable/disable the device to advertise Best External routes to peers.";
                  }
                  leaf load-balancing-enable {
                    // NCS drop when statement
                    type boolean;
                    // NCS drop default statement
                    description
                      "Enable/disable a neighbour to participate in load balancing.";
                  }
                  choice load-balancing-ignore-as-type {
                    description
                      "Set load balancing as path type.";
                    case as-attribute {
                      description
                        "Ignore the as-path attribute.";
                      leaf load-balancing-as-path-ignore {
                        // NCS drop when statement
                        type empty;
                        description
                          "Configure BGP to ignore the AS_Path attribute when selecting the equal route. After as-path-neglect is selected, BGP does not compare the AS_Path length.";
                      }
                    }
                    case same-length-as-attribute {
                      description
                        "Ignore comparison of as-path attributes with the same length.";
                      leaf load-balancing-as-path-relax {
                        // NCS drop when statement
                        type empty;
                        description
                          "Configure BGP to ignore comparison of AS_Path attributes with the same length when selecting the equal route. After as-path-neglect is selected, BGP does not compare the AS_Path length.";
                      }
                    }
                  }
                  uses live_ncs_advertise-large-community-type;
                  uses live_ncs_peer-independent-peer-group-type;
                  uses live_ncs_route-limit-accept-type;
                  uses live_ncs_public-as-only-type;
                  uses live_ncs_peer-public-as-only-import-type;
                  container entropy-label-parameter {
                    // NCS drop when statement
                    description
                      "Configure information about entropy label parameter configuration in a peer.";
                    uses live_ncs_peer-entropy-label-type;
                  }
                  uses live_ncs_path-attr-map-type;
                }
                container ipv4-multicast {
                  // NCS drop when statement
                  description
                    "Configure IPv4 multicast options.";
                  leaf group-name {
                    type leafref {
                      path "../../../../../../peer-groups/peer-group/name";
                    }
                    // NCS drop must statement
                    // NCS drop must statement
                    description
                      "Configure a name for a peer group. After a peer is deleted from the peer group, the peer is disabled from the address family. The object cannot be modified.";
                    ext:operation-exclude "update" {
                      description
                        "The node cannot be modified, when the peer already belongs to a peer-group.";
                    }
                  }
                  uses live_ncs_default-route-advertise-type;
                  uses live_ncs_ip-prefix-filter-type;
                  uses live_ncs_as-path-filter-type;
                  uses live_ncs_peer-group-acl-name-or-num-type;
                  leaf advertise-ext-community {
                    type boolean;
                    // NCS drop default statement
                    description
                      "Enable/disable advertise the extended community attribute to a peer or peer group.";
                  }
                  leaf discard-ext-community {
                    type boolean;
                    // NCS drop default statement
                    description
                      "Enable/disable discard the extended community attribute in the routing information about a specified peer.";
                  }
                  leaf allow-as-loop {
                    type uint32 {
                      range "1..10";
                    }
                    description
                      "Allow repetitive local AS numbers. By default, repetitive local AS numbers are not allowed.";
                  }
                  leaf nexthop-configure {
                    type live_ncs_nexthop-configuration-type;
                    // NCS drop must statement
                    description
                      "Both the next-hop-local mode and next-hop-invariable mode are available when the peer address family is the VPNv4/VPNV6/L2VPN AD address family. Only the next-hop-local mode is available when the peer address family is not VPNv4/VPNV6/L2VPN AD address family. In next-hop-local mode, you can configure a BGP speaker to set its IP address of as the next hop of the routes to be advertised to IBGP peers or IBGP peer groups. In next-hop-invariable mode, you can configure PEs in different ASs not to change the next hop of routes when the PEs advertise the routes to their EBGP peers and use the next hop addresses of IGP routes to advertise imported IGP routes to IBGP peers. By default, when a BGP speaker advertises routes to EBGP peers and imported IGP routes to IBGP peers, the BGP speaker changes the next hop to its interface address.";
                  }
                  leaf advertise-community {
                    type boolean;
                    // NCS drop default statement
                    description
                      "Enable/disable advertise the community attribute to a peer or a peer group.";
                  }
                  leaf keep-all-routes {
                    // NCS drop when statement
                    type boolean;
                    // NCS drop default statement
                    description
                      "Enable/disable saving all the updated information about BGP routes from a specified peer or peer group after a BGP connection is established, even though these BGP routes fail to match the routing policy on the ingress. By default, the updated information about BGP routes from a specified peer is saved only when the routes match the routing policy on the ingress. If a router supports route refreshing, this option is not required.";
                  }
                  uses live_ncs_peer-policy-filter-type;
                  leaf reflect-client {
                    type boolean;
                    // NCS drop default statement
                    description
                      "Enable/disable the local device as a route reflector (RR) and a peer or peer group as its client. This configuration is applicable between IBGP peers only. The configurations of RRs and its clients in an address family are valid only in this address family. Therefore, it is recommended to configure RRs and its clients in the specified address family that is required.";
                  }
                  leaf load-balancing-enable {
                    type boolean;
                    // NCS drop default statement
                    description
                      "Enable/disable a neighbour to participate in load balancing.";
                  }
                  choice load-balancing-ignore-as-type {
                    description
                      "Set load balancing as path type.";
                    case as-attribute {
                      description
                        "Ignore the as-path attribute.";
                      leaf load-balancing-as-path-ignore {
                        // NCS drop when statement
                        type empty;
                        description
                          "Configure BGP to ignore the AS_Path attribute when selecting the equal route. After as-path-neglect is selected, BGP does not compare the AS_Path length.";
                      }
                    }
                    case same-length-as-attribute {
                      description
                        "Ignore comparison of as-path attributes with the same length.";
                      leaf load-balancing-as-path-relax {
                        // NCS drop when statement
                        type empty;
                        description
                          "Configure BGP to ignore comparison of AS_Path attributes with the same length when selecting the equal route. After as-path-neglect is selected, BGP does not compare the AS_Path length.";
                      }
                    }
                  }
                  uses live_ncs_advertise-large-community-type;
                  uses live_ncs_rt-update-interval-type;
                  uses bgp:live_ncs_preferred-value-type;
                  uses live_ncs_peer-independent-peer-group-type;
                  uses live_ncs_route-limit-type;
                  uses live_ncs_public-as-only-type;
                  uses live_ncs_peer-public-as-only-import-type;
                  uses live_ncs_path-attr-map-type;
                }
                container state {
                  description
                    "Operational state of peer information.";
                  leaf type {
                    type live_ncs_peer-type-info;
                    description
                      "Configures the type of BGP peers: IBGP or EBGP.";
                  }
                  leaf version {
                    type uint8;
                    description
                      "The current BGP version is BGP-4. BGP-4 provides a set of new mechanisms to support Classless Inter-Domain Routing (CIDR). The new mechanisms also support the network prefix-based advertisement, cancellation of the 'class' concept for a BGP network during the network prefix-supported advertisements, and route summarization and AS path summarization.";
                  }
                  leaf remote-router-id {
                    type inet:ipv4-address-no-zone;
                    description
                      "Router ID for a peer.";
                  }
                  leaf current-state {
                    type live_ncs_peer-state;
                    description
                      "Current BGP state, which can be Idle, Active, Established, Connect, OpenSent, or OpenConfirm.
                       Idle: In this state, BGP denies all connection requests. This is the initial state of BGP.
                       Active: In this state, BGP tries to establish TCP connections. This is the intermediate state of BGP.
                       Established: In this state, BGP peers can exchange Update, Notification, and Keepalive packets with each other.
                       Connect: In this state, BGP determines the subsequent operation after the TCP connections are established.
                       OpenSent: In this state, BGP is waiting for the Open packet from the peer.
                       OpenConfirm: In this state, BGP is waiting for a Notification packet and a Keepalive packet.";
                  }
                  leaf local-port {
                    type uint32;
                    description
                      "Local port number. BGP uses TCP as the transport layer protocol, and the port number of the TCP connection initiator is 179.";
                  }
                  leaf remote-port {
                    type uint32 {
                      range "0..4294967295";
                    }
                    description
                      "Port number for a peer to establish a peer relationship.";
                  }
                  leaf current-event {
                    type string {
                      length "1..39";
                    }
                    description
                      "Recent event that occurs on a peer.";
                  }
                  leaf last-state {
                    type live_ncs_peer-state;
                    description
                      "Last state of a peer, which can be Idle, Connect, Active, OpenSent, OpenConfirm, or Established.";
                  }
                  leaf up-down-duration {
                    type string {
                      length "1..49";
                    }
                    description
                      "Duration in which a BGP peer is in the Up or Down state.
                       The Up state indicates the established state, and the Down state indicates a non-established state (including the Idle, Active, Connect, OpenSent and OpenConfirm state). When the state is switched between Up and Down, the upDownDuration timer is reset and starts from 0.";
                  }
                  leaf send-message {
                    type uint32 {
                      range "0..4294967295";
                    }
                    description
                      "Number of messages sent to the peer.";
                  }
                  leaf rpd-capability {
                    type live_ncs_rpd-cap-type;
                    description
                      "Peer route-policy distribute capability.";
                  }
                  leaf local-rpd-capability {
                    type live_ncs_rpd-cap-type;
                    description
                      "Local route-policy distribute capability.";
                  }
                  leaf negotiate-rpd-capability {
                    type live_ncs_rpd-cap-type;
                    description
                      "Negotiated route-policy distribute capability.";
                  }
                  leaf receive-message {
                    type uint32 {
                      range "0..4294967295";
                    }
                    description
                      "Number of messages received from the peer.";
                  }
                  leaf out-queue {
                    type uint32 {
                      range "0..4294967295";
                    }
                    description
                      "Number of messages to be sent in a queue.";
                  }
                  leaf receive-hold-time {
                    type uint32 {
                      range "0..65535";
                    }
                    units "s";
                    description
                      "Hold time of a peer.";
                  }
                  leaf receive-last-keepalive-time {
                    type yang:date-and-time;
                    description
                      "Last time when Keepalive packets were received from a peer.";
                  }
                  leaf negotiate-hold-time {
                    type uint32 {
                      range "0..65535";
                    }
                    units "s";
                    description
                      "Hold time negotiated by BGP peers.";
                  }
                  leaf negotiate-keepalive-time {
                    type uint32 {
                      range "0..21845";
                    }
                    units "s";
                    description
                      "Keepalive time negotiated by BGP peers.";
                  }
                  leaf receive-update-count {
                    type uint32 {
                      range "0..4294967295";
                    }
                    description
                      "Number of Update packets received from a peer.";
                  }
                  leaf receive-open-count {
                    type uint32 {
                      range "0..4294967295";
                    }
                    description
                      "Number of Open packets received from a peer.";
                  }
                  leaf receive-keepalive-count {
                    type uint32 {
                      range "0..4294967295";
                    }
                    description
                      "Number of Keepalive packets received from a peer.";
                  }
                  leaf receive-notification-count {
                    type uint32 {
                      range "0..4294967295";
                    }
                    description
                      "Number of Notification packets received from a peer.";
                  }
                  leaf receive-route-refresh-count {
                    type uint32 {
                      range "0..4294967295";
                    }
                    description
                      "Number of Route-Refresh packets received from a peer.";
                  }
                  leaf send-update-count {
                    type uint32 {
                      range "0..4294967295";
                    }
                    description
                      "Number of Update packets sent to a peer.";
                  }
                  leaf send-open-count {
                    type uint32 {
                      range "0..4294967295";
                    }
                    description
                      "Number of Open packets sent to a peer.";
                  }
                  leaf send-keepalive-count {
                    type uint32 {
                      range "0..4294967295";
                    }
                    description
                      "Number of Keepalive packets sent to a peer.";
                  }
                  leaf send-notification-count {
                    type uint32 {
                      range "0..4294967295";
                    }
                    description
                      "Number of Notification packets sent to a peer.";
                  }
                  leaf send-route-refresh-count {
                    type uint32 {
                      range "0..4294967295";
                    }
                    description
                      "Number of Route-Refresh packets sent to a peer.";
                  }
                  leaf send-graceful-restart-capability {
                    type boolean;
                    description
                      "Whether the local end supports the GR (Graceful Restart) capability.";
                  }
                  leaf receive-refresh-capability {
                    type boolean;
                    description
                      "Whether the peer supports RR.";
                  }
                  leaf receive-four-byte-as-capability {
                    type boolean;
                    description
                      "Whether the peer supports 4-byte AS numbers.";
                  }
                  leaf receive-multi-protocol-capability {
                    type boolean;
                    description
                      "Whether the peer supports MP.";
                  }
                  leaf receive-graceful-restart-capability {
                    type boolean;
                    description
                      "Whether the peer supports GR.";
                  }
                  leaf receive-add-path {
                    type string {
                      length "1..50";
                    }
                    description
                      "Whether the peer supports Add-Path.";
                  }
                  leaf negotiate-add-path {
                    type string {
                      length "1..50";
                    }
                    description
                      "Negotiated Add-Path.";
                  }
                  leaf receive-label-add-path {
                    type string {
                      length "1..50";
                    }
                    description
                      "Whether the peer supports labeled Add-Path.";
                  }
                  leaf negotiate-label-add-path {
                    type string {
                      length "1..50";
                    }
                    description
                      "Negotiated Label Add-Path.";
                  }
                  leaf receive-prefix {
                    type uint32 {
                      range "0..4294967295";
                    }
                    description
                      "Number of received route prefixes.";
                  }
                  leaf receive-active-prefix {
                    type uint32 {
                      range "0..4294967295";
                    }
                    description
                      "Number of received prefixes of active routes.";
                  }
                  leaf advertise-prefix {
                    type uint32 {
                      range "0..4294967295";
                    }
                    description
                      "Number of advertised route prefixes.";
                  }
                  leaf discard-attribute {
                    type string {
                      length "1..300";
                    }
                    description
                      "The attribute id discard info.";
                  }
                  leaf check-first-as {
                    type live_ncs_first-as-state;
                    description
                      "Check the first AS in the AS_Path of the update messages from EBGP peers.";
                  }
                  leaf extend-nexthop-capability {
                    type boolean;
                    description
                      "Peer extended next hop encoding capability.";
                  }
                  leaf egress-engineer-capability {
                    type boolean;
                    description
                      "Whether the peer supports EPE.";
                  }
                  leaf orf-capability {
                    type boolean;
                    description
                      "Whether the peer supports VPN orf capability.";
                  }
                  leaf rely-interface-capability {
                    type boolean;
                    description
                      "Whether the peer supports check interface.";
                  }
                  leaf remote-as {
                    type string {
                      length "1..11";
                    }
                    description
                      "AS number of the BGP peer.";
                  }
                  leaf memory-priority {
                    type live_ncs_memory-priority;
                    description
                      "Priority that is used to determine the disconnection order of a BGP peer relationship if memory overload occurs.";
                  }
                }
              }
            }
          }
        }
        container peer-bfd-session-states {
          description
            "List of BFD sessions.";
          list peer-bfd-session-state {
            key "address";
            description
              "Operational state of BFD session.";
            leaf address {
              type inet:ip-address-no-zone;
              description
                "Peer address of the BFD session.";
            }
            leaf local-address {
              type inet:ip-address-no-zone;
              description
                "Local address of the BFD session.";
            }
            leaf if-name {
              type pub-type:live_ncs_if-name;
              description
                "Name of an interface of the BFD session.";
            }
            leaf tx-interval {
              type uint32;
              units "ms";
              // NCS drop default statement
              description
                "Interval at which BFD packets are sent.";
            }
            leaf rx-interval {
              type uint32;
              units "ms";
              // NCS drop default statement
              description
                "Interval at which BFD packets are received.";
            }
            leaf multiplier {
              type uint32 {
                range "0..50";
              }
              description
                "Detection multiplier.";
            }
            leaf status {
              type live_ncs_bfd-state;
              description
                "State of the BFD session.";
            }
            leaf global-bfd-enable {
              type boolean;
              description
                "Global BFD state.";
            }
            leaf valid-ttl-hops {
              type uint8 {
                range "1..255";
              }
              description
                "The valid TTL hops value.";
            }
          }
        }
        container egress-engineer-peer-sets {
          // NCS drop when statement
          description
            "List of peer set information under BGP instance.";
          list egress-engineer-peer-set {
            key "peer-set-name";
            description
              "Configure peer set information.";
            leaf peer-set-name {
              type string {
                length "1..63";
              }
              description
                "The name for peer set.";
            }
            leaf static-label {
              type uint32 {
                range "16..1048575";
              }
              description
                "The static label for peer set.";
            }
            leaf label-pop {
              // NCS drop when statement
              type boolean;
              // NCS drop must statement
              // NCS drop default statement
              description
                "Enable/disable the BGP-EPE label popping function.";
            }
            leaf relate-bfd {
              type boolean;
              // NCS drop must statement
              // NCS drop default statement
              description
                "Enable/disable association between the BGP-EPE label and BFD status.";
            }
          }
        }
      }
      container instance-processs {
        // NCS drop when statement
        description
          "List of all BGP instances.";
        list instance-process {
          key "name";
          // NCS drop max-elements statement
          description
            "Configure a BGP instance.";
          ext:generated-by "system" {
            // NCS drop when statement
            description
              "The BGP public instance is generated automatically when BGP instances is enabled.";
          }
          leaf name {
            type leafref {
              path "/ncs:devices/ncs:device/ncs:live-status/bgp:bgp/bgp:instance-processs/bgp:instance-process/bgp:name" {
                tailf:xpath-root 3;
              }
            }
            description
              "Name of BGP Site.";
          }
          leaf router-id {
            type inet:ipv4-address-no-zone;
            description
              "ID of a router that is in IPv4 address format. Certain dynamic routing protocols require a router ID. If no router ID is specified for a router when these protocols are enabled, the router ID in the RM module is used by default. The default router ID in the RM module is 0.0.0.0 when the router is not configured with any interface.
               The rules for selecting a router ID are as follows:
               1. If you set a router ID through this configuration, the set router ID is used. If the router ID is not set, you need to select a router ID according to the following rules:
               (1) If loopback interfaces configured with IP addresses exist, the largest IP address among the IP addresses of the loopback interfaces is selected as the router ID.
               (2) If no loopback interface configured with an IP address exists, the largest IP address among the IP addresses of other interfaces is selected as the router ID, regardless of whether the interface is Up.
               The router ID is reselected only when the interface address that is selected as the router ID is deleted or changed. The router ID is not reselected in any of the following cases:
               a. The interface is Down.
               b. A loopback interface is configured when the IP address of a non-loopback interface is selected as the router ID.
               c. A larger IP address of an interface is configured.
               2. Each VPN instance selects the router ID from the addresses of the interfaces of the VPN instance according to the preceding rules.
               3. When both the AMB and SMB exist on the router, the system backs up the router ID set through the related command and the router ID that is selected from IP addresses of the interfaces. After the active/standby switchover is performed, the system checks the validity of the router ID selected from the interface addresses. If the router ID is invalid, the system reselects a router ID.";
          }
          leaf effect-router-id {
            type inet:ipv4-address-no-zone;
            // NCS drop default statement
            description
              "Router ID that takes effect.";
          }
          container afs {
            description
              "List of BGP address family instances.";
            list af {
              key "type";
              description
                "Configure BGP address family instance.";
              leaf type {
                type bgp:live_ncs_instance-af-type;
                description
                  "Address family type of a BGP instance.";
              }
              container ipv4-vpn {
                // NCS drop when statement
                description
                  "Configure IPv4 VPNv4 options.";
                uses live_ncs_vpn-target-type;
                uses live_ncs_reflector-cluster-type;
                uses live_ncs_reflect-type;
                leaf auto-frr {
                  type boolean;
                  // NCS drop default statement
                  description
                    "Enable/disable BGP Auto FRR. If IP FRR, VPN FRR, and Auto FRR are all enabled, IP FRR and VPN FRR take precedence over Auto FRR. If a route fails to match the routing policy of IP FRR or VPN FRR, Auto FRR takes effect.";
                }
                leaf tunnel-selector-name {
                  type leafref {
                    path "/ncs:devices/ncs:device/ncs:live-status/rtp:routing-policy/rtp:tunnel-selectors/rtp:tunnel-selector/rtp:name" {
                      tailf:xpath-root 3;
                    }
                  }
                  description
                    "Configure a tunnel selector and apply it to the BGP IPv4 unicast, BGP VPNv4 address families and BGP VPNv6 address families so that IPv4,VPNv4 and VPNv6 labeled routes can be iterated to tunnels based on the tunnel selector.";
                }
                leaf route-select-delay {
                  type uint16 {
                    range "0..3600";
                  }
                  units "s";
                  // NCS drop default statement
                  description
                    "Route selection delay.";
                }
                leaf apply-label-mode {
                  type live_ncs_apply-label-type;
                  // NCS drop default statement
                  description
                    "Method of distributing labels to VPNV4 and VPNV6 routes. The way which assigns the label depends on the paf value. If there are a large number of routes, assign a label for the routes that have same nexthop and out-label. This allows all routes which have same nexthop and out-label to use one label.";
                }
                leaf nexthop-select-depend-type {
                  type live_ncs_select-depend-type-ext;
                  // NCS drop default statement
                  description
                    "Specify the route iteration mode: IP or tunnel. In tunnel mode, the labeled BGP IPv4 route can participate in route selection only after its next hop is iterated to an LSP. In IP
                     mode, the labeled BGP IPv4 route can participate in route selection only after its next hop is iterated to an IP address. By default, the labeled BGP IPv4 route can participate in route selection
                     if its next hop can be iterated to an IP address, regardless of whether the LSP of the next hop exists. This allows the RR that is not enabled with MPLS to forward labeled routes. In non-RR
                     networking or RR networking where the BGP next hop is changed, BGP needs to check whether there is an LSP destined for the next hop. If such an LSP is not found, BGP needs to establish an LSP in
                     advance. If the default setting is adopted, a labeled BGP IPv4 unicast route may be selected prior to LSP establishment. As a result, services are incorrectly switched before LSP establishment and
                     service stability is affected. Therefore, allow route selection only after the labeled BGP IPv4 route is iterated to an LSP.";
                }
                leaf default-med {
                  type uint32;
                  // NCS drop default statement
                  description
                    "Specify the Multi-Exit-Discriminator (MED) of BGP routes. The value is an integer. This value is valid only for the imported routes and BGP summarized routes on the local router.";
                }
                leaf best-external {
                  type boolean;
                  // NCS drop default statement
                  description
                    "Enable/disable best external route selection.";
                }
                leaf label-free-delay {
                  type uint8 {
                    range "0..180";
                  }
                  units "s";
                  // NCS drop default statement
                  description
                    "Label free delay.";
                }
                leaf add-path-select-num {
                  type uint8 {
                    range "2..64";
                  }
                  description
                    "Number of Add-Path routes.";
                }
                leaf default-local-preference {
                  type uint32 {
                    range "0..4294967295";
                  }
                  // NCS drop default statement
                  description
                    "The local preference of BGP routes.";
                }
                uses live_ncs_bestroute-med-plus-igp-type;
                uses live_ncs_bestroute-router-id-prior-clusterlist-type;
                leaf reflect-between-client {
                  type boolean;
                  // NCS drop default statement
                  description
                    "Enable/disable route reflection between clients. If clients of a route reflector (RR) are fully meshed, you can disable route reflection among clients to reduce the cost.";
                }
                leaf activate-route-tag {
                  type boolean;
                  // NCS drop default statement
                  description
                    "Enable/disable tag-based filtering.";
                }
                uses live_ncs_route-reflector-ext-community-filter-type;
                uses live_ncs_vrf-af-dampening-routes-ext;
                container nexthop-recursive-lookup {
                  description
                    "Configure next hop iteration.";
                  container common {
                    description
                      "Configure next hop iteration common options.";
                    uses live_ncs_nexthop-recursive-lookup-restrain;
                  }
                  uses live_ncs_nexthop-recursive-lookup-delay;
                  uses live_ncs_bit-error-detection-type;
                }
                uses live_ncs_ipv4-import-filter-protocol-type;
                uses live_ncs_ipv4vpn-export-filter-protocol-type;
                uses live_ncs_slow-peer-type;
              }
            }
          }
        }
      }
    }
  }
  augment "/ncs:devices/ncs:device/ncs:config/ni:network-instance/ni:instances/ni:instance" {
    description
      "BGP network instance configuration.";
    container bgp {
      tailf:ncs-device-type "netconf";
      tailf:display-when "not(../../../../../ncs:module) or ../../../../../ncs:module[ncs:name='huawei-bgp']";
      description
        "Configure BGP network instance. All nodes of private VPN Instance in this container can be used only when the value of the global BGP enabling node (/bgp:bgp/bgp:global/bgp:yang-enable) is set to true.";
      container base-process {
        when "/bgp:bgp/bgp:base-process/bgp:enable='true'" {
          tailf:xpath-root 3;
        }
        presence "Create vrf session.";
        description
          "Enable/disable BGP instances.";
        ext:generated-by "system" {
          when "../../ni:name = '_public_'" {
            tailf:xpath-root 3;
          }
          description
            "The BGP public instance is generated automatically when BGP is enabled.";
        }
        leaf router-id {
          type inet:ipv4-address-no-zone;
          description
            "ID of a router that is in IPv4 address format. Certain dynamic routing protocols require a router ID. If no router ID is specified for a router when these protocols are enabled, the router ID in the RM module is used by default. The default router ID in the RM module is 0.0.0.0 when the router is not configured with any interface.
             The rules for selecting a router ID are as follows:
             1. If you set a router ID through this configuration, the set router ID is used. If the router ID is not set, you need to select a router ID according to the following rules:
             (1) If loopback interfaces configured with IP addresses exist, the largest IP address among the IP addresses of the loopback interfaces is selected as the router ID.
             (2) If no loopback interface configured with an IP address exists, the largest IP address among the IP addresses of other interfaces is selected as the router ID, regardless of whether the interface is Up.
             The router ID is reselected only when the interface address that is selected as the router ID is deleted or changed. The router ID is not reselected in any of the following cases:
             a. The interface is Down.
             b. A loopback interface is configured when the IP address of a non-loopback interface is selected as the router ID.
             c. A larger IP address of an interface is configured.
             2. Each VPN instance selects the router ID from the addresses of the interfaces of the VPN instance according to the preceding rules.
             3. When both the AMB and SMB exist on the router, the system backs up the router ID set through the related command and the router ID that is selected from IP addresses of the interfaces. After the active/standby switchover is performed, the system checks the validity of the router ID selected from the interface addresses. If the router ID is invalid, the system reselects a router ID.";
        }
        leaf router-id-auto-select {
          when "../../../ni:name!='_public_'" {
            tailf:xpath-root 3;
          }
          type boolean;
          must "../router-id-auto-select!='true' or (../router-id-auto-select='true' and not (../router-id))" {
            tailf:xpath-root 3;
          }
          default "false";
          description
            "Enable/disable router ID auto select. If a BGP VPN instance is not enabled to select a router ID, a router ID can be configured for the BGP VPN instance. If no router ID is configured for the BGP VPN instance, the BGP VPN instance inherits the router ID of the public network instance. If a BGP VPN instance is enabled to select a router ID, it uses the address of an interface bound to a VPN as the router ID based on the following rules:

             1. If Loopback interfaces configured with IP addresses exist, the largest IP address among the IP addresses of the Loopback interfaces is selected as the router ID.

             2. If there is no Loopback interface configured with an IP address, the largest IP address among the IP addresses of other interfaces is selected as the router ID, regardless of whether the interface is Up.";
        }
        // NCS drop config false leaf 'effect-router-id'
        container afs {
          description
            "List of BGP address family instances.";
          list af {
            key "type";
            description
              "Configure BGP address family instance. In public network instances, all types of address families can be configured. In IPv4 VPN instances, the IPv4 unicast, IPv4 flow, and IPv4 labeled unicast address families can be configured. In IPv6 VPN instances, the IPv6 unicast and IPv6 flow address families can be configured. The IPv4 address family in the BGP _public_ VPN instance cannot be deleted.";
            ext:generated-by "system" {
              when "../../../../ni:name = '_public_'" {
                tailf:xpath-root 3;
              }
              ext:filter "type = 'ipv4uni'";
              description
                "The IPv4 unicast of the BGP public instance is generated automatically when BGP is enabled.";
            }
            leaf type {
              type bgp:af-type;
              description
                "Address family type of a BGP instance.";
            }
            container ipv4-unicast {
              when "../type = 'ipv4uni'" {
                tailf:xpath-root 3;
              }
              description
                "Configure IPv4 unicast options.";
              container common {
                description
                  "Configure IPv4 unicast common options.";
                leaf auto-frr {
                  type boolean;
                  default "false";
                  description
                    "Enable/disable BGP Auto FRR. If IP FRR, VPN FRR, and Auto FRR are all enabled, IP FRR and VPN FRR take precedence over Auto FRR. If a route fails to match the routing policy of IP FRR or VPN FRR, Auto FRR takes effect.";
                }
                leaf tunnel-selector-name {
                  when "../../../../../../../ni:name='_public_'" {
                    tailf:xpath-root 3;
                  }
                  type leafref {
                    path "/ncs:devices/ncs:device/ncs:config/rtp:routing-policy/rtp:tunnel-selectors/rtp:tunnel-selector/rtp:name" {
                      tailf:xpath-root 3;
                    }
                  }
                  description
                    "Configure a tunnel selector and apply it to the BGP IPv4 unicast, BGP VPNv4 address families and BGP VPNv6 address families so that IPv4,VPNv4 and VPNv6 labeled routes can be iterated to tunnels based on the tunnel selector. By default, no tunnel selector is configured.";
                }
                leaf tunnel-selector-all {
                  when '../tunnel-selector-name' {
                    tailf:xpath-root 3;
                  }
                  type boolean;
                  default "false";
                  description
                    "Enable/disable tunnel selector for labeled, imported, and network segment routes.";
                }
                leaf route-select-delay {
                  type uint16 {
                    range "0..3600";
                  }
                  units "s";
                  default "0";
                  description
                    "Route selection delay.";
                }
                uses reflector-cluster-type;
                uses reflect-type;
                leaf maximum-load-balancing-ibgp {
                  type uint16 {
                    range "1..65535";
                  }
                  must "not (../maximum-load-balancing>1 or ../maximum-load-balancing-eibgp or ../load-balancing-eibgp-enable='true') or ../maximum-load-balancing-ibgp=1" {
                    tailf:xpath-root 3;
                  }
                  default "1";
                  description
                    "Specify the maximum number of equal-cost IBGP routes.";
                }
                leaf maximum-load-balancing-ebgp {
                  type uint16 {
                    range "1..65535";
                  }
                  must "not (../maximum-load-balancing>1 or ../maximum-load-balancing-eibgp or ../load-balancing-eibgp-enable='true') or ../maximum-load-balancing-ebgp=1" {
                    tailf:xpath-root 3;
                  }
                  default "1";
                  description
                    "Specify the maximum number of equal-cost EBGP routes.";
                }
                leaf nexthop-select-depend-type {
                  when "../../../../../../../ni:name='_public_'" {
                    tailf:xpath-root 3;
                  }
                  type select-depend-type;
                  default "depend-ip";
                  description
                    "Specify the route iteration mode: IP or tunnel. In tunnel mode, the labeled BGP IPv4 route can participate in route selection only after its next hop is iterated to an LSP. In IP
                     mode, the labeled BGP IPv4 route can participate in route selection only after its next hop is iterated to an IP address. By default, the labeled BGP IPv4 route can participate in route selection
                     if its next hop can be iterated to an IP address, regardless of whether the LSP of the next hop exists. This allows the RR that is not enabled with MPLS to forward labeled routes. In non-RR
                     networking or RR networking where the BGP next hop is changed, BGP needs to check whether there is an LSP destined for the next hop. If such an LSP is not found, BGP needs to establish an LSP in
                     advance. If the default setting is adopted, a labeled BGP IPv4 unicast route may be selected prior to LSP establishment. As a result, services are incorrectly switched before LSP establishment and
                     service stability is affected. Therefore, allow route selection only after the labeled BGP IPv4 route is iterated to an LSP.";
                }
                leaf nexthop-inherit-ip-cost {
                  when "../nexthop-select-depend-type='depend-tunnel'" {
                    tailf:xpath-root 3;
                  }
                  type boolean;
                  default "false";
                  description
                    "Enable/disable next hop iteration mode to IP. Specify the route iteration mode: IP or tunnel. In tunnel mode, the labeled BGP IPv4 route can participate in route selection only after its next hop is iterated to an LSP.";
                }
                leaf nexthop-resolve-aigp {
                  when "../../../../../../../ni:name!='_public_'" {
                    tailf:xpath-root 3;
                  }
                  type boolean;
                  default "false";
                  description
                    "Enable/disable route with AIGP attribute for route selection.";
                }
                leaf always-compare-med {
                  type boolean;
                  default "false";
                  description
                    "Enable/disable BGP to compare the MEDs of routes from peers in different ASs in route selection. If
                     there are multiple reachable routes to the same destination, the route with the smallest MED is preferred. Do not use this option unless different ASs use the same IGP and route selection mode.";
                }
                leaf default-med {
                  type uint32;
                  default "0";
                  description
                    "Specify the Multi-Exit-Discriminator (MED) of BGP routes. The value is an integer. This value is valid only for the imported routes and BGP summarized routes on the local router.";
                }
                leaf summary-automatic {
                  type boolean;
                  default "false";
                  description
                    "Enable/disable automatic summarization for imported routes. Manual summarization takes precedence over automatic summarization. After automatic summarization is enabled, BGP summarizes routes based on the natural network segment (for example, 10.1.1.1/24 and 10.2.1.1/24 are summarized into 10.0.0.0/8, a Class A address), and sends only the summarized route to peers. This reduces the number of routes.";
                }
                leaf nexthop-third-party {
                  type boolean;
                  default "false";
                  description
                    "Enable/disable BGP third-party next hop.";
                }
                leaf best-route-bit-error-detection {
                  when "../../../../../../../ni:name!='_public_'" {
                    tailf:xpath-root 3;
                  }
                  type boolean;
                  default "false";
                  description
                    "Enable/disable the function to reroute traffic when a bit error event occurs.";
                }
                leaf supernet-unicast-advertise {
                  type boolean;
                  default "false";
                  description
                    "Enable/disable the function to advertise supernet unicast routes.";
                }
                leaf supernet-label-advertise {
                  type boolean;
                  default "true";
                  description
                    "Enable/disable the function to advertise supernet labeled routes.";
                }
                leaf lsp-mtu {
                  type uint16 {
                    range "46..65535";
                  }
                  default "1500";
                  description
                    "BGP LSP MTU.";
                }
                leaf label-free-delay {
                  type uint8 {
                    range "0..180";
                  }
                  units "s";
                  default "0";
                  description
                    "Label Free Delay.";
                }
                leaf bestroute-med-confederation {
                  when "../../../../../../../ni:name='_public_'" {
                    tailf:xpath-root 3;
                  }
                  type boolean;
                  default "false";
                  description
                    "Enable/disable BGP to compare MED value only within the federation.";
                }
                leaf bestroute-as-path-ignore {
                  type boolean;
                  must "../bestroute-as-path-ignore = 'false' or ../load-balanc-as-path-ignore ='false'" {
                    tailf:xpath-root 3;
                  }
                  default "false";
                  description
                    "Enable/disable BGP to ignore the AS_Path attribute when selecting the optimal route. By default, BGP uses the AS_Path attribute as one of route selection rules, and a route with a shorter AS_Path is preferred. After bestroute-as-path-ignore is selected, BGP does not compare the AS_Path length.";
                }
                leaf determin-med {
                  type boolean;
                  default "false";
                  description
                    "Enable/disable deterministic MED so that the route selection result is relevant to the sequence in which routes are received.";
                }
                leaf best-external {
                  when "../../../../../../../ni:name='_public_'" {
                    tailf:xpath-root 3;
                  }
                  type boolean;
                  must "../best-external ='false' or ../determin-med ='false'" {
                    tailf:xpath-root 3;
                  }
                  default "false";
                  description
                    "Enable/disable best external route selection.";
                }
                leaf attribute-set-enable {
                  when "../../../../../../../ni:name!='_public_'" {
                    tailf:xpath-root 3;
                  }
                  type boolean;
                  default "false";
                  description
                    "Enable/disable the capability of processing attribute set.";
                }
                leaf attribute-set-mode {
                  when "../attribute-set-enable='true'" {
                    tailf:xpath-root 3;
                  }
                  type bgp:attribute-set-type;
                  default "both";
                  description
                    "The processing mode of attribute set.";
                }
                leaf add-path-select-num {
                  when "../../../../../../../ni:name='_public_'" {
                    tailf:xpath-root 3;
                  }
                  type uint8 {
                    range "2..64";
                  }
                  must "../determin-med ='false'" {
                    tailf:xpath-root 3;
                  }
                  description
                    "Number of Add-Path routes.";
                }
                leaf load-balanc-igp-metric-ignore {
                  type boolean;
                  default "false";
                  description
                    "Enable/disable BGP to ignore the IGP cost of each BGP route to the next hop when selecting routes for load balancing. By default, only the routes with the same IGP cost can participate in load balancing.";
                }
                leaf load-balanc-as-path-ignore {
                  type boolean;
                  must "../load-balanc-as-path-ignore ='false' or (../load-balanc-as-path-relax ='false' and ../bestroute-as-path-ignore ='false')" {
                    tailf:xpath-root 3;
                  }
                  default "false";
                  description
                    "Enable/disable BGP to ignore the AS_Path of each BGP route to the next hop when selecting routes for load balancing. By default, only the routes with the same AS_Path can participate in load balancing.";
                }
                leaf load-balanc-as-path-relax {
                  type boolean;
                  must "../load-balanc-as-path-relax ='false' or ../load-balanc-as-path-ignore ='false'" {
                    tailf:xpath-root 3;
                  }
                  default "false";
                  description
                    "Enable/disable BGP to ignore comparison of AS_Path attributes with the same length. By default, only the routes with the same AS_Path can participate in load balancing.";
                }
                leaf default-local-preference {
                  type uint32 {
                    range "0..4294967295";
                  }
                  default "100";
                  description
                    "The local preference of BGP routes.";
                }
                leaf default-route-import {
                  type boolean;
                  default "false";
                  description
                    "Enable/disable the function to import default routes into the BGP routing table. Default-route-imported must be used with import-routes so that default routes can be imported to the BGP routing table. If only import-routes is used, no default routes can be added to the BGP routing table. In addition, default-route-imported can only import the default routes in the routing table into the BGP routing table.";
                }
                leaf routerid-neglect {
                  type boolean;
                  default "false";
                  description
                    "Enable/disable BGP to ignore router IDs when selecting the optimal route. Comparing router IDs is the last resort in route selection. This means that if one optimal route must be selected and no other parameters can be used to break the tie, router IDs can be used. If this option is selected, the first received route will be selected as the optimal route, and BGP will ignore the router ID and peer address in route selection.";
                }
                leaf maximum-load-balancing {
                  type uint16 {
                    range "1..65535";
                  }
                  must 'not (../maximum-load-balancing-ibgp>1 or ../maximum-load-balancing-ebgp>1 or ../maximum-load-balancing-eibgp) or ../maximum-load-balancing=1' {
                    tailf:xpath-root 3;
                  }
                  default "1";
                  description
                    "Specify the maximum number of equal-cost routes in the BGP routing table. The value can be 1 or an integer greater than 1. The value depends on the associated license. Equal-cost BGP routes can be generated for load balancing only when the BGP routes meet the first nine rules of the route-selection policy and have the same AS-Path attribute.";
                }
                leaf reflect-between-client {
                  type boolean;
                  default "true";
                  description
                    "Enable/disable route reflection between clients. If clients of a route reflector (RR) are fully meshed, you can disable route reflection among clients to reduce the cost.";
                }
                leaf import-rib-nexthop-invariable {
                  when "../../../../../../../ni:name!='_public_'" {
                    tailf:xpath-root 3;
                  }
                  type boolean;
                  default "false";
                  description
                    "Enable/disable the function to advertise the route without modifying the next-hop.";
                }
                leaf route-relay-tunnel {
                  type boolean;
                  must "not(../route-relay-tunnel='true' and /rt:routing/rt:routing-manage/rt:relay-tunnel/rt:enable='true')" {
                    tailf:xpath-root 3;
                  }
                  default "false";
                  description
                    "Enable/disable unicast route recursive-lookup tunnel.";
                }
                leaf route-relay-tunnel-selector {
                  when "../route-relay-tunnel='true'" {
                    tailf:xpath-root 3;
                  }
                  type leafref {
                    path "/ncs:devices/ncs:device/ncs:config/rtp:routing-policy/rtp:tunnel-selectors/rtp:tunnel-selector/rtp:name" {
                      tailf:xpath-root 3;
                    }
                  }
                  description
                    "Unicast route tunnel selector name.";
                }
                leaf route-relay-tunnel-v6-selector {
                  when "../../../../../../../ni:name='_public_'" {
                    tailf:xpath-root 3;
                  }
                  type leafref {
                    path "/ncs:devices/ncs:device/ncs:config/rtp:routing-policy/rtp:tunnel-selectors/rtp:tunnel-selector/rtp:name" {
                      tailf:xpath-root 3;
                    }
                  }
                  description
                    "Enable/disable unicast route recursive-lookup IPv6 tunnel by tunnel selector name.";
                }
                uses bestroute-med-plus-igp-type;
                uses bestroute-router-id-prior-clusterlist-type;
                leaf bestroute-med-none-as-maximum {
                  type boolean;
                  default "false";
                  description
                    "Enable/disable BGP considers its MED as the largest MED value (4294967295). If a route does not carry MED, BGP considers its MED as the default value (0) during route selection.";
                }
                leaf bestroute-rd-large-first {
                  when "../../../../../../../ni:name!='_public_'" {
                    tailf:xpath-root 3;
                  }
                  type boolean;
                  default "false";
                  description
                    "Enable/disable a BGP device to select the route with the largest route distinguisher (RD) during route selection.";
                }
                leaf ebgp-ecmp-nexthop-changed {
                  when '../maximum-load-balancing-ebgp and ../maximum-load-balancing-ebgp>1' {
                    tailf:xpath-root 3;
                  }
                  type boolean;
                  default "false";
                  description
                    "Enable/disable next hop of equal-cost EBGP routes is changed. When equal-cost EBGP routes are load-balancing traffic, the next hop of these routes is changed to a local interface before these routes are advertised. This function can be enabled only when the maximum number of equal-cost EBGP routes is greater than 1.";
                }
                leaf ibgp-ecmp-nexthop-changed {
                  when '../maximum-load-balancing-ibgp and ../maximum-load-balancing-ibgp>1' {
                    tailf:xpath-root 3;
                  }
                  type boolean;
                  default "false";
                  description
                    "Enable/disable next hop of equal-cost IBGP routes is changed. When equal-cost IBGP routes are load-balancing traffic, the next hop of these routes is changed to a local interface before these routes are advertised. This function can be enabled only when the maximum number of equal-cost IBGP routes is greater than 1.";
                }
                leaf ecmp-nexthop-changed {
                  when '../maximum-load-balancing and ../maximum-load-balancing>1' {
                    tailf:xpath-root 3;
                  }
                  type boolean;
                  default "false";
                  description
                    "Enable/disable next hop of equal-cost routes is changed. When equal-cost BGP routes are load-balancing traffic, the next hop of these routes is changed to a local interface before these routes are advertised. This function can be enabled only when the maximum number of equal-cost BGP routes is greater than 1.";
                }
                leaf maximum-load-balancing-eibgp {
                  when "../../../../../../../ni:name!='_public_'" {
                    tailf:xpath-root 3;
                  }
                  type uint16 {
                    range "1..65535";
                  }
                  must "../maximum-load-balancing-ibgp=1 and ../maximum-load-balancing-ebgp=1 and ../maximum-load-balancing=1 and ../load-balancing-eibgp-enable='false'" {
                    tailf:xpath-root 3;
                  }
                  description
                    "Specify the maximum number of equal-cost EBGP routes and IBGP routes. After the attribute is set, load balancing is performed among equal-cost BGP VPN routes, regardless of the route type, EBGP or IBGP.";
                }
                leaf eibgp-ecmp-nexthop-changed {
                  when '../maximum-load-balancing-eibgp' {
                    tailf:xpath-root 3;
                  }
                  type boolean;
                  default "false";
                  description
                    "Enable/disable next hop of equal-cost EBGP and IBGP routes is changed. When equal-cost EBGP and IBGP routes are load-balancing traffic, the next hop of these routes is changed to a local interface before these routes are advertised.";
                }
                leaf load-balancing-eibgp-enable {
                  when "../../../../../../../ni:name!='_public_'" {
                    tailf:xpath-root 3;
                  }
                  type boolean;
                  must "not (../maximum-load-balancing-ibgp>1 or ../maximum-load-balancing-ebgp>1 or ../maximum-load-balancing-eibgp) or ../load-balancing-eibgp-enable='false'" {
                    tailf:xpath-root 3;
                  }
                  default "false";
                  description
                    "Enable/disable EIBGP route load balancing.";
                }
                leaf ext-community-change {
                  type boolean;
                  default "false";
                  description
                    "Enable/disable the function to change the extended community attribute.";
                }
                leaf active-route-advertise {
                  type boolean;
                  default "false";
                  description
                    "Enable/disable the function to advertise the optimal routes in the RM module to peers.";
                }
                leaf nexthop-priority {
                  type nexthop-priority-address-type;
                  description
                    "Routes with next-hop IPv4 addresses and routes with next-hop IPv6 addresses coexist. If the next-hop address type is set to IPv4, routes with next-hop IPv4 addresses have a higher priority. If the next-hop address type is set to IPv6, routes with next-hop IPv6 addresses have a higher priority.";
                }
                leaf ebgp-interface-sensitive {
                  type boolean;
                  default "true";
                  description
                    "Enable/disable the function of EBGP interface fast sensing. If this function is enabled, the sessions of directly connected EBGP peers are immediately cleared from the associated interface when the interface becomes down.";
                }
                uses group-origin-as-validation-type;
                leaf advertise-route-mode {
                  when "../../../../../../../ni:name!='_public_'" {
                    tailf:xpath-root 3;
                  }
                  type bgp-advertise-route-mode;
                  default "all";
                  description
                    "VPN advertise route mode.";
                }
                leaf reoriginate-route {
                  when "../../../../../../../ni:name!='_public_'" {
                    tailf:xpath-root 3;
                  }
                  type boolean;
                  default "false";
                  description
                    "Enable/disable route reorigination.";
                }
                leaf rpd-policy-change-delay {
                  when "../../../../../../../ni:name='_public_'" {
                    tailf:xpath-root 3;
                  }
                  type uint16 {
                    range "0..180";
                  }
                  default "30";
                  description
                    "Specify the delay time of RPD policy's change.";
                }
              }
              uses bgp-route-preference-options;
              container nexthop-recursive-lookup {
                description
                  "Configure next hop iteration.";
                container common {
                  description
                    "Configure next hop iteration common options.";
                  uses nexthop-recursive-lookup-restrain;
                  uses nexthop-recursive-lookup-default-route;
                }
                uses nexthop-recursive-lookup-delay;
              }
              container import-routes {
                description
                  "List of imported routes.";
                list import-route {
                  key "protocol process-id";
                  description
                    "Configure route import. Routes of other protocol types can be imported by BGP. By default, BGP does not import routes of other protocol types.";
                  leaf protocol {
                    type bgp:ipv4-import-route-protocol-type;
                    description
                      "Routing protocol from which routes can be imported.";
                  }
                  leaf process-id {
                    type uint32 {
                      range "0..4294967295";
                    }
                    description
                      "Process ID of an imported routing protocol. The process ID is 0, if the imported routing protocol is direct routes, static routes, UNRs, or OP-routes. The process ID must be specified range from 1 to 4294967295, if the imported routing protocol is RIP, OSPF, ISIS.";
                  }
                  leaf med {
                    type uint32;
                    description
                      "Specifies the MED metric of the imported route.";
                  }
                  choice policy-type {
                    description
                      "Set route policy or filter.";
                    case rtp-ref {
                      description
                        "Route policy.";
                      leaf policy-name {
                        type leafref {
                          path "/ncs:devices/ncs:device/ncs:config/rtp:routing-policy/rtp:policy-definitions/rtp:policy-definition/rtp:name" {
                            tailf:xpath-root 3;
                          }
                        }
                        description
                          "When routes are imported from other routing protocols, the route-policy filter can be used to filter the routes and change route attributes.";
                      }
                    }
                    case xpl-ref {
                      description
                        "Route filter.";
                      uses route-filter-type;
                    }
                  }
                  leaf non-relay-tunnel {
                    when "../../../../../../../../ni:name='_public_'" {
                      tailf:xpath-root 3;
                    }
                    type boolean;
                    default "false";
                    description
                      "Enable/disable imported route relay a tunnel.";
                  }
                }
              }
              container aggregate-routes {
                description
                  "List of summarized routes.";
                list aggregate-route {
                  key "address mask-length";
                  description
                    "Configure a summarized route in the BGP routing table. The local outbound interface of the summarized route is Null0. When another router receives the route, the route adds an outbound interface to the route. If the Origin attributes of the specific routes for the route summarization are different, the Origin attribute of the summarized route is that with the highest priority. Origin attributes are arranged in the priority order of complete > egp > igp. A summarized route carries the community attribute of each specific route.";
                  // NCS expand uses statement
                  leaf address {
                    type inet:ip-address-no-zone;
                    description
                      "Specify the IPv4 address or IPv6 address of a summarized route. Only IPv4 summarized routes can be configured in the IPv4 address family and only IPv6 summarized routes can be configured in the IPv6 address family.";
                    must "not(contains(../address,':'))" {
                      tailf:xpath-root 3;
                    }
                  }
                  leaf mask-length {
                    type uint8 {
                      range "1..128";
                    }
                    description
                      "Specify the mask length of a summarized address.";
                    must '../mask-length<=32' {
                      tailf:xpath-root 3;
                    }
                  }
                  leaf as-set {
                    type boolean;
                    default "false";
                    description
                      "Enable/disable the generation of routes with the AS-SET attribute. This option can be used to create a summarized route. The AS_Path attribute of the summarized route contains the AS-Path attributes of the specific routes for the route summarization. Exercise caution when using this option if multiple AS_Paths need to be summarized to prevent route flapping.";
                  }
                  leaf detail-suppressed {
                    type boolean;
                    default "false";
                    description
                      "Enable/disable detail-suppressed. Suppress the advertisement of specific routes for the route summarization. Only the summarized route is advertised.";
                  }
                  choice policy-type {
                    description
                      "Set route policy or filter.";
                    case rtp-ref {
                      description
                        "Route policy.";
                      leaf attribute-policy {
                        type leafref {
                          path "/ncs:devices/ncs:device/ncs:config/rtp:routing-policy/rtp:policy-definitions/rtp:policy-definition/rtp:name" {
                            tailf:xpath-root 3;
                          }
                        }
                        description
                          "Specify an attribute of summarized routes. If apply as-path is used to configure the AS_Path attribute that is used in the route Summarization policy, and the as-set keyword is set, the AS_Path attribute in the policy does not take effect. This parameter and any of the following parameters overwrite each other: suppressFilter, originFilter, and attributeFilter.";
                      }
                      leaf origin-policy {
                        type leafref {
                          path "/ncs:devices/ncs:device/ncs:config/rtp:routing-policy/rtp:policy-definitions/rtp:policy-definition/rtp:name" {
                            tailf:xpath-root 3;
                          }
                        }
                        description
                          "Specify the name of a policy for generating summarized routes. Summarized routes are generated only when the routes match route-policy. This parameter and any of the following parameters overwrite each other: suppressFilter, originFilter, and attributeFilter.";
                      }
                      leaf suppress-policy {
                        type leafref {
                          path "/ncs:devices/ncs:device/ncs:config/rtp:routing-policy/rtp:policy-definitions/rtp:policy-definition/rtp:name" {
                            tailf:xpath-root 3;
                          }
                        }
                        description
                          "Specify a policy for suppressing the advertisement of specified routes. The routes matching the policy are not advertised, and other routes are advertised. This parameter and any of the following parameters overwrite each other: suppressFilter, originFilter, and attributeFilter.";
                      }
                    }
                    case xpl-ref {
                      description
                        "Route filter.";
                      leaf attribute-filter-name {
                        type leafref {
                          path "/ncs:devices/ncs:device/ncs:config/xpl:xpl/xpl:route-filters/xpl:route-filter/xpl:name" {
                            tailf:xpath-root 3;
                          }
                        }
                        description
                          "Specify a route-filter name.";
                      }
                      leaf attribute-filter-parameter {
                        when '../attribute-filter-name' {
                          tailf:xpath-root 3;
                        }
                        type xpl:filter-parameter-type;
                        description
                          "Specify a route-filter parameter.";
                      }
                      leaf origin-filter-name {
                        type leafref {
                          path "/ncs:devices/ncs:device/ncs:config/xpl:xpl/xpl:route-filters/xpl:route-filter/xpl:name" {
                            tailf:xpath-root 3;
                          }
                        }
                        description
                          "Specify a route-filter name.";
                      }
                      leaf origin-filter-parameter {
                        when '../origin-filter-name' {
                          tailf:xpath-root 3;
                        }
                        type xpl:filter-parameter-type;
                        description
                          "Specify a route-filter parameter.";
                      }
                      leaf suppress-filter-name {
                        type leafref {
                          path "/ncs:devices/ncs:device/ncs:config/xpl:xpl/xpl:route-filters/xpl:route-filter/xpl:name" {
                            tailf:xpath-root 3;
                          }
                        }
                        description
                          "Specify a route-filter name.";
                      }
                      leaf suppress-filter-parameter {
                        when '../suppress-filter-name' {
                          tailf:xpath-root 3;
                        }
                        type xpl:filter-parameter-type;
                        description
                          "Specify a route-filter parameter.";
                      }
                    }
                  }
                }
              }
              container aggregate-default-route {
                description
                  "Configure aggregate default route.";
                leaf origin-ip-prefix {
                  type leafref {
                    path "/ncs:devices/ncs:device/ncs:config/rtp:routing-policy/rtp:ipv4-prefix-filters/rtp:ipv4-prefix-filter/rtp:name" {
                      tailf:xpath-root 3;
                    }
                  }
                  description
                    "Specify the name of an IPv4 prefix list for a summary default route. Only the name of an IPv4 prefix list can be configured in a BGP IPv4 address family.";
                }
                leaf attribute-policy {
                  when '../origin-ip-prefix' {
                    tailf:xpath-root 3;
                  }
                  type leafref {
                    path "/ncs:devices/ncs:device/ncs:config/rtp:routing-policy/rtp:policy-definitions/rtp:policy-definition/rtp:name" {
                      tailf:xpath-root 3;
                    }
                  }
                  description
                    "Specify an attribute policy of a summary default route.";
                }
              }
              container network-routes {
                description
                  "List of network routes.";
                list network-route {
                  key "address mask-length";
                  description
                    "Configure a network route in the BGP routing table.";
                  uses network-route-ipv4;
                  leaf non-relay-tunnel {
                    when "../../../../../../../../ni:name='_public_'" {
                      tailf:xpath-root 3;
                    }
                    type boolean;
                    default "false";
                    description
                      "Enable/disable imported route relay a tunnel.";
                  }
                }
              }
              container advertise-route-to-evpns {
                when "../../../../../../ni:name!='_public_'" {
                  tailf:xpath-root 3;
                }
                description
                  "Configure advertise route protocol.";
                uses advertise-route-to-evpn-type;
              }
              container import-ribs {
                description
                  "List of imported RIBs configuration.";
                list import-rib {
                  key "source-vpn source-address-family";
                  description
                    "Configure imported RIBs.";
                  leaf source-vpn {
                    type leafref {
                      path "/ncs:devices/ncs:device/ncs:config/ni:network-instance/ni:instances/ni:instance/ni:name" {
                        tailf:xpath-root 3;
                      }
                    }
                    must '../../../../../../../../ni:name != current()' {
                      tailf:xpath-root 3;
                    }
                    description
                      "Source VPN name.";
                  }
                  leaf source-address-family {
                    type bgp:import-rib-ipv4-safi-type;
                    description
                      "Source address family type.";
                  }
                  leaf valid-route {
                    type boolean;
                    default "false";
                    description
                      "Enable/disable imported valid route.";
                  }
                  leaf include-label-route {
                    when "../source-address-family='ipv4uni'" {
                      tailf:xpath-root 3;
                    }
                    type boolean;
                    default "false";
                    description
                      "Enable/disable imported include label route.";
                  }
                  // NCS expand uses statement
                  choice policy-type {
                    case rtp-ref {
                      description
                        "Specify the route policy.";
                      leaf policy-name {
                        type leafref {
                          path "/ncs:devices/ncs:device/ncs:config/rtp:routing-policy/rtp:policy-definitions/rtp:policy-definition/rtp:name" {
                            tailf:xpath-root 3;
                          }
                        }
                        description
                          "Specify the route policy.";
                      }
                    }
                    case xpl-ref {
                      description
                        "Route filter.";
                      uses route-filter-type;
                    }
                    description
                      "Specify the route-policy or filter for imported RIBs.";
                  }
                }
              }
              uses ipv4-import-filter-protocol-type;
              container export-filter-policys {
                description
                  "List of filtering policies.";
                list export-filter-policy {
                  key "protocol process-id";
                  description
                    "Apply a filtering policy. It is used to filter the routes to be advertised to the peer. By default, routes are not filtered.";
                  leaf protocol {
                    type bgp:ipv4-export-filter-protocol-type;
                    description
                      "Specify the name of a routing protocol. The routing protocol takes effect only on the routes to be advertised. The IPv4 address family supports the direct, IS-IS, OSPF, RIP, and static routing protocols. The IPv6 unicast address family of a public network instance supports the direct, IS-IS, OSPFv3, RIPng, and static routing protocols. The IPv6 address family of a VPNv6 instance supports the direct, IS-IS, RIPng, and static routing protocols.";
                  }
                  leaf process-id {
                    type uint32 {
                      range "0..4294967295";
                    }
                    description
                      "Specify the process ID required to be matched. The value is an integer ranging from 0 to 4294967295. If direct or static routes need to be filtered, no process ID is required.";
                  }
                  uses ipv4-filter-protocol-policy-choice-type;
                }
              }
              container lsp-options {
                description
                  "Configure parameters for lsp.";
                uses safi-lsp-options;
                leaf maximum-load-balancing-transit {
                  when "../../../../../../../ni:name='_public_'" {
                    tailf:xpath-root 3;
                  }
                  type uint16 {
                    range "1..65535";
                  }
                  default "1";
                  description
                    "Maximum number of transit LSPs for load balancing.";
                }
                leaf unicast-rt-label-advertise {
                  when "../../../../../../../ni:name='_public_'" {
                    tailf:xpath-root 3;
                  }
                  type boolean;
                  default "false";
                  description
                    "Enable/disable a device to convert received IPv4 public network unicast routes to labeled routes by allocating one BGP label to each route and advertise the labeled routes to peers with the labeled route exchange capability.";
                }
                leaf unicast-rt-label-advertise-popgo {
                  when "../unicast-rt-label-advertise = 'true'" {
                    tailf:xpath-root 3;
                  }
                  type boolean;
                  default "false";
                  description
                    "Enable/disable a device to convert received IPv4 public network unicast routes to labeled routes by adding a BGP label to each route and advertise the labeled routes to peers with the labeled route exchange capability. If the IP address of an outbound interface is reachable but no LSP is reachable, traffic is forwarded through the outbound interface and a specific next hop, during which the label POPGO action is performed.";
                }
                leaf lsp-operation {
                  when "../../../../../../../ni:name='_public_'" {
                    tailf:xpath-root 3;
                  }
                  type lsp-operation-type;
                  default "pop";
                  description
                    "Label operation type.";
                }
                uses ingress-choice-policy-set;
              }
              container segment-routing-ipv6 {
                description
                  "Configure BGP segment-routing IPv6.";
                leaf srv6-best-effort-enable {
                  type empty;
                  description
                    "Enable SRv6 BE iteration.";
                }
                leaf srv6-traffic-engineer-enable {
                  type empty;
                  description
                    "Enable SRv6 TE iteration.";
                }
              }
              uses vrf-af-dampening-routes;
              uses bgp:slow-peer-type;
              // NCS expand uses statement
              container routing-table-rib-only {
                description
                  "Configure disable route delivery to the IP routing table.";
                leaf enable {
                  type boolean;
                  default "false";
                  description
                    "Enable/disable prevent BGP routes from being added to the IP routing table.";
                  must "not (../../common/active-route-advertise = 'true' and ../enable = 'true')" {
                    tailf:xpath-root 3;
                  }
                }
                choice policy-type {
                  description
                    "Set route policy or filter.";
                  case rtp-ref {
                    description
                      "Route policy.";
                    leaf policy-name {
                      when "../enable = 'true'" {
                        tailf:xpath-root 3;
                      }
                      type leafref {
                        path "/ncs:devices/ncs:device/ncs:config/rtp:routing-policy/rtp:policy-definitions/rtp:policy-definition/rtp:name" {
                          tailf:xpath-root 3;
                        }
                      }
                      description
                        "When routes are imported from other routing protocols, the route-policy filter can be used to filter the routes and change route attributes.";
                    }
                  }
                  case xpl-ref {
                    description
                      "Route filter.";
                    leaf filter-name {
                      when "../enable = 'true'" {
                        tailf:xpath-root 3;
                      }
                      type leafref {
                        path "/ncs:devices/ncs:device/ncs:config/xpl:xpl/xpl:route-filters/xpl:route-filter/xpl:name" {
                          tailf:xpath-root 3;
                        }
                      }
                      description
                        "Specify a route-filter name.";
                    }
                    leaf filter-parameter {
                      when '../filter-name' {
                        tailf:xpath-root 3;
                      }
                      type xpl:filter-parameter-type;
                      description
                        "Specify a route-filter parameter.";
                    }
                  }
                }
              }
              uses qos-local-id-type;
            }
            container ipv6-unicast {
              when "../type = 'ipv6uni'" {
                tailf:xpath-root 3;
              }
              description
                "Configure IPv6 unicast options.";
              container common {
                description
                  "Configure IPv6 unicast common options.";
                leaf auto-frr {
                  type boolean;
                  default "false";
                  description
                    "Enable/disable BGP auto FRR. If IP FRR, VPN FRR, and Auto FRR are all enabled, IP FRR and VPN FRR take precedence over Auto FRR. If a route fails to match the routing policy of IP FRR or VPN FRR, Auto FRR takes effect.";
                }
                leaf route-select-delay {
                  type uint16 {
                    range "0..3600";
                  }
                  units "s";
                  default "0";
                  description
                    "Route selection delay.";
                }
                uses reflector-cluster-type;
                uses reflect-type;
                leaf maximum-load-balancing-ibgp {
                  type uint16 {
                    range "1..65535";
                  }
                  default "1";
                  description
                    "Specify the maximum number of equal-cost IBGP routes.";
                }
                leaf maximum-load-balancing-ebgp {
                  type uint16 {
                    range "1..65535";
                  }
                  default "1";
                  description
                    "Specify the maximum number of equal-cost EBGP routes.";
                }
                leaf explicit-null {
                  when "../../../../../../../ni:name='_public_'" {
                    tailf:xpath-root 3;
                  }
                  type boolean;
                  must "not(../lsp-operation='pop-go' and ../explicit-null='true')" {
                    tailf:xpath-root 3;
                  }
                  default "false";
                  description
                    "Enable/disable the function to explicit null. After 6PE routes are enabled to share a single label, all routes share the explicit-null label 2 when the 6PE sends IPv6 routes to its 6PE peer. This can save label resources on the 6PE. Therefore, when there are a large number of IPv6 routes that need to be sent, the problem that the IPv6 routes cannot be forwarded due to the shortage of labels can be avoided.";
                }
                leaf lsp-operation {
                  when "../../../../../../../ni:name='_public_'" {
                    tailf:xpath-root 3;
                  }
                  type lsp-operation-type;
                  must "not(../lsp-operation='pop-go' and ../explicit-null='true')" {
                    tailf:xpath-root 3;
                  }
                  default "pop";
                  description
                    "Label operation mode.";
                }
                leaf nexthop-select-depend-type {
                  when "../../../../../../../ni:name='_public_'" {
                    tailf:xpath-root 3;
                  }
                  type select-depend-type;
                  default "depend-tunnel";
                  description
                    "Specify the route iteration mode: IP or tunnel. In tunnel mode, the labeled BGP IPv4 route can participate in route selection only after its next hop is iterated to an LSP. In IP
                     mode, the labeled BGP IPv4 route can participate in route selection only after its next hop is iterated to an IP address. By default, the labeled BGP IPv4 route can participate in route selection
                     if its next hop can be iterated to an IP address, regardless of whether the LSP of the next hop exists. This allows the RR that is not enabled with MPLS to forward labeled routes. In non-RR
                     networking or RR networking where the BGP next hop is changed, BGP needs to check whether there is an LSP destined for the next hop. If such an LSP is not found, BGP needs to establish an LSP in
                     advance. If the default setting is adopted, a labeled BGP IPv4 unicast route may be selected prior to LSP establishment. As a result, services are incorrectly switched before LSP establishment and
                     service stability is affected. Therefore, allow route selection only after the labeled BGP IPv4 route is iterated to an LSP.";
                }
                leaf nexthop-inherit-ip-cost {
                  when "../nexthop-select-depend-type='depend-tunnel'" {
                    tailf:xpath-root 3;
                  }
                  type boolean;
                  default "false";
                  description
                    "Enable/disable next hop iteration mode to IP. Specify the route iteration mode: IP or tunnel. In tunnel mode, the labeled BGP IPv4 route can participate in route selection only after its next hop is iterated to an LSP.";
                }
                leaf nexthop-resolve-aigp {
                  when "../../../../../../../ni:name!='_public_'" {
                    tailf:xpath-root 3;
                  }
                  type boolean;
                  default "false";
                  description
                    "Enable/disable route with AIGP attribute for route selection.";
                }
                leaf always-compare-med {
                  type boolean;
                  default "false";
                  description
                    "Enable/disable BGP to compare the MEDs of routes from peers in different ASs in route selection. If
                     there are multiple reachable routes to the same destination, the route with the smallest MED is preferred. Do not use this option unless different ASs use the same IGP and route selection mode.";
                }
                leaf default-med {
                  type uint32;
                  default "0";
                  description
                    "Specify the Multi-Exit-Discriminator (MED) of BGP routes. The value is an integer. This value is valid only for the imported routes and BGP summarized routes on the local router.";
                }
                leaf nexthop-third-party {
                  type boolean;
                  default "false";
                  description
                    "Enable/disable BGP third-party next hop.";
                }
                leaf supernet-unicast-advertise {
                  type boolean;
                  default "false";
                  description
                    "Enable/disable advertise supernet unicast routes.";
                }
                leaf bestroute-med-confederation {
                  when "../../../../../../../ni:name='_public_'" {
                    tailf:xpath-root 3;
                  }
                  type boolean;
                  default "false";
                  description
                    "Enable/disable BGP to compare Med value only within the federation.";
                }
                leaf bestroute-as-path-ignore {
                  type boolean;
                  must "../bestroute-as-path-ignore = 'false' or ../load-balanc-as-path-ignore ='false'" {
                    tailf:xpath-root 3;
                  }
                  default "false";
                  description
                    "Enable/disable BGP to ignore the AS_Path attribute when selecting the optimal route. By default, BGP uses the AS_Path attribute as one of route selection rules, and a route with a shorter AS_Path is preferred. After bestroute-as-path-ignore is selected, BGP does not compare the AS_Path length.";
                }
                leaf determin-med {
                  type boolean;
                  default "false";
                  description
                    "Enable/disable deterministic MED so that the route selection result is relevant to the sequence in which routes are received.";
                }
                leaf best-external {
                  when "../../../../../../../ni:name='_public_'" {
                    tailf:xpath-root 3;
                  }
                  type boolean;
                  must "../best-external ='false' or ../determin-med ='false'" {
                    tailf:xpath-root 3;
                  }
                  default "false";
                  description
                    "Enable/disable best external route selection.";
                }
                leaf attribute-set-enable {
                  when "../../../../../../../ni:name!='_public_'" {
                    tailf:xpath-root 3;
                  }
                  type boolean;
                  default "false";
                  description
                    "Enable/disable the capability of processing attribute set.";
                }
                leaf attribute-set-mode {
                  when "../attribute-set-enable='true'" {
                    tailf:xpath-root 3;
                  }
                  type bgp:attribute-set-type;
                  default "both";
                  description
                    "The processing mode of attribute set.";
                }
                leaf add-path-select-num {
                  when "../../../../../../../ni:name='_public_'" {
                    tailf:xpath-root 3;
                  }
                  type uint8 {
                    range "2..64";
                  }
                  must "../determin-med ='false'" {
                    tailf:xpath-root 3;
                  }
                  description
                    "Number of add-path routes.";
                }
                leaf load-balanc-igp-metric-ignore {
                  type boolean;
                  default "false";
                  description
                    "Enable/disable BGP to ignore the IGP cost of each BGP route to the next hop when selecting routes for load balancing. By default, only the routes with the same IGP cost can participate in load balancing.";
                }
                leaf load-balanc-as-path-ignore {
                  type boolean;
                  must "../load-balanc-as-path-ignore ='false' or (../load-balanc-as-path-relax ='false' and ../bestroute-as-path-ignore ='false')" {
                    tailf:xpath-root 3;
                  }
                  default "false";
                  description
                    "Enable/disable BGP to ignore the AS_Path of each BGP route to the next hop when selecting routes for load balancing. By default, only the routes with the same AS_Path can participate in load balancing.";
                }
                leaf load-balanc-as-path-relax {
                  type boolean;
                  must "../load-balanc-as-path-relax ='false' or ../load-balanc-as-path-ignore ='false'" {
                    tailf:xpath-root 3;
                  }
                  default "false";
                  description
                    "Enable/disable BGP to ignore comparison of AS_Path attributes with the same length. By default, only the routes with the same AS_Path can participate in load balancing.";
                }
                leaf default-local-preference {
                  type uint32 {
                    range "0..4294967295";
                  }
                  default "100";
                  description
                    "The local preference of BGP routes.";
                }
                leaf default-route-import {
                  type boolean;
                  default "false";
                  description
                    "Enable/disable the function to import default routes into the BGP routing table. Default-route-imported must be used with import-routes so that default routes can be imported to the BGP routing table. If only import-routes is used, no default routes can be added to the BGP routing table. In addition, default-route-imported can only import the default routes in the routing table into the BGP routing table.";
                }
                leaf routerid-neglect {
                  type boolean;
                  default "false";
                  description
                    "Enable/disable BGP to ignore router IDs when selecting the optimal route. Comparing router IDs is the last resort in route selection. This means that if one optimal route must be selected and no other parameters can be used to break the tie, router IDs can be used. If this option is selected, the first received route will be selected as the optimal route, and BGP will ignore the router ID and peer address in route selection.";
                }
                leaf maximum-load-balancing {
                  type uint16 {
                    range "1..65535";
                  }
                  default "1";
                  description
                    "Specify the maximum number of equal-cost routes in the BGP routing table. The value depends on the associated license. Equal-cost BGP routes can be generated for load balancing only when the BGP routes meet the first nine rules of the route-selection policy and have the same AS-Path attribute.";
                }
                leaf reflect-between-client {
                  type boolean;
                  default "true";
                  description
                    "Enable/disable route reflection between clients. If clients of a route reflector (RR) are fully meshed, you can disable route reflection among clients to reduce the cost.";
                }
                leaf best-route-bit-error-detection {
                  when "../../../../../../../ni:name!='_public_'" {
                    tailf:xpath-root 3;
                  }
                  type boolean;
                  default "false";
                  description
                    "Enable/disable the function to reroute traffic when a bit error event occurs.";
                }
                leaf import-rib-nexthop-invariable {
                  when "../../../../../../../ni:name!='_public_'" {
                    tailf:xpath-root 3;
                  }
                  type boolean;
                  default "false";
                  description
                    "Enable/disable advertise the route without modifying the next-hop.";
                }
                leaf route-relay-tunnel-v4 {
                  type boolean;
                  default "false";
                  description
                    "Enable/disable unicast-route recursive-lookup tunnel.";
                }
                leaf route-relay-tunnel-v4-selector {
                  when "../route-relay-tunnel-v4='true'" {
                    tailf:xpath-root 3;
                  }
                  type leafref {
                    path "/ncs:devices/ncs:device/ncs:config/rtp:routing-policy/rtp:tunnel-selectors/rtp:tunnel-selector/rtp:name" {
                      tailf:xpath-root 3;
                    }
                  }
                  description
                    "Unicast route tunnel selector name.";
                }
                leaf route-relay-tunnel-v6-selector {
                  when "../../../../../../../ni:name='_public_'" {
                    tailf:xpath-root 3;
                  }
                  type leafref {
                    path "/ncs:devices/ncs:device/ncs:config/rtp:routing-policy/rtp:tunnel-selectors/rtp:tunnel-selector/rtp:name" {
                      tailf:xpath-root 3;
                    }
                  }
                  description
                    "Enable/disable unicast route recursive-lookup IPv6 tunnel by tunnel selector name.";
                }
                uses bestroute-med-plus-igp-type;
                uses bestroute-router-id-prior-clusterlist-type;
                leaf bestroute-med-none-as-maximum {
                  type boolean;
                  default "false";
                  description
                    "Enable/disable BGP considers its MED as the largest MED value (4294967295). If a route does not carry MED, BGP considers its MED as the default value (0) during route selection.";
                }
                leaf bestroute-rd-large-first {
                  when "../../../../../../../ni:name!='_public_'" {
                    tailf:xpath-root 3;
                  }
                  type boolean;
                  default "false";
                  description
                    "Enable/disable a BGP device to select the route with the largest route distinguisher (RD) during route selection.";
                }
                leaf nexthop-priority {
                  when "../../../../../../../ni:name!='_public_'" {
                    tailf:xpath-root 3;
                  }
                  type nexthop-priority-address-type;
                  description
                    "In the VRF instance, routes with next-hop IPv4 addresses and routes with next-hop IPv6 addresses coexist. If the next-hop address type is set to IPv4, routes with next-hop IPv4 addresses have a higher priority. If the next-hop address type is set to IPv6, routes with next-hop IPv6 addresses have a higher priority.";
                }
                leaf ebgp-ecmp-nexthop-changed {
                  when '../maximum-load-balancing-ebgp and ../maximum-load-balancing-ebgp>1' {
                    tailf:xpath-root 3;
                  }
                  type boolean;
                  default "false";
                  description
                    "Enable/disable next hop of equal-cost EBGP routes is changed. Enable/disable next hop of equal-cost EBGP routes is changed. When equal-cost EBGP routes are load-balancing traffic, the next hop of these routes is changed to a local interface before these routes are advertised. This function can be enabled only when the maximum number of equal-cost EBGP routes is greater than 1.";
                }
                leaf ibgp-ecmp-nexthop-changed {
                  when '../maximum-load-balancing-ibgp and ../maximum-load-balancing-ibgp>1' {
                    tailf:xpath-root 3;
                  }
                  type boolean;
                  default "false";
                  description
                    "Enable/disable next hop of equal-cost IBGP routes is changed. When equal-cost IBGP routes are load-balancing traffic, the next hop of these routes is changed to a local interface before these routes are advertised. This function can be enabled only when the maximum number of equal-cost IBGP routes is greater than 1.";
                }
                leaf ecmp-nexthop-changed {
                  when '../maximum-load-balancing and ../maximum-load-balancing>1' {
                    tailf:xpath-root 3;
                  }
                  type boolean;
                  default "false";
                  description
                    "Enable/disable next hop of equal-cost routes is changed. When equal-cost BGP routes are load-balancing traffic, the next hop of these routes is changed to a local interface before these routes are advertised. This function can be enabled only when the maximum number of equal-cost BGP routes is greater than 1.";
                }
                leaf maximum-load-balancing-eibgp {
                  when "../../../../../../../ni:name!='_public_'" {
                    tailf:xpath-root 3;
                  }
                  type uint16 {
                    range "1..65535";
                  }
                  must "../maximum-load-balancing-ibgp=1 and ../maximum-load-balancing-ebgp=1 and ../maximum-load-balancing=1 and ../load-balancing-eibgp-enable='false'" {
                    tailf:xpath-root 3;
                  }
                  description
                    "Specify the maximum number of equal-cost EBGP routes and IBGP routes. After the attribute is set, load balancing is performed among equal-cost BGP VPN routes, regardless of the route type, EBGP or IBGP.";
                }
                leaf eibgp-ecmp-nexthop-changed {
                  when '../maximum-load-balancing-eibgp' {
                    tailf:xpath-root 3;
                  }
                  type boolean;
                  default "false";
                  description
                    "Enable/disable next hop of equal-cost EBGP and IBGP routes is changed. When equal-cost EBGP and IBGP routes are load-balancing traffic, the next hop of these routes is changed to a local interface before these routes are advertised.";
                }
                leaf load-balancing-eibgp-enable {
                  when "../../../../../../../ni:name!='_public_'" {
                    tailf:xpath-root 3;
                  }
                  type boolean;
                  must "not (../maximum-load-balancing-ibgp>1 or ../maximum-load-balancing-ebgp>1 or ../maximum-load-balancing-eibgp) or ../load-balancing-eibgp-enable='false'" {
                    tailf:xpath-root 3;
                  }
                  default "false";
                  description
                    "Enable/disable EIBGP route load balancing.";
                }
                leaf ext-community-change {
                  type boolean;
                  default "false";
                  description
                    "Enable/disable the function to change the extended community attribute.";
                }
                leaf active-route-advertise {
                  type boolean;
                  default "false";
                  description
                    "Enable/disable the function to advertise the optimal routes in the RM module to peers.";
                }
                leaf ebgp-interface-sensitive {
                  type boolean;
                  default "true";
                  description
                    "Enable/disable the function of EBGP interface fast sensing. If this function is enabled, the sessions of directly connected EBGP peers are immediately cleared from the associated interface when the interface becomes down.";
                }
                uses group-origin-as-validation-type;
                leaf advertise-route-mode {
                  when "../../../../../../../ni:name!='_public_'" {
                    tailf:xpath-root 3;
                  }
                  type bgp-advertise-route-mode;
                  default "all";
                  description
                    "VPN advertise route mode.";
                }
              }
              uses bgp-route-preference-options;
              container nexthop-recursive-lookup {
                description
                  "Configure next hop iteration.";
                container common {
                  description
                    "Configure next hop iteration common options.";
                  uses nexthop-recursive-lookup-restrain;
                  uses nexthop-recursive-lookup-default-route;
                }
                uses nexthop-recursive-lookup-delay;
              }
              container import-routes {
                description
                  "List of imported routes.";
                list import-route {
                  key "protocol process-id";
                  description
                    "Configure route import. Routes of other protocol types can be imported by BGP. By default, BGP does not import routes of other protocol types.";
                  leaf protocol {
                    type bgp:ipv6-import-route-protocol-type;
                    description
                      "Routing protocol from which routes can be imported.";
                  }
                  leaf process-id {
                    type uint32 {
                      range "0..4294967295";
                    }
                    description
                      "Process ID of an imported routing protocol. The process ID is 0, if the imported routing protocol is direct routes, static routes, UNRs, or OP-routes. The process ID must be specified range from 1 to 4294967295, if the imported routing protocol is ISIS, RIPng, or OSPFv3.";
                  }
                  leaf med {
                    type uint32;
                    description
                      "Specifies the MED metric of the imported route.";
                  }
                  choice policy-type {
                    description
                      "Set route policy or filter.";
                    case rtp-ref {
                      description
                        "Route policy.";
                      leaf policy-name {
                        type leafref {
                          path "/ncs:devices/ncs:device/ncs:config/rtp:routing-policy/rtp:policy-definitions/rtp:policy-definition/rtp:name" {
                            tailf:xpath-root 3;
                          }
                        }
                        description
                          "When routes are imported from other routing protocols, the route-policy filter can be used to filter the routes and change route attributes.";
                      }
                    }
                    case xpl-ref {
                      description
                        "Route filter.";
                      uses route-filter-type;
                    }
                  }
                }
              }
              container aggregate-routes {
                description
                  "List of summarized routes.";
                list aggregate-route {
                  key "address mask-length";
                  description
                    "Configure a summarized route in the BGP routing table. The local outbound interface of the summarized route is Null0. When another router receives the route, the route adds an outbound interface to the route. By default, route summarization is not performed. If the Origin attributes of the specific routes for the route summarization are different, the Origin attribute of the summarized route is that with the highest priority. Origin attributes are arranged in the priority order of complete > egp > igp. A summarized route carries the community attribute of each specific route.";
                  // NCS expand uses statement
                  leaf address {
                    type inet:ip-address-no-zone;
                    description
                      "Specify the IPv4 address or IPv6 address of a summarized route. Only IPv4 summarized routes can be configured in the IPv4 address family and only IPv6 summarized routes can be configured in the IPv6 address family.";
                    must "contains(../address,':')" {
                      tailf:xpath-root 3;
                    }
                  }
                  leaf mask-length {
                    type uint8 {
                      range "1..128";
                    }
                    description
                      "Specify the mask length of a summarized address.";
                    must '../mask-length<=128' {
                      tailf:xpath-root 3;
                    }
                  }
                  leaf as-set {
                    type boolean;
                    default "false";
                    description
                      "Enable/disable the generation of routes with the AS-SET attribute. This option can be used to create a summarized route. The AS_Path attribute of the summarized route contains the AS-Path attributes of the specific routes for the route summarization. Exercise caution when using this option if multiple AS_Paths need to be summarized to prevent route flapping.";
                  }
                  leaf detail-suppressed {
                    type boolean;
                    default "false";
                    description
                      "Enable/disable detail-suppressed. Suppress the advertisement of specific routes for the route summarization. Only the summarized route is advertised.";
                  }
                  choice policy-type {
                    description
                      "Set route policy or filter.";
                    case rtp-ref {
                      description
                        "Route policy.";
                      leaf attribute-policy {
                        type leafref {
                          path "/ncs:devices/ncs:device/ncs:config/rtp:routing-policy/rtp:policy-definitions/rtp:policy-definition/rtp:name" {
                            tailf:xpath-root 3;
                          }
                        }
                        description
                          "Specify an attribute of summarized routes. If apply as-path is used to configure the AS_Path attribute that is used in the route Summarization policy, and the as-set keyword is set, the AS_Path attribute in the policy does not take effect. This parameter and any of the following parameters overwrite each other: suppressFilter, originFilter, and attributeFilter.";
                      }
                      leaf origin-policy {
                        type leafref {
                          path "/ncs:devices/ncs:device/ncs:config/rtp:routing-policy/rtp:policy-definitions/rtp:policy-definition/rtp:name" {
                            tailf:xpath-root 3;
                          }
                        }
                        description
                          "Specify the name of a policy for generating summarized routes. Summarized routes are generated only when the routes match route-policy. This parameter and any of the following parameters overwrite each other: suppressFilter, originFilter, and attributeFilter.";
                      }
                      leaf suppress-policy {
                        type leafref {
                          path "/ncs:devices/ncs:device/ncs:config/rtp:routing-policy/rtp:policy-definitions/rtp:policy-definition/rtp:name" {
                            tailf:xpath-root 3;
                          }
                        }
                        description
                          "Specify a policy for suppressing the advertisement of specified routes. The routes matching the policy are not advertised, and other routes are advertised. This parameter and any of the following parameters overwrite each other: suppressFilter, originFilter, and attributeFilter.";
                      }
                    }
                    case xpl-ref {
                      description
                        "Route filter.";
                      leaf attribute-filter-name {
                        type leafref {
                          path "/ncs:devices/ncs:device/ncs:config/xpl:xpl/xpl:route-filters/xpl:route-filter/xpl:name" {
                            tailf:xpath-root 3;
                          }
                        }
                        description
                          "Specify a route-filter name.";
                      }
                      leaf attribute-filter-parameter {
                        when '../attribute-filter-name' {
                          tailf:xpath-root 3;
                        }
                        type xpl:filter-parameter-type;
                        description
                          "Specify a route-filter parameter.";
                      }
                      leaf origin-filter-name {
                        type leafref {
                          path "/ncs:devices/ncs:device/ncs:config/xpl:xpl/xpl:route-filters/xpl:route-filter/xpl:name" {
                            tailf:xpath-root 3;
                          }
                        }
                        description
                          "Specify a route-filter name.";
                      }
                      leaf origin-filter-parameter {
                        when '../origin-filter-name' {
                          tailf:xpath-root 3;
                        }
                        type xpl:filter-parameter-type;
                        description
                          "Specify a route-filter parameter.";
                      }
                      leaf suppress-filter-name {
                        type leafref {
                          path "/ncs:devices/ncs:device/ncs:config/xpl:xpl/xpl:route-filters/xpl:route-filter/xpl:name" {
                            tailf:xpath-root 3;
                          }
                        }
                        description
                          "Specify a route-filter name.";
                      }
                      leaf suppress-filter-parameter {
                        when '../suppress-filter-name' {
                          tailf:xpath-root 3;
                        }
                        type xpl:filter-parameter-type;
                        description
                          "Specify a route-filter parameter.";
                      }
                    }
                  }
                }
              }
              container aggregate-default-route {
                description
                  "Configure aggregate default route.";
                leaf origin-ipv6-prefix {
                  type leafref {
                    path "/ncs:devices/ncs:device/ncs:config/rtp:routing-policy/rtp:ipv6-prefix-filters/rtp:ipv6-prefix-filter/rtp:name" {
                      tailf:xpath-root 3;
                    }
                  }
                  description
                    "Specify the name of an IPv6 prefix list for a summary default route. Only the name of an IPv6 prefix list can be configured in a BGP IPv6 address family.";
                }
                leaf attribute-policy {
                  when '../origin-ipv6-prefix' {
                    tailf:xpath-root 3;
                  }
                  type leafref {
                    path "/ncs:devices/ncs:device/ncs:config/rtp:routing-policy/rtp:policy-definitions/rtp:policy-definition/rtp:name" {
                      tailf:xpath-root 3;
                    }
                  }
                  description
                    "Specify an attribute policy of a summary default route.";
                }
              }
              container network-routes {
                description
                  "List of network routes.";
                list network-route {
                  key "address mask-length";
                  description
                    "Configure a network route in the BGP routing table.";
                  uses network-route-ipv6;
                }
              }
              container advertise-route-to-evpns {
                when "../../../../../../ni:name!='_public_'" {
                  tailf:xpath-root 3;
                }
                description
                  "Configure advertise route protocol.";
                uses advertise-route-to-evpn-type;
              }
              container import-ribs {
                description
                  "List of imported RIBs configuration.";
                list import-rib {
                  key "source-vpn source-address-family";
                  description
                    "Configure imported RIBs.";
                  leaf source-vpn {
                    type leafref {
                      path "/ncs:devices/ncs:device/ncs:config/ni:network-instance/ni:instances/ni:instance/ni:name" {
                        tailf:xpath-root 3;
                      }
                    }
                    must '../../../../../../../../ni:name != current()' {
                      tailf:xpath-root 3;
                    }
                    description
                      "Source VPN name for imported RIBs.";
                  }
                  leaf source-address-family {
                    type bgp:import-rib-ipv6-safi-type;
                    description
                      "Source address family type for imported RIBs.";
                  }
                  leaf valid-route {
                    type boolean;
                    default "false";
                    description
                      "Enable/disable imported valid route.";
                  }
                  leaf include-label-route {
                    type boolean;
                    default "false";
                    description
                      "Enable/disable imported include label route.";
                  }
                  // NCS expand uses statement
                  choice policy-type {
                    case rtp-ref {
                      description
                        "Specify the route policy.";
                      leaf policy-name {
                        type leafref {
                          path "/ncs:devices/ncs:device/ncs:config/rtp:routing-policy/rtp:policy-definitions/rtp:policy-definition/rtp:name" {
                            tailf:xpath-root 3;
                          }
                        }
                        description
                          "Specify the route policy.";
                      }
                    }
                    case xpl-ref {
                      description
                        "Route filter.";
                      uses route-filter-type;
                    }
                    description
                      "Specify the route-policy or filter for imported RIBs.";
                  }
                }
              }
              container segment-routing-ipv6 {
                when "../../../../../../ni:name='_public_'" {
                  tailf:xpath-root 3;
                }
                description
                  "Configure BGP segment-routing IPv6.";
                leaf srv6-best-effort-enable {
                  type empty;
                  description
                    "Enable SRv6 BE iteration.";
                }
                leaf srv6-traffic-engineer-enable {
                  type empty;
                  description
                    "Enable SRv6 TE iteration.";
                }
              }
              uses vrf-af-dampening-routes;
              uses ipv6-import-filter-protocol-type;
              uses ipv6-export-filter-protocol-type;
              uses bgp:slow-peer-type;
              // NCS expand uses statement
              container routing-table-rib-only {
                description
                  "Configure disable route delivery to the IP routing table.";
                leaf enable {
                  type boolean;
                  default "false";
                  description
                    "Enable/disable prevent BGP routes from being added to the IP routing table.";
                  must "not (../../common/active-route-advertise = 'true' and ../enable = 'true')" {
                    tailf:xpath-root 3;
                  }
                }
                choice policy-type {
                  description
                    "Set route policy or filter.";
                  case rtp-ref {
                    description
                      "Route policy.";
                    leaf policy-name {
                      when "../enable = 'true'" {
                        tailf:xpath-root 3;
                      }
                      type leafref {
                        path "/ncs:devices/ncs:device/ncs:config/rtp:routing-policy/rtp:policy-definitions/rtp:policy-definition/rtp:name" {
                          tailf:xpath-root 3;
                        }
                      }
                      description
                        "When routes are imported from other routing protocols, the route-policy filter can be used to filter the routes and change route attributes.";
                    }
                  }
                  case xpl-ref {
                    description
                      "Route filter.";
                    leaf filter-name {
                      when "../enable = 'true'" {
                        tailf:xpath-root 3;
                      }
                      type leafref {
                        path "/ncs:devices/ncs:device/ncs:config/xpl:xpl/xpl:route-filters/xpl:route-filter/xpl:name" {
                          tailf:xpath-root 3;
                        }
                      }
                      description
                        "Specify a route-filter name.";
                    }
                    leaf filter-parameter {
                      when '../filter-name' {
                        tailf:xpath-root 3;
                      }
                      type xpl:filter-parameter-type;
                      description
                        "Specify a route-filter parameter.";
                    }
                  }
                }
              }
              uses ipv6-qos-local-id-type;
            }
            container ipv4-vpn {
              when "../type = 'ipv4vpn'" {
                tailf:xpath-root 3;
              }
              description
                "Configure IPv4 VPNv4 options.";
              uses vpn-target-type;
              uses reflector-cluster-type;
              uses reflect-type;
              leaf auto-frr {
                type boolean;
                default "false";
                description
                  "Enable/disable BGP Auto FRR. If IP FRR, VPN FRR, and Auto FRR are all enabled, IP FRR and VPN FRR take precedence over Auto FRR. If a route fails to match the routing policy of IP FRR or VPN FRR, Auto FRR takes effect.";
              }
              leaf tunnel-selector-name {
                type leafref {
                  path "/ncs:devices/ncs:device/ncs:config/rtp:routing-policy/rtp:tunnel-selectors/rtp:tunnel-selector/rtp:name" {
                    tailf:xpath-root 3;
                  }
                }
                description
                  "Configure a tunnel selector and apply it to the BGP IPv4 unicast, BGP VPNv4 address families and BGP VPNv6 address families so that IPv4,VPNv4 and VPNv6 labeled routes can be iterated to tunnels based on the tunnel selector.";
              }
              leaf route-select-delay {
                type uint16 {
                  range "0..3600";
                }
                units "s";
                default "0";
                description
                  "Route selection delay.";
              }
              leaf apply-label-mode {
                type apply-label-type;
                default "per-route";
                description
                  "Method of distributing labels to VPNV4 and VPNV6 routes. The way which assigns the label depends on the paf value. If there are a large number of routes, assign a label for the routes that have same nexthop and out-label. This allows all routes which have same nexthop and out-label to use one label.";
              }
              leaf nexthop-select-depend-type {
                type select-depend-type-ext;
                default "depend-ip";
                description
                  "In none mode, route selection does not depend on whether the next hop is reachable. In tunnel mode, the labeled BGP IPv4 route can participate in route selection only after its next hop is iterated to an LSP. In IP
                   mode, the labeled BGP IPv4 route can participate in route selection only after its next hop is iterated to an IP address. By default, the labeled BGP IPv4 route can participate in route selection
                   if its next hop can be iterated to an IP address, regardless of whether the LSP of the next hop exists. This allows the RR that is not enabled with MPLS to forward labeled routes. In non-RR
                   networking or RR networking where the BGP next hop is changed, BGP needs to check whether there is an LSP destined for the next hop. If such an LSP is not found, BGP needs to establish an LSP in
                   advance. If the default setting is adopted, a labeled BGP IPv4 unicast route may be selected prior to LSP establishment. As a result, services are incorrectly switched before LSP establishment and
                   service stability is affected. Therefore, allow route selection only after the labeled BGP IPv4 route is iterated to an LSP.";
              }
              leaf default-med {
                type uint32;
                default "0";
                description
                  "Specify the Multi-Exit-Discriminator (MED) of BGP routes. The value is an integer. This value is valid only for the imported routes and BGP summarized routes on the local router.";
              }
              leaf best-external {
                when "../../../../../../ni:name='_public_'" {
                  tailf:xpath-root 3;
                }
                type boolean;
                default "false";
                description
                  "Enable/disable best external route selection.";
              }
              leaf label-free-delay {
                type uint8 {
                  range "0..180";
                }
                units "s";
                default "0";
                description
                  "Label free delay.";
              }
              leaf add-path-select-num {
                when "../../../../../../ni:name='_public_'" {
                  tailf:xpath-root 3;
                }
                type uint8 {
                  range "2..64";
                }
                description
                  "Number of Add-Path routes.";
              }
              leaf default-local-preference {
                type uint32 {
                  range "0..4294967295";
                }
                default "100";
                description
                  "The local preference of BGP routes.";
              }
              uses bestroute-med-plus-igp-type;
              uses bestroute-router-id-prior-clusterlist-type;
              leaf reflect-between-client {
                type boolean;
                default "true";
                description
                  "Enable/disable route reflection between clients. If clients of a route reflector (RR) are fully meshed, you can disable route reflection among clients to reduce the cost.";
              }
              leaf activate-route-tag {
                type boolean;
                default "false";
                description
                  "Enable/disable tag-based filtering.";
              }
              uses route-reflector-ext-community-filter-type;
              uses vrf-af-dampening-routes-ext;
              container nexthop-recursive-lookup {
                description
                  "Configure next hop iteration.";
                container common {
                  description
                    "Configure next hop iteration common options.";
                  uses nexthop-recursive-lookup-restrain;
                  uses nexthop-recursive-lookup-default-route;
                }
                uses nexthop-recursive-lookup-delay;
                uses bit-error-detection-type;
              }
              uses ipv4-import-filter-protocol-type;
              uses ipv4vpn-export-filter-protocol-type;
              uses bgp:slow-peer-type;
            }
            container ipv6-vpn {
              when "../type = 'ipv6vpn'" {
                tailf:xpath-root 3;
              }
              description
                "Configure IPv6 VPNv6 options.";
              uses vpn-target-type;
              uses reflector-cluster-type;
              uses reflect-type;
              leaf auto-frr {
                type boolean;
                default "false";
                description
                  "Enable/disable BGP Auto FRR. If IP FRR, VPN FRR, and Auto FRR are all enabled, IP FRR and VPN FRR take precedence over Auto FRR. If a route fails to match the routing policy of IP FRR or VPN FRR, Auto FRR takes effect.";
              }
              leaf tunnel-selector-name {
                type leafref {
                  path "/ncs:devices/ncs:device/ncs:config/rtp:routing-policy/rtp:tunnel-selectors/rtp:tunnel-selector/rtp:name" {
                    tailf:xpath-root 3;
                  }
                }
                description
                  "Configure a tunnel selector and apply it to the BGP IPv4 unicast, BGP VPNv4 address families and BGP VPNv6 address families so that IPv4,VPNv4 and VPNv6 labeled routes can be iterated to tunnels based on the tunnel selector. By default, no tunnel selector is configured.";
              }
              leaf route-select-delay {
                type uint16 {
                  range "0..3600";
                }
                units "s";
                default "0";
                description
                  "Route selection delay.";
              }
              leaf apply-label-mode {
                type apply-label-type;
                default "per-route";
                description
                  "Method of distributing labels to VPNV4 and VPNV6 routes. The way which assigns the label depends on the paf value. If there are a large number of routes, assign a label for the routes that have same nexthop and out-label. This allows all routes which have same nexthop and out-label to use one label.";
              }
              leaf nexthop-select-depend-type {
                type select-depend-type-ext;
                default "depend-ip";
                description
                  "In none mode, route selection does not depend on whether the next hop is reachable. In tunnel mode, the labeled BGP IPv4 route can participate in route selection only after its next hop is iterated to an LSP. In IP
                   mode, the labeled BGP IPv4 route can participate in route selection only after its next hop is iterated to an IP address. By default, the labeled BGP IPv4 route can participate in route selection
                   if its next hop can be iterated to an IP address, regardless of whether the LSP of the next hop exists. This allows the RR that is not enabled with MPLS to forward labeled routes. In non-RR
                   networking or RR networking where the BGP next hop is changed, BGP needs to check whether there is an LSP destined for the next hop. If such an LSP is not found, BGP needs to establish an LSP in
                   advance. If the default setting is adopted, a labeled BGP IPv4 unicast route may be selected prior to LSP establishment. As a result, services are incorrectly switched before LSP establishment and
                   service stability is affected. Therefore, allow route selection only after the labeled BGP IPv4 route is iterated to an LSP.";
              }
              leaf default-med {
                type uint32;
                default "0";
                description
                  "Specify the Multi-Exit-Discriminator (MED) of BGP routes. The value is an integer. This value is valid only for the imported routes and BGP summarized routes on the local router.";
              }
              leaf best-external {
                when "../../../../../../ni:name='_public_'" {
                  tailf:xpath-root 3;
                }
                type boolean;
                default "false";
                description
                  "Enable/disable best external route selection.";
              }
              leaf add-path-select-num {
                when "../../../../../../ni:name='_public_'" {
                  tailf:xpath-root 3;
                }
                type uint8 {
                  range "2..64";
                }
                description
                  "Number of add-path routes.";
              }
              leaf default-local-preference {
                type uint32 {
                  range "0..4294967295";
                }
                default "100";
                description
                  "The local preference of BGP routes.";
              }
              uses bestroute-med-plus-igp-type;
              uses bestroute-router-id-prior-clusterlist-type;
              leaf reflect-between-client {
                type boolean;
                default "true";
                description
                  "Enable/disable route reflection between clients. If clients of a route reflector (RR) are fully meshed, you can disable route reflection among clients to reduce the cost.";
              }
              leaf label-free-delay {
                type uint8 {
                  range "0..180";
                }
                units "s";
                default "0";
                description
                  "Label free delay.";
              }
              uses route-reflector-ext-community-filter-type;
              container nexthop-recursive-lookup {
                description
                  "Configure next hop iteration.";
                container common {
                  description
                    "Configure next hop iteration common options.";
                  uses nexthop-recursive-lookup-restrain;
                  uses nexthop-recursive-lookup-default-route;
                }
                uses nexthop-recursive-lookup-delay;
                uses bit-error-detection-type;
              }
              uses ipv6-import-filter-protocol-type;
              uses ipv6vpn-export-filter-protocol-type;
              uses bgp:slow-peer-type;
              uses vrf-af-dampening-routes-ext;
            }
            container ipv4-labeluni {
              when "../type = 'ipv4labeluni'" {
                tailf:xpath-root 3;
              }
              description
                "Configure IPv4 label unicast options.";
              container common {
                description
                  "Configure IPv4 label unicast common options.";
                leaf auto-frr {
                  type boolean;
                  default "false";
                  description
                    "Enable/disable BGP Auto FRR. If IP FRR, VPN FRR, and Auto FRR are all enabled, IP FRR and VPN FRR take precedence over Auto FRR. If a route fails to match the routing policy of IP FRR or VPN FRR, Auto FRR takes effect.";
                }
                leaf tunnel-selector-name {
                  when "../../../../../../../ni:name='_public_'" {
                    tailf:xpath-root 3;
                  }
                  type leafref {
                    path "/ncs:devices/ncs:device/ncs:config/rtp:routing-policy/rtp:tunnel-selectors/rtp:tunnel-selector/rtp:name" {
                      tailf:xpath-root 3;
                    }
                  }
                  description
                    "Configure a tunnel selector and apply it to the BGP IPv4 unicast, BGP VPNv4 address families and BGP VPNv6 address families so that IPv4,VPNv4 and VPNv6 labeled routes can be iterated to tunnels based on the tunnel selector. By default, no tunnel selector is configured.";
                }
                leaf tunnel-selector-all {
                  when '../tunnel-selector-name' {
                    tailf:xpath-root 3;
                  }
                  type boolean;
                  default "false";
                  description
                    "Enable/disable tunnel selector for labeled, imported, and network segment routes.";
                }
                leaf nexthop-select-depend-type {
                  when "../../../../../../../ni:name='_public_'" {
                    tailf:xpath-root 3;
                  }
                  type select-depend-type;
                  default "depend-tunnel";
                  description
                    "Specify the route iteration mode: IP or tunnel. In tunnel mode, the labeled BGP IPv4 route can participate in route selection only after its next hop is iterated to an LSP. In IP
                     mode, the labeled BGP IPv4 route can participate in route selection only after its next hop is iterated to an IP address. By default, the labeled BGP IPv4 route can participate in route selection
                     if its next hop can be iterated to an IP address, regardless of whether the LSP of the next hop exists. This allows the RR that is not enabled with MPLS to forward labeled routes. In non-RR
                     networking or RR networking where the BGP next hop is changed, BGP needs to check whether there is an LSP destined for the next hop. If such an LSP is not found, BGP needs to establish an LSP in
                     advance. If the default setting is adopted, a labeled BGP IPv4 unicast route may be selected prior to LSP establishment. As a result, services are incorrectly switched before LSP establishment and
                     service stability is affected. Therefore, allow route selection only after the labeled BGP IPv4 route is iterated to an LSP.";
                }
                leaf nexthop-inherit-ip-cost {
                  when "../nexthop-select-depend-type='depend-tunnel'" {
                    tailf:xpath-root 3;
                  }
                  type boolean;
                  default "false";
                  description
                    "Enable/disable next hop iteration mode to IP. Specify the route iteration mode: IP or tunnel. In tunnel mode, the labeled BGP IPv4 route can participate in route selection only after its next hop is iterated to an LSP.";
                }
                leaf always-compare-med {
                  type boolean;
                  default "false";
                  description
                    "Enable/disable BGP to compare the MEDs of routes from peers in different ASs in route selection. If
                     there are multiple reachable routes to the same destination, the route with the smallest MED is preferred. Do not use this option unless different ASs use the same IGP and route selection mode.";
                }
                leaf default-med {
                  type uint32;
                  default "0";
                  description
                    "Specify the Multi-Exit-Discriminator (MED) of BGP routes. The value is an integer. This value is valid only for the imported routes and BGP summarized routes on the local router.";
                }
                leaf best-route-bit-error-detection {
                  when "../../../../../../../ni:name!='_public_'" {
                    tailf:xpath-root 3;
                  }
                  type boolean;
                  default "false";
                  description
                    "Enable/disable the function to reroute traffic when a bit error event occurs.";
                }
                leaf supernet-label-advertise {
                  type boolean;
                  default "true";
                  description
                    "Enable/disable the function to advertise supernet labeled routes.";
                }
                leaf lsp-mtu {
                  type uint16 {
                    range "46..65535";
                  }
                  default "1500";
                  description
                    "BGP LSP MTU.";
                }
                leaf label-free-delay {
                  type uint8 {
                    range "0..180";
                  }
                  units "s";
                  default "0";
                  description
                    "Label free delay.";
                }
                leaf bestroute-med-confederation {
                  when "../../../../../../../ni:name='_public_'" {
                    tailf:xpath-root 3;
                  }
                  type boolean;
                  default "false";
                  description
                    "Enable/disable BGP to compare Med value only within the federation.";
                }
                leaf bestroute-as-path-ignore {
                  type boolean;
                  must "../bestroute-as-path-ignore = 'false' or ../load-balanc-as-path-ignore ='false'" {
                    tailf:xpath-root 3;
                  }
                  default "false";
                  description
                    "Enable/disable BGP to ignore the AS_Path attribute when selecting the optimal route. By default, BGP uses the AS_Path attribute as one of route selection rules, and a route with a shorter AS_Path is preferred. After bestroute-as-path-ignore is selected, BGP does not compare the AS_Path length.";
                }
                leaf determin-med {
                  type boolean;
                  must "../determin-med ='false' or (not(../add-path-select-num) and ../best-external ='false')" {
                    tailf:xpath-root 3;
                  }
                  default "false";
                  description
                    "Enable/disable deterministic MED so that the route selection result is relevant to the sequence in which routes are received.";
                }
                leaf best-external {
                  when "../../../../../../../ni:name='_public_'" {
                    tailf:xpath-root 3;
                  }
                  type boolean;
                  must "../best-external ='false' or ../determin-med ='false'" {
                    tailf:xpath-root 3;
                  }
                  default "false";
                  description
                    "Enable/disable best external route selection.";
                }
                leaf add-path-select-num {
                  when "../../../../../../../ni:name='_public_'" {
                    tailf:xpath-root 3;
                  }
                  type uint8 {
                    range "2..64";
                  }
                  must "../determin-med ='false'" {
                    tailf:xpath-root 3;
                  }
                  description
                    "Number of add-path routes.";
                }
                leaf load-balanc-igp-metric-ignore {
                  when "../../../../../../../ni:name='_public_'" {
                    tailf:xpath-root 3;
                  }
                  type boolean;
                  default "false";
                  description
                    "Enable/disable BGP to ignore the IGP cost of each BGP route to the next hop when selecting routes for load balancing. By default, only the routes with the same IGP cost can participate in load balancing.";
                }
                leaf load-balanc-as-path-ignore {
                  when "../../../../../../../ni:name='_public_'" {
                    tailf:xpath-root 3;
                  }
                  type boolean;
                  must "../load-balanc-as-path-ignore ='false' or (../load-balanc-as-path-relax ='false' and ../bestroute-as-path-ignore ='false')" {
                    tailf:xpath-root 3;
                  }
                  default "false";
                  description
                    "Enable/disable BGP to ignore the AS_Path of each BGP route to the next hop when selecting routes for load balancing. By default, only the routes with the same AS_Path can participate in load balancing.";
                }
                leaf load-balanc-as-path-relax {
                  when "../../../../../../../ni:name='_public_'" {
                    tailf:xpath-root 3;
                  }
                  type boolean;
                  must "../load-balanc-as-path-relax ='false' or ../load-balanc-as-path-ignore ='false'" {
                    tailf:xpath-root 3;
                  }
                  default "false";
                  description
                    "Enable/disable BGP to ignore comparison of AS_Path attributes with the same length. By default, only the routes with the same AS_Path can participate in load balancing.";
                }
                leaf default-local-preference {
                  type uint32 {
                    range "0..4294967295";
                  }
                  default "100";
                  description
                    "The local preference of BGP routes.";
                }
                leaf default-route-import {
                  type boolean;
                  default "false";
                  description
                    "Enable/disable the function to import default routes into the BGP routing table. Default-route-imported must be used with import-routes so that default routes can be imported to the BGP routing table. If only import-routes is used, no default routes can be added to the BGP routing table. In addition, default-route-imported can only import the default routes in the routing table into the BGP routing table.";
                }
                leaf routerid-neglect {
                  type boolean;
                  default "false";
                  description
                    "Enable/disable BGP to ignore router IDs when selecting the optimal route. Comparing router IDs is the last resort in route selection. This means that if one optimal route must be selected and no other parameters can be used to break the tie, router IDs can be used. If this option is selected, the first received route will be selected as the optimal route, and BGP will ignore the router ID and peer address in route selection.";
                }
                leaf route-select-delay {
                  type uint16 {
                    range "0..3600";
                  }
                  units "s";
                  default "0";
                  description
                    "Route selection delay.";
                }
                leaf import-rib-nexthop-invariable {
                  when "../../../../../../../ni:name!='_public_'" {
                    tailf:xpath-root 3;
                  }
                  type boolean;
                  default "false";
                  description
                    "Enable/disable the command to enable advertise the route without modifying the next-hop.";
                }
                uses reflect-type;
                uses reflector-cluster-type;
                leaf reflect-between-client {
                  type boolean;
                  default "true";
                  description
                    "Enable/disable route reflection between clients. If clients of a route reflector (RR) are fully meshed, you can disable route reflection among clients to reduce the cost.";
                }
                uses bestroute-med-plus-igp-type;
                uses bestroute-router-id-prior-clusterlist-type;
                leaf bestroute-med-none-as-maximum {
                  type boolean;
                  default "false";
                  description
                    "Enable/disable BGP considers its MED as the largest MED value (4294967295). If a route does not carry MED, BGP considers its MED as the default value (0) during route selection.";
                }
                leaf ext-community-change {
                  type boolean;
                  default "false";
                  description
                    "Enable/disable the function to change the extended community attribute.";
                }
              }
              container nexthop-recursive-lookup {
                description
                  "Configure next hop iteration.";
                container common {
                  description
                    "Configure next hop iteration common options.";
                  uses nexthop-recursive-lookup-restrain;
                }
              }
              container import-routes {
                description
                  "List of imported routes.";
                list import-route {
                  key "protocol process-id";
                  description
                    "Apply route import policy. Routes of other protocol types can be imported by BGP. By default, BGP does not import routes of other protocol types.";
                  uses import-routes-type;
                  leaf non-relay-tunnel {
                    when "../../../../../../../../ni:name='_public_'" {
                      tailf:xpath-root 3;
                    }
                    type boolean;
                    default "false";
                    description
                      "Enable/disable imported route relay a tunnel.";
                  }
                }
              }
              container network-routes {
                description
                  "List of network routes.";
                list network-route {
                  key "address mask-length";
                  description
                    "Configure a network route in the BGP routing table.";
                  uses network-route-ipv4;
                  leaf non-relay-tunnel {
                    when "../../../../../../../../ni:name='_public_'" {
                      tailf:xpath-root 3;
                    }
                    type boolean;
                    default "false";
                    description
                      "Enable/disable imported route relay a tunnel.";
                  }
                }
              }
              container import-ribs {
                description
                  "List of imported RIBs configuration.";
                list import-rib {
                  key "source-vpn source-address-family";
                  description
                    "Configure imported RIBs.";
                  leaf source-vpn {
                    type leafref {
                      path "/ncs:devices/ncs:device/ncs:config/ni:network-instance/ni:instances/ni:instance/ni:name" {
                        tailf:xpath-root 3;
                      }
                    }
                    must '../../../../../../../../ni:name != current()' {
                      tailf:xpath-root 3;
                    }
                    description
                      "Source VPN name.";
                  }
                  leaf source-address-family {
                    type bgp:import-rib-ipv4-safi-type;
                    description
                      "Source address family type.";
                  }
                  leaf valid-route {
                    type boolean;
                    default "false";
                    description
                      "Enable/disable imported valid route.";
                  }
                  leaf include-label-route {
                    when "../source-address-family='ipv4uni'" {
                      tailf:xpath-root 3;
                    }
                    type boolean;
                    default "false";
                    description
                      "Enable/disable imported include label route.";
                  }
                  // NCS expand uses statement
                  choice policy-type {
                    case rtp-ref {
                      description
                        "Specify the route policy.";
                      leaf policy-name {
                        type leafref {
                          path "/ncs:devices/ncs:device/ncs:config/rtp:routing-policy/rtp:policy-definitions/rtp:policy-definition/rtp:name" {
                            tailf:xpath-root 3;
                          }
                        }
                        description
                          "Specify the route policy.";
                      }
                    }
                    case xpl-ref {
                      description
                        "Route filter.";
                      uses route-filter-type;
                    }
                    description
                      "Specify the route-policy or filter for imported RIBs.";
                  }
                }
              }
              container lsp-options {
                description
                  "Configure BGP ingress-lsp.";
                uses safi-lsp-options;
                leaf maximum-load-balancing-transit {
                  when "../../../../../../../ni:name='_public_'" {
                    tailf:xpath-root 3;
                  }
                  type uint16 {
                    range "1..65535";
                  }
                  default "1";
                  description
                    "Maximum number of transit LSPs for load balancing.";
                }
                leaf unicast-rt-label-advertise-popgo {
                  when "../../../../../../../ni:name='_public_'" {
                    tailf:xpath-root 3;
                  }
                  type boolean;
                  default "false";
                  description
                    "Enable/disable a device to convert received IPv4 public network unicast routes to labeled routes by adding a BGP label to each route and advertise the labeled routes to peers with the labeled route exchange capability. If the IP address of an outbound interface is reachable but no LSP is reachable, traffic is forwarded through the outbound interface and a specific next hop, during which the label POPGO action is performed.";
                }
                leaf lsp-operation {
                  when "../../../../../../../ni:name='_public_'" {
                    tailf:xpath-root 3;
                  }
                  type lsp-operation-type;
                  default "pop";
                  description
                    "Label operation type.";
                }
                uses ingress-choice-policy-set;
              }
              uses vrf-af-dampening-routes;
              uses bgp:slow-peer-type;
            }
            container ipv4-multicast {
              when "../type='ipv4multi'" {
                tailf:xpath-root 3;
              }
              description
                "Configure IPv4 multicast options.";
              container common {
                description
                  "Configure BGP IPv4-multicast address family options.";
                leaf always-compare-med {
                  type boolean;
                  default "false";
                  description
                    "Enable/disable BGP to compare the MEDs of routes from peers in different ASs in route selection. If
                     there are multiple reachable routes to the same destination, the route with the smallest MED is preferred. Do not use this option unless different ASs use the same IGP and route selection mode.";
                }
                leaf default-med {
                  type uint32;
                  default "0";
                  description
                    "Specify the Multi-Exit-Discriminator (MED) of BGP routes. The value is an integer. This value is valid only for the imported routes and BGP summarized routes on the local router.";
                }
                leaf summary-automatic {
                  type boolean;
                  default "false";
                  description
                    "Enable/disable automatic summarization for imported routes. Manual summarization takes precedence over automatic summarization. After automatic summarization is enabled, BGP summarizes routes based on the natural network segment (for example, 10.1.1.1/24 and 10.2.1.1/24 are summarized into 10.0.0.0/8, a Class A address), and sends only the summarized route to peers. This reduces the number of routes.";
                }
                leaf bestroute-med-confederation {
                  type boolean;
                  default "false";
                  description
                    "Enable/disable BGP to compare Med value only within the federation.";
                }
                leaf default-local-preference {
                  type uint32 {
                    range "0..4294967295";
                  }
                  default "100";
                  description
                    "The local preference of BGP routes.";
                }
                leaf default-route-import {
                  type boolean;
                  default "false";
                  description
                    "Enable/disable the function to import default routes into the BGP routing table. Default-route-imported must be used with import-routes so that default routes can be imported to the BGP routing table. If only import-routes is used, no default routes can be added to the BGP routing table. In addition, default-route-imported can only import the default routes in the routing table into the BGP routing table.";
                }
                leaf routerid-neglect {
                  type boolean;
                  default "false";
                  description
                    "Enable/disable BGP to ignore router IDs when selecting the optimal route. Comparing router IDs is the last resort in route selection. This means that if one optimal route must be selected and no other parameters can be used to break the tie, router IDs can be used. If this option is selected, the first received route will be selected as the optimal route, and BGP will ignore the router ID and peer address in route selection.";
                }
                leaf route-select-delay {
                  type uint16 {
                    range "0..3600";
                  }
                  units "s";
                  default "0";
                  description
                    "Route selection delay.";
                }
                uses reflect-type;
                uses reflector-cluster-type;
                leaf reflect-between-client {
                  type boolean;
                  default "true";
                  description
                    "Enable/disable route reflection between clients. If clients of a route reflector (RR) are fully meshed, you can disable route reflection among clients to reduce the cost.";
                }
                leaf determin-med {
                  type boolean;
                  default "false";
                  description
                    "Enable/disable deterministic MED so that the route selection result is relevant to the sequence in which routes are received.";
                }
                uses bestroute-med-plus-igp-type;
                uses bestroute-router-id-prior-clusterlist-type;
                leaf bestroute-as-path-ignore {
                  type boolean;
                  default "false";
                  description
                    "Enable/disable BGP to ignore the AS_Path attribute when selecting the optimal route. By default, BGP uses the AS_Path attribute as one of route selection rules, and a route with a shorter AS_Path is preferred. After bestroute-as-path-ignore is selected, BGP does not compare the AS_Path length.";
                }
                leaf bestroute-med-none-as-maximum {
                  type boolean;
                  default "false";
                  description
                    "Enable/disable BGP considers its MED as the largest MED value (4294967295). If a route does not carry MED, BGP considers its MED as the default value (0) during route selection.";
                }
                leaf maximum-load-balancing {
                  type uint16 {
                    range "1..65535";
                  }
                  must 'not (../maximum-load-balancing-ibgp>1 or ../maximum-load-balancing-ebgp>1) or ../maximum-load-balancing=1' {
                    tailf:xpath-root 3;
                  }
                  default "1";
                  description
                    "Specify the maximum number of equal-cost routes in the BGP routing table. The value can be 1 or an integer greater than 1. The value depends on the associated license. By default, the maximum number of equal-cost routes is 1. Equal-cost BGP routes can be generated for load balancing only when the BGP routes meet the first nine rules of the route-selection policy and have the same AS-Path attribute.";
                }
                leaf maximum-load-balancing-ibgp {
                  type uint16 {
                    range "1..65535";
                  }
                  must 'not (../maximum-load-balancing>1) or ../maximum-load-balancing-ibgp=1' {
                    tailf:xpath-root 3;
                  }
                  default "1";
                  description
                    "Specify the maximum number of equal-cost IBGP routes.";
                }
                leaf maximum-load-balancing-ebgp {
                  type uint16 {
                    range "1..65535";
                  }
                  must 'not (../maximum-load-balancing>1) or ../maximum-load-balancing-ebgp=1' {
                    tailf:xpath-root 3;
                  }
                  default "1";
                  description
                    "Specify the maximum number of equal-cost EBGP routes.";
                }
                leaf ext-community-change {
                  type boolean;
                  default "false";
                  description
                    "Enable/disable the function to change the extended community attribute.";
                }
              }
              container nexthop-recursive-lookup {
                description
                  "Configure next hop iteration.";
                container common {
                  description
                    "Configure next hop iteration common options.";
                  choice policy-type {
                    description
                      "Set route-policy or route-filter.";
                    case rtp-ref {
                      description
                        "Route policy.";
                      leaf route-policy {
                        type leafref {
                          path "/ncs:devices/ncs:device/ncs:config/rtp:routing-policy/rtp:policy-definitions/rtp:policy-definition/rtp:name" {
                            tailf:xpath-root 3;
                          }
                        }
                        description
                          "Specify the name of a routing policy.";
                      }
                    }
                    case xpl-ref {
                      description
                        "Route filter.";
                      uses route-filter-type;
                    }
                  }
                }
                uses nexthop-recursive-lookup-delay;
              }
              uses bgp-route-preference-options;
              uses vrf-af-dampening-routes;
              container network-routes {
                description
                  "List of network routes.";
                list network-route {
                  key "address mask-length";
                  description
                    "Configure a network route in the BGP routing table.";
                  uses network-route-ipv4;
                }
              }
              container import-routes {
                description
                  "List of imported routes.";
                list import-route {
                  key "protocol process-id";
                  description
                    "Configure route import. Routes of other protocol types can be imported by BGP. By default, BGP does not import routes of other protocol types.";
                  leaf protocol {
                    type bgp:ipv4multi-import-route-protocol-type;
                    description
                      "Routing protocol from which routes can be imported.";
                  }
                  leaf process-id {
                    type uint32 {
                      range "0..4294967295";
                    }
                    must "((../protocol='ospf' or ../protocol='isis' or ../protocol='rip') and ../process-id!=0) or (../protocol!='ospf' and ../protocol!='isis' and ../protocol!='rip' and ../process-id=0)" {
                      tailf:xpath-root 3;
                    }
                    description
                      "Process ID of an imported routing protocol. The process ID is 0, if the imported routing protocol is direct routes, static routes, UNRs, or OP-routes. The process ID must be specified range from 1 to 4294967295, if the imported routing protocol is RIP, OSPF, ISIS.";
                  }
                  leaf med {
                    type uint32;
                    description
                      "Specifies the MED metric of the imported route.";
                  }
                  choice policy-type {
                    description
                      "Set route policy or filter.";
                    case rtp-ref {
                      description
                        "Route policy.";
                      leaf policy-name {
                        type leafref {
                          path "/ncs:devices/ncs:device/ncs:config/rtp:routing-policy/rtp:policy-definitions/rtp:policy-definition/rtp:name" {
                            tailf:xpath-root 3;
                          }
                        }
                        description
                          "When routes are imported from other routing protocols, the route-policy filter can be used to filter the routes and change route attributes.";
                      }
                    }
                    case xpl-ref {
                      description
                        "Route filter.";
                      uses route-filter-type;
                    }
                  }
                }
              }
              container aggregate-routes {
                description
                  "List of summarized routes.";
                list aggregate-route {
                  key "address mask-length";
                  description
                    "Configure a summarized route in the BGP routing table. The local outbound interface of the summarized route is Null0. When another router receives the route, the route adds an outbound interface to the route. By default, route summarization is not performed. If the Origin attributes of the specific routes for the route summarization are different, the Origin attribute of the summarized route is that with the highest priority. Origin attributes are arranged in the priority order of complete > egp > igp. A summarized route carries the community attribute of each specific route.";
                  // NCS expand uses statement
                  leaf address {
                    type inet:ip-address-no-zone;
                    description
                      "Specify the IPv4 address or IPv6 address of a summarized route. Only IPv4 summarized routes can be configured in the IPv4 address family and only IPv6 summarized routes can be configured in the IPv6 address family.";
                    must "not(contains(../address,':'))" {
                      tailf:xpath-root 3;
                    }
                  }
                  leaf mask-length {
                    type uint8 {
                      range "1..128";
                    }
                    description
                      "Specify the mask length of a summarized address.";
                    must '../mask-length<=32' {
                      tailf:xpath-root 3;
                    }
                  }
                  leaf as-set {
                    type boolean;
                    default "false";
                    description
                      "Enable/disable the generation of routes with the AS-SET attribute. This option can be used to create a summarized route. The AS_Path attribute of the summarized route contains the AS-Path attributes of the specific routes for the route summarization. Exercise caution when using this option if multiple AS_Paths need to be summarized to prevent route flapping.";
                  }
                  leaf detail-suppressed {
                    type boolean;
                    default "false";
                    description
                      "Enable/disable detail-suppressed. Suppress the advertisement of specific routes for the route summarization. Only the summarized route is advertised.";
                  }
                  choice policy-type {
                    description
                      "Set route policy or filter.";
                    case rtp-ref {
                      description
                        "Route policy.";
                      leaf attribute-policy {
                        type leafref {
                          path "/ncs:devices/ncs:device/ncs:config/rtp:routing-policy/rtp:policy-definitions/rtp:policy-definition/rtp:name" {
                            tailf:xpath-root 3;
                          }
                        }
                        description
                          "Specify an attribute of summarized routes. If apply as-path is used to configure the AS_Path attribute that is used in the route Summarization policy, and the as-set keyword is set, the AS_Path attribute in the policy does not take effect. This parameter and any of the following parameters overwrite each other: suppressFilter, originFilter, and attributeFilter.";
                      }
                      leaf origin-policy {
                        type leafref {
                          path "/ncs:devices/ncs:device/ncs:config/rtp:routing-policy/rtp:policy-definitions/rtp:policy-definition/rtp:name" {
                            tailf:xpath-root 3;
                          }
                        }
                        description
                          "Specify the name of a policy for generating summarized routes. Summarized routes are generated only when the routes match route-policy. This parameter and any of the following parameters overwrite each other: suppressFilter, originFilter, and attributeFilter.";
                      }
                      leaf suppress-policy {
                        type leafref {
                          path "/ncs:devices/ncs:device/ncs:config/rtp:routing-policy/rtp:policy-definitions/rtp:policy-definition/rtp:name" {
                            tailf:xpath-root 3;
                          }
                        }
                        description
                          "Specify a policy for suppressing the advertisement of specified routes. The routes matching the policy are not advertised, and other routes are advertised. This parameter and any of the following parameters overwrite each other: suppressFilter, originFilter, and attributeFilter.";
                      }
                    }
                    case xpl-ref {
                      description
                        "Route filter.";
                      leaf attribute-filter-name {
                        type leafref {
                          path "/ncs:devices/ncs:device/ncs:config/xpl:xpl/xpl:route-filters/xpl:route-filter/xpl:name" {
                            tailf:xpath-root 3;
                          }
                        }
                        description
                          "Specify a route-filter name.";
                      }
                      leaf attribute-filter-parameter {
                        when '../attribute-filter-name' {
                          tailf:xpath-root 3;
                        }
                        type xpl:filter-parameter-type;
                        description
                          "Specify a route-filter parameter.";
                      }
                      leaf origin-filter-name {
                        type leafref {
                          path "/ncs:devices/ncs:device/ncs:config/xpl:xpl/xpl:route-filters/xpl:route-filter/xpl:name" {
                            tailf:xpath-root 3;
                          }
                        }
                        description
                          "Specify a route-filter name.";
                      }
                      leaf origin-filter-parameter {
                        when '../origin-filter-name' {
                          tailf:xpath-root 3;
                        }
                        type xpl:filter-parameter-type;
                        description
                          "Specify a route-filter parameter.";
                      }
                      leaf suppress-filter-name {
                        type leafref {
                          path "/ncs:devices/ncs:device/ncs:config/xpl:xpl/xpl:route-filters/xpl:route-filter/xpl:name" {
                            tailf:xpath-root 3;
                          }
                        }
                        description
                          "Specify a route-filter name.";
                      }
                      leaf suppress-filter-parameter {
                        when '../suppress-filter-name' {
                          tailf:xpath-root 3;
                        }
                        type xpl:filter-parameter-type;
                        description
                          "Specify a route-filter parameter.";
                      }
                    }
                  }
                }
              }
              uses ipv4-import-filter-protocol-type;
              container export-filter-policys {
                description
                  "List of filtering policies.";
                list export-filter-policy {
                  key "protocol process-id";
                  description
                    "Apply a filtering policy. It is used to filter the routes to be advertised to the peer. By default, routes are not filtered.";
                  leaf protocol {
                    type bgp:ipv4-export-filter-protocol-type;
                    description
                      "Specify the name of a routing protocol. The routing protocol takes effect only on the routes to be advertised. The IPv4 address family supports the direct, IS-IS, OSPF, RIP, and static routing protocols. The IPv6 unicast address family of a public network instance supports the direct, IS-IS, OSPFv3, RIPng, and static routing protocols. The IPv6 address family of a VPNv6 instance supports the direct, IS-IS, RIPng, and static routing protocols.";
                  }
                  leaf process-id {
                    type uint32 {
                      range "0..4294967295";
                    }
                    must "((../protocol='ospf' or ../protocol='rip' or ../protocol='isis') and ../process-id!=0) or ((../protocol!='ospf' and ../protocol!='rip' and ../protocol!='isis') and ../process-id=0)" {
                      tailf:xpath-root 3;
                    }
                    description
                      "Specify the process ID required to be matched. The value is an integer ranging from 0 to 4294967295. If direct or static routes need to be filtered, no process ID is required.";
                  }
                  uses ipv4-filter-protocol-policy-choice-type;
                }
              }
              uses bgp:slow-peer-type;
              uses qos-local-id-type;
            }
          }
        }
        container dynamic-peer-prefixes {
          description
            "List of IP prefixes from which a dynamic BGP peer group listens for BGP connection requests.";
          list dynamic-peer-prefix {
            key "address mask-length peer-group";
            description
              "Configure an IP prefix from which a dynamic BGP peer group listens for BGP connection requests.";
            leaf address {
              type inet:ip-address-no-zone;
              must "contains(., ':') = 'false'" {
                tailf:xpath-root 3;
              }
              description
                "Network segment address for a dynamic peer connection.";
            }
            leaf mask-length {
              type uint8 {
                range "0..32";
              }
              description
                "Mask length of a network segment. For an IPv4 network address, the value ranges from 0 to 32.";
            }
            leaf peer-group {
              type leafref {
                path "../../../peer-groups/peer-group/name";
              }
              must "../../../peer-groups/peer-group[name = current()]/peer-establish-mode = 'dynamic'" {
                tailf:xpath-root 3;
              }
              must "../../../peer-groups/peer-group[name = current()]/listen-as or ../../../peer-groups/peer-group[name = current()]/listen-as-segments/listen-as-segment or /ni:network-instance/ni:instances/ni:instance[ni:name='_public_']/bgp:bgp/bgp:base-process/bgp:peer-groups/bgp:peer-group[name = current()]/bgp:as-number-type='confederation'" {
                tailf:xpath-root 3;
              }
              description
                "The peer-group within which the dynamic neighbor will be configured.";
            }
          }
        }
        container peer-groups {
          description
            "List of BGP peer groups. The BGP peer groups can help you simplify the configurations. If you want to perform the same configuration for several peers, you can create a peer group and then configure the peer group. After you add these peers to the peer group, all these peers will have the same configurations as the peer group.";
          list peer-group {
            key "name";
            description
              "Configure information about a BGP peer group.";
            leaf name {
              type string {
                length "1..47";
                pattern '([^\? ]+)';
              }
              description
                "Specify the name of a peer group. The value is a string of characters, spaces not supported.";
            }
            leaf type {
              type group-type;
              mandatory true;
              description
                "Specify the type of a peer group. The value can be IBGP or EBGP.The object cannot be modified.";
              ext:operation-exclude "update" {
                description
                  "The node cannot be modified, when node is already configured.";
              }
            }
            uses peer-local-if-type;
            uses authentication-attr-type;
            leaf description {
              type string {
                length "1..255";
                pattern '([^?]*)';
              }
              description
                "Specify the description of a peer group. The value is a string, which can be letters or digits, spaces supported. By default, no description is configured.";
            }
            leaf group-as {
              when "not(../type='ibgp') and ../peer-establish-mode = 'static'" {
                tailf:xpath-root 3;
              }
              type as-number-validate;
              description
                "Specify the AS number of a peer group. The AS number is in either a 2-byte or 4-byte format.
                 The two-byte format is X. X is an integer ranging from 1 to 65535.
                 The four-byte format is X.Y and X. When the format is X.Y, X and Y are both integers, with the value of X ranging from 1 to 65535, and the value of Y ranging from 0 to 65535; when the format is X, X is an interger, with the value of X ranging from 1 to 4294967295.";
            }
            leaf tcp-mss {
              type uint16 {
                range "176..4096";
              }
              description
                "Maximum TCP MSS value used for TCP connection establishment for a peer group.";
            }
            leaf ebgp-max-hop {
              when "../type='ebgp'" {
                tailf:xpath-root 3;
              }
              type uint32 {
                range "1..255";
              }
              must 'not(../valid-ttl-hops) or (../valid-ttl-hops>=1 and not(../valid-ttl-hops>255) and ../ebgp-max-hop=1)' {
                tailf:xpath-root 3;
              }
              default "1";
              description
                "Maximum number of hops in an indirect EBGP connection. By default, EBGP connections can be established only between directly connected peers. The function must be configured on both ends.";
            }
            leaf valid-ttl-hops {
              type uint16 {
                range "1..255";
              }
              must 'not(../ebgp-max-hop and ../ebgp-max-hop>1 and ../ebgp-max-hop<=255)' {
                tailf:xpath-root 3;
              }
              description
                "Enable GTSM on a peer or peer group. The valid-TTL-Value parameter is used to specify the number of TTL hops to be detected. If the value is configured as hops, the valid TTL range of the detected packet is [255-hops+1, 255].";
            }
            uses peer-tracking-type;
            leaf conventional {
              type boolean;
              default "false";
              description
                "Enable/disable general router functions on peers. In conventional mode, not all the extended router functions, such as, route refreshing, GR, and multi-address family negotiation, are available. Therefore, the router of a new version can be compatible with the routers of earlier versions.";
            }
            leaf route-refresh {
              type boolean;
              default "true";
              description
                "Enable/disable BGP to advertise Refresh messages to peers.";
            }
            leaf four-byte-as {
              type boolean;
              default "true";
              description
                "Enable/disable BGP to advertise routes carrying 4-byte AS numbers to peers. After the 4-byte AS number function is disabled, Open packets will not carry 4-byte AS number capability flag, and peer ends will not know that local ends have the 4-byte AS number function. The 4-byte AS number function cannot be disabled from peers (peer groups) if a 4-byte AS number, fake AS number, or confederation ID is configured on a router and the AS number of a peer is 4-byte. If the 4-byte AS number function is disabled in such a situation, BGP sessions may fail to be established, and route transmission may be affected.";
            }
            leaf ignore {
              type boolean;
              default "false";
              description
                "Enable/disable the function to tear down sessions between peers and clear all related routing information.";
            }
            leaf connect-mode {
              when "../peer-establish-mode = 'static'" {
                tailf:xpath-root 3;
              }
              type connect-mode;
              default "null";
              description
                "The value can be Connect-only, Listen-only, or Both. If the value is Connect-only, the specified peer or peer group only initiatively sends connection requests, instead of listening to connection requests. If the value is Listen-only, the specified peer or peer group only listens to connection requests, instead of initiatively sending connection requests. If the value is Both, the specified peer or peer group not only initiatively sends connection requests, but also listens to connection requests. The default value is Both.";
            }
            leaf log-change {
              type boolean;
              default "true";
              description
                "Enable/disable BGP to record the session status and events of the specified peer or peer group.";
            }
            leaf path-mtu-auto-discovery {
              when "../peer-establish-mode = 'static'" {
                tailf:xpath-root 3;
              }
              type boolean;
              default "false";
              description
                "Enable/disable path mtu auto discovery.";
            }
            leaf local-ifnet-disable {
              type boolean;
              description
                "Enable/disable MPLS local IFNET tunnel creation on a BGP peer. By default, MPLS local IFNET tunnels can be created on an EBGP peer,but such tunnels cannot be created on an IBGP peer.";
              ext:dynamic-default;
            }
            leaf check-first-as {
              when "../type='ebgp'" {
                tailf:xpath-root 3;
              }
              type peer-cap-config-state;
              default "default";
              description
                "Check the first AS in the AS_Path of the update messages from EBGP peers.";
            }
            leaf memory-priority {
              type memory-priority;
              default "medium";
              description
                "Set a priority that determines the disconnection order of each BGP peer relationship in a peer group if memory overload occurs.";
            }
            leaf oscillation-dampening {
              when "../peer-establish-mode = 'static'" {
                tailf:xpath-root 3;
              }
              type boolean;
              default "true";
              description
                "Enable/disable BGP to suppress the establishment of a specified peer group's peer relationships that flap continuously. By default, the capability is enabled.";
            }
            leaf peer-establish-mode {
              type peer-establish-mode;
              default "static";
              description
                "Specify mode in which a BGP peer is established. The value can be static or dynamic.";
              ext:operation-exclude "update|delete" {
                description
                  "The node cannot be modified, deleted when node is already configured.";
              }
            }
            leaf as-number-type {
              when "../peer-establish-mode = 'dynamic' and ../../../../../ni:name='_public_'" {
                tailf:xpath-root 3;
              }
              type as-number-type;
              must ". = 'dynamic-neighbor' or (. = 'confederation' and /bgp:bgp/bgp:base-process/bgp:confederation/bgp:id and ../type = 'ebgp')" {
                tailf:xpath-root 3;
              }
              default "dynamic-neighbor";
              description
                "Specify the type of the AS number that is used to establish a BGP peer relationship dynamically. The value can be dynamic-neighbor or confederation.";
              ext:operation-exclude "update|delete" {
                description
                  "The node cannot be modified, deleted when node is already configured.";
              }
            }
            leaf-list listen-as {
              when "../peer-establish-mode = 'dynamic' and ../type = 'ebgp'" {
                tailf:xpath-root 3;
              }
              type as-number-validate;
              must "not(. = /bgp:bgp/bgp:base-process/bgp:as) and not(/ni:network-instance/ni:instances/ni:instance[ni:name='_public_']/bgp:bgp/bgp:base-process/bgp:peer-groups/bgp:peer-group[name = current()/../name]/bgp:as-number-type='confederation')" {
                tailf:xpath-root 3;
              }
              max-elements 6;
              description
                "Specify the peer AS from which a dynamic EBGP peer group listens for BGP connection requests.";
            }
            container listen-as-segments {
              when "../peer-establish-mode = 'dynamic' and ../type = 'ebgp'" {
                tailf:xpath-root 3;
              }
              description
                "List of AS number ranges for listening.";
              list listen-as-segment {
                must "not(../../listen-as) and not(/ni:network-instance/ni:instances/ni:instance[ni:name='_public_']/bgp:bgp/bgp:base-process/bgp:peer-groups/bgp:peer-group[name = current()/../../name]/bgp:as-number-type='confederation')" {
                  tailf:xpath-root 3;
                }
                key "begin-as end-as";
                max-elements 16;
                description
                  "Specify an AS number range from which a dynamic EBGP peer group listens for connection requests. The value of begin-as must be smaller than that of end-as. The value of As-Segment cannot contain the value of LocalAS or the value of fake-as. An AS number range cannot contain a confederation AS number, and any two AS number ranges cannot contain each other.";
                leaf begin-as {
                  type as-number-validate;
                  description
                    "Specify the start AS number in an AS range.";
                }
                leaf end-as {
                  type as-number-validate;
                  description
                    "Specify the end AS number in an AS range.";
                }
              }
            }
            container fake-as-parameter {
              description
                "Configure BGP fake-as parameters.";
              leaf fake-as {
                when "../../bgp:type='ebgp'" {
                  tailf:xpath-root 3;
                }
                type bgp:as-number-validate;
                description
                  "Fake AS number that is specified for a local peer. By default, a peer uses the actual AS number of the local end.
                   An AS number can be in either two-byte format or four-byte format:
                   The two-byte format is X. X is an integer ranging from 1 to 65535.
                   The four-byte format is X.Y and X. When the format is X.Y, X and Y are both integers, with the value of X ranging from 1 to 65535, and the value of Y ranging from 0 to 65535; when the format is X, X is an interger, with the value of X ranging from 1 to 4294967295.";
              }
              leaf dual-as {
                when '../fake-as' {
                  tailf:xpath-root 3;
                }
                type boolean;
                default "false";
                description
                  "Enable/disable the function to the remote EBGP peer can use the actual or fake AS number when specifying the AS number for a local peer. The local peer uses the fake and actual AS numbers to establish a BGP peer relationship with the remote end and identifies the AS number configured by the remote end through the error code (OPEN Message Error) and sub-error code (Bad Peer AS) of the Notification message from the remote end.";
              }
              leaf prepend-global-as {
                when '../fake-as' {
                  tailf:xpath-root 3;
                }
                type boolean;
                default "false";
                description
                  "Enable/disable the function to add the global AS number to the Update packets to be advertised.";
              }
              leaf prepend-fake-as {
                when '../fake-as' {
                  tailf:xpath-root 3;
                }
                type boolean;
                default "false";
                description
                  "Enable/disable the function to add the Fake AS number to received Update packets.";
              }
            }
            uses peer-timer-para-type;
            uses group-bfd-parameter-type;
            container graceful-restart {
              when "../peer-establish-mode = 'static'" {
                tailf:xpath-root 3;
              }
              description
                "Configure graceful restart.";
              uses group-graceful-restart-type;
              leaf peer-reset {
                type boolean;
                default "false";
                description
                  "Enable/disable reseting BGP peer graceful.";
              }
            }
            container local-graceful-restart {
              when "../peer-establish-mode = 'static'" {
                tailf:xpath-root 3;
              }
              description
                "Configure local graceful restart.";
              uses group-graceful-restart-type;
            }
            // NCS drop config false container members
            container afs {
              description
                "List of all peer groups that are enabled in a specified address family.";
              list af {
                key "type";
                description
                  "Configure peer group enabled in a specified address family.";
                leaf type {
                  type bgp:group-af-type;
                  must '../../../../../afs/af[type = current()]' {
                    tailf:xpath-root 3;
                  }
                  description
                    "Address family type of a BGP instance.";
                }
                container ipv4-unicast {
                  when "../type = 'ipv4uni'" {
                    tailf:xpath-root 3;
                  }
                  description
                    "Configure IPv4 unicast options.";
                  leaf advertise-community {
                    type boolean;
                    default "false";
                    description
                      "Enable/disable advertise the community attribute to a peer or a peer group.";
                  }
                  leaf reflect-client {
                    when "../../../../bgp:type='ibgp'" {
                      tailf:xpath-root 3;
                    }
                    type boolean;
                    default "false";
                    description
                      "Enable/disable the local device as a route reflector (RR) and a peer or peer group as its client. This configuration is applicable between IBGP peers only. The configurations of RRs and its clients in an address family are valid only in this address family. Therefore, it is recommended to configure RRs and its clients in the specified address family that is required.";
                  }
                  leaf orf-type {
                    when "../../../../../../../../ni:name='_public_'" {
                      tailf:xpath-root 3;
                    }
                    type bgp:bgp-orf-type;
                    must "(../orf-mode='null' and ../orf-type='null') or (../orf-mode!='null' and ../orf-type!='null')" {
                      tailf:xpath-root 3;
                    }
                    default "null";
                    description
                      "ORF Type.";
                  }
                  leaf orf-mode {
                    when "../../../../../../../../ni:name='_public_'" {
                      tailf:xpath-root 3;
                    }
                    type bgp:bgp-orf-mode-type;
                    must "(../orf-mode='null' and ../orf-type='null') or (../orf-mode!='null' and ../orf-type!='null')" {
                      tailf:xpath-root 3;
                    }
                    default "null";
                    description
                      "Configure an outbound route filtering (ORF) mode, which can be Receive, Send, or Both, and the default ORF mode is Both.";
                  }
                  leaf label-route-capability {
                    type boolean;
                    default "false";
                    description
                      "Enable/disable a device to exchange labeled routes.";
                  }
                  leaf check-tunnel-reachable {
                    when "../label-route-capability='true'" {
                      tailf:xpath-root 3;
                    }
                    type boolean;
                    default "false";
                    description
                      "Enable/disable tunnel reachability check.";
                  }
                  leaf check-withdraw-type {
                    when "../label-route-capability='true'" {
                      tailf:xpath-root 3;
                    }
                    type boolean;
                    default "true";
                    status obsolete;
                    description
                      "Enable/disable withdraw type check.";
                  }
                  leaf nexthop-configure {
                    type nexthop-configuration-type;
                    description
                      "Both the next-hop-local mode and next-hop-invariable mode are available when the peer address family is the VPNv4/VPNv6/L2VPN AD address family. Only the next-hop-local mode is available when the peer address family is not VPNv4/VPNV6/L2VPN AD address family. In next-hop-local mode, you can configure a BGP speaker to set its IP address of as the next hop of the routes to be advertised to IBGP peers or IBGP peer groups. In next-hop-invariable mode, you can configure PEs in different ASs not to change the next hop of routes when the PEs advertise the routes to their EBGP peers and use the next hop addresses of IGP routes to advertise imported IGP routes to IBGP peers. By default, when a BGP speaker advertises routes to EBGP peers and imported IGP routes to IBGP peers, the BGP speaker changes the next hop to its interface address.";
                  }
                  uses peer-policy-filter-type;
                  leaf advertise-ext-community {
                    type boolean;
                    default "false";
                    description
                      "Enable/disable advertise the extended community attribute to a peer or peer group.";
                  }
                  leaf origin-as-validation {
                    when "../advertise-ext-community='true' and ../../../../peer-establish-mode='static'" {
                      tailf:xpath-root 3;
                    }
                    type boolean;
                    default "false";
                    description
                      "Enable/disable the BGP peer origin validation.";
                  }
                  leaf discard-ext-community {
                    type boolean;
                    default "false";
                    description
                      "Enable/disable discard the extended community attribute in the routing information about a specified peer.";
                  }
                  leaf allow-as-loop {
                    type uint32 {
                      range "1..10";
                    }
                    description
                      "Allow repetitive local AS numbers. By default, repetitive local AS numbers are not allowed.";
                  }
                  leaf aigp {
                    when "../../../../../../../../ni:name='_public_'" {
                      tailf:xpath-root 3;
                    }
                    type boolean;
                    default "false";
                    description
                      "Enable/disable route with AIGP attribute advertisement to or from a peer.";
                  }
                  leaf add-path-mode {
                    when "../../../../../../../../ni:name='_public_' and ../../../../bgp:type='ibgp'" {
                      tailf:xpath-root 3;
                    }
                    type add-path-cap-type;
                    default "null";
                    description
                      "Enable Add-Path route advertisement to a peer.";
                  }
                  uses ip-prefix-filter-type;
                  uses as-path-filter-type;
                  uses peer-group-acl-name-or-num-type;
                  uses default-route-advertise-type;
                  leaf default-route-match-mode {
                    when "../default-route-advertise='true'" {
                      tailf:xpath-root 3;
                    }
                    type cra-match-mode;
                    default "null";
                    description
                      "Configure the matching mode of default route advertisement, which can be disabling of route advertisement conditions, enabling of all route advertisement conditions, and enabling of part route advertisement conditions. Enabling of all route advertisement conditions indicates that a default route can be advertised only when it matches all the conditions. Enabling of part route advertisement conditions indicates that a default route can be advertised only when it matches one condition.";
                  }
                  uses rt-update-interval-type;
                  uses preferred-value-type;
                  leaf add-path-number {
                    when "../../../../../../../../ni:name='_public_' and ../../../../bgp:type='ibgp'" {
                      tailf:xpath-root 3;
                    }
                    type uint8 {
                      range "2..64";
                    }
                    description
                      "Number of Add-Path routes that can be advertised to a peer.";
                  }
                  leaf substitute-as-enable {
                    when "../../../../bgp:type='ebgp'" {
                      tailf:xpath-root 3;
                    }
                    type boolean;
                    default "false";
                    description
                      "Enable/disable replace the AS number of a specified peer in the AS_Path attribute with the local AS number. On a PE where AS number replacement is enabled, if an AS number in the AS_Path attribute of a route is same as that of the CE to which the PE advertises the route, the PE replaces the AS number with its own AS number before advertising the route.";
                  }
                  leaf soo {
                    when "../../../../../../../../ni:name!='_public_'" {
                      tailf:xpath-root 3;
                    }
                    type string {
                      length "3..21";
                    }
                    description
                      "Configure the Site-of-Origin (SoO) extended community attribute. This attribute can be expressed in the following formats: X.X.X.X:number<0-65535>, number<0-65535>:number<0-4294967295>, or number<0-65535>.number<0-65535>:number<0-65535> or <65536-4294967295>:<0-65535>. 0:0 or 0.0:0 is not supported.
                       Two CEs are in the same site and can advertise routes to each other, and they are connected to a VPN through PEs. If the local routes of a CE are advertised to the other CE over the VPN, a routing loop may occur.
                       The SoO feature can prevent a route advertised by a site from being sent back to the site, preventing routing loops. After SoO is enabled and a PE receives a route from a CE, the specified SoO attribute will be added to the route. Before advertising the route to the other CE, the PE checks the SoO attribute. If the SoO attribute is the same as the locally configured SoO attribute, the PE does not advertise the route, preventing routing loops.";
                  }
                  leaf keep-all-routes {
                    when "/bgp:bgp/bgp:base-process/bgp:keep-all-routes='false'" {
                      tailf:xpath-root 3;
                    }
                    type boolean;
                    default "false";
                    description
                      "Enable/disable saving all the updated information about BGP routes from a specified peer or peer group after a BGP connection is established, even though these BGP routes fail to match the routing policy on the ingress. By default, the updated information about BGP routes from a specified peer is saved only when the routes match the routing policy on the ingress. If a router supports route refreshing, this option is not required.";
                  }
                  leaf exp-mode {
                    type exp-mode-type;
                    default "null";
                    description
                      "Specify the ASs in which a BGP label can inherit the QoS priority carried in the outer label of public tunnel in the Core AS and the ASs in which the priorities of BGP LSPs must be restored before the LSPs are advertised to a non-core AS.";
                  }
                  leaf advertise-best-external {
                    when "../../../../../../../../ni:name='_public_' and ../../../../bgp:type='ibgp'" {
                      tailf:xpath-root 3;
                    }
                    type boolean;
                    must "../reflect-client='false' or ../advertise-best-external='false'" {
                      tailf:xpath-root 3;
                    }
                    must "../add-path-mode='null' or not(../add-path-mode) or ../advertise-best-external='false'" {
                      tailf:xpath-root 3;
                    }
                    must "not(../add-path-number and ../advertise-best-external='true')" {
                      tailf:xpath-root 3;
                    }
                    default "false";
                    description
                      "Enable/disable the device to advertise Best External routes to peers.";
                  }
                  leaf load-balancing-enable {
                    type boolean;
                    default "false";
                    description
                      "Enable/disable a neighbour to participate in load balancing.";
                  }
                  choice load-balancing-ignore-as-type {
                    description
                      "Set load balancing as path type.";
                    case as-attribute {
                      description
                        "Ignore the as-path attribute.";
                      leaf load-balancing-as-path-ignore {
                        when "../load-balancing-enable='true'" {
                          tailf:xpath-root 3;
                        }
                        type empty;
                        description
                          "Configure BGP to ignore the AS_Path attribute when selecting the equal route. After as-path-neglect is selected, BGP does not compare the AS_Path length.";
                      }
                    }
                    case same-length-as-attribute {
                      description
                        "Ignore comparison of as-path attributes with the same length.";
                      leaf load-balancing-as-path-relax {
                        when "../load-balancing-enable='true'" {
                          tailf:xpath-root 3;
                        }
                        type empty;
                        description
                          "Configure BGP to ignore comparison of AS_Path attributes with the same length when selecting the equal route. After as-path-neglect is selected, BGP does not compare the AS_Path length.";
                      }
                    }
                  }
                  leaf prefix-sid {
                    when "../../../../../../../../ni:name='_public_'" {
                      tailf:xpath-root 3;
                    }
                    type boolean;
                    default "false";
                    description
                      "Enable/disable a device to exchange IPv4 prefix SIDs with a specified IPv6 peer group.";
                  }
                  choice prefix-sid-packet {
                    description
                      "Prefix-sid packet method.";
                    case sid-type5 {
                      description
                        "Packet by type5.";
                      leaf advertise-srv6-locator {
                        when "../prefix-sid='true'" {
                          tailf:xpath-root 3;
                        }
                        type empty;
                        description
                          "Advertise SRv6 locators.";
                      }
                    }
                  }
                  uses group-independent-peer-group-type;
                  uses advertise-large-community-group-type;
                  uses ipv4-default-route-match-conditions-type;
                  uses route-limit-accept-type;
                  uses public-as-only-type;
                  uses group-public-as-only-import-type;
                  uses advertise-dependent-filter-group-type;
                  container entropy-label-parameter {
                    when "../../../../../../../../ni:name='_public_' and ../label-route-capability='true'" {
                      tailf:xpath-root 3;
                    }
                    description
                      "Configure information about entropy label parameter in a peer group.";
                    uses group-entropy-label-type;
                  }
                }
                container ipv6-unicast {
                  when "../type = 'ipv6uni'" {
                    tailf:xpath-root 3;
                  }
                  description
                    "Configure IPv6 unicast options.";
                  leaf advertise-community {
                    type boolean;
                    default "false";
                    description
                      "Enable/disable advertise the community attribute to a peer or a peer group.";
                  }
                  leaf reflect-client {
                    when "../../../../bgp:type='ibgp'" {
                      tailf:xpath-root 3;
                    }
                    type boolean;
                    default "false";
                    description
                      "Enable/disable the local device as a route reflector (RR) and a peer or peer group as its client. This configuration is applicable between IBGP peers only. The configurations of RRs and its clients in an address family are valid only in this address family. Therefore, it is recommended to configure RRs and its clients in the specified address family that is required.";
                  }
                  leaf label-route-capability {
                    type boolean;
                    default "false";
                    description
                      "Enable/disable a device to exchange labeled routes.";
                  }
                  leaf nexthop-configure {
                    type nexthop-configuration-type;
                    description
                      "Both the next-hop-local mode and next-hop-invariable mode are available when the peer address family is the VPNv4/VPNV6/L2VPN AD address family. Only the next-hop-local mode is available when the peer address family is not VPNv4/VPNV6/L2VPN AD address family. In next-hop-local mode, you can configure a BGP speaker to set its IP address of as the next hop of the routes to be advertised to IBGP peers or IBGP peer groups. In next-hop-invariable mode, you can configure PEs in different ASs not to change the next hop of routes when the PEs advertise the routes to their EBGP peers and use the next hop addresses of IGP routes to advertise imported IGP routes to IBGP peers. By default, when a BGP speaker advertises routes to EBGP peers and imported IGP routes to IBGP peers, the BGP speaker changes the next hop to its interface address.";
                  }
                  uses peer-policy-filter-type;
                  leaf advertise-ext-community {
                    type boolean;
                    default "false";
                    description
                      "Enable/disable advertise the extended community attribute to a peer or peer group.";
                  }
                  leaf origin-as-validation {
                    when "../advertise-ext-community='true' and ../../../../peer-establish-mode='static'" {
                      tailf:xpath-root 3;
                    }
                    type boolean;
                    default "false";
                    description
                      "Enable/disable the BGP peer origin validation.";
                  }
                  leaf discard-ext-community {
                    type boolean;
                    default "false";
                    description
                      "Enable/disable discard the extended community attribute in the routing information about a specified peer.";
                  }
                  leaf allow-as-loop {
                    type uint32 {
                      range "1..10";
                    }
                    description
                      "Allow repetitive local AS numbers. By default, repetitive local AS numbers are not allowed.";
                  }
                  leaf aigp {
                    when "../../../../../../../../ni:name='_public_'" {
                      tailf:xpath-root 3;
                    }
                    type boolean;
                    default "false";
                    description
                      "Enable/disable route with AIGP attribute advertisement to or from a peer.";
                  }
                  uses default-route-advertise-type;
                  leaf default-route-match-mode {
                    when "../default-route-advertise='true'" {
                      tailf:xpath-root 3;
                    }
                    type cra-match-mode;
                    default "null";
                    description
                      "Configure the matching mode of default route advertisement, which can be disabling of route advertisement conditions, enabling of all route advertisement conditions, and enabling of part route advertisement conditions. Enabling of all route advertisement conditions indicates that a default route can be advertised only when it matches all the conditions. Enabling of part route advertisement conditions indicates that a default route can be advertised only when it matches one condition.";
                  }
                  leaf add-path-mode {
                    when "../../../../../../../../ni:name='_public_' and ../../../../bgp:type='ibgp'" {
                      tailf:xpath-root 3;
                    }
                    type add-path-cap-type;
                    default "null";
                    description
                      "Enable Add-Path route advertisement to a peer.";
                  }
                  uses ipv6-prefix-filter-type;
                  uses as-path-filter-type;
                  uses peer-group-acl6-name-or-num-type;
                  uses rt-update-interval-type;
                  uses preferred-value-type;
                  leaf add-path-number {
                    when "../../../../../../../../ni:name='_public_' and ../../../../bgp:type='ibgp'" {
                      tailf:xpath-root 3;
                    }
                    type uint8 {
                      range "2..64";
                    }
                    description
                      "Number of Add-Path routes that can be advertised to a peer.";
                  }
                  leaf substitute-as-enable {
                    when "../../../../bgp:type='ebgp'" {
                      tailf:xpath-root 3;
                    }
                    type boolean;
                    default "false";
                    description
                      "Enable/disable replace the AS number of a specified peer in the AS_Path attribute with the local AS number. On a PE where AS number replacement is enabled, if an AS number in the AS_Path attribute of a route is same as that of the CE to which the PE advertises the route, the PE replaces the AS number with its own AS number before advertising the route.";
                  }
                  leaf soo {
                    when "../../../../../../../../ni:name!='_public_'" {
                      tailf:xpath-root 3;
                    }
                    type string {
                      length "3..21";
                    }
                    description
                      "Configure the Site-of-Origin (SoO) extended community attribute. This attribute can be expressed in the following formats: X.X.X.X:number<0-65535>, number<0-65535>:number<0-4294967295>, or number<0-65535>.number<0-65535>:number<0-65535> or <65536-4294967295>:<0-65535>. 0:0 or 0.0:0 is not supported.
                       Two CEs are in the same site and can advertise routes to each other, and they are connected to a VPN through PEs. If the local routes of a CE are advertised to the other CE over the VPN, a routing loop may occur.
                       The SoO feature can prevent a route advertised by a site from being sent back to the site, preventing routing loops. After SoO is enabled and a PE receives a route from a CE, the specified SoO attribute will be added to the route. Before advertising the route to the other CE, the PE checks the SoO attribute. If the SoO attribute is the same as the locally configured SoO attribute, the PE does not advertise the route, preventing routing loops.";
                  }
                  leaf keep-all-routes {
                    when "/bgp:bgp/bgp:base-process/bgp:keep-all-routes='false'" {
                      tailf:xpath-root 3;
                    }
                    type boolean;
                    default "false";
                    description
                      "Enable/disable saving all the updated information about BGP routes from a specified peer or peer group after a BGP connection is established, even though these BGP routes fail to match the routing policy on the ingress. By default, the updated information about BGP routes from a specified peer is saved only when the routes match the routing policy on the ingress. If a router supports route refreshing, this option is not required.";
                  }
                  leaf advertise-best-external {
                    when "../../../../../../../../ni:name='_public_' and ../../../../bgp:type='ibgp'" {
                      tailf:xpath-root 3;
                    }
                    type boolean;
                    must "../reflect-client='false' or ../advertise-best-external='false'" {
                      tailf:xpath-root 3;
                    }
                    must "../add-path-mode='null' or not(../add-path-mode) or ../advertise-best-external='false'" {
                      tailf:xpath-root 3;
                    }
                    must "not(../add-path-number and ../advertise-best-external='true')" {
                      tailf:xpath-root 3;
                    }
                    default "false";
                    description
                      "Enable/disable the device to advertise Best External routes to peers.";
                  }
                  leaf load-balancing-enable {
                    type boolean;
                    default "false";
                    description
                      "Enable/disable a neighbour to participate in load balancing.";
                  }
                  choice load-balancing-ignore-as-type {
                    description
                      "Set load balancing as path type.";
                    case as-attribute {
                      description
                        "Ignore the as-path attribute.";
                      leaf load-balancing-as-path-ignore {
                        when "../load-balancing-enable='true'" {
                          tailf:xpath-root 3;
                        }
                        type empty;
                        description
                          "Configure BGP to ignore the AS_Path attribute when selecting the equal route. After as-path-neglect is selected, BGP does not compare the AS_Path length.";
                      }
                    }
                    case same-length-as-attribute {
                      description
                        "Ignore comparison of as-path attributes with the same length.";
                      leaf load-balancing-as-path-relax {
                        when "../load-balancing-enable='true'" {
                          tailf:xpath-root 3;
                        }
                        type empty;
                        description
                          "Configure BGP to ignore comparison of AS_Path attributes with the same length when selecting the equal route. After as-path-neglect is selected, BGP does not compare the AS_Path length.";
                      }
                    }
                  }
                  leaf prefix-sid {
                    when "../../../../../../../../ni:name='_public_'" {
                      tailf:xpath-root 3;
                    }
                    type boolean;
                    default "false";
                    description
                      "Enable/disable a device to exchange IPv4 prefix SIDs with a specified IPv6 peer group.";
                  }
                  choice prefix-sid-packet {
                    description
                      "Prefix-sid packet method.";
                    case sid-type5 {
                      description
                        "Packet by type5.";
                      leaf advertise-srv6-locator {
                        when "../prefix-sid='true'" {
                          tailf:xpath-root 3;
                        }
                        type empty;
                        description
                          "Advertise SRv6 locators.";
                      }
                    }
                  }
                  uses advertise-large-community-group-type;
                  uses group-independent-peer-group-type;
                  uses ipv6-default-route-match-conditions-type;
                  uses route-limit-accept-type;
                  uses public-as-only-type;
                  uses group-public-as-only-import-type;
                  uses advertise-dependent-filter6-group-type;
                }
                container ipv4-vpn {
                  when "../type = 'ipv4vpn'" {
                    tailf:xpath-root 3;
                  }
                  description
                    "Configure IPv4 vpnv4 options.";
                  leaf advertise-community {
                    type boolean;
                    default "false";
                    description
                      "Enable/disable advertise the community attribute to a peer or a peer group.";
                  }
                  leaf reflect-client {
                    when "../../../../bgp:type='ibgp'" {
                      tailf:xpath-root 3;
                    }
                    type boolean;
                    default "false";
                    description
                      "Enable/disable the local device as a route reflector (RR) and a peer or peer group as its client. This configuration is applicable between IBGP peers only. The configurations of RRs and its clients in an address family are valid only in this address family. Therefore, it is recommended to configure RRs and its clients in the specified address family that is required.";
                  }
                  leaf nexthop-configure {
                    type nexthop-configuration-type;
                    description
                      "Both the next-hop-local mode and next-hop-invariable mode are available when the peer address family is the VPNv4/VPNV6/L2VPN AD address family. Only the next-hop-local mode is available when the peer address family is not VPNv4/VPNV6/L2VPN AD address family. In next-hop-local mode, you can configure a BGP speaker to set its IP address of as the next hop of the routes to be advertised to IBGP peers or IBGP peer groups. In next-hop-invariable mode, you can configure PEs in different ASs not to change the next hop of routes when the PEs advertise the routes to their EBGP peers and use the next hop addresses of IGP routes to advertise imported IGP routes to IBGP peers. By default, when a BGP speaker advertises routes to EBGP peers and imported IGP routes to IBGP peers, the BGP speaker changes the next hop to its interface address.";
                  }
                  uses peer-policy-filter-type;
                  leaf ignore-bit-error {
                    when '../export-policy or ../export-filter' {
                      tailf:xpath-root 3;
                    }
                    type boolean;
                    default "false";
                    description
                      "Enable/disable the peer to ignore bit error detection results.";
                  }
                  leaf allow-as-loop {
                    type uint32 {
                      range "1..10";
                    }
                    description
                      "Allow repetitive local AS numbers. By default, repetitive local AS numbers are not allowed.";
                  }
                  leaf aigp {
                    type boolean;
                    default "false";
                    description
                      "Enable/disable route with AIGP attribute advertisement to or from a peer.";
                  }
                  leaf add-path-mode {
                    when "../../../../bgp:type='ibgp'" {
                      tailf:xpath-root 3;
                    }
                    type add-path-cap-type;
                    default "null";
                    description
                      "Enable Add-Path route advertisement to a peer.";
                  }
                  uses ip-prefix-filter-type;
                  uses peer-ipv4-reoriginate-type;
                  uses as-path-filter-type;
                  uses peer-group-acl-name-or-num-type;
                  uses rt-update-interval-type;
                  uses preferred-value-type;
                  leaf add-path-number {
                    when "../../../../bgp:type='ibgp'" {
                      tailf:xpath-root 3;
                    }
                    type uint8 {
                      range "2..64";
                    }
                    description
                      "Number of Add-Path routes that can be advertised to a peer.";
                  }
                  leaf upe {
                    type boolean;
                    default "false";
                    description
                      "Enable/disable the peer as an underlayer PE (UPE).";
                  }
                  leaf advertise-best-external {
                    when "../../../../bgp:type='ibgp'" {
                      tailf:xpath-root 3;
                    }
                    type boolean;
                    must "../reflect-client='false' or ../advertise-best-external='false'" {
                      tailf:xpath-root 3;
                    }
                    must "../add-path-mode='null' or not(../add-path-mode) or ../advertise-best-external='false'" {
                      tailf:xpath-root 3;
                    }
                    must "not(../add-path-number and ../advertise-best-external='true')" {
                      tailf:xpath-root 3;
                    }
                    default "false";
                    description
                      "Enable/disable the device to advertise Best External routes to peers.";
                  }
                  uses advertise-large-community-group-type;
                  leaf keep-all-routes {
                    when "/bgp:bgp/bgp:base-process/bgp:keep-all-routes='false'" {
                      tailf:xpath-root 3;
                    }
                    type boolean;
                    default "false";
                    description
                      "Enable/disable saving all the updated information about BGP routes from a specified peer or peer group after a BGP connection is established, even though these BGP routes fail to match the routing policy on the ingress. By default, the updated information about BGP routes from a specified peer is saved only when the routes match the routing policy on the ingress. If a router supports route refreshing, this option is not required.";
                  }
                  uses group-independent-peer-group-type;
                  leaf origin-as-validation {
                    when "../../../../peer-establish-mode='static'" {
                      tailf:xpath-root 3;
                    }
                    type boolean;
                    default "false";
                    description
                      "Enable/disable the BGP peer origin validation.";
                  }
                  container default-route-originates {
                    description
                      "Configure advertised default VPNv4 routes.";
                    uses default-route-originate-type;
                  }
                  uses route-limit-type;
                  uses public-as-only-type;
                  uses group-public-as-only-import-type;
                }
                container ipv6-vpn {
                  when "../type = 'ipv6vpn'" {
                    tailf:xpath-root 3;
                  }
                  description
                    "Configure IPv6 vpn options.";
                  leaf advertise-community {
                    type boolean;
                    default "false";
                    description
                      "Enable/disable advertise the community attribute to a peer or a peer group.";
                  }
                  leaf reflect-client {
                    when "../../../../bgp:type='ibgp'" {
                      tailf:xpath-root 3;
                    }
                    type boolean;
                    default "false";
                    description
                      "Enable/disable the local device as a route reflector (RR) and a peer or peer group as its client. This configuration is applicable between IBGP peers only. The configurations of RRs and its clients in an address family are valid only in this address family. Therefore, it is recommended to configure RRs and its clients in the specified address family that is required.";
                  }
                  leaf nexthop-configure {
                    type nexthop-configuration-type;
                    description
                      "Both the next-hop-local mode and next-hop-invariable mode are available when the peer address family is the VPNv4/VPNV6/L2VPN AD address family. Only the next-hop-local mode is available when the peer address family is not VPNv4/VPNV6/L2VPN AD address family. In next-hop-local mode, you can configure a BGP speaker to set its IP address of as the next hop of the routes to be advertised to IBGP peers or IBGP peer groups. In next-hop-invariable mode, you can configure PEs in different ASs not to change the next hop of routes when the PEs advertise the routes to their EBGP peers and use the next hop addresses of IGP routes to advertise imported IGP routes to IBGP peers. By default, when a BGP speaker advertises routes to EBGP peers and imported IGP routes to IBGP peers, the BGP speaker changes the next hop to its interface address.";
                  }
                  uses peer-policy-filter-type;
                  leaf ignore-bit-error {
                    when '../export-policy or ../export-filter' {
                      tailf:xpath-root 3;
                    }
                    type boolean;
                    default "false";
                    description
                      "Enable/disable the peer to ignore bit error detection results.";
                  }
                  leaf allow-as-loop {
                    type uint32 {
                      range "1..10";
                    }
                    description
                      "Allow repetitive local AS numbers. By default, repetitive local AS numbers are not allowed.";
                  }
                  leaf aigp {
                    type boolean;
                    default "false";
                    description
                      "Enable/disable route with AIGP attribute advertisement to or from a peer.";
                  }
                  leaf add-path-mode {
                    when "../../../../bgp:type='ibgp'" {
                      tailf:xpath-root 3;
                    }
                    type add-path-cap-type;
                    default "null";
                    description
                      "Enable Add-Path route advertisement to a peer.";
                  }
                  uses ipv6-prefix-filter-type;
                  leaf reoriginate-route-enable {
                    type boolean;
                    default "false";
                    description
                      "Enable/disable route regeneration.";
                  }
                  leaf reoriginate-ipv6-enable {
                    type boolean;
                    default "false";
                    description
                      "Enable/disable IP route regeneration and advertisement.";
                  }
                  leaf reoriginate-mac-ipv6-enable {
                    type boolean;
                    default "false";
                    description
                      "Enable/disable MAC-IP route regeneration and advertisement.";
                  }
                  uses as-path-filter-type;
                  uses peer-group-acl6-name-or-num-type;
                  uses rt-update-interval-type;
                  uses preferred-value-type;
                  leaf add-path-number {
                    when "../../../../bgp:type='ibgp'" {
                      tailf:xpath-root 3;
                    }
                    type uint8 {
                      range "2..64";
                    }
                    description
                      "Number of Add-Path routes that can be advertised to a peer.";
                  }
                  leaf advertise-best-external {
                    when "../../../../bgp:type='ibgp'" {
                      tailf:xpath-root 3;
                    }
                    type boolean;
                    must "../reflect-client='false' or ../advertise-best-external='false'" {
                      tailf:xpath-root 3;
                    }
                    must "../add-path-mode='null' or not(../add-path-mode) or ../advertise-best-external='false'" {
                      tailf:xpath-root 3;
                    }
                    must "not(../add-path-number and ../advertise-best-external='true')" {
                      tailf:xpath-root 3;
                    }
                    default "false";
                    description
                      "Enable/disable the device to advertise Best External routes to peers.";
                  }
                  uses advertise-large-community-group-type;
                  leaf keep-all-routes {
                    when "/bgp:bgp/bgp:base-process/bgp:keep-all-routes='false'" {
                      tailf:xpath-root 3;
                    }
                    type boolean;
                    default "false";
                    description
                      "Enable/disable saving all the updated information about BGP routes from a specified peer or peer group after a BGP connection is established, even though these BGP routes fail to match the routing policy on the ingress. By default, the updated information about BGP routes from a specified peer is saved only when the routes match the routing policy on the ingress. If a router supports route refreshing, this option is not required.";
                  }
                  uses group-independent-peer-group-type;
                  leaf origin-as-validation {
                    when "../../../../peer-establish-mode='static'" {
                      tailf:xpath-root 3;
                    }
                    type boolean;
                    default "false";
                    description
                      "Enable/disable the BGP peer origin validation.";
                  }
                  uses route-limit-type;
                  uses public-as-only-type;
                  uses group-public-as-only-import-type;
                }
                container ipv4-labeluni {
                  when "../type = 'ipv4labeluni'" {
                    tailf:xpath-root 3;
                  }
                  description
                    "Configure IPv4 label unicast options.";
                  leaf advertise-community {
                    type boolean;
                    default "false";
                    description
                      "Enable/disable advertise the community attribute to a peer or a peer group.";
                  }
                  leaf reflect-client {
                    when "../../../../bgp:type='ibgp'" {
                      tailf:xpath-root 3;
                    }
                    type boolean;
                    default "false";
                    description
                      "Enable/disable the local device as a route reflector (RR) and a peer or peer group as its client. This configuration is applicable between IBGP peers only. The configurations of RRs and its clients in an address family are valid only in this address family. Therefore, it is recommended to configure RRs and its clients in the specified address family that is required.";
                  }
                  leaf check-tunnel-reachable {
                    type boolean;
                    default "false";
                    description
                      "Enable/disable tunnel reachability check.";
                  }
                  uses peer-policy-filter-type;
                  leaf advertise-ext-community {
                    type boolean;
                    default "false";
                    description
                      "Enable/disable advertise the extended community attribute to a peer or peer group.";
                  }
                  leaf discard-ext-community {
                    type boolean;
                    default "false";
                    description
                      "Enable/disable discard the extended community attribute in the routing information about a specified peer.";
                  }
                  leaf allow-as-loop {
                    type uint32 {
                      range "1..10";
                    }
                    description
                      "Allow repetitive local AS numbers. By default, repetitive local AS numbers are not allowed.";
                  }
                  leaf aigp {
                    when "../../../../../../../../ni:name='_public_'" {
                      tailf:xpath-root 3;
                    }
                    type boolean;
                    default "false";
                    description
                      "Enable/disable route with AIGP attribute advertisement to or from a peer.";
                  }
                  leaf add-path-mode {
                    when "../../../../../../../../ni:name='_public_' and ../../../../bgp:type='ibgp'" {
                      tailf:xpath-root 3;
                    }
                    type add-path-cap-type;
                    default "null";
                    description
                      "Enable Add-Path route advertisement to a peer.";
                  }
                  uses ip-prefix-filter-type;
                  uses as-path-filter-type;
                  uses peer-group-acl-name-or-num-type;
                  uses rt-update-interval-type;
                  leaf nexthop-configure {
                    type nexthop-configuration-type;
                    description
                      "Both the next-hop-local mode and next-hop-invariable mode are available when the peer address family is the VPNv4/VPNV6/L2VPN AD address family. Only the next-hop-local mode is available when the peer address family is not VPNv4/VPNV6/L2VPN AD address family. In next-hop-local mode, you can configure a BGP speaker to set its IP address of as the next hop of the routes to be advertised to IBGP peers or IBGP peer groups. In next-hop-invariable mode, you can configure PEs in different ASs not to change the next hop of routes when the PEs advertise the routes to their EBGP peers and use the next hop addresses of IGP routes to advertise imported IGP routes to IBGP peers. By default, when a BGP speaker advertises routes to EBGP peers and imported IGP routes to IBGP peers, the BGP speaker changes the next hop to its interface address.";
                  }
                  uses preferred-value-type;
                  leaf exp-mode {
                    when "../../../../../../../../ni:name!='_public_'" {
                      tailf:xpath-root 3;
                    }
                    type exp-mode-type;
                    default "null";
                    description
                      "Specify the ASs in which a BGP label can inherit the QoS priority carried in the outer label of public tunnel in the Core AS and the ASs in which the priorities of BGP LSPs must be restored before the LSPs are advertised to a non-core AS.";
                  }
                  leaf add-path-number {
                    when "../../../../../../../../ni:name='_public_' and ../../../../bgp:type='ibgp'" {
                      tailf:xpath-root 3;
                    }
                    type uint8 {
                      range "2..64";
                    }
                    description
                      "Number of Add-Path routes that can be advertised to a peer.";
                  }
                  leaf substitute-as-enable {
                    when "../../../../bgp:type='ebgp'" {
                      tailf:xpath-root 3;
                    }
                    type boolean;
                    default "false";
                    description
                      "Enable/disable replace the AS number of a specified peer in the AS_Path attribute with the local AS number. On a PE where AS number replacement is enabled, if an AS number in the AS_Path attribute of a route is same as that of the CE to which the PE advertises the route, the PE replaces the AS number with its own AS number before advertising the route.";
                  }
                  leaf soo {
                    when "../../../../../../../../ni:name!='_public_'" {
                      tailf:xpath-root 3;
                    }
                    type string {
                      length "3..21";
                    }
                    description
                      "Configure the Site-of-Origin (SoO) extended community attribute. This attribute can be expressed in the following formats: X.X.X.X:number<0-65535>, number<0-65535>:number<0-4294967295>, or number<0-65535>.number<0-65535>:number<0-65535> or <65536-4294967295>:<0-65535>. 0:0 or 0.0:0 is not supported.
                       Two CEs are in the same site and can advertise routes to each other, and they are connected to a VPN through PEs. If the local routes of a CE are advertised to the other CE over the VPN, a routing loop may occur.
                       The SoO feature can prevent a route advertised by a site from being sent back to the site, preventing routing loops. After SoO is enabled and a PE receives a route from a CE, the specified SoO attribute will be added to the route. Before advertising the route to the other CE, the PE checks the SoO attribute. If the SoO attribute is the same as the locally configured SoO attribute, the PE does not advertise the route, preventing routing loops.";
                  }
                  leaf advertise-best-external {
                    when "../../../../../../../../ni:name='_public_' and ../../../../bgp:type='ibgp'" {
                      tailf:xpath-root 3;
                    }
                    type boolean;
                    must "../reflect-client='false' or ../advertise-best-external='false'" {
                      tailf:xpath-root 3;
                    }
                    must "../add-path-mode='null' or not(../add-path-mode) or ../advertise-best-external='false'" {
                      tailf:xpath-root 3;
                    }
                    must "not(../add-path-number and ../advertise-best-external='true')" {
                      tailf:xpath-root 3;
                    }
                    default "false";
                    description
                      "Enable/disable the device to advertise Best External routes to peers.";
                  }
                  leaf load-balancing-enable {
                    when "../../../../../../../../ni:name='_public_'" {
                      tailf:xpath-root 3;
                    }
                    type boolean;
                    default "false";
                    description
                      "Enable/disable a neighbour to participate in load balancing.";
                  }
                  choice load-balancing-ignore-as-type {
                    description
                      "Set load balancing as path type.";
                    case as-attribute {
                      description
                        "Ignore the as-path attribute.";
                      leaf load-balancing-as-path-ignore {
                        when "../load-balancing-enable='true'" {
                          tailf:xpath-root 3;
                        }
                        type empty;
                        description
                          "Configure BGP to ignore the AS_Path attribute when selecting the equal route. After as-path-neglect is selected, BGP does not compare the AS_Path length.";
                      }
                    }
                    case same-length-as-attribute {
                      description
                        "Ignore comparison of as-path attributes with the same length.";
                      leaf load-balancing-as-path-relax {
                        when "../load-balancing-enable='true'" {
                          tailf:xpath-root 3;
                        }
                        type empty;
                        description
                          "Configure BGP to ignore comparison of AS_Path attributes with the same length when selecting the equal route. After as-path-neglect is selected, BGP does not compare the AS_Path length.";
                      }
                    }
                  }
                  uses advertise-large-community-group-type;
                  uses group-independent-peer-group-type;
                  uses route-limit-accept-type;
                  uses public-as-only-type;
                  uses group-public-as-only-import-type;
                  container entropy-label-parameter {
                    when "../../../../../../../../ni:name='_public_'" {
                      tailf:xpath-root 3;
                    }
                    description
                      "Configure information about entropy label parameter in a peer group.";
                    uses group-entropy-label-type;
                  }
                }
                container ipv4-multicast {
                  when "../type='ipv4multi'" {
                    tailf:xpath-root 3;
                  }
                  description
                    "Configure IPv4 multicast options.";
                  uses default-route-advertise-type;
                  uses ip-prefix-filter-type;
                  uses as-path-filter-type;
                  uses peer-group-acl-name-or-num-type;
                  leaf advertise-ext-community {
                    type boolean;
                    default "false";
                    description
                      "Enable/disable advertise the extended community attribute to a peer or peer group.";
                  }
                  leaf discard-ext-community {
                    type boolean;
                    default "false";
                    description
                      "Enable/disable discard the extended community attribute in the routing information about a specified peer.";
                  }
                  leaf allow-as-loop {
                    type uint32 {
                      range "1..10";
                    }
                    description
                      "Allow repetitive local AS numbers. By default, repetitive local AS numbers are not allowed.";
                  }
                  leaf nexthop-configure {
                    type nexthop-configuration-type;
                    must "../nexthop-configure='local'" {
                      tailf:xpath-root 3;
                    }
                    description
                      "Both the next-hop-local mode and next-hop-invariable mode are available when the peer address family is the VPNv4/VPNV6/L2VPN AD address family. Only the next-hop-local mode is available when the peer address family is not VPNv4/VPNV6/L2VPN AD address family. In next-hop-local mode, you can configure a BGP speaker to set its IP address of as the next hop of the routes to be advertised to IBGP peers or IBGP peer groups. In next-hop-invariable mode, you can configure PEs in different ASs not to change the next hop of routes when the PEs advertise the routes to their EBGP peers and use the next hop addresses of IGP routes to advertise imported IGP routes to IBGP peers. By default, when a BGP speaker advertises routes to EBGP peers and imported IGP routes to IBGP peers, the BGP speaker changes the next hop to its interface address.";
                  }
                  leaf advertise-community {
                    type boolean;
                    default "false";
                    description
                      "Enable/disable advertise the community attribute to a peer or a peer group.";
                  }
                  leaf keep-all-routes {
                    when "/bgp:bgp/bgp:base-process/bgp:keep-all-routes='false'" {
                      tailf:xpath-root 3;
                    }
                    type boolean;
                    default "false";
                    description
                      "Enable/disable saving all the updated information about BGP routes from a specified peer or peer group after a BGP connection is established, even though these BGP routes fail to match the routing policy on the ingress. By default, the updated information about BGP routes from a specified peer is saved only when the routes match the routing policy on the ingress. If a router supports route refreshing, this option is not required.";
                  }
                  uses peer-policy-filter-type;
                  leaf reflect-client {
                    when "../../../../bgp:type='ibgp'" {
                      tailf:xpath-root 3;
                    }
                    type boolean;
                    default "false";
                    description
                      "Enable/disable the local device as a route reflector (RR) and a peer or peer group as its client. This configuration is applicable between IBGP peers only. The configurations of RRs and its clients in an address family are valid only in this address family. Therefore, it is recommended to configure RRs and its clients in the specified address family that is required.";
                  }
                  leaf load-balancing-enable {
                    type boolean;
                    default "false";
                    description
                      "Enable/disable a neighbour to participate in load balancing.";
                  }
                  choice load-balancing-ignore-as-type {
                    description
                      "Set load balancing as path type.";
                    case as-attribute {
                      description
                        "Ignore the as-path attribute.";
                      leaf load-balancing-as-path-ignore {
                        when "../load-balancing-enable='true'" {
                          tailf:xpath-root 3;
                        }
                        type empty;
                        description
                          "Configure BGP to ignore the AS_Path attribute when selecting the equal route. After as-path-neglect is selected, BGP does not compare the AS_Path length.";
                      }
                    }
                    case same-length-as-attribute {
                      description
                        "Ignore comparison of as-path attributes with the same length.";
                      leaf load-balancing-as-path-relax {
                        when "../load-balancing-enable='true'" {
                          tailf:xpath-root 3;
                        }
                        type empty;
                        description
                          "Configure BGP to ignore comparison of AS_Path attributes with the same length when selecting the equal route. After as-path-neglect is selected, BGP does not compare the AS_Path length.";
                      }
                    }
                  }
                  uses advertise-large-community-group-type;
                  uses rt-update-interval-type;
                  uses bgp:preferred-value-type;
                  uses group-independent-peer-group-type;
                  uses route-limit-type;
                  uses public-as-only-type;
                  uses group-public-as-only-import-type;
                }
              }
            }
          }
        }
        container peers {
          description
            "List of BGP peers.";
          list peer {
            key "address";
            description
              "Configure a single BGP peer.";
            leaf address {
              type inet:ip-address-no-zone;
              description
                "Connection address of a peer, which can be an IPv4 or IPv6 address.";
            }
            leaf remote-as {
              type as-number-validate;
              mandatory true;
              description
                "AS number of a peer, which must be selected or group name when creating, and which can be in either two-byte format or four-byte format:
                 The two-byte format is X. X is an integer ranging from 1 to 65535.
                 The four-byte format is X.Y and X. When the format is X.Y, X and Y are both integers, with the value of X ranging from 1 to 65535, and the value of Y ranging from 0 to 65535; when the format is X, X is an interger, with the value of X ranging from 1 to 4294967295.
                 The object cannot be modified.";
              ext:operation-exclude "update" {
                description
                  "The node cannot be modified, when node is already configured.";
              }
            }
            leaf group-name {
              type leafref {
                path "../../../peer-groups/peer-group/name";
              }
              must "../../../peer-groups/peer-group[name = current()]/peer-establish-mode = 'static'" {
                tailf:xpath-root 3;
              }
              description
                "Specify the name of a peer group that BGP peers need to join. That must be selected group name or AS when creating, and the value is a string, spaces not supported. By default, BGP peers join no peer group. BGP peers distinguish the peer group type when joining a peer group. IBGP peers cannot join an EBGP peer group. BGP peers will be deleted when they leave a peer group. The object cannot be modified.";
              ext:operation-exclude "update" {
                description
                  "The node cannot be modified, when the peer already belongs to a peer-group.";
              }
            }
            uses peer-local-if-type;
            uses authentication-attr-type;
            leaf description {
              type string {
                length "1..255";
                pattern '([^?]*)';
              }
              description
                "Description of a peer, which can be letters or digits. The description is a string, spaces supported. By default, no description is configured for a peer.";
            }
            leaf ebgp-max-hop {
              type uint32 {
                range "1..255";
              }
              must 'not(../valid-ttl-hops) or (../valid-ttl-hops>=1 and ../valid-ttl-hops<=255 and ../ebgp-max-hop=1)' {
                tailf:xpath-root 3;
              }
              description
                "Maximum number of hops in an indirect EBGP connection. By default, EBGP connections can be established only between directly connected peers. The function must be configured on both ends. By default, value is determined by the neighbor type, the default value of EBGP is 1 and the default value of IBGP is 0.";
            }
            uses peer-tracking-type;
            leaf conventional {
              type boolean;
              default "false";
              description
                "Enable/disable general router functions on peers. In conventional mode, not all the extended router functions, such as, route refreshing, GR, and multi-address family negotiation, are available. Therefore, the router of a new version can be compatible with the routers of earlier versions.";
            }
            leaf route-refresh {
              type boolean;
              default "true";
              description
                "Enable/disable BGP to advertise Refresh messages to peers.";
            }
            leaf four-byte-as {
              type boolean;
              default "true";
              description
                "Enable/disable BGP to advertise routes carrying 4-byte AS numbers to peers. After the 4-byte AS number function is disabled, Open packets will not carry 4-byte AS number capability flag, and peer ends will not know that local ends have the 4-byte AS number function. The 4-byte AS number function cannot be disabled from peers (peer groups) if a 4-byte AS number, fake AS number, or confederation ID is configured on a router and the AS number of a peer is 4-byte. If the 4-byte AS number function is disabled in such a situation, BGP sessions may fail to be established, and route transmission may be affected.";
            }
            leaf ignore {
              type boolean;
              default "false";
              description
                "Enable/disable the function to tear down sessions between peers and clear all related routing information.";
            }
            leaf valid-ttl-hops {
              type uint16 {
                range "1..255";
              }
              must 'not(../ebgp-max-hop and ../ebgp-max-hop>1 and ../ebgp-max-hop<=255)' {
                tailf:xpath-root 3;
              }
              description
                "Enable GTSM on a peer or peer group. The valid-TTL-Value parameter is used to specify the number of TTL hops to be detected. If the value is configured as hops, the valid TTL range of the detected packet is [255-hops+1, 255].";
            }
            leaf connect-mode {
              type connect-mode;
              default "null";
              description
                "The value can be Connect-only, Listen-only, or Both. If the value is Connect-only, the specified peer or peer group only initiatively sends connection requests, instead of listening to connection requests. If the value is Listen-only, the specified peer or peer group only listens to connection requests, instead of initiatively sending connection requests. If the value is Both, the specified peer or peer group not only initiatively sends connection requests, but also listens to connection requests. The default value is Both.";
            }
            leaf log-change {
              type boolean;
              default "true";
              description
                "Enable/disable BGP to record the session status and events of the specified peer or peer group.";
            }
            leaf path-mtu-auto-discovery {
              type boolean;
              default "false";
              description
                "Enable/disable path mtu auto discovery.";
            }
            leaf local-ifnet-disable {
              type boolean;
              description
                "Enable/disable MPLS local IFNET tunnel creation on a BGP IPv4 peer. By default, MPLS local IFNET tunnels can be created on an EBGP peer,but such tunnels cannot be created on an IBGP peer.";
              ext:dynamic-default;
            }
            leaf check-first-as {
              type peer-cap-config-state;
              default "default";
              description
                "Check the first AS in the AS_Path of the update messages from EBGP peers.";
            }
            leaf egress-engineer {
              when "../../../../../ni:name='_public_'" {
                tailf:xpath-root 3;
              }
              type epe-state;
              default "default";
              description
                "BGP Egress Peer Engineering (BGP-EPE) is enable or disable. The default value is default (The function is disable, If the neighbour joins the group, the function is Inheritance group).";
            }
            leaf tcp-mss {
              type uint16 {
                range "176..4096";
              }
              description
                "Maximum TCP MSS value used for TCP connection establishment for a peer.";
            }
            leaf memory-priority {
              type peer-memory-priority;
              default "default";
              description
                "Set a priority that determines the disconnection order of a BGP peer relationship if memory overload occurs.";
            }
            // NCS drop config false leaf 'memory-priority-capability'
            leaf oscillation-dampening {
              type peer-attr-enable-type;
              description
                "Enable/disable BGP to suppress the establishment of a specified peer relationship that flaps continuously. By default, the capability is enabled.";
            }
            // NCS drop config false container 'effect-state'
            uses fake-as-type;
            uses peer-timer-para-type;
            uses peer-bfd-parameter-type;
            // NCS drop config false container 'bfd-parameter-state'
            container egress-engineer-parameter {
              when "../egress-engineer='enable'" {
                tailf:xpath-root 3;
              }
              description
                "Configure BGP peer egress engineering information.";
              leaf static-label {
                type uint32 {
                  range "16..1048575";
                }
                description
                  "The static label for BGP EPE.";
              }
              leaf label-pop {
                when '../static-label' {
                  tailf:xpath-root 3;
                }
                type boolean;
                must "not(../relate-bfd='true' and ../label-pop='true')" {
                  tailf:xpath-root 3;
                }
                default "false";
                description
                  "Enable/disable the BGP-EPE label popping function.";
              }
              leaf relate-bfd {
                type boolean;
                must "not(../relate-bfd='true' and ../label-pop='true')" {
                  tailf:xpath-root 3;
                }
                default "false";
                description
                  "Enable/disable association between the BGP-EPE label and BFD status.";
              }
              leaf peer-set-name {
                type leafref {
                  path "../../../../bgp:egress-engineer-peer-sets/bgp:egress-engineer-peer-set/bgp:peer-set-name";
                }
                description
                  "Add peer to peer set.";
              }
            }
            container graceful-restart {
              description
                "Configure graceful restart.";
              uses peer-graceful-restart-type;
              leaf peer-reset {
                type peer-comm-config-type;
                default "default";
                description
                  "Enable/disable reseting BGP peer graceful.";
              }
              // NCS drop config false leaf 'effect-peer-reset'
            }
            container local-graceful-restart {
              description
                "Configure local graceful restart.";
              uses peer-graceful-restart-type;
            }
            container afs {
              description
                "List of peers in a specified address family.";
              list af {
                key "type";
                description
                  "Configure peer in a specified address family.";
                leaf type {
                  type bgp:af-type;
                  must '../../../../../afs/af[type = current()]' {
                    tailf:xpath-root 3;
                  }
                  description
                    "Specify the address family type to set the peer enable.";
                }
                container ipv4-unicast {
                  when "../type='ipv4uni'" {
                    tailf:xpath-root 3;
                  }
                  description
                    "Configure IPv4 unicast options.";
                  leaf group-name {
                    type leafref {
                      path "../../../../../../peer-groups/peer-group/name";
                    }
                    must "../../../../../../peer-groups/peer-group[name = current()]/afs/af[type = 'ipv4uni']" {
                      tailf:xpath-root 3;
                    }
                    must "../../../../../../peer-groups/peer-group[name = current()]/peer-establish-mode = 'static'" {
                      tailf:xpath-root 3;
                    }
                    description
                      "Configure a name for a peer group. After a peer is deleted from the peer group, the peer is disabled from the address family. The object cannot be modified.";
                    ext:operation-exclude "update" {
                      description
                        "The node cannot be modified, when the peer already belongs to a peer-group.";
                    }
                  }
                  leaf advertise-community {
                    type boolean;
                    default "false";
                    description
                      "Enable/disable advertise the community attribute to a peer or a peer group.";
                  }
                  leaf reflect-client {
                    type boolean;
                    default "false";
                    description
                      "Enable/disable the local device as a route reflector (RR) and a peer or peer group as its client. This configuration is applicable between IBGP peers only. The configurations of RRs and its clients in an address family are valid only in this address family. Therefore, it is recommended to configure RRs and its clients in the specified address family that is required.";
                  }
                  leaf orf-type {
                    when "../../../../../../../../ni:name='_public_'" {
                      tailf:xpath-root 3;
                    }
                    type bgp:bgp-orf-type;
                    must "(../orf-mode='null' and ../orf-type='null') or (../orf-mode!='null' and ../orf-type!='null')" {
                      tailf:xpath-root 3;
                    }
                    default "null";
                    description
                      "ORF Type.";
                  }
                  leaf orf-mode {
                    when "../../../../../../../../ni:name='_public_'" {
                      tailf:xpath-root 3;
                    }
                    type bgp:bgp-orf-mode-type;
                    must "(../orf-mode='null' and ../orf-type='null') or (../orf-mode!='null' and ../orf-type!='null')" {
                      tailf:xpath-root 3;
                    }
                    default "null";
                    description
                      "Configure an outbound route filtering (ORF) mode, which can be Receive, Send, or Both, and the default ORF mode is Both.";
                  }
                  leaf label-route-capability {
                    type boolean;
                    default "false";
                    description
                      "Enable/disable a device to exchange labeled routes.";
                  }
                  leaf check-tunnel-reachable {
                    when "../label-route-capability='true'" {
                      tailf:xpath-root 3;
                    }
                    type boolean;
                    default "false";
                    description
                      "Enable/disable tunnel reachability check.";
                  }
                  leaf check-withdraw-type {
                    when "../label-route-capability='true'" {
                      tailf:xpath-root 3;
                    }
                    type boolean;
                    default "true";
                    status obsolete;
                    description
                      "Enable/disable withdraw type check.";
                  }
                  leaf nexthop-configure {
                    type nexthop-configuration-type;
                    description
                      "Both the next-hop-local mode and next-hop-invariable mode are available when the peer address family is the VPNv4/VPNV6/L2VPN AD address family. Only the next-hop-local mode is available when the peer address family is not VPNv4/VPNV6/L2VPN AD address family. In next-hop-local mode, you can configure a BGP speaker to set its IP address of as the next hop of the routes to be advertised to IBGP peers or IBGP peer groups. In next-hop-invariable mode, you can configure PEs in different ASs not to change the next hop of routes when the PEs advertise the routes to their EBGP peers and use the next hop addresses of IGP routes to advertise imported IGP routes to IBGP peers. By default, when a BGP speaker advertises routes to EBGP peers and imported IGP routes to IBGP peers, the BGP speaker changes the next hop to its interface address.";
                  }
                  uses peer-policy-filter-type;
                  leaf advertise-ext-community {
                    type boolean;
                    default "false";
                    description
                      "Enable/disable advertise the extended community attribute to a peer or peer group.";
                  }
                  leaf origin-as-validation {
                    when "../advertise-ext-community='true'" {
                      tailf:xpath-root 3;
                    }
                    type boolean;
                    default "false";
                    description
                      "Enable/disable the BGP peer origin validation.";
                  }
                  leaf discard-ext-community {
                    type boolean;
                    default "false";
                    description
                      "Enable/disable discard the extended community attribute in the routing information about a specified peer.";
                  }
                  leaf allow-as-loop {
                    type uint32 {
                      range "1..10";
                    }
                    description
                      "Allow repetitive local AS numbers. By default, repetitive local AS numbers are not allowed.";
                  }
                  leaf aigp {
                    when "../../../../../../../../ni:name='_public_'" {
                      tailf:xpath-root 3;
                    }
                    type boolean;
                    default "false";
                    description
                      "Enable/disable route with AIGP attribute advertisement to or from a peer.";
                  }
                  uses default-route-advertise-type;
                  leaf default-route-match-mode {
                    when "../default-route-advertise='true'" {
                      tailf:xpath-root 3;
                    }
                    type cra-match-mode;
                    default "null";
                    description
                      "Configure the matching mode of default route advertisement, which can be disabling of route advertisement conditions, enabling of all route advertisement conditions, and enabling of part route advertisement conditions. Enabling of all route advertisement conditions indicates that a default route can be advertised only when it matches all the conditions. Enabling of part route advertisement conditions indicates that a default route can be advertised only when it matches one condition.";
                  }
                  leaf add-path-mode {
                    when "../../../../../../../../ni:name='_public_'" {
                      tailf:xpath-root 3;
                    }
                    type add-path-cap-type;
                    default "null";
                    description
                      "Enable add-path route advertisement to a peer.";
                  }
                  uses ip-prefix-filter-type;
                  uses as-path-filter-type;
                  uses peer-group-acl-name-or-num-type;
                  uses rt-update-interval-type;
                  uses preferred-value-type;
                  leaf add-path-number {
                    when "../../../../../../../../ni:name='_public_'" {
                      tailf:xpath-root 3;
                    }
                    type uint8 {
                      range "2..64";
                    }
                    description
                      "Number of add-path routes that can be advertised to a peer.";
                  }
                  leaf substitute-as-enable {
                    type boolean;
                    default "false";
                    description
                      "Enable/disable replace the AS number of a specified peer in the AS_Path attribute with the local AS number. On a PE where AS number replacement is enabled, if an AS number in the AS_Path attribute of a route is same as that of the CE to which the PE advertises the route, the PE replaces the AS number with its own AS number before advertising the route.";
                  }
                  leaf soo {
                    when "../../../../../../../../ni:name!='_public_'" {
                      tailf:xpath-root 3;
                    }
                    type string {
                      length "3..21";
                    }
                    description
                      "Configure the Site-of-Origin (SoO) extended community attribute. This attribute can be expressed in the following formats: X.X.X.X:number<0-65535>, number<0-65535>:number<0-4294967295>, or number<0-65535>.number<0-65535>:number<0-65535> or <65536-4294967295>:<0-65535>. 0:0 or 0.0:0 is not supported.
                       Two CEs are in the same site and can advertise routes to each other, and they are connected to a VPN through PEs. If the local routes of a CE are advertised to the other CE over the VPN, a routing loop may occur.
                       The SoO feature can prevent a route advertised by a site from being sent back to the site, preventing routing loops. After SoO is enabled and a PE receives a route from a CE, the specified SoO attribute will be added to the route. Before advertising the route to the other CE, the PE checks the SoO attribute. If the SoO attribute is the same as the locally configured SoO attribute, the PE does not advertise the route, preventing routing loops.";
                  }
                  leaf keep-all-routes {
                    when "/bgp:bgp/bgp:base-process/bgp:keep-all-routes='false'" {
                      tailf:xpath-root 3;
                    }
                    type boolean;
                    default "false";
                    description
                      "Enable/disable saving all the updated information about BGP routes from a specified peer or peer group after a BGP connection is established, even though these BGP routes fail to match the routing policy on the ingress. By default, the updated information about BGP routes from a specified peer is saved only when the routes match the routing policy on the ingress. If a router supports route refreshing, this option is not required.";
                  }
                  leaf exp-mode {
                    type exp-mode-type;
                    default "null";
                    description
                      "Specify the ASs in which a BGP label can inherit the QoS priority carried in the outer label of public tunnel in the Core AS and the ASs in which the priorities of BGP LSPs must be restored before the LSPs are advertised to a non-core AS.";
                  }
                  leaf advertise-best-external {
                    when "../../../../../../../../ni:name='_public_'" {
                      tailf:xpath-root 3;
                    }
                    type boolean;
                    must "../reflect-client='false' or ../advertise-best-external='false'" {
                      tailf:xpath-root 3;
                    }
                    must "../add-path-mode='null' or not(../add-path-mode) or ../advertise-best-external='false'" {
                      tailf:xpath-root 3;
                    }
                    must "not(../add-path-number and ../advertise-best-external='true')" {
                      tailf:xpath-root 3;
                    }
                    default "false";
                    description
                      "Enable/disable the device to advertise Best External routes to peers.";
                  }
                  leaf load-balancing-enable {
                    type boolean;
                    default "false";
                    description
                      "Enable/disable a neighbour to participate in load balancing.";
                  }
                  choice load-balancing-ignore-as-type {
                    description
                      "Set load balancing as path type.";
                    case as-attribute {
                      description
                        "Ignore the as-path attribute.";
                      leaf load-balancing-as-path-ignore {
                        when "../load-balancing-enable='true'" {
                          tailf:xpath-root 3;
                        }
                        type empty;
                        description
                          "Configure BGP to ignore the AS_Path attribute when selecting the equal route. After as-path-neglect is selected, BGP does not compare the AS_Path length.";
                      }
                    }
                    case same-length-as-attribute {
                      description
                        "Ignore comparison of as-path attributes with the same length.";
                      leaf load-balancing-as-path-relax {
                        when "../load-balancing-enable='true'" {
                          tailf:xpath-root 3;
                        }
                        type empty;
                        description
                          "Configure BGP to ignore comparison of AS_Path attributes with the same length when selecting the equal route. After as-path-neglect is selected, BGP does not compare the AS_Path length.";
                      }
                    }
                  }
                  leaf prefix-sid {
                    when "../../../../../../../../ni:name='_public_'" {
                      tailf:xpath-root 3;
                    }
                    type bgp:peer-comm-config-type;
                    default "default";
                    description
                      "Enable/disable a device to exchange IPv4 prefix SIDs with a specified IPv6 peer.";
                  }
                  // NCS drop config false leaf 'prefix-sid-state'
                  choice prefix-sid-packet {
                    description
                      "Prefix-sid packet method.";
                    case sid-type5 {
                      description
                        "Packet by type5.";
                      leaf advertise-srv6-locator {
                        when "../prefix-sid='enable'" {
                          tailf:xpath-root 3;
                        }
                        type empty;
                        description
                          "Advertise SRv6 locators.";
                      }
                    }
                  }
                  // NCS drop config false container 'effect-state'
                  uses advertise-large-community-type;
                  uses peer-independent-peer-group-type;
                  leaf rpd-policy-export {
                    when "../../../../../../../../ni:name='_public_'" {
                      tailf:xpath-root 3;
                    }
                    type bgp:peer-enable-config-type;
                    default "default";
                    description
                      "Enable/disable RPD export policy.";
                  }
                  uses ipv4-default-route-match-conditions-type;
                  uses route-limit-accept-type;
                  uses public-as-only-type;
                  uses peer-public-as-only-import-type;
                  container entropy-label-parameter {
                    when "../../../../../../../../ni:name='_public_' and ../label-route-capability='true'" {
                      tailf:xpath-root 3;
                    }
                    description
                      "Configure information about entropy label parameter configuration in a peer.";
                    uses peer-entropy-label-type;
                  }
                  uses path-attr-map-type;
                  uses advertise-dependent-filter-type;
                }
                container ipv6-unicast {
                  when "../type = 'ipv6uni'" {
                    tailf:xpath-root 3;
                  }
                  description
                    "Configure IPv6 unicast options.";
                  leaf group-name {
                    type leafref {
                      path "../../../../../../peer-groups/peer-group/name";
                    }
                    must "../../../../../../peer-groups/peer-group[name = current()]/afs/af[type = 'ipv6uni']" {
                      tailf:xpath-root 3;
                    }
                    must "../../../../../../peer-groups/peer-group[name = current()]/peer-establish-mode = 'static'" {
                      tailf:xpath-root 3;
                    }
                    description
                      "Configure a name for a peer group. After a peer is deleted from the peer group, the peer is disabled from the address family. The object cannot be modified.";
                    ext:operation-exclude "update" {
                      description
                        "The node cannot be modified, when the peer already belongs to a peer-group.";
                    }
                  }
                  leaf advertise-community {
                    type boolean;
                    default "false";
                    description
                      "Enable/disable advertise the community attribute to a peer or a peer group.";
                  }
                  leaf reflect-client {
                    type boolean;
                    default "false";
                    description
                      "Enable/disable the local device as a route reflector (RR) and a peer or peer group as its client. This configuration is applicable between IBGP peers only. The configurations of RRs and its clients in an address family are valid only in this address family. Therefore, it is recommended to configure RRs and its clients in the specified address family that is required.";
                  }
                  leaf label-route-capability {
                    type boolean;
                    default "false";
                    description
                      "Enable/disable a device to exchange labeled routes.";
                  }
                  leaf nexthop-configure {
                    type nexthop-configuration-type;
                    must "(not(contains(../../../../address,':')) and ../nexthop-configure='local') or contains(../../../../address,':')" {
                      tailf:xpath-root 3;
                    }
                    description
                      "Both the next-hop-local mode and next-hop-invariable mode are available when the peer address family is the VPNv4/VPNV6/L2VPN AD address family. Only the next-hop-local mode is available when the peer address family is not VPNv4/VPNV6/L2VPN AD address family. In next-hop-local mode, you can configure a BGP speaker to set its IP address of as the next hop of the routes to be advertised to IBGP peers or IBGP peer groups. In next-hop-invariable mode, you can configure PEs in different ASs not to change the next hop of routes when the PEs advertise the routes to their EBGP peers and use the next hop addresses of IGP routes to advertise imported IGP routes to IBGP peers. By default, when a BGP speaker advertises routes to EBGP peers and imported IGP routes to IBGP peers, the BGP speaker changes the next hop to its interface address.";
                  }
                  uses peer-policy-filter-type;
                  leaf advertise-ext-community {
                    type boolean;
                    default "false";
                    description
                      "Enable/disable advertise the extended community attribute to a peer or peer group.";
                  }
                  leaf origin-as-validation {
                    when "../advertise-ext-community='true'" {
                      tailf:xpath-root 3;
                    }
                    type boolean;
                    default "false";
                    description
                      "Enable/disable the BGP peer origin validation.";
                  }
                  leaf discard-ext-community {
                    type boolean;
                    default "false";
                    description
                      "Enable/disable discard the extended community attribute in the routing information about a specified peer.";
                  }
                  leaf allow-as-loop {
                    type uint32 {
                      range "1..10";
                    }
                    description
                      "Allow repetitive local AS numbers. By default, repetitive local AS numbers are not allowed.";
                  }
                  leaf aigp {
                    when "../../../../../../../../ni:name='_public_'" {
                      tailf:xpath-root 3;
                    }
                    type boolean;
                    default "false";
                    description
                      "Enable/disable route with AIGP attribute advertisement to or from a peer.";
                  }
                  uses default-route-advertise-type;
                  leaf default-route-match-mode {
                    when "../default-route-advertise='true'" {
                      tailf:xpath-root 3;
                    }
                    type cra-match-mode;
                    default "null";
                    description
                      "Configure the matching mode of default route advertisement, which can be disabling of route advertisement conditions, enabling of all route advertisement conditions, and enabling of part route advertisement conditions. Enabling of all route advertisement conditions indicates that a default route can be advertised only when it matches all the conditions. Enabling of part route advertisement conditions indicates that a default route can be advertised only when it matches one condition.";
                  }
                  leaf add-path-mode {
                    when "../../../../../../../../ni:name='_public_'" {
                      tailf:xpath-root 3;
                    }
                    type add-path-cap-type;
                    default "null";
                    description
                      "Enable Add-Path route advertisement to a peer.";
                  }
                  uses ipv6-prefix-filter-type;
                  uses as-path-filter-type;
                  uses peer-group-acl6-name-or-num-type;
                  uses rt-update-interval-type;
                  uses preferred-value-type;
                  leaf add-path-number {
                    when "../../../../../../../../ni:name='_public_'" {
                      tailf:xpath-root 3;
                    }
                    type uint8 {
                      range "2..64";
                    }
                    description
                      "Number of Add-Path routes that can be advertised to a peer.";
                  }
                  leaf substitute-as-enable {
                    type boolean;
                    default "false";
                    description
                      "Enable/disable replace the AS number of a specified peer in the AS_Path attribute with the local AS number. On a PE where AS number replacement is enabled, if an AS number in the AS_Path attribute of a route is same as that of the CE to which the PE advertises the route, the PE replaces the AS number with its own AS number before advertising the route.";
                  }
                  leaf soo {
                    when "../../../../../../../../ni:name!='_public_'" {
                      tailf:xpath-root 3;
                    }
                    type string {
                      length "3..21";
                    }
                    description
                      "Configure the Site-of-Origin (SoO) extended community attribute. This attribute can be expressed in the following formats: X.X.X.X:number<0-65535>, number<0-65535>:number<0-4294967295>, or number<0-65535>.number<0-65535>:number<0-65535> or <65536-4294967295>:<0-65535>. 0:0 or 0.0:0 is not supported.
                       Two CEs are in the same site and can advertise routes to each other, and they are connected to a VPN through PEs. If the local routes of a CE are advertised to the other CE over the VPN, a routing loop may occur.
                       The SoO feature can prevent a route advertised by a site from being sent back to the site, preventing routing loops. After SoO is enabled and a PE receives a route from a CE, the specified SoO attribute will be added to the route. Before advertising the route to the other CE, the PE checks the SoO attribute. If the SoO attribute is the same as the locally configured SoO attribute, the PE does not advertise the route, preventing routing loops.";
                  }
                  leaf keep-all-routes {
                    when "/bgp:bgp/bgp:base-process/bgp:keep-all-routes='false'" {
                      tailf:xpath-root 3;
                    }
                    type boolean;
                    default "false";
                    description
                      "Enable/disable saving all the updated information about BGP routes from a specified peer or peer group after a BGP connection is established, even though these BGP routes fail to match the routing policy on the ingress. By default, the updated information about BGP routes from a specified peer is saved only when the routes match the routing policy on the ingress. If a router supports route refreshing, this option is not required.";
                  }
                  leaf advertise-best-external {
                    when "../../../../../../../../ni:name='_public_'" {
                      tailf:xpath-root 3;
                    }
                    type boolean;
                    must "../reflect-client='false' or ../advertise-best-external='false'" {
                      tailf:xpath-root 3;
                    }
                    must "../add-path-mode='null' or not(../add-path-mode) or ../advertise-best-external='false'" {
                      tailf:xpath-root 3;
                    }
                    must "not(../add-path-number and ../advertise-best-external='true')" {
                      tailf:xpath-root 3;
                    }
                    default "false";
                    description
                      "Enable/disable the device to advertise Best External routes to peers.";
                  }
                  leaf load-balancing-enable {
                    type boolean;
                    default "false";
                    description
                      "Enable/disable a neighbour to participate in load balancing.";
                  }
                  choice load-balancing-ignore-as-type {
                    description
                      "Set load balancing as path type.";
                    case as-attribute {
                      description
                        "Ignore the as-path attribute.";
                      leaf load-balancing-as-path-ignore {
                        when "../load-balancing-enable='true'" {
                          tailf:xpath-root 3;
                        }
                        type empty;
                        description
                          "Configure BGP to ignore the AS_Path attribute when selecting the equal route. After as-path-neglect is selected, BGP does not compare the AS_Path length.";
                      }
                    }
                    case same-length-as-attribute {
                      description
                        "Ignore comparison of as-path attributes with the same length.";
                      leaf load-balancing-as-path-relax {
                        when "../load-balancing-enable='true'" {
                          tailf:xpath-root 3;
                        }
                        type empty;
                        description
                          "Configure BGP to ignore comparison of AS_Path attributes with the same length when selecting the equal route. After as-path-neglect is selected, BGP does not compare the AS_Path length.";
                      }
                    }
                  }
                  leaf tunnel-policy {
                    when "../../../../../../../../ni:name='_public_'" {
                      tailf:xpath-root 3;
                    }
                    type leafref {
                      path "/ncs:devices/ncs:device/ncs:config/tnlm:tunnel-management/tnlm:tunnel-policys/tnlm:tunnel-policy/tnlm:name" {
                        tailf:xpath-root 3;
                      }
                    }
                    description
                      "Apply a tunnel policy for a 6PE peer. By default, no tunnel policy is configured.";
                  }
                  leaf prefix-sid {
                    when "../../../../../../../../ni:name='_public_'" {
                      tailf:xpath-root 3;
                    }
                    type bgp:peer-comm-config-type;
                    default "default";
                    description
                      "Enable/disable a device to exchange prefix SIDs with a specified IPv6 peer.";
                  }
                  // NCS drop config false leaf 'prefix-sid-state'
                  choice prefix-sid-packet {
                    description
                      "Prefix-sid packet method.";
                    case sid-type5 {
                      description
                        "Packet by type5.";
                      leaf advertise-srv6-locator {
                        when "../prefix-sid='enable'" {
                          tailf:xpath-root 3;
                        }
                        type empty;
                        description
                          "Advertise SRv6 locators.";
                      }
                    }
                  }
                  // NCS drop config false container 'effect-state'
                  uses advertise-large-community-type;
                  uses peer-independent-peer-group-type;
                  uses ipv6-default-route-match-conditions-type;
                  uses route-limit-accept-type;
                  uses public-as-only-type;
                  uses peer-public-as-only-import-type;
                  uses path-attr-map-type;
                  uses advertise-dependent-filter6-type;
                }
                container ipv4-vpn {
                  when "../type = 'ipv4vpn'" {
                    tailf:xpath-root 3;
                  }
                  description
                    "Configure IPv4 VPNv4 options.";
                  leaf group-name {
                    type leafref {
                      path "../../../../../../peer-groups/peer-group/name";
                    }
                    must "../../../../../../peer-groups/peer-group[name = current()]/afs/af[type = 'ipv4vpn']" {
                      tailf:xpath-root 3;
                    }
                    must "../../../../../../peer-groups/peer-group[name = current()]/peer-establish-mode = 'static'" {
                      tailf:xpath-root 3;
                    }
                    description
                      "Configure a name for a peer group. After a peer is deleted from the peer group, the peer is disabled from the address family. The object cannot be modified.";
                    ext:operation-exclude "update" {
                      description
                        "The node cannot be modified, when the peer already belongs to a peer-group.";
                    }
                  }
                  leaf advertise-community {
                    type boolean;
                    default "false";
                    description
                      "Enable/disable advertise the community attribute to a peer or a peer group.";
                  }
                  leaf reflect-client {
                    type boolean;
                    default "false";
                    description
                      "Enable/disable the local device as a route reflector (RR) and a peer or peer group as its client. This configuration is applicable between IBGP peers only. The configurations of RRs and its clients in an address family are valid only in this address family. Therefore, it is recommended to configure RRs and its clients in the specified address family that is required.";
                  }
                  leaf nexthop-configure {
                    type nexthop-configuration-type;
                    description
                      "Both the next-hop-local mode and next-hop-invariable mode are available when the peer address family is the VPNv4/VPNV6/L2VPN AD address family. Only the next-hop-local mode is available when the peer address family is not VPNv4/VPNV6/L2VPN AD address family. In next-hop-local mode, you can configure a BGP speaker to set its IP address of as the next hop of the routes to be advertised to IBGP peers or IBGP peer groups. In next-hop-invariable mode, you can configure PEs in different ASs not to change the next hop of routes when the PEs advertise the routes to their EBGP peers and use the next hop addresses of IGP routes to advertise imported IGP routes to IBGP peers. By default, when a BGP speaker advertises routes to EBGP peers and imported IGP routes to IBGP peers, the BGP speaker changes the next hop to its interface address.";
                  }
                  uses peer-policy-filter-type;
                  leaf ignore-bit-error {
                    when '../export-policy or ../export-filter' {
                      tailf:xpath-root 3;
                    }
                    type boolean;
                    default "false";
                    description
                      "Enable/disable the peer to ignore bit error detection results.";
                  }
                  leaf allow-as-loop {
                    type uint32 {
                      range "1..10";
                    }
                    description
                      "Allow repetitive local AS numbers. By default, repetitive local AS numbers are not allowed.";
                  }
                  leaf aigp {
                    type boolean;
                    default "false";
                    description
                      "Enable/disable route with AIGP attribute advertisement to or from a peer.";
                  }
                  uses peer-add-path-type;
                  uses ip-prefix-filter-type;
                  uses peer-ipv4-reoriginate-type;
                  uses as-path-filter-type;
                  uses peer-group-acl-name-or-num-type;
                  uses rt-update-interval-type;
                  uses preferred-value-type;
                  leaf upe {
                    type boolean;
                    default "false";
                    description
                      "Enable/disable the peer as an underlayer PE (UPE).";
                  }
                  leaf high-priority {
                    type peer-enable-config-type;
                    default "default";
                    description
                      "Enable vpn-router high priority.";
                  }
                  leaf prefix-sid {
                    type bgp:peer-enable-config-type;
                    default "default";
                    description
                      "Specify a SID mode relay for peer.";
                  }
                  choice prefix-sid-packet {
                    description
                      "Prefix-sid packet method.";
                    case sid-type5 {
                      description
                        "Packet by type5.";
                      leaf sid-type5 {
                        when "../prefix-sid='enable'" {
                          tailf:xpath-root 3;
                        }
                        type empty;
                        description
                          "Packet by type5.";
                      }
                      leaf advertise-srv6-locator {
                        when '../sid-type5' {
                          tailf:xpath-root 3;
                        }
                        type empty;
                        description
                          "Advertise SRv6 locators.";
                      }
                    }
                  }
                  leaf advertise-best-external {
                    type boolean;
                    must "../reflect-client='false' or ../advertise-best-external='false'" {
                      tailf:xpath-root 3;
                    }
                    must "../add-path-mode='null' or not(../add-path-mode) or ../advertise-best-external='false'" {
                      tailf:xpath-root 3;
                    }
                    must "not(../add-path-number and ../advertise-best-external='true')" {
                      tailf:xpath-root 3;
                    }
                    default "false";
                    description
                      "Enable/disable the device to advertise Best External routes to peers.";
                  }
                  uses advertise-large-community-type;
                  leaf keep-all-routes {
                    when "/bgp:bgp/bgp:base-process/bgp:keep-all-routes='false'" {
                      tailf:xpath-root 3;
                    }
                    type boolean;
                    default "false";
                    description
                      "Enable/disable saving all the updated information about BGP routes from a specified peer or peer group after a BGP connection is established, even though these BGP routes fail to match the routing policy on the ingress. By default, the updated information about BGP routes from a specified peer is saved only when the routes match the routing policy on the ingress. If a router supports route refreshing, this option is not required.";
                  }
                  uses peer-independent-peer-group-type;
                  uses peer-origin-as-validation-type;
                  container default-route-originates {
                    description
                      "Configure advertised default VPNv4 routes.";
                    uses default-route-originate-type;
                  }
                  uses route-limit-type;
                  uses public-as-only-type;
                  uses peer-public-as-only-import-type;
                  uses path-attr-map-type;
                }
                container ipv6-vpn {
                  when "../type = 'ipv6vpn'" {
                    tailf:xpath-root 3;
                  }
                  description
                    "Configure IPv6 vpn options.";
                  leaf group-name {
                    type leafref {
                      path "../../../../../../peer-groups/peer-group/name";
                    }
                    must "../../../../../../peer-groups/peer-group[name = current()]/afs/af[type = 'ipv6vpn']" {
                      tailf:xpath-root 3;
                    }
                    must "../../../../../../peer-groups/peer-group[name = current()]/peer-establish-mode = 'static'" {
                      tailf:xpath-root 3;
                    }
                    description
                      "Configure a name for a peer group. After a peer is deleted from the peer group, the peer is disabled from the address family. The object cannot be modified.";
                    ext:operation-exclude "update" {
                      description
                        "The node cannot be modified, when the peer already belongs to a peer-group.";
                    }
                  }
                  leaf advertise-community {
                    type boolean;
                    default "false";
                    description
                      "Enable/disable advertise the community attribute to a peer or a peer group.";
                  }
                  leaf reflect-client {
                    type boolean;
                    default "false";
                    description
                      "Enable/disable the local device as a route reflector (RR) and a peer or peer group as its client. This configuration is applicable between IBGP peers only. The configurations of RRs and its clients in an address family are valid only in this address family. Therefore, it is recommended to configure RRs and its clients in the specified address family that is required.";
                  }
                  leaf nexthop-configure {
                    type nexthop-configuration-type;
                    description
                      "Both the next-hop-local mode and next-hop-invariable mode are available when the peer address family is the VPNv4/VPNV6/L2VPN AD address family. Only the next-hop-local mode is available when the peer address family is not VPNv4/VPNV6/L2VPN AD address family. In next-hop-local mode, you can configure a BGP speaker to set its IP address of as the next hop of the routes to be advertised to IBGP peers or IBGP peer groups. In next-hop-invariable mode, you can configure PEs in different ASs not to change the next hop of routes when the PEs advertise the routes to their EBGP peers and use the next hop addresses of IGP routes to advertise imported IGP routes to IBGP peers. By default, when a BGP speaker advertises routes to EBGP peers and imported IGP routes to IBGP peers, the BGP speaker changes the next hop to its interface address.";
                  }
                  uses peer-policy-filter-type;
                  leaf ignore-bit-error {
                    when '../export-policy or ../export-filter' {
                      tailf:xpath-root 3;
                    }
                    type boolean;
                    default "false";
                    description
                      "Enable/disable the peer to ignore bit error detection results.";
                  }
                  leaf allow-as-loop {
                    type uint32 {
                      range "1..10";
                    }
                    description
                      "Allow repetitive local AS numbers. By default, repetitive local AS numbers are not allowed.";
                  }
                  leaf aigp {
                    type boolean;
                    default "false";
                    description
                      "Enable/disable route with AIGP attribute advertisement to or from a peer.";
                  }
                  uses peer-add-path-type;
                  uses ipv6-prefix-filter-type;
                  leaf reoriginate-route-enable {
                    type boolean;
                    default "false";
                    description
                      "Enable/disable route regeneration.";
                  }
                  leaf reoriginate-ipv6-enable {
                    type boolean;
                    default "false";
                    description
                      "Enable/disable IP route regeneration and advertisement.";
                  }
                  leaf reoriginate-mac-ipv6-enable {
                    type boolean;
                    default "false";
                    description
                      "Enable/disable MAC-IP route regeneration and advertisement.";
                  }
                  uses as-path-filter-type;
                  uses peer-group-acl6-name-or-num-type;
                  uses rt-update-interval-type;
                  uses preferred-value-type;
                  leaf advertise-best-external {
                    type boolean;
                    must "../reflect-client='false' or ../advertise-best-external='false'" {
                      tailf:xpath-root 3;
                    }
                    must "../add-path-mode='null' or not(../add-path-mode) or ../advertise-best-external='false'" {
                      tailf:xpath-root 3;
                    }
                    must "not(../add-path-number and ../advertise-best-external='true')" {
                      tailf:xpath-root 3;
                    }
                    default "false";
                    description
                      "Enable/disable the device to advertise Best External routes to peers.";
                  }
                  uses advertise-large-community-type;
                  leaf keep-all-routes {
                    when "/bgp:bgp/bgp:base-process/bgp:keep-all-routes='false'" {
                      tailf:xpath-root 3;
                    }
                    type boolean;
                    default "false";
                    description
                      "Enable/disable saving all the updated information about BGP routes from a specified peer or peer group after a BGP connection is established, even though these BGP routes fail to match the routing policy on the ingress. By default, the updated information about BGP routes from a specified peer is saved only when the routes match the routing policy on the ingress. If a router supports route refreshing, this option is not required.";
                  }
                  uses peer-independent-peer-group-type;
                  uses peer-origin-as-validation-type;
                  uses route-limit-type;
                  uses public-as-only-type;
                  uses peer-public-as-only-import-type;
                  uses path-attr-map-type;
                }
                container ipv4-labeluni {
                  when "../type = 'ipv4labeluni'" {
                    tailf:xpath-root 3;
                  }
                  description
                    "Configure IPv4 label unicast options.";
                  leaf group-name {
                    type leafref {
                      path "../../../../../../peer-groups/peer-group/name";
                    }
                    must "../../../../../../peer-groups/peer-group[name = current()]/afs/af[type = 'ipv4labeluni']" {
                      tailf:xpath-root 3;
                    }
                    must "../../../../../../peer-groups/peer-group[name = current()]/peer-establish-mode = 'static'" {
                      tailf:xpath-root 3;
                    }
                    description
                      "Configure a name for a peer group. After a peer is deleted from the peer group, the peer is disabled from the address family. The object cannot be modified.";
                    ext:operation-exclude "update" {
                      description
                        "The node cannot be modified, when the peer already belongs to a peer-group.";
                    }
                  }
                  leaf advertise-community {
                    type boolean;
                    default "false";
                    description
                      "Enable/disable advertise the community attribute to a peer or a peer group.";
                  }
                  leaf reflect-client {
                    type boolean;
                    default "false";
                    description
                      "Enable/disable the local device as a route reflector (RR) and a peer or peer group as its client. This configuration is applicable between IBGP peers only. The configurations of RRs and its clients in an address family are valid only in this address family. Therefore, it is recommended to configure RRs and its clients in the specified address family that is required.";
                  }
                  leaf check-tunnel-reachable {
                    type boolean;
                    default "false";
                    description
                      "Enable/disable tunnel reachability check.";
                  }
                  uses peer-policy-filter-type;
                  leaf advertise-ext-community {
                    type boolean;
                    default "false";
                    description
                      "Enable/disable advertise the extended community attribute to a peer or peer group.";
                  }
                  leaf discard-ext-community {
                    type boolean;
                    default "false";
                    description
                      "Enable/disable discard the extended community attribute in the routing information about a specified peer.";
                  }
                  leaf allow-as-loop {
                    type uint32 {
                      range "1..10";
                    }
                    description
                      "Allow repetitive local AS numbers. By default, repetitive local AS numbers are not allowed.";
                  }
                  leaf aigp {
                    when "../../../../../../../../ni:name='_public_'" {
                      tailf:xpath-root 3;
                    }
                    type boolean;
                    default "false";
                    description
                      "Enable/disable route with AIGP attribute advertisement to or from a peer.";
                  }
                  leaf add-path-mode {
                    when "../../../../../../../../ni:name='_public_'" {
                      tailf:xpath-root 3;
                    }
                    type add-path-cap-type;
                    default "null";
                    description
                      "Enable add-path route advertisement to a peer.";
                  }
                  uses ip-prefix-filter-type;
                  uses as-path-filter-type;
                  uses peer-group-acl-name-or-num-type;
                  uses rt-update-interval-type;
                  leaf nexthop-configure {
                    type nexthop-configuration-type;
                    description
                      "Both the next-hop-local mode and next-hop-invariable mode are available when the peer address family is the VPNv4/VPNV6/L2VPN AD address family. Only the next-hop-local mode is available when the peer address family is not VPNv4/VPNV6/L2VPN AD address family. In next-hop-local mode, you can configure a BGP speaker to set its IP address of as the next hop of the routes to be advertised to IBGP peers or IBGP peer groups. In next-hop-invariable mode, you can configure PEs in different ASs not to change the next hop of routes when the PEs advertise the routes to their EBGP peers and use the next hop addresses of IGP routes to advertise imported IGP routes to IBGP peers. By default, when a BGP speaker advertises routes to EBGP peers and imported IGP routes to IBGP peers, the BGP speaker changes the next hop to its interface address.";
                  }
                  uses preferred-value-type;
                  leaf exp-mode {
                    when "../../../../../../../../ni:name!='_public_'" {
                      tailf:xpath-root 3;
                    }
                    type exp-mode-type;
                    default "null";
                    description
                      "Specify the ASs in which a BGP label can inherit the QoS priority carried in the outer label of public tunnel in the Core AS and the ASs in which the priorities of BGP LSPs must be restored before the LSPs are advertised to a non-core AS.";
                  }
                  leaf add-path-number {
                    when "../../../../../../../../ni:name='_public_'" {
                      tailf:xpath-root 3;
                    }
                    type uint8 {
                      range "2..64";
                    }
                    description
                      "Number of Add-Path routes that can be advertised to a peer.";
                  }
                  leaf substitute-as-enable {
                    type boolean;
                    default "false";
                    description
                      "Enable/disable replace the AS number of a specified peer in the AS_Path attribute with the local AS number. On a PE where AS number replacement is enabled, if an AS number in the AS_Path attribute of a route is same as that of the CE to which the PE advertises the route, the PE replaces the AS number with its own AS number before advertising the route.";
                  }
                  leaf soo {
                    when "../../../../../../../../ni:name!='_public_'" {
                      tailf:xpath-root 3;
                    }
                    type string {
                      length "3..21";
                    }
                    description
                      "Configure the Site-of-Origin (SoO) extended community attribute. This attribute can be expressed in the following formats: X.X.X.X:number<0-65535>, number<0-65535>:number<0-4294967295>, or number<0-65535>.number<0-65535>:number<0-65535> or <65536-4294967295>:<0-65535>. 0:0 or 0.0:0 is not supported.
                       Two CEs are in the same site and can advertise routes to each other, and they are connected to a VPN through PEs. If the local routes of a CE are advertised to the other CE over the VPN, a routing loop may occur.
                       The SoO feature can prevent a route advertised by a site from being sent back to the site, preventing routing loops. After SoO is enabled and a PE receives a route from a CE, the specified SoO attribute will be added to the route. Before advertising the route to the other CE, the PE checks the SoO attribute. If the SoO attribute is the same as the locally configured SoO attribute, the PE does not advertise the route, preventing routing loops.";
                  }
                  leaf advertise-best-external {
                    when "../../../../../../../../ni:name='_public_'" {
                      tailf:xpath-root 3;
                    }
                    type boolean;
                    must "../reflect-client='false' or ../advertise-best-external='false'" {
                      tailf:xpath-root 3;
                    }
                    must "../add-path-mode='null' or not(../add-path-mode) or ../advertise-best-external='false'" {
                      tailf:xpath-root 3;
                    }
                    must "not(../add-path-number and ../advertise-best-external='true')" {
                      tailf:xpath-root 3;
                    }
                    default "false";
                    description
                      "Enable/disable the device to advertise Best External routes to peers.";
                  }
                  leaf load-balancing-enable {
                    when "../../../../../../../../ni:name='_public_'" {
                      tailf:xpath-root 3;
                    }
                    type boolean;
                    default "false";
                    description
                      "Enable/disable a neighbour to participate in load balancing.";
                  }
                  choice load-balancing-ignore-as-type {
                    description
                      "Set load balancing as path type.";
                    case as-attribute {
                      description
                        "Ignore the as-path attribute.";
                      leaf load-balancing-as-path-ignore {
                        when "../load-balancing-enable='true'" {
                          tailf:xpath-root 3;
                        }
                        type empty;
                        description
                          "Configure BGP to ignore the AS_Path attribute when selecting the equal route. After as-path-neglect is selected, BGP does not compare the AS_Path length.";
                      }
                    }
                    case same-length-as-attribute {
                      description
                        "Ignore comparison of as-path attributes with the same length.";
                      leaf load-balancing-as-path-relax {
                        when "../load-balancing-enable='true'" {
                          tailf:xpath-root 3;
                        }
                        type empty;
                        description
                          "Configure BGP to ignore comparison of AS_Path attributes with the same length when selecting the equal route. After as-path-neglect is selected, BGP does not compare the AS_Path length.";
                      }
                    }
                  }
                  uses advertise-large-community-type;
                  uses peer-independent-peer-group-type;
                  uses route-limit-accept-type;
                  uses public-as-only-type;
                  uses peer-public-as-only-import-type;
                  container entropy-label-parameter {
                    when "../../../../../../../../ni:name='_public_'" {
                      tailf:xpath-root 3;
                    }
                    description
                      "Configure information about entropy label parameter configuration in a peer.";
                    uses peer-entropy-label-type;
                  }
                  uses path-attr-map-type;
                }
                container ipv4-multicast {
                  when "../type='ipv4multi'" {
                    tailf:xpath-root 3;
                  }
                  description
                    "Configure IPv4 multicast options.";
                  leaf group-name {
                    type leafref {
                      path "../../../../../../peer-groups/peer-group/name";
                    }
                    must "../../../../../../peer-groups/peer-group[name = current()]/afs/af[type = 'ipv4multi']" {
                      tailf:xpath-root 3;
                    }
                    must "../../../../../../peer-groups/peer-group[name = current()]/peer-establish-mode = 'static'" {
                      tailf:xpath-root 3;
                    }
                    description
                      "Configure a name for a peer group. After a peer is deleted from the peer group, the peer is disabled from the address family. The object cannot be modified.";
                    ext:operation-exclude "update" {
                      description
                        "The node cannot be modified, when the peer already belongs to a peer-group.";
                    }
                  }
                  uses default-route-advertise-type;
                  uses ip-prefix-filter-type;
                  uses as-path-filter-type;
                  uses peer-group-acl-name-or-num-type;
                  leaf advertise-ext-community {
                    type boolean;
                    default "false";
                    description
                      "Enable/disable advertise the extended community attribute to a peer or peer group.";
                  }
                  leaf discard-ext-community {
                    type boolean;
                    default "false";
                    description
                      "Enable/disable discard the extended community attribute in the routing information about a specified peer.";
                  }
                  leaf allow-as-loop {
                    type uint32 {
                      range "1..10";
                    }
                    description
                      "Allow repetitive local AS numbers. By default, repetitive local AS numbers are not allowed.";
                  }
                  leaf nexthop-configure {
                    type nexthop-configuration-type;
                    must "../nexthop-configure='local'" {
                      tailf:xpath-root 3;
                    }
                    description
                      "Both the next-hop-local mode and next-hop-invariable mode are available when the peer address family is the VPNv4/VPNV6/L2VPN AD address family. Only the next-hop-local mode is available when the peer address family is not VPNv4/VPNV6/L2VPN AD address family. In next-hop-local mode, you can configure a BGP speaker to set its IP address of as the next hop of the routes to be advertised to IBGP peers or IBGP peer groups. In next-hop-invariable mode, you can configure PEs in different ASs not to change the next hop of routes when the PEs advertise the routes to their EBGP peers and use the next hop addresses of IGP routes to advertise imported IGP routes to IBGP peers. By default, when a BGP speaker advertises routes to EBGP peers and imported IGP routes to IBGP peers, the BGP speaker changes the next hop to its interface address.";
                  }
                  leaf advertise-community {
                    type boolean;
                    default "false";
                    description
                      "Enable/disable advertise the community attribute to a peer or a peer group.";
                  }
                  leaf keep-all-routes {
                    when "/bgp:bgp/bgp:base-process/bgp:keep-all-routes='false'" {
                      tailf:xpath-root 3;
                    }
                    type boolean;
                    default "false";
                    description
                      "Enable/disable saving all the updated information about BGP routes from a specified peer or peer group after a BGP connection is established, even though these BGP routes fail to match the routing policy on the ingress. By default, the updated information about BGP routes from a specified peer is saved only when the routes match the routing policy on the ingress. If a router supports route refreshing, this option is not required.";
                  }
                  uses peer-policy-filter-type;
                  leaf reflect-client {
                    type boolean;
                    default "false";
                    description
                      "Enable/disable the local device as a route reflector (RR) and a peer or peer group as its client. This configuration is applicable between IBGP peers only. The configurations of RRs and its clients in an address family are valid only in this address family. Therefore, it is recommended to configure RRs and its clients in the specified address family that is required.";
                  }
                  leaf load-balancing-enable {
                    type boolean;
                    default "false";
                    description
                      "Enable/disable a neighbour to participate in load balancing.";
                  }
                  choice load-balancing-ignore-as-type {
                    description
                      "Set load balancing as path type.";
                    case as-attribute {
                      description
                        "Ignore the as-path attribute.";
                      leaf load-balancing-as-path-ignore {
                        when "../load-balancing-enable='true'" {
                          tailf:xpath-root 3;
                        }
                        type empty;
                        description
                          "Configure BGP to ignore the AS_Path attribute when selecting the equal route. After as-path-neglect is selected, BGP does not compare the AS_Path length.";
                      }
                    }
                    case same-length-as-attribute {
                      description
                        "Ignore comparison of as-path attributes with the same length.";
                      leaf load-balancing-as-path-relax {
                        when "../load-balancing-enable='true'" {
                          tailf:xpath-root 3;
                        }
                        type empty;
                        description
                          "Configure BGP to ignore comparison of AS_Path attributes with the same length when selecting the equal route. After as-path-neglect is selected, BGP does not compare the AS_Path length.";
                      }
                    }
                  }
                  uses advertise-large-community-type;
                  uses rt-update-interval-type;
                  uses bgp:preferred-value-type;
                  uses peer-independent-peer-group-type;
                  uses route-limit-type;
                  uses public-as-only-type;
                  uses peer-public-as-only-import-type;
                  uses path-attr-map-type;
                }
                // NCS drop config false container state
              }
            }
          }
        }
        // NCS drop config false container 'peer-bfd-session-states'
        container egress-engineer-peer-sets {
          when "../../../ni:name='_public_'" {
            tailf:xpath-root 3;
          }
          description
            "List of peer set information under BGP instance.";
          list egress-engineer-peer-set {
            key "peer-set-name";
            description
              "Configure peer set information.";
            leaf peer-set-name {
              type string {
                length "1..63";
              }
              description
                "The name for peer set.";
            }
            leaf static-label {
              type uint32 {
                range "16..1048575";
              }
              description
                "The static label for peer set.";
            }
            leaf label-pop {
              when '../static-label' {
                tailf:xpath-root 3;
              }
              type boolean;
              must "not(../relate-bfd='true' and ../label-pop='true')" {
                tailf:xpath-root 3;
              }
              default "false";
              description
                "Enable/disable the BGP-EPE label popping function.";
            }
            leaf relate-bfd {
              type boolean;
              must "not(../relate-bfd='true' and ../label-pop='true')" {
                tailf:xpath-root 3;
              }
              default "false";
              description
                "Enable/disable association between the BGP-EPE label and BFD status.";
            }
          }
        }
      }
      container instance-processs {
        when "../../ni:name = '_public_'" {
          tailf:xpath-root 3;
        }
        description
          "List of all BGP instances.";
        list instance-process {
          key "name";
          max-elements 1;
          description
            "Configure a BGP instance.";
          ext:generated-by "system" {
            when "../../../ni:name = '_public_'" {
              tailf:xpath-root 3;
            }
            description
              "The BGP public instance is generated automatically when BGP instances is enabled.";
          }
          leaf name {
            type leafref {
              path "/ncs:devices/ncs:device/ncs:config/bgp:bgp/bgp:instance-processs/bgp:instance-process/bgp:name" {
                tailf:xpath-root 3;
              }
            }
            description
              "Name of BGP Site.";
          }
          leaf router-id {
            type inet:ipv4-address-no-zone;
            description
              "ID of a router that is in IPv4 address format. Certain dynamic routing protocols require a router ID. If no router ID is specified for a router when these protocols are enabled, the router ID in the RM module is used by default. The default router ID in the RM module is 0.0.0.0 when the router is not configured with any interface.
               The rules for selecting a router ID are as follows:
               1. If you set a router ID through this configuration, the set router ID is used. If the router ID is not set, you need to select a router ID according to the following rules:
               (1) If loopback interfaces configured with IP addresses exist, the largest IP address among the IP addresses of the loopback interfaces is selected as the router ID.
               (2) If no loopback interface configured with an IP address exists, the largest IP address among the IP addresses of other interfaces is selected as the router ID, regardless of whether the interface is Up.
               The router ID is reselected only when the interface address that is selected as the router ID is deleted or changed. The router ID is not reselected in any of the following cases:
               a. The interface is Down.
               b. A loopback interface is configured when the IP address of a non-loopback interface is selected as the router ID.
               c. A larger IP address of an interface is configured.
               2. Each VPN instance selects the router ID from the addresses of the interfaces of the VPN instance according to the preceding rules.
               3. When both the AMB and SMB exist on the router, the system backs up the router ID set through the related command and the router ID that is selected from IP addresses of the interfaces. After the active/standby switchover is performed, the system checks the validity of the router ID selected from the interface addresses. If the router ID is invalid, the system reselects a router ID.";
          }
          // NCS drop config false leaf 'effect-router-id'
          container afs {
            description
              "List of BGP address family instances.";
            list af {
              key "type";
              description
                "Configure BGP address family instance.";
              leaf type {
                type bgp:instance-af-type;
                description
                  "Address family type of a BGP instance.";
              }
              container ipv4-vpn {
                when "../type = 'ipv4vpn' and ../../../../../../ni:name='_public_'" {
                  tailf:xpath-root 3;
                }
                description
                  "Configure IPv4 VPNv4 options.";
                uses vpn-target-type;
                uses reflector-cluster-type;
                uses reflect-type;
                leaf auto-frr {
                  type boolean;
                  default "false";
                  description
                    "Enable/disable BGP Auto FRR. If IP FRR, VPN FRR, and Auto FRR are all enabled, IP FRR and VPN FRR take precedence over Auto FRR. If a route fails to match the routing policy of IP FRR or VPN FRR, Auto FRR takes effect.";
                }
                leaf tunnel-selector-name {
                  type leafref {
                    path "/ncs:devices/ncs:device/ncs:config/rtp:routing-policy/rtp:tunnel-selectors/rtp:tunnel-selector/rtp:name" {
                      tailf:xpath-root 3;
                    }
                  }
                  description
                    "Configure a tunnel selector and apply it to the BGP IPv4 unicast, BGP VPNv4 address families and BGP VPNv6 address families so that IPv4,VPNv4 and VPNv6 labeled routes can be iterated to tunnels based on the tunnel selector.";
                }
                leaf route-select-delay {
                  type uint16 {
                    range "0..3600";
                  }
                  units "s";
                  default "0";
                  description
                    "Route selection delay.";
                }
                leaf apply-label-mode {
                  type apply-label-type;
                  default "per-route";
                  description
                    "Method of distributing labels to VPNV4 and VPNV6 routes. The way which assigns the label depends on the paf value. If there are a large number of routes, assign a label for the routes that have same nexthop and out-label. This allows all routes which have same nexthop and out-label to use one label.";
                }
                leaf nexthop-select-depend-type {
                  type select-depend-type-ext;
                  default "depend-ip";
                  description
                    "Specify the route iteration mode: IP or tunnel. In tunnel mode, the labeled BGP IPv4 route can participate in route selection only after its next hop is iterated to an LSP. In IP
                     mode, the labeled BGP IPv4 route can participate in route selection only after its next hop is iterated to an IP address. By default, the labeled BGP IPv4 route can participate in route selection
                     if its next hop can be iterated to an IP address, regardless of whether the LSP of the next hop exists. This allows the RR that is not enabled with MPLS to forward labeled routes. In non-RR
                     networking or RR networking where the BGP next hop is changed, BGP needs to check whether there is an LSP destined for the next hop. If such an LSP is not found, BGP needs to establish an LSP in
                     advance. If the default setting is adopted, a labeled BGP IPv4 unicast route may be selected prior to LSP establishment. As a result, services are incorrectly switched before LSP establishment and
                     service stability is affected. Therefore, allow route selection only after the labeled BGP IPv4 route is iterated to an LSP.";
                }
                leaf default-med {
                  type uint32;
                  default "0";
                  description
                    "Specify the Multi-Exit-Discriminator (MED) of BGP routes. The value is an integer. This value is valid only for the imported routes and BGP summarized routes on the local router.";
                }
                leaf best-external {
                  type boolean;
                  default "false";
                  description
                    "Enable/disable best external route selection.";
                }
                leaf label-free-delay {
                  type uint8 {
                    range "0..180";
                  }
                  units "s";
                  default "0";
                  description
                    "Label free delay.";
                }
                leaf add-path-select-num {
                  type uint8 {
                    range "2..64";
                  }
                  description
                    "Number of Add-Path routes.";
                }
                leaf default-local-preference {
                  type uint32 {
                    range "0..4294967295";
                  }
                  default "100";
                  description
                    "The local preference of BGP routes.";
                }
                uses bestroute-med-plus-igp-type;
                uses bestroute-router-id-prior-clusterlist-type;
                leaf reflect-between-client {
                  type boolean;
                  default "true";
                  description
                    "Enable/disable route reflection between clients. If clients of a route reflector (RR) are fully meshed, you can disable route reflection among clients to reduce the cost.";
                }
                leaf activate-route-tag {
                  type boolean;
                  default "false";
                  description
                    "Enable/disable tag-based filtering.";
                }
                uses route-reflector-ext-community-filter-type;
                uses vrf-af-dampening-routes-ext;
                container nexthop-recursive-lookup {
                  description
                    "Configure next hop iteration.";
                  container common {
                    description
                      "Configure next hop iteration common options.";
                    uses nexthop-recursive-lookup-restrain;
                  }
                  uses nexthop-recursive-lookup-delay;
                  uses bit-error-detection-type;
                }
                uses ipv4-import-filter-protocol-type;
                uses ipv4vpn-export-filter-protocol-type;
                uses slow-peer-type;
              }
            }
          }
        }
      }
    }
  }
}
