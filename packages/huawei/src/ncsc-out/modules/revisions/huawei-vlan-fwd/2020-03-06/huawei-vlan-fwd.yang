module huawei-vlan-fwd {
  // Generated by yanger -t ncs
  tailf:mount-id "huawei-nc-1.0:huawei-nc-1.0";
  tailf:ncs-device-type "netconf";

  namespace "urn:huawei:yang:huawei-vlan-fwd";
  prefix vlan-fwd;

  import huawei-pub-type {
    prefix pub-type;
  }
  import huawei-extension {
    prefix ext;
  }
  import huawei-ifm {
    prefix ifm;
  }
  import huawei-ethernet {
    prefix ethernet;
  }
  import huawei-fim-ifm {
    prefix fim-ifm;
  }
  import huawei-vlan {
    prefix vlan;
  }
  ext:task-name "vlan";

  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Forwarding VLAN service.";

  revision 2020-03-06 {
    description
      "Change description.";
    reference "Huawei private.";
  }
  revision 2019-04-15 {
    description
      "Init revision.";
    reference "Huawei private.";
  }

  augment "/ncs:devices/ncs:device/ncs:rpc" {
    container rpc-reset-vlan-ac-suppression-statistics {
      tailf:ncs-device-type "netconf";
      tailf:display-when "not(../../ncs:module) or ../../ncs:module[ncs:name='huawei-vlan-fwd']";
      tailf:action reset-vlan-ac-suppression-statistics {
        tailf:actionpoint ncsproxy {
          tailf:internal;
        }
        description
          "Reset AC suppression.";
        ext:node-ref "/ifm:ifm/ifm:interfaces/ifm:interface/ethernet:ethernet/ethernet:main-interface/ethernet:l2-attribute";
        input {
          leaf interface-name {
            type string;
            mandatory true;
            description
              "Interface name.";
          }
          leaf vlan-id {
            type string;
            mandatory true;
            description
              "VLAN ID.";
          }
        }
      }
    }
  }
  augment "/ncs:devices/ncs:device-group/ncs:ned-id/ncs:rpc" {
    container rpc-reset-vlan-ac-suppression-statistics {
      tailf:ncs-device-type "netconf";
      tailf:display-when "/ncs:devices/ncs:device[ncs:name=current()/../../../ncs:member]/ncs:module[ncs:name='huawei-vlan-fwd']";
      tailf:action reset-vlan-ac-suppression-statistics {
        tailf:actionpoint ncsproxy {
          tailf:internal;
        }
        description
          "Reset AC suppression.";
        ext:node-ref "/ifm:ifm/ifm:interfaces/ifm:interface/ethernet:ethernet/ethernet:main-interface/ethernet:l2-attribute";
        input {
          leaf interface-name {
            type string;
            mandatory true;
            description
              "Interface name.";
          }
          leaf vlan-id {
            type string;
            mandatory true;
            description
              "VLAN ID.";
          }
        }
      }
    }
  }
  augment "/ncs:devices/ncs:template/ncs:ned-id/ncs:config/ifm:ifm/ifm:interfaces/ifm:interface" {
    description
      "Unknown-unicast alarm threshold.";
    container unknow-unicast-threshold {
      // NCS drop when statement
      description
        "Configure unknown-unicast alarm threshold.";
      leaf threshold {
        type string;
        // NCS drop must statement
        description
          "Unknown-unicast alarm threshold, which can be disabled.";
      }
    }
  }
  augment "/ncs:devices/ncs:device/ncs:live-status/ifm:ifm/ifm:interfaces/ifm:interface" {
    description
      "Unknown-unicast alarm threshold.";
    container unknow-unicast-threshold {
      tailf:ncs-device-type "netconf";
      tailf:display-when "not(../../../../../ncs:module) or ../../../../../ncs:module[ncs:name='huawei-vlan-fwd'] or (../../../../../ncs:live-status-protocol[not(ncs:capability)]) or (../../../../../ncs:live-status-protocol/ncs:capability/ncs:module[.='huawei-vlan-fwd'])";
      // NCS drop when statement
      description
        "Configure unknown-unicast alarm threshold.";
      leaf threshold {
        type uint32 {
          range "1..100";
        }
        // NCS drop must statement
        description
          "Unknown-unicast alarm threshold, which can be disabled.";
      }
    }
  }
  augment "/ncs:devices/ncs:device/ncs:config/ifm:ifm/ifm:interfaces/ifm:interface" {
    description
      "Unknown-unicast alarm threshold.";
    container unknow-unicast-threshold {
      tailf:ncs-device-type "netconf";
      tailf:display-when "not(../../../../../ncs:module) or ../../../../../ncs:module[ncs:name='huawei-vlan-fwd']";
      when "../ifm:type='Ethernet' or ../ifm:type='GigabitEthernet' or ../ifm:type='Eth-Trunk' or ../ifm:type='100GE' or ../ifm:type='XGigabitEthernet' or ../ifm:type='40GE' or ../ifm:type='10GE' or ../ifm:type='400GE' or ../ifm:type='25GE' or ../ifm:type='FlexE' or ../ifm:type='50GE' or ../ifm:type='50|100GE'" {
        tailf:xpath-root 3;
      }
      description
        "Configure unknown-unicast alarm threshold.";
      leaf threshold {
        type uint32 {
          range "1..100";
        }
        must "(../../ethernet:ethernet/ethernet:main-interface/ethernet:l2-attribute and not(../../fim-ifm:fim/fim-ifm:statistic-mode='forward')) or (../../ifm:parent-name and ../../ifm:statistic-enable='true') or not(../threshold)" {
          tailf:xpath-root 3;
        }
        description
          "Unknown-unicast alarm threshold, which can be disabled.";
      }
    }
  }
  augment "/ncs:devices/ncs:template/ncs:ned-id/ncs:config/ifm:ifm/ifm:interfaces/ifm:interface/ethernet:ethernet/ethernet:main-interface/ethernet:l2-attribute" {
    description
      "Forwarding VLAN service.";
    container vlan-isolate-attribute {
      description
        "Configure VLAN isolation.";
      leaf isolate-vlanlist {
        type pub-type:ncs_template_vlan-range;
        description
          "Isolated VLAN list.";
      }
      leaf outside-vlan-iso {
        type string;
        // NCS drop default statement
        description
          "Enable/disable VLAN isolation state.";
      }
    }
  }
  augment "/ncs:devices/ncs:device/ncs:live-status/ifm:ifm/ifm:interfaces/ifm:interface/ethernet:ethernet/ethernet:main-interface/ethernet:l2-attribute" {
    description
      "Forwarding VLAN service.";
    container vlan-isolate-attribute {
      tailf:ncs-device-type "netconf";
      tailf:display-when "not(../../../../../../../../ncs:module) or ../../../../../../../../ncs:module[ncs:name='huawei-vlan-fwd'] or (../../../../../../../../ncs:live-status-protocol[not(ncs:capability)]) or (../../../../../../../../ncs:live-status-protocol/ncs:capability/ncs:module[.='huawei-vlan-fwd'])";
      description
        "Configure VLAN isolation.";
      leaf isolate-vlanlist {
        type pub-type:live_ncs_vlan-range;
        description
          "Isolated VLAN list.";
      }
      leaf outside-vlan-iso {
        type boolean;
        // NCS drop default statement
        description
          "Enable/disable VLAN isolation state.";
      }
    }
  }
  augment "/ncs:devices/ncs:device/ncs:config/ifm:ifm/ifm:interfaces/ifm:interface/ethernet:ethernet/ethernet:main-interface/ethernet:l2-attribute" {
    description
      "Forwarding VLAN service.";
    container vlan-isolate-attribute {
      tailf:ncs-device-type "netconf";
      tailf:display-when "not(../../../../../../../../ncs:module) or ../../../../../../../../ncs:module[ncs:name='huawei-vlan-fwd']";
      description
        "Configure VLAN isolation.";
      leaf isolate-vlanlist {
        type pub-type:vlan-range;
        description
          "Isolated VLAN list.";
      }
      leaf outside-vlan-iso {
        type boolean;
        default "false";
        description
          "Enable/disable VLAN isolation state.";
      }
    }
  }
}
