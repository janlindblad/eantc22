module huawei-netstream-notification {
  // Generated by yanger -t ncs
  tailf:mount-id "huawei-nc-1.0:huawei-nc-1.0";
  tailf:ncs-device-type "netconf";

  yang-version 1;
  namespace "urn:huawei:yang:huawei-netstream-notification";
  prefix netstream-notification;

  import huawei-extension {
    prefix ext;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Notification of netstream.";

  revision 2020-09-01 {
    description
      "Initial revision.";
    reference "Huawei private.";
  }
  ext:task-name "netstream";

  augment "/ncs:devices/ncs:device/ncs:notifications/ncs:received-notifications/ncs:notification/ncs:data" {
    container sampler-rate-inconsistent-resume {
      presence "";
      config false;
      description
        "The configured NetStream sampling ratio was same from the effective one.";
      leaf slot-id {
        type string {
          length "1..31";
        }
        description
          "Slot Id.";
      }
      leaf fix-packets-lower-limit {
        type string {
          length "1..31";
        }
        description
          "Lower limit for fixed-packet-number-based sampling ratio.";
      }
      leaf random-packets-lower-limit {
        type string {
          length "1..31";
        }
        description
          "Lower limit for random-packet-number-based sampling ratio.";
      }
      leaf fix-time-lower-limit {
        type string {
          length "1..31";
        }
        description
          "Lower limit for fixed-time-based sampling ratio.";
      }
    }
  }
  augment "/ncs:devices/ncs:device/ncs:notifications/ncs:received-notifications/ncs:notification/ncs:data" {
    container sampler-rate-inconsistent {
      presence "";
      config false;
      description
        "The configured NetStream sampling ratio was different from the effective one.";
      leaf slot-id {
        type string {
          length "1..31";
        }
        description
          "Slot Id.";
      }
      leaf fix-packets-lower-limit {
        type string {
          length "1..31";
        }
        description
          "Lower limit for fixed-packet-number-based sampling ratio.";
      }
      leaf random-packets-lower-limit {
        type string {
          length "1..31";
        }
        description
          "Lower limit for random-packet-number-based sampling ratio.";
      }
      leaf fix-time-lower-limit {
        type string {
          length "1..31";
        }
        description
          "Lower limit for fixed-time-based sampling ratio.";
      }
    }
  }
  augment "/ncs:devices/ncs:device/ncs:netconf-notifications/ncs:received-notifications/ncs:notification/ncs:data" {
    container sampler-rate-inconsistent-resume {
      presence "";
      config false;
      description
        "The configured NetStream sampling ratio was same from the effective one.";
      leaf slot-id {
        type string {
          length "1..31";
        }
        description
          "Slot Id.";
      }
      leaf fix-packets-lower-limit {
        type string {
          length "1..31";
        }
        description
          "Lower limit for fixed-packet-number-based sampling ratio.";
      }
      leaf random-packets-lower-limit {
        type string {
          length "1..31";
        }
        description
          "Lower limit for random-packet-number-based sampling ratio.";
      }
      leaf fix-time-lower-limit {
        type string {
          length "1..31";
        }
        description
          "Lower limit for fixed-time-based sampling ratio.";
      }
    }
  }
  augment "/ncs:devices/ncs:device/ncs:netconf-notifications/ncs:received-notifications/ncs:notification/ncs:data" {
    container sampler-rate-inconsistent {
      presence "";
      config false;
      description
        "The configured NetStream sampling ratio was different from the effective one.";
      leaf slot-id {
        type string {
          length "1..31";
        }
        description
          "Slot Id.";
      }
      leaf fix-packets-lower-limit {
        type string {
          length "1..31";
        }
        description
          "Lower limit for fixed-packet-number-based sampling ratio.";
      }
      leaf random-packets-lower-limit {
        type string {
          length "1..31";
        }
        description
          "Lower limit for random-packet-number-based sampling ratio.";
      }
      leaf fix-time-lower-limit {
        type string {
          length "1..31";
        }
        description
          "Lower limit for fixed-time-based sampling ratio.";
      }
    }
  }
}
