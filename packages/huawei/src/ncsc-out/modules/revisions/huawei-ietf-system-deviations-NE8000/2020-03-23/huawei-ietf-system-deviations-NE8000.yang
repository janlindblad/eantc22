module huawei-ietf-system-deviations-NE8000 {
  // Generated by yanger -t ncs
  tailf:mount-id "huawei-nc-1.0:huawei-nc-1.0";
  tailf:ncs-device-type "netconf";

  namespace "urn:huawei:yang:huawei-ietf-system-deviations-NE8000";
  prefix system-devs-NE8000;

  import ietf-system {
    prefix sys;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "This module contains a collection of YANG definitions for the
     configuration and identification of some common system
     properties within a device containing a NETCONF server. This
     includes data node definitions for system identification,
     time-of-day management, user management, DNS resolver
     configuration, and some protocol operations for system
     management.";

  revision 2020-03-23 {
    description
      "Initial revision.";
    reference "Huawei private.";
  }

  deviation "/ncs:devices/ncs:template/ncs:ned-id/ncs:config/sys:system/sys:radius" {
    deviate not-supported;
  }
  deviation "/ncs:devices/ncs:device/ncs:live-status/sys:system/sys:radius" {
    deviate not-supported;
  }
  deviation "/ncs:devices/ncs:device/ncs:config/sys:system/sys:radius" {
    deviate not-supported;
  }
  deviation "/ncs:devices/ncs:template/ncs:ned-id/ncs:config/sys:system/sys:authentication" {
    deviate not-supported;
  }
  deviation "/ncs:devices/ncs:device/ncs:live-status/sys:system/sys:authentication" {
    deviate not-supported;
  }
  deviation "/ncs:devices/ncs:device/ncs:config/sys:system/sys:authentication" {
    deviate not-supported;
  }
  deviation "/ncs:devices/ncs:template/ncs:ned-id/ncs:config/sys:system/sys:dns-resolver" {
    deviate not-supported;
  }
  deviation "/ncs:devices/ncs:device/ncs:live-status/sys:system/sys:dns-resolver" {
    deviate not-supported;
  }
  deviation "/ncs:devices/ncs:device/ncs:config/sys:system/sys:dns-resolver" {
    deviate not-supported;
  }
  deviation "/ncs:devices/ncs:device/ncs:rpc/sys:rpc-system-shutdown/sys:system-shutdown" {
    deviate not-supported;
  }
  deviation "/ncs:devices/ncs:device/ncs:live-status/sys:system-state/sys:platform" {
    deviate not-supported;
  }
  deviation "/ncs:devices/ncs:template/ncs:ned-id/ncs:config/sys:system/sys:contact" {
    deviate not-supported;
  }
  deviation "/ncs:devices/ncs:device/ncs:live-status/sys:system/sys:contact" {
    deviate not-supported;
  }
  deviation "/ncs:devices/ncs:device/ncs:config/sys:system/sys:contact" {
    deviate not-supported;
  }
  deviation "/ncs:devices/ncs:template/ncs:ned-id/ncs:config/sys:system/sys:hostname" {
    deviate replace {
      type string;
    }
    deviate add {
      // NCS drop default statement
    }
  }
  deviation "/ncs:devices/ncs:device/ncs:live-status/sys:system/sys:hostname" {
    deviate replace {
      type string {
        length "1..246";
      }
    }
    deviate add {
      // NCS drop default statement
    }
  }
  deviation "/ncs:devices/ncs:device/ncs:config/sys:system/sys:hostname" {
    deviate replace {
      type string {
        length "1..246";
      }
    }
    deviate add {
      default "HUAWEI";
    }
  }
  deviation "/ncs:devices/ncs:template/ncs:ned-id/ncs:config/sys:system/sys:location" {
    deviate not-supported;
  }
  deviation "/ncs:devices/ncs:device/ncs:live-status/sys:system/sys:location" {
    deviate not-supported;
  }
  deviation "/ncs:devices/ncs:device/ncs:config/sys:system/sys:location" {
    deviate not-supported;
  }
  deviation "/ncs:devices/ncs:template/ncs:ned-id/ncs:config/sys:system/sys:clock/sys:timezone/sys:timezone-name" {
    deviate not-supported;
  }
  deviation "/ncs:devices/ncs:device/ncs:live-status/sys:system/sys:clock/sys:timezone/sys:timezone-name" {
    deviate not-supported;
  }
  deviation "/ncs:devices/ncs:device/ncs:config/sys:system/sys:clock/sys:timezone/sys:timezone-name" {
    deviate not-supported;
  }
  deviation "/ncs:devices/ncs:template/ncs:ned-id/ncs:config/sys:system/sys:clock/sys:timezone/sys:timezone-utc-offset/sys:timezone-utc-offset" {
    deviate replace {
      type string;
    }
    deviate add {
      // NCS drop default statement
    }
  }
  deviation "/ncs:devices/ncs:device/ncs:live-status/sys:system/sys:clock/sys:timezone/sys:timezone-utc-offset/sys:timezone-utc-offset" {
    deviate replace {
      type int16 {
        range "-1080..1080";
      }
    }
    deviate add {
      // NCS drop default statement
    }
  }
  deviation "/ncs:devices/ncs:device/ncs:config/sys:system/sys:clock/sys:timezone/sys:timezone-utc-offset/sys:timezone-utc-offset" {
    deviate replace {
      type int16 {
        range "-1080..1080";
      }
    }
    deviate add {
      default "0";
    }
  }
  deviation "/ncs:devices/ncs:template/ncs:ned-id/ncs:config/sys:system/sys:ntp/sys:server/sys:name" {
    deviate replace {
      type string;
    }
  }
  deviation "/ncs:devices/ncs:device/ncs:live-status/sys:system/sys:ntp/sys:server/sys:name" {
    deviate replace {
      type string {
        length "1..63";
      }
    }
  }
  deviation "/ncs:devices/ncs:device/ncs:config/sys:system/sys:ntp/sys:server/sys:name" {
    deviate replace {
      type string {
        length "1..63";
      }
    }
  }
  deviation "/ncs:devices/ncs:template/ncs:ned-id/ncs:config/sys:system/sys:ntp/sys:server/sys:association-type" {
    deviate replace {
      type string;
    }
  }
  deviation "/ncs:devices/ncs:device/ncs:live-status/sys:system/sys:ntp/sys:server/sys:association-type" {
    deviate replace {
      type enumeration {
        enum "server" {
          value 0;
          description
            "Use client association mode. This device
             will not provide synchronization to the
             configured NTP server.";
        }
        enum "peer" {
          value 1;
          description
            "Use symmetric active association mode.
             This device may provide synchronization
             to the configured NTP server.";
        }
      }
    }
  }
  deviation "/ncs:devices/ncs:device/ncs:config/sys:system/sys:ntp/sys:server/sys:association-type" {
    deviate replace {
      type enumeration {
        enum "server" {
          value 0;
          description
            "Use client association mode. This device
             will not provide synchronization to the
             configured NTP server.";
        }
        enum "peer" {
          value 1;
          description
            "Use symmetric active association mode.
             This device may provide synchronization
             to the configured NTP server.";
        }
      }
    }
  }
}
