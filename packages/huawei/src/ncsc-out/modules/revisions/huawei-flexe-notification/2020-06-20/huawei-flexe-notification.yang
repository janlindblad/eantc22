module huawei-flexe-notification {
  // Generated by yanger -t ncs
  tailf:mount-id "huawei-nc-1.0:huawei-nc-1.0";
  tailf:ncs-device-type "netconf";

  yang-version 1;
  namespace "urn:huawei:yang:huawei-flexe-notification";
  prefix flexe-notification;

  import huawei-extension {
    prefix ext;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Notification of flexe module.";

  revision 2020-06-20 {
    description
      "Initial revision.";
    reference "Huawei private.";
  }
  ext:task-name "device-mgr";

  augment "/ncs:devices/ncs:device/ncs:notifications/ncs:received-notifications/ncs:notification/ncs:data" {
    container flexe-speed-mismatch-resume {
      presence "";
      config false;
      description
        "The speed modes of the FlexE physical interfaces in the FlexE group mismatch alarm resume.";
      leaf group-index {
        type uint32;
        description
          "Indicates the FlexE group index.";
      }
      leaf group-name {
        type string {
          length "1..32";
        }
        description
          "Indicates the FlexE group name.";
      }
    }
  }
  augment "/ncs:devices/ncs:device/ncs:notifications/ncs:received-notifications/ncs:notification/ncs:data" {
    container flexe-speed-mismatch {
      presence "";
      config false;
      description
        "The speed modes of the FlexE physical interfaces in the FlexE group mismatch alarm.";
      leaf group-index {
        type uint32;
        description
          "Indicates the FlexE group index.";
      }
      leaf group-name {
        type string {
          length "1..32";
        }
        description
          "Indicates the FlexE group name.";
      }
    }
  }
  augment "/ncs:devices/ncs:device/ncs:notifications/ncs:received-notifications/ncs:notification/ncs:data" {
    container flexe-negotiation-fail-resume {
      presence "";
      config false;
      description
        "FlexE group negotiation fail alarm resume.";
      leaf group-index {
        type uint32;
        description
          "Indicates the FlexE group index.";
      }
      leaf group-name {
        type string {
          length "1..32";
        }
        description
          "Indicates the FlexE group name.";
      }
    }
  }
  augment "/ncs:devices/ncs:device/ncs:notifications/ncs:received-notifications/ncs:notification/ncs:data" {
    container flexe-negotiation-fail {
      presence "";
      config false;
      description
        "FlexE group negotiation fail alarm.";
      leaf group-index {
        type uint32;
        description
          "Indicates the FlexE group index.";
      }
      leaf group-name {
        type string {
          length "1..32";
        }
        description
          "Indicates the FlexE group name.";
      }
    }
  }
  augment "/ncs:devices/ncs:device/ncs:notifications/ncs:received-notifications/ncs:notification/ncs:data" {
    container flexe-sub-ts-mismatch-resume {
      presence "";
      config false;
      description
        "This object indicates that a clear alarm is generated when the sub-timeslot granularity of the interface does not match.";
      leaf physical-index {
        type uint32;
        description
          "This object indicates the interface index.";
      }
      leaf physical-port-name {
        type string {
          length "1..32";
        }
        description
          "Indicates the alarm is cleared.";
      }
    }
  }
  augment "/ncs:devices/ncs:device/ncs:notifications/ncs:received-notifications/ncs:notification/ncs:data" {
    container flexe-sub-ts-mismatch {
      presence "";
      config false;
      description
        "This object indicates that an alarm is generated when the sub-timeslot granularity of the interface does not match.";
      leaf physical-index {
        type uint32;
        description
          "This object indicates the interface index.";
      }
      leaf physical-port-name {
        type string {
          length "1..32";
        }
        description
          "Indicates the alarm is cleared.";
      }
    }
  }
  augment "/ncs:devices/ncs:device/ncs:notifications/ncs:received-notifications/ncs:notification/ncs:data" {
    container flexe-remote-fault-resume {
      presence "";
      config false;
      description
        "This object indicates that a clear alarm is generated when the transmit link from the remote device to the local device recovers.";
      leaf physical-index {
        type uint32;
        description
          "This object indicates the interface index.";
      }
      leaf physical-port-name {
        type string {
          length "1..32";
        }
        description
          "Indicates the alarm is cleared.";
      }
    }
  }
  augment "/ncs:devices/ncs:device/ncs:notifications/ncs:received-notifications/ncs:notification/ncs:data" {
    container flexe-remote-fault {
      presence "";
      config false;
      description
        "This object indicates that an alarm is generated when the transmit link from the remote device to the local device fails.";
      leaf physical-index {
        type uint32;
        description
          "This object indicates the interface index.";
      }
      leaf physical-port-name {
        type string {
          length "1..32";
        }
        description
          "Indicates the physical port name.";
      }
    }
  }
  augment "/ncs:devices/ncs:device/ncs:notifications/ncs:received-notifications/ncs:notification/ncs:data" {
    container flexe-number-mismatch-resume {
      presence "";
      config false;
      description
        "This object indicates that a clear alarm is generated when the communication parameter number of the physical interfaces do not match.";
      leaf physical-index {
        type uint32;
        description
          "This object indicates the interface index.";
      }
      leaf physical-port-name {
        type string {
          length "1..32";
        }
        description
          "Indicates the physical port name.";
      }
      leaf physical-port-local-phy-num {
        type string {
          length "1..32";
        }
        description
          "Indicates the local physical port phy number.";
      }
      leaf physical-port-remote-phy-num {
        type string {
          length "1..32";
        }
        description
          "Indicates the remote physical port phy number.";
      }
    }
  }
  augment "/ncs:devices/ncs:device/ncs:notifications/ncs:received-notifications/ncs:notification/ncs:data" {
    container flexe-number-mismatch {
      presence "";
      config false;
      description
        "This object indicates that an alarm is generated when the communication parameter number of the physical interfaces do not match.";
      leaf physical-index {
        type uint32;
        description
          "This object indicates the interface index.";
      }
      leaf physical-port-name {
        type string {
          length "1..32";
        }
        description
          "Indicates the physical port name.";
      }
      leaf physical-port-local-phy-num {
        type string {
          length "1..32";
        }
        description
          "Indicates the local physical port phy number.";
      }
      leaf physical-port-remote-phy-num {
        type string {
          length "1..32";
        }
        description
          "Indicates the remote physical port phy number.";
      }
    }
  }
  augment "/ncs:devices/ncs:device/ncs:notifications/ncs:received-notifications/ncs:notification/ncs:data" {
    container flexe-local-fault-resume {
      presence "";
      config false;
      description
        "This object indicates that a clear alarm is generated when the receive link from the remote device to the local device recovers.";
      leaf physical-index {
        type uint32;
        description
          "This object indicates the interface index.";
      }
      leaf physical-port-name {
        type string {
          length "1..32";
        }
        description
          "Indicates the physical port name.";
      }
    }
  }
  augment "/ncs:devices/ncs:device/ncs:notifications/ncs:received-notifications/ncs:notification/ncs:data" {
    container flexe-local-fault {
      presence "";
      config false;
      description
        "This object indicates that an alarm is generated when the receive link from the remote device to the local device fails.";
      leaf physical-index {
        type uint32;
        description
          "This object indicates the interface index.";
      }
      leaf physical-port-name {
        type string {
          length "1..32";
        }
        description
          "Indicates the physical port name.";
      }
    }
  }
  augment "/ncs:devices/ncs:device/ncs:notifications/ncs:received-notifications/ncs:notification/ncs:data" {
    container flexe-group-mismatch-resume {
      presence "";
      config false;
      description
        "This object indicates that the clear alarm is generated when the group ID of the physical interface does not match.";
      leaf physical-index {
        type uint32;
        description
          "This object indicates the interface index.";
      }
      leaf physical-port-name {
        type string {
          length "1..32";
        }
        description
          "Indicates the physical port name.";
      }
      leaf physical-port-local-groupid {
        type uint32;
        description
          "Indicates the local physical port groupid.";
      }
      leaf physical-port-remte-groupid {
        type uint32;
        description
          "Indicates the remote physical port groupID.";
      }
    }
  }
  augment "/ncs:devices/ncs:device/ncs:notifications/ncs:received-notifications/ncs:notification/ncs:data" {
    container flexe-group-mismatch {
      presence "";
      config false;
      description
        "This object indicates that an alarm is generated when the group ID of the physical interface does not match.";
      leaf physical-index {
        type uint32;
        description
          "This object indicates the interface index.";
      }
      leaf physical-port-name {
        type string {
          length "1..32";
        }
        description
          "Indicates the physical port name.";
      }
      leaf physical-port-local-groupid {
        type uint32;
        description
          "Indicates the local physical port groupid.";
      }
      leaf physical-port-remte-groupid {
        type uint32;
        description
          "Indicates the remote physical port groupID.";
      }
    }
  }
  augment "/ncs:devices/ncs:device/ncs:notifications/ncs:received-notifications/ncs:notification/ncs:data" {
    container flexe-physical-fcs-sd-resume {
      presence "";
      config false;
      description
        "This object indicates that a clear alarm is generated when MAC FCS SD alarm notification.";
      leaf physical-index {
        type uint32;
        description
          "This object indicates the interface index.";
      }
      leaf physical-port-name {
        type string {
          length "1..32";
        }
        description
          "Indicates the physical port name.";
      }
    }
  }
  augment "/ncs:devices/ncs:device/ncs:notifications/ncs:received-notifications/ncs:notification/ncs:data" {
    container flexe-physical-fcs-sd {
      presence "";
      config false;
      description
        "This object indicates that an alarm is generated when MAC FCS SD alarm notification.";
      leaf physical-index {
        type uint32;
        description
          "This object indicates the interface index.";
      }
      leaf physical-port-name {
        type string {
          length "1..32";
        }
        description
          "Indicates the physical port name.";
      }
    }
  }
  augment "/ncs:devices/ncs:device/ncs:notifications/ncs:received-notifications/ncs:notification/ncs:data" {
    container flexe-physical-delay-resume {
      presence "";
      config false;
      description
        "This object indicates that the clear alarm is generated when the delay difference between FlexE physical interfaces in the same group is too large.";
      leaf physical-index {
        type uint32;
        description
          "This object indicates the interface index.";
      }
      leaf physical-port-list {
        type string {
          length "1..32";
        }
        description
          "Indicates the physical port list.";
      }
    }
  }
  augment "/ncs:devices/ncs:device/ncs:notifications/ncs:received-notifications/ncs:notification/ncs:data" {
    container flexe-physical-delay {
      presence "";
      config false;
      description
        "This object indicates that an alarm is generated when the delay difference between FlexE physical interfaces in the same group is too large.";
      leaf physical-index {
        type uint32;
        description
          "This object indicates the interface index.";
      }
      leaf physical-port-list {
        type string {
          length "1..32";
        }
        description
          "Indicates the physical port list.";
      }
    }
  }
  augment "/ncs:devices/ncs:device/ncs:notifications/ncs:received-notifications/ncs:notification/ncs:data" {
    container flexe-client-mismatch-resume {
      presence "";
      config false;
      description
        "Indicates the alarm is cleared.";
      leaf physical-index {
        type uint32;
        description
          "This object indicates the interface index.";
      }
      leaf physical-port-name {
        type string {
          length "1..32";
        }
        description
          "Indicates the physical port name.";
      }
    }
  }
  augment "/ncs:devices/ncs:device/ncs:notifications/ncs:received-notifications/ncs:notification/ncs:data" {
    container flexe-client-mismatch {
      presence "";
      config false;
      description
        "Indicates the alarm is detected.";
      leaf physical-index {
        type uint32;
        description
          "This object indicates the interface index.";
      }
      leaf physical-port-name {
        type string {
          length "1..32";
        }
        description
          "Indicates the physical port name.";
      }
    }
  }
  augment "/ncs:devices/ncs:device/ncs:notifications/ncs:received-notifications/ncs:notification/ncs:data" {
    container flexe-band-insufficient-resume {
      presence "";
      config false;
      description
        "This object indicates a clear alarm that the existing bandwidth does not meet the configuration requirements.";
      leaf physical-index {
        type uint32;
        description
          "This object indicates the interface index.";
      }
      leaf physical-port-name {
        type string {
          length "1..32";
        }
        description
          "Indicates the physical port name.";
      }
      leaf port-bw {
        type string {
          length "1..32";
        }
        description
          "Indicates the physical port name.";
      }
    }
  }
  augment "/ncs:devices/ncs:device/ncs:notifications/ncs:received-notifications/ncs:notification/ncs:data" {
    container flexe-band-insufficient {
      presence "";
      config false;
      description
        "This object indicates an alarm that the existing bandwidth does not meet the configuration requirements.";
      leaf physical-index {
        type uint32;
        description
          "This object indicates the interface index.";
      }
      leaf physical-port-name {
        type string {
          length "1..32";
        }
        description
          "Indicates the physical port name.";
      }
      leaf port-bw {
        type string {
          length "1..32";
        }
        description
          "Indicates the physical port name.";
      }
    }
  }
  augment "/ncs:devices/ncs:device/ncs:notifications/ncs:received-notifications/ncs:notification/ncs:data" {
    container flexe-band-mismatch-resume {
      presence "";
      config false;
      description
        "Indicates the alarm is cleared.";
      leaf physical-index {
        type uint32;
        description
          "This object indicates the interface index.";
      }
      leaf physical-port-name {
        type string {
          length "1..32";
        }
        description
          "Indicates the physical port name.";
      }
    }
  }
  augment "/ncs:devices/ncs:device/ncs:notifications/ncs:received-notifications/ncs:notification/ncs:data" {
    container flexe-band-mismatch {
      presence "";
      config false;
      description
        "Indicates the alarm is detected.";
      leaf physical-index {
        type uint32;
        description
          "This object indicates the interface index.";
      }
      leaf physical-port-name {
        type string {
          length "1..32";
        }
        description
          "Indicates the physical port name.";
      }
    }
  }
  augment "/ncs:devices/ncs:device/ncs:notifications/ncs:received-notifications/ncs:notification/ncs:data" {
    container flexe-calendar-mismatch-resume {
      presence "";
      config false;
      description
        "The alarm of mismatch between the actually received and expected client calendars on the FlexE Group is cleared.";
      leaf group-index {
        type uint32;
        description
          "Indicates the FlexE group index.";
      }
      leaf group-name {
        type string {
          length "1..32";
        }
        description
          "Indicates the FlexE group name.";
      }
    }
  }
  augment "/ncs:devices/ncs:device/ncs:notifications/ncs:received-notifications/ncs:notification/ncs:data" {
    container flexe-calendar-mismatch {
      presence "";
      config false;
      description
        "Alarm of mismatch between the actually received and expected client calendars on the FlexE Group.";
      leaf group-index {
        type uint32;
        description
          "Indicates the FlexE group index.";
      }
      leaf group-name {
        type string {
          length "1..32";
        }
        description
          "Indicates the FlexE group name.";
      }
    }
  }
  augment "/ncs:devices/ncs:device/ncs:netconf-notifications/ncs:received-notifications/ncs:notification/ncs:data" {
    container flexe-speed-mismatch-resume {
      presence "";
      config false;
      description
        "The speed modes of the FlexE physical interfaces in the FlexE group mismatch alarm resume.";
      leaf group-index {
        type uint32;
        description
          "Indicates the FlexE group index.";
      }
      leaf group-name {
        type string {
          length "1..32";
        }
        description
          "Indicates the FlexE group name.";
      }
    }
  }
  augment "/ncs:devices/ncs:device/ncs:netconf-notifications/ncs:received-notifications/ncs:notification/ncs:data" {
    container flexe-speed-mismatch {
      presence "";
      config false;
      description
        "The speed modes of the FlexE physical interfaces in the FlexE group mismatch alarm.";
      leaf group-index {
        type uint32;
        description
          "Indicates the FlexE group index.";
      }
      leaf group-name {
        type string {
          length "1..32";
        }
        description
          "Indicates the FlexE group name.";
      }
    }
  }
  augment "/ncs:devices/ncs:device/ncs:netconf-notifications/ncs:received-notifications/ncs:notification/ncs:data" {
    container flexe-negotiation-fail-resume {
      presence "";
      config false;
      description
        "FlexE group negotiation fail alarm resume.";
      leaf group-index {
        type uint32;
        description
          "Indicates the FlexE group index.";
      }
      leaf group-name {
        type string {
          length "1..32";
        }
        description
          "Indicates the FlexE group name.";
      }
    }
  }
  augment "/ncs:devices/ncs:device/ncs:netconf-notifications/ncs:received-notifications/ncs:notification/ncs:data" {
    container flexe-negotiation-fail {
      presence "";
      config false;
      description
        "FlexE group negotiation fail alarm.";
      leaf group-index {
        type uint32;
        description
          "Indicates the FlexE group index.";
      }
      leaf group-name {
        type string {
          length "1..32";
        }
        description
          "Indicates the FlexE group name.";
      }
    }
  }
  augment "/ncs:devices/ncs:device/ncs:netconf-notifications/ncs:received-notifications/ncs:notification/ncs:data" {
    container flexe-sub-ts-mismatch-resume {
      presence "";
      config false;
      description
        "This object indicates that a clear alarm is generated when the sub-timeslot granularity of the interface does not match.";
      leaf physical-index {
        type uint32;
        description
          "This object indicates the interface index.";
      }
      leaf physical-port-name {
        type string {
          length "1..32";
        }
        description
          "Indicates the alarm is cleared.";
      }
    }
  }
  augment "/ncs:devices/ncs:device/ncs:netconf-notifications/ncs:received-notifications/ncs:notification/ncs:data" {
    container flexe-sub-ts-mismatch {
      presence "";
      config false;
      description
        "This object indicates that an alarm is generated when the sub-timeslot granularity of the interface does not match.";
      leaf physical-index {
        type uint32;
        description
          "This object indicates the interface index.";
      }
      leaf physical-port-name {
        type string {
          length "1..32";
        }
        description
          "Indicates the alarm is cleared.";
      }
    }
  }
  augment "/ncs:devices/ncs:device/ncs:netconf-notifications/ncs:received-notifications/ncs:notification/ncs:data" {
    container flexe-remote-fault-resume {
      presence "";
      config false;
      description
        "This object indicates that a clear alarm is generated when the transmit link from the remote device to the local device recovers.";
      leaf physical-index {
        type uint32;
        description
          "This object indicates the interface index.";
      }
      leaf physical-port-name {
        type string {
          length "1..32";
        }
        description
          "Indicates the alarm is cleared.";
      }
    }
  }
  augment "/ncs:devices/ncs:device/ncs:netconf-notifications/ncs:received-notifications/ncs:notification/ncs:data" {
    container flexe-remote-fault {
      presence "";
      config false;
      description
        "This object indicates that an alarm is generated when the transmit link from the remote device to the local device fails.";
      leaf physical-index {
        type uint32;
        description
          "This object indicates the interface index.";
      }
      leaf physical-port-name {
        type string {
          length "1..32";
        }
        description
          "Indicates the physical port name.";
      }
    }
  }
  augment "/ncs:devices/ncs:device/ncs:netconf-notifications/ncs:received-notifications/ncs:notification/ncs:data" {
    container flexe-number-mismatch-resume {
      presence "";
      config false;
      description
        "This object indicates that a clear alarm is generated when the communication parameter number of the physical interfaces do not match.";
      leaf physical-index {
        type uint32;
        description
          "This object indicates the interface index.";
      }
      leaf physical-port-name {
        type string {
          length "1..32";
        }
        description
          "Indicates the physical port name.";
      }
      leaf physical-port-local-phy-num {
        type string {
          length "1..32";
        }
        description
          "Indicates the local physical port phy number.";
      }
      leaf physical-port-remote-phy-num {
        type string {
          length "1..32";
        }
        description
          "Indicates the remote physical port phy number.";
      }
    }
  }
  augment "/ncs:devices/ncs:device/ncs:netconf-notifications/ncs:received-notifications/ncs:notification/ncs:data" {
    container flexe-number-mismatch {
      presence "";
      config false;
      description
        "This object indicates that an alarm is generated when the communication parameter number of the physical interfaces do not match.";
      leaf physical-index {
        type uint32;
        description
          "This object indicates the interface index.";
      }
      leaf physical-port-name {
        type string {
          length "1..32";
        }
        description
          "Indicates the physical port name.";
      }
      leaf physical-port-local-phy-num {
        type string {
          length "1..32";
        }
        description
          "Indicates the local physical port phy number.";
      }
      leaf physical-port-remote-phy-num {
        type string {
          length "1..32";
        }
        description
          "Indicates the remote physical port phy number.";
      }
    }
  }
  augment "/ncs:devices/ncs:device/ncs:netconf-notifications/ncs:received-notifications/ncs:notification/ncs:data" {
    container flexe-local-fault-resume {
      presence "";
      config false;
      description
        "This object indicates that a clear alarm is generated when the receive link from the remote device to the local device recovers.";
      leaf physical-index {
        type uint32;
        description
          "This object indicates the interface index.";
      }
      leaf physical-port-name {
        type string {
          length "1..32";
        }
        description
          "Indicates the physical port name.";
      }
    }
  }
  augment "/ncs:devices/ncs:device/ncs:netconf-notifications/ncs:received-notifications/ncs:notification/ncs:data" {
    container flexe-local-fault {
      presence "";
      config false;
      description
        "This object indicates that an alarm is generated when the receive link from the remote device to the local device fails.";
      leaf physical-index {
        type uint32;
        description
          "This object indicates the interface index.";
      }
      leaf physical-port-name {
        type string {
          length "1..32";
        }
        description
          "Indicates the physical port name.";
      }
    }
  }
  augment "/ncs:devices/ncs:device/ncs:netconf-notifications/ncs:received-notifications/ncs:notification/ncs:data" {
    container flexe-group-mismatch-resume {
      presence "";
      config false;
      description
        "This object indicates that the clear alarm is generated when the group ID of the physical interface does not match.";
      leaf physical-index {
        type uint32;
        description
          "This object indicates the interface index.";
      }
      leaf physical-port-name {
        type string {
          length "1..32";
        }
        description
          "Indicates the physical port name.";
      }
      leaf physical-port-local-groupid {
        type uint32;
        description
          "Indicates the local physical port groupid.";
      }
      leaf physical-port-remte-groupid {
        type uint32;
        description
          "Indicates the remote physical port groupID.";
      }
    }
  }
  augment "/ncs:devices/ncs:device/ncs:netconf-notifications/ncs:received-notifications/ncs:notification/ncs:data" {
    container flexe-group-mismatch {
      presence "";
      config false;
      description
        "This object indicates that an alarm is generated when the group ID of the physical interface does not match.";
      leaf physical-index {
        type uint32;
        description
          "This object indicates the interface index.";
      }
      leaf physical-port-name {
        type string {
          length "1..32";
        }
        description
          "Indicates the physical port name.";
      }
      leaf physical-port-local-groupid {
        type uint32;
        description
          "Indicates the local physical port groupid.";
      }
      leaf physical-port-remte-groupid {
        type uint32;
        description
          "Indicates the remote physical port groupID.";
      }
    }
  }
  augment "/ncs:devices/ncs:device/ncs:netconf-notifications/ncs:received-notifications/ncs:notification/ncs:data" {
    container flexe-physical-fcs-sd-resume {
      presence "";
      config false;
      description
        "This object indicates that a clear alarm is generated when MAC FCS SD alarm notification.";
      leaf physical-index {
        type uint32;
        description
          "This object indicates the interface index.";
      }
      leaf physical-port-name {
        type string {
          length "1..32";
        }
        description
          "Indicates the physical port name.";
      }
    }
  }
  augment "/ncs:devices/ncs:device/ncs:netconf-notifications/ncs:received-notifications/ncs:notification/ncs:data" {
    container flexe-physical-fcs-sd {
      presence "";
      config false;
      description
        "This object indicates that an alarm is generated when MAC FCS SD alarm notification.";
      leaf physical-index {
        type uint32;
        description
          "This object indicates the interface index.";
      }
      leaf physical-port-name {
        type string {
          length "1..32";
        }
        description
          "Indicates the physical port name.";
      }
    }
  }
  augment "/ncs:devices/ncs:device/ncs:netconf-notifications/ncs:received-notifications/ncs:notification/ncs:data" {
    container flexe-physical-delay-resume {
      presence "";
      config false;
      description
        "This object indicates that the clear alarm is generated when the delay difference between FlexE physical interfaces in the same group is too large.";
      leaf physical-index {
        type uint32;
        description
          "This object indicates the interface index.";
      }
      leaf physical-port-list {
        type string {
          length "1..32";
        }
        description
          "Indicates the physical port list.";
      }
    }
  }
  augment "/ncs:devices/ncs:device/ncs:netconf-notifications/ncs:received-notifications/ncs:notification/ncs:data" {
    container flexe-physical-delay {
      presence "";
      config false;
      description
        "This object indicates that an alarm is generated when the delay difference between FlexE physical interfaces in the same group is too large.";
      leaf physical-index {
        type uint32;
        description
          "This object indicates the interface index.";
      }
      leaf physical-port-list {
        type string {
          length "1..32";
        }
        description
          "Indicates the physical port list.";
      }
    }
  }
  augment "/ncs:devices/ncs:device/ncs:netconf-notifications/ncs:received-notifications/ncs:notification/ncs:data" {
    container flexe-client-mismatch-resume {
      presence "";
      config false;
      description
        "Indicates the alarm is cleared.";
      leaf physical-index {
        type uint32;
        description
          "This object indicates the interface index.";
      }
      leaf physical-port-name {
        type string {
          length "1..32";
        }
        description
          "Indicates the physical port name.";
      }
    }
  }
  augment "/ncs:devices/ncs:device/ncs:netconf-notifications/ncs:received-notifications/ncs:notification/ncs:data" {
    container flexe-client-mismatch {
      presence "";
      config false;
      description
        "Indicates the alarm is detected.";
      leaf physical-index {
        type uint32;
        description
          "This object indicates the interface index.";
      }
      leaf physical-port-name {
        type string {
          length "1..32";
        }
        description
          "Indicates the physical port name.";
      }
    }
  }
  augment "/ncs:devices/ncs:device/ncs:netconf-notifications/ncs:received-notifications/ncs:notification/ncs:data" {
    container flexe-band-insufficient-resume {
      presence "";
      config false;
      description
        "This object indicates a clear alarm that the existing bandwidth does not meet the configuration requirements.";
      leaf physical-index {
        type uint32;
        description
          "This object indicates the interface index.";
      }
      leaf physical-port-name {
        type string {
          length "1..32";
        }
        description
          "Indicates the physical port name.";
      }
      leaf port-bw {
        type string {
          length "1..32";
        }
        description
          "Indicates the physical port name.";
      }
    }
  }
  augment "/ncs:devices/ncs:device/ncs:netconf-notifications/ncs:received-notifications/ncs:notification/ncs:data" {
    container flexe-band-insufficient {
      presence "";
      config false;
      description
        "This object indicates an alarm that the existing bandwidth does not meet the configuration requirements.";
      leaf physical-index {
        type uint32;
        description
          "This object indicates the interface index.";
      }
      leaf physical-port-name {
        type string {
          length "1..32";
        }
        description
          "Indicates the physical port name.";
      }
      leaf port-bw {
        type string {
          length "1..32";
        }
        description
          "Indicates the physical port name.";
      }
    }
  }
  augment "/ncs:devices/ncs:device/ncs:netconf-notifications/ncs:received-notifications/ncs:notification/ncs:data" {
    container flexe-band-mismatch-resume {
      presence "";
      config false;
      description
        "Indicates the alarm is cleared.";
      leaf physical-index {
        type uint32;
        description
          "This object indicates the interface index.";
      }
      leaf physical-port-name {
        type string {
          length "1..32";
        }
        description
          "Indicates the physical port name.";
      }
    }
  }
  augment "/ncs:devices/ncs:device/ncs:netconf-notifications/ncs:received-notifications/ncs:notification/ncs:data" {
    container flexe-band-mismatch {
      presence "";
      config false;
      description
        "Indicates the alarm is detected.";
      leaf physical-index {
        type uint32;
        description
          "This object indicates the interface index.";
      }
      leaf physical-port-name {
        type string {
          length "1..32";
        }
        description
          "Indicates the physical port name.";
      }
    }
  }
  augment "/ncs:devices/ncs:device/ncs:netconf-notifications/ncs:received-notifications/ncs:notification/ncs:data" {
    container flexe-calendar-mismatch-resume {
      presence "";
      config false;
      description
        "The alarm of mismatch between the actually received and expected client calendars on the FlexE Group is cleared.";
      leaf group-index {
        type uint32;
        description
          "Indicates the FlexE group index.";
      }
      leaf group-name {
        type string {
          length "1..32";
        }
        description
          "Indicates the FlexE group name.";
      }
    }
  }
  augment "/ncs:devices/ncs:device/ncs:netconf-notifications/ncs:received-notifications/ncs:notification/ncs:data" {
    container flexe-calendar-mismatch {
      presence "";
      config false;
      description
        "Alarm of mismatch between the actually received and expected client calendars on the FlexE Group.";
      leaf group-index {
        type uint32;
        description
          "Indicates the FlexE group index.";
      }
      leaf group-name {
        type string {
          length "1..32";
        }
        description
          "Indicates the FlexE group name.";
      }
    }
  }
}
