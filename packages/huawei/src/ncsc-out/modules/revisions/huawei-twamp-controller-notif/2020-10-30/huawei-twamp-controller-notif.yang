module huawei-twamp-controller-notif {
  // Generated by yanger -t ncs
  tailf:mount-id "huawei-nc-1.0:huawei-nc-1.0";
  tailf:ncs-device-type "netconf";

  yang-version 1;
  namespace "urn:huawei:yang:huawei-twamp-controller-notif";
  prefix twamp-controller-notif;

  import huawei-pub-type {
    prefix pub-type;
  }
  import huawei-extension {
    prefix ext;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Notification of twamp controller.";

  revision 2020-10-30 {
    description
      "Initial revision.";
    reference "Huawei private.";
  }
  ext:task-name "twampclient";

  augment "/ncs:devices/ncs:device/ncs:notifications/ncs:received-notifications/ncs:notification/ncs:data" {
    container member-twoway-loc-recovery {
      presence "";
      config false;
      description
        "The two-way loss ratio of the TWAMP test instance was under the LOC threshold in three consecutive test intervals.";
      leaf session-id {
        type uint32;
        description
          "TWAMP Light test session ID.";
      }
      leaf member-id {
        type uint32;
        description
          "TWAMP Light test session member ID.";
      }
      leaf member-name {
        type pub-type:ncs_rpc_notif_if-name;
        description
          "TWAMP Light test session member name.";
      }
      leaf value {
        type uint32;
        description
          "Packet loss rate.";
      }
    }
  }
  augment "/ncs:devices/ncs:device/ncs:notifications/ncs:received-notifications/ncs:notification/ncs:data" {
    container member-twoway-loc-exceed {
      presence "";
      config false;
      description
        "The two-way loss ratio of the TWAMP test instance reached the LOC threshold in three consecutive test intervals.";
      leaf session-id {
        type uint32;
        description
          "TWAMP Light test session ID.";
      }
      leaf member-id {
        type uint32;
        description
          "TWAMP Light test session member ID.";
      }
      leaf member-name {
        type pub-type:ncs_rpc_notif_if-name;
        description
          "TWAMP Light test session member name.";
      }
      leaf value {
        type uint32;
        description
          "Packet loss rate.";
      }
    }
  }
  augment "/ncs:devices/ncs:device/ncs:notifications/ncs:received-notifications/ncs:notification/ncs:data" {
    container member-twoway-jitter-recovery {
      presence "";
      config false;
      description
        "The two-way jitter of the TWAMP test instance was under the lower threshold in three consecutive test intervals.";
      leaf session-id {
        type uint32;
        description
          "TWAMP Light test session ID.";
      }
      leaf member-id {
        type uint32;
        description
          "TWAMP Light test session member ID.";
      }
      leaf member-name {
        type pub-type:ncs_rpc_notif_if-name;
        description
          "TWAMP Light test session member name.";
      }
      leaf value {
        type uint32;
        description
          "Jitter value.";
      }
      leaf upper-limit-threshold {
        type uint32;
        description
          "The jitter trigger-alarm threshold value.";
      }
      leaf lower-limit-threshold {
        type uint32;
        description
          "The clear-alarm jitter threshold value.";
      }
    }
  }
  augment "/ncs:devices/ncs:device/ncs:notifications/ncs:received-notifications/ncs:notification/ncs:data" {
    container member-twoway-jitter-exceed {
      presence "";
      config false;
      description
        "The two-way jitter of the TWAMP test instance exceeded the upper threshold in three consecutive test intervals.";
      leaf session-id {
        type uint32;
        description
          "TWAMP Light test session ID.";
      }
      leaf member-id {
        type uint32;
        description
          "TWAMP Light test session member ID.";
      }
      leaf member-name {
        type pub-type:ncs_rpc_notif_if-name;
        description
          "TWAMP Light test session member name.";
      }
      leaf value {
        type uint32;
        description
          "Jitter value.";
      }
      leaf upper-limit-threshold {
        type uint32;
        description
          "The jitter trigger-alarm threshold value.";
      }
      leaf lower-limit-threshold {
        type uint32;
        description
          "The clear-alarm jitter threshold value.";
      }
    }
  }
  augment "/ncs:devices/ncs:device/ncs:notifications/ncs:received-notifications/ncs:notification/ncs:data" {
    container member-twoway-lossratio-recovery {
      presence "";
      config false;
      description
        "The two-way loss ratio of the TWAMP test instance was under the lower threshold in the 1-minute statistics period.";
      leaf session-id {
        type uint32;
        description
          "TWAMP Light test session ID.";
      }
      leaf member-id {
        type uint32;
        description
          "TWAMP Light test session member ID.";
      }
      leaf member-name {
        type pub-type:ncs_rpc_notif_if-name;
        description
          "TWAMP Light test session member name.";
      }
      leaf value {
        type uint32;
        description
          "Packet loss rate.";
      }
      leaf upper-limit-threshold {
        type uint32;
        description
          "The Loss trigger-alarm threshold value.";
      }
      leaf lower-limit-threshold {
        type uint32;
        description
          "The clear-alarm Loss threshold value.";
      }
    }
  }
  augment "/ncs:devices/ncs:device/ncs:notifications/ncs:received-notifications/ncs:notification/ncs:data" {
    container member-twoway-lossratio-exceed {
      presence "";
      config false;
      description
        "The two-way loss ratio of the TWAMP test instance exceeded the upper threshold in the 1-minute statistics period.";
      leaf session-id {
        type uint32;
        description
          "TWAMP Light test session ID.";
      }
      leaf member-id {
        type uint32;
        description
          "TWAMP Light test session member ID.";
      }
      leaf member-name {
        type pub-type:ncs_rpc_notif_if-name;
        description
          "TWAMP Light test session member name.";
      }
      leaf value {
        type uint32;
        description
          "Packet loss rate.";
      }
      leaf upper-limit-threshold {
        type uint32;
        description
          "The Loss trigger-alarm threshold value.";
      }
      leaf lower-limit-threshold {
        type uint32;
        description
          "The clear-alarm Loss threshold value.";
      }
    }
  }
  augment "/ncs:devices/ncs:device/ncs:notifications/ncs:received-notifications/ncs:notification/ncs:data" {
    container member-twoway-delay-recovery {
      presence "";
      config false;
      description
        "The two-way delay of the TWAMP test instance was under the lower threshold in three consecutive test intervals.";
      leaf session-id {
        type uint32;
        description
          "TWAMP Light test session ID.";
      }
      leaf member-id {
        type uint32;
        description
          "TWAMP Light test session member ID.";
      }
      leaf member-name {
        type pub-type:ncs_rpc_notif_if-name;
        description
          "TWAMP Light test session member name.";
      }
      leaf value {
        type uint32;
        description
          "Delay value.";
      }
      leaf upper-limit-threshold {
        type uint32;
        description
          "The Delay trigger-alarm threshold value.";
      }
      leaf lower-limit-threshold {
        type uint32;
        description
          "The clear-alarm Delay threshold value.";
      }
    }
  }
  augment "/ncs:devices/ncs:device/ncs:notifications/ncs:received-notifications/ncs:notification/ncs:data" {
    container member-twoway-delay-exceed {
      presence "";
      config false;
      description
        "The two-way delay of the TWAMP test instance exceeded the upper threshold in three consecutive test intervals.";
      leaf session-id {
        type uint32;
        description
          "TWAMP Light test session ID.";
      }
      leaf member-id {
        type uint32;
        description
          "TWAMP Light test session member ID.";
      }
      leaf member-name {
        type pub-type:ncs_rpc_notif_if-name;
        description
          "TWAMP Light test session member name.";
      }
      leaf value {
        type uint32;
        description
          "Delay value.";
      }
      leaf upper-limit-threshold {
        type uint32;
        description
          "The Delay trigger-alarm threshold value.";
      }
      leaf lower-limit-threshold {
        type uint32;
        description
          "The clear-alarm Delay threshold value.";
      }
    }
  }
  augment "/ncs:devices/ncs:device/ncs:notifications/ncs:received-notifications/ncs:notification/ncs:data" {
    container twoway-lossratio-recovery {
      presence "";
      config false;
      description
        "The two-way loss ratio of the TWAMP test instance was under the lower threshold in the 1-minute statistics period.";
      leaf session-id {
        type uint32;
        description
          "TWAMP Light test session ID.";
      }
      leaf value {
        type uint32;
        description
          "Packet loss rate.";
      }
      leaf upper-limit-threshold {
        type uint32;
        description
          "The Loss trigger-alarm threshold value.";
      }
      leaf lower-limit-threshold {
        type uint32;
        description
          "The clear-alarm Loss threshold value.";
      }
    }
  }
  augment "/ncs:devices/ncs:device/ncs:notifications/ncs:received-notifications/ncs:notification/ncs:data" {
    container twoway-lossratio-exceed {
      presence "";
      config false;
      description
        "The two-way loss ratio of the TWAMP test instance exceeded the upper threshold in the 1-minute statistics period.";
      leaf session-id {
        type uint32;
        description
          "TWAMP Light test session ID.";
      }
      leaf value {
        type uint32;
        description
          "Packet loss rate.";
      }
      leaf upper-limit-threshold {
        type uint32;
        description
          "The Loss trigger-alarm threshold value.";
      }
      leaf lower-limit-threshold {
        type uint32;
        description
          "The clear-alarm Loss threshold value.";
      }
    }
  }
  augment "/ncs:devices/ncs:device/ncs:notifications/ncs:received-notifications/ncs:notification/ncs:data" {
    container twoway-loc-recovery {
      presence "";
      config false;
      description
        "The two-way loss ratio of the TWAMP test instance was under the LOC threshold in three consecutive test intervals.";
      leaf session-id {
        type uint32;
        description
          "TWAMP Light test session ID.";
      }
      leaf value {
        type uint32;
        description
          "Packet loss rate.";
      }
    }
  }
  augment "/ncs:devices/ncs:device/ncs:notifications/ncs:received-notifications/ncs:notification/ncs:data" {
    container twoway-loc-exceed {
      presence "";
      config false;
      description
        "The two-way loss ratio of the TWAMP test instance reached the LOC threshold in three consecutive test intervals.";
      leaf session-id {
        type uint32;
        description
          "TWAMP Light test session ID.";
      }
      leaf value {
        type uint32;
        description
          "Packet loss rate.";
      }
    }
  }
  augment "/ncs:devices/ncs:device/ncs:notifications/ncs:received-notifications/ncs:notification/ncs:data" {
    container twoway-jitter-recovery {
      presence "";
      config false;
      description
        "The two-way jitter of the TWAMP test instance was under the lower threshold in three consecutive test intervals.";
      leaf session-id {
        type uint32;
        description
          "TWAMP Light test session ID.";
      }
      leaf value {
        type uint32;
        description
          "Jitter value.";
      }
      leaf upper-limit-threshold {
        type uint32;
        description
          "The jitter trigger-alarm threshold value.";
      }
      leaf lower-limit-threshold {
        type uint32;
        description
          "The clear-alarm jitter threshold value.";
      }
    }
  }
  augment "/ncs:devices/ncs:device/ncs:notifications/ncs:received-notifications/ncs:notification/ncs:data" {
    container twoway-jitter-exceed {
      presence "";
      config false;
      description
        "The two-way jitter of the TWAMP test instance exceeded the upper threshold in three consecutive test intervals.";
      leaf session-id {
        type uint32;
        description
          "TWAMP Light test session ID.";
      }
      leaf value {
        type uint32;
        description
          "Jitter value.";
      }
      leaf upper-limit-threshold {
        type uint32;
        description
          "The jitter trigger-alarm threshold value.";
      }
      leaf lower-limit-threshold {
        type uint32;
        description
          "The clear-alarm jitter threshold value.";
      }
    }
  }
  augment "/ncs:devices/ncs:device/ncs:notifications/ncs:received-notifications/ncs:notification/ncs:data" {
    container twoway-delay-recovery {
      presence "";
      config false;
      description
        "The two-way delay of the TWAMP test instance was under the lower threshold in three consecutive test intervals.";
      leaf session-id {
        type uint32;
        description
          "TWAMP Light test session ID.";
      }
      leaf value {
        type uint32;
        description
          "Delay value.";
      }
      leaf upper-limit-threshold {
        type uint32;
        description
          "The Delay trigger-alarm threshold value.";
      }
      leaf lower-limit-threshold {
        type uint32;
        description
          "The clear-alarm Delay threshold value.";
      }
    }
  }
  augment "/ncs:devices/ncs:device/ncs:notifications/ncs:received-notifications/ncs:notification/ncs:data" {
    container twoway-delay-exceed {
      presence "";
      config false;
      description
        "The two-way delay of the TWAMP test instance exceeded the upper threshold in three consecutive test intervals.";
      leaf session-id {
        type uint32;
        description
          "TWAMP Light test session ID.";
      }
      leaf value {
        type uint32;
        description
          "Delay value.";
      }
      leaf upper-limit-threshold {
        type uint32;
        description
          "The Delay trigger-alarm threshold value.";
      }
      leaf lower-limit-threshold {
        type uint32;
        description
          "The clear-alarm Delay threshold value.";
      }
    }
  }
  augment "/ncs:devices/ncs:device/ncs:notifications/ncs:received-notifications/ncs:notification/ncs:data" {
    container sender-session-num-recovery {
      presence "";
      config false;
      description
        "The number of TWAMP sender session is under device capability.";
    }
  }
  augment "/ncs:devices/ncs:device/ncs:notifications/ncs:received-notifications/ncs:notification/ncs:data" {
    container sender-session-num-exceed {
      presence "";
      config false;
      description
        "The number of TWAMP sender session is out of device capability.";
    }
  }
  augment "/ncs:devices/ncs:device/ncs:netconf-notifications/ncs:received-notifications/ncs:notification/ncs:data" {
    container member-twoway-loc-recovery {
      presence "";
      config false;
      description
        "The two-way loss ratio of the TWAMP test instance was under the LOC threshold in three consecutive test intervals.";
      leaf session-id {
        type uint32;
        description
          "TWAMP Light test session ID.";
      }
      leaf member-id {
        type uint32;
        description
          "TWAMP Light test session member ID.";
      }
      leaf member-name {
        type pub-type:ncs_rpc_notif_if-name;
        description
          "TWAMP Light test session member name.";
      }
      leaf value {
        type uint32;
        description
          "Packet loss rate.";
      }
    }
  }
  augment "/ncs:devices/ncs:device/ncs:netconf-notifications/ncs:received-notifications/ncs:notification/ncs:data" {
    container member-twoway-loc-exceed {
      presence "";
      config false;
      description
        "The two-way loss ratio of the TWAMP test instance reached the LOC threshold in three consecutive test intervals.";
      leaf session-id {
        type uint32;
        description
          "TWAMP Light test session ID.";
      }
      leaf member-id {
        type uint32;
        description
          "TWAMP Light test session member ID.";
      }
      leaf member-name {
        type pub-type:ncs_rpc_notif_if-name;
        description
          "TWAMP Light test session member name.";
      }
      leaf value {
        type uint32;
        description
          "Packet loss rate.";
      }
    }
  }
  augment "/ncs:devices/ncs:device/ncs:netconf-notifications/ncs:received-notifications/ncs:notification/ncs:data" {
    container member-twoway-jitter-recovery {
      presence "";
      config false;
      description
        "The two-way jitter of the TWAMP test instance was under the lower threshold in three consecutive test intervals.";
      leaf session-id {
        type uint32;
        description
          "TWAMP Light test session ID.";
      }
      leaf member-id {
        type uint32;
        description
          "TWAMP Light test session member ID.";
      }
      leaf member-name {
        type pub-type:ncs_rpc_notif_if-name;
        description
          "TWAMP Light test session member name.";
      }
      leaf value {
        type uint32;
        description
          "Jitter value.";
      }
      leaf upper-limit-threshold {
        type uint32;
        description
          "The jitter trigger-alarm threshold value.";
      }
      leaf lower-limit-threshold {
        type uint32;
        description
          "The clear-alarm jitter threshold value.";
      }
    }
  }
  augment "/ncs:devices/ncs:device/ncs:netconf-notifications/ncs:received-notifications/ncs:notification/ncs:data" {
    container member-twoway-jitter-exceed {
      presence "";
      config false;
      description
        "The two-way jitter of the TWAMP test instance exceeded the upper threshold in three consecutive test intervals.";
      leaf session-id {
        type uint32;
        description
          "TWAMP Light test session ID.";
      }
      leaf member-id {
        type uint32;
        description
          "TWAMP Light test session member ID.";
      }
      leaf member-name {
        type pub-type:ncs_rpc_notif_if-name;
        description
          "TWAMP Light test session member name.";
      }
      leaf value {
        type uint32;
        description
          "Jitter value.";
      }
      leaf upper-limit-threshold {
        type uint32;
        description
          "The jitter trigger-alarm threshold value.";
      }
      leaf lower-limit-threshold {
        type uint32;
        description
          "The clear-alarm jitter threshold value.";
      }
    }
  }
  augment "/ncs:devices/ncs:device/ncs:netconf-notifications/ncs:received-notifications/ncs:notification/ncs:data" {
    container member-twoway-lossratio-recovery {
      presence "";
      config false;
      description
        "The two-way loss ratio of the TWAMP test instance was under the lower threshold in the 1-minute statistics period.";
      leaf session-id {
        type uint32;
        description
          "TWAMP Light test session ID.";
      }
      leaf member-id {
        type uint32;
        description
          "TWAMP Light test session member ID.";
      }
      leaf member-name {
        type pub-type:ncs_rpc_notif_if-name;
        description
          "TWAMP Light test session member name.";
      }
      leaf value {
        type uint32;
        description
          "Packet loss rate.";
      }
      leaf upper-limit-threshold {
        type uint32;
        description
          "The Loss trigger-alarm threshold value.";
      }
      leaf lower-limit-threshold {
        type uint32;
        description
          "The clear-alarm Loss threshold value.";
      }
    }
  }
  augment "/ncs:devices/ncs:device/ncs:netconf-notifications/ncs:received-notifications/ncs:notification/ncs:data" {
    container member-twoway-lossratio-exceed {
      presence "";
      config false;
      description
        "The two-way loss ratio of the TWAMP test instance exceeded the upper threshold in the 1-minute statistics period.";
      leaf session-id {
        type uint32;
        description
          "TWAMP Light test session ID.";
      }
      leaf member-id {
        type uint32;
        description
          "TWAMP Light test session member ID.";
      }
      leaf member-name {
        type pub-type:ncs_rpc_notif_if-name;
        description
          "TWAMP Light test session member name.";
      }
      leaf value {
        type uint32;
        description
          "Packet loss rate.";
      }
      leaf upper-limit-threshold {
        type uint32;
        description
          "The Loss trigger-alarm threshold value.";
      }
      leaf lower-limit-threshold {
        type uint32;
        description
          "The clear-alarm Loss threshold value.";
      }
    }
  }
  augment "/ncs:devices/ncs:device/ncs:netconf-notifications/ncs:received-notifications/ncs:notification/ncs:data" {
    container member-twoway-delay-recovery {
      presence "";
      config false;
      description
        "The two-way delay of the TWAMP test instance was under the lower threshold in three consecutive test intervals.";
      leaf session-id {
        type uint32;
        description
          "TWAMP Light test session ID.";
      }
      leaf member-id {
        type uint32;
        description
          "TWAMP Light test session member ID.";
      }
      leaf member-name {
        type pub-type:ncs_rpc_notif_if-name;
        description
          "TWAMP Light test session member name.";
      }
      leaf value {
        type uint32;
        description
          "Delay value.";
      }
      leaf upper-limit-threshold {
        type uint32;
        description
          "The Delay trigger-alarm threshold value.";
      }
      leaf lower-limit-threshold {
        type uint32;
        description
          "The clear-alarm Delay threshold value.";
      }
    }
  }
  augment "/ncs:devices/ncs:device/ncs:netconf-notifications/ncs:received-notifications/ncs:notification/ncs:data" {
    container member-twoway-delay-exceed {
      presence "";
      config false;
      description
        "The two-way delay of the TWAMP test instance exceeded the upper threshold in three consecutive test intervals.";
      leaf session-id {
        type uint32;
        description
          "TWAMP Light test session ID.";
      }
      leaf member-id {
        type uint32;
        description
          "TWAMP Light test session member ID.";
      }
      leaf member-name {
        type pub-type:ncs_rpc_notif_if-name;
        description
          "TWAMP Light test session member name.";
      }
      leaf value {
        type uint32;
        description
          "Delay value.";
      }
      leaf upper-limit-threshold {
        type uint32;
        description
          "The Delay trigger-alarm threshold value.";
      }
      leaf lower-limit-threshold {
        type uint32;
        description
          "The clear-alarm Delay threshold value.";
      }
    }
  }
  augment "/ncs:devices/ncs:device/ncs:netconf-notifications/ncs:received-notifications/ncs:notification/ncs:data" {
    container twoway-lossratio-recovery {
      presence "";
      config false;
      description
        "The two-way loss ratio of the TWAMP test instance was under the lower threshold in the 1-minute statistics period.";
      leaf session-id {
        type uint32;
        description
          "TWAMP Light test session ID.";
      }
      leaf value {
        type uint32;
        description
          "Packet loss rate.";
      }
      leaf upper-limit-threshold {
        type uint32;
        description
          "The Loss trigger-alarm threshold value.";
      }
      leaf lower-limit-threshold {
        type uint32;
        description
          "The clear-alarm Loss threshold value.";
      }
    }
  }
  augment "/ncs:devices/ncs:device/ncs:netconf-notifications/ncs:received-notifications/ncs:notification/ncs:data" {
    container twoway-lossratio-exceed {
      presence "";
      config false;
      description
        "The two-way loss ratio of the TWAMP test instance exceeded the upper threshold in the 1-minute statistics period.";
      leaf session-id {
        type uint32;
        description
          "TWAMP Light test session ID.";
      }
      leaf value {
        type uint32;
        description
          "Packet loss rate.";
      }
      leaf upper-limit-threshold {
        type uint32;
        description
          "The Loss trigger-alarm threshold value.";
      }
      leaf lower-limit-threshold {
        type uint32;
        description
          "The clear-alarm Loss threshold value.";
      }
    }
  }
  augment "/ncs:devices/ncs:device/ncs:netconf-notifications/ncs:received-notifications/ncs:notification/ncs:data" {
    container twoway-loc-recovery {
      presence "";
      config false;
      description
        "The two-way loss ratio of the TWAMP test instance was under the LOC threshold in three consecutive test intervals.";
      leaf session-id {
        type uint32;
        description
          "TWAMP Light test session ID.";
      }
      leaf value {
        type uint32;
        description
          "Packet loss rate.";
      }
    }
  }
  augment "/ncs:devices/ncs:device/ncs:netconf-notifications/ncs:received-notifications/ncs:notification/ncs:data" {
    container twoway-loc-exceed {
      presence "";
      config false;
      description
        "The two-way loss ratio of the TWAMP test instance reached the LOC threshold in three consecutive test intervals.";
      leaf session-id {
        type uint32;
        description
          "TWAMP Light test session ID.";
      }
      leaf value {
        type uint32;
        description
          "Packet loss rate.";
      }
    }
  }
  augment "/ncs:devices/ncs:device/ncs:netconf-notifications/ncs:received-notifications/ncs:notification/ncs:data" {
    container twoway-jitter-recovery {
      presence "";
      config false;
      description
        "The two-way jitter of the TWAMP test instance was under the lower threshold in three consecutive test intervals.";
      leaf session-id {
        type uint32;
        description
          "TWAMP Light test session ID.";
      }
      leaf value {
        type uint32;
        description
          "Jitter value.";
      }
      leaf upper-limit-threshold {
        type uint32;
        description
          "The jitter trigger-alarm threshold value.";
      }
      leaf lower-limit-threshold {
        type uint32;
        description
          "The clear-alarm jitter threshold value.";
      }
    }
  }
  augment "/ncs:devices/ncs:device/ncs:netconf-notifications/ncs:received-notifications/ncs:notification/ncs:data" {
    container twoway-jitter-exceed {
      presence "";
      config false;
      description
        "The two-way jitter of the TWAMP test instance exceeded the upper threshold in three consecutive test intervals.";
      leaf session-id {
        type uint32;
        description
          "TWAMP Light test session ID.";
      }
      leaf value {
        type uint32;
        description
          "Jitter value.";
      }
      leaf upper-limit-threshold {
        type uint32;
        description
          "The jitter trigger-alarm threshold value.";
      }
      leaf lower-limit-threshold {
        type uint32;
        description
          "The clear-alarm jitter threshold value.";
      }
    }
  }
  augment "/ncs:devices/ncs:device/ncs:netconf-notifications/ncs:received-notifications/ncs:notification/ncs:data" {
    container twoway-delay-recovery {
      presence "";
      config false;
      description
        "The two-way delay of the TWAMP test instance was under the lower threshold in three consecutive test intervals.";
      leaf session-id {
        type uint32;
        description
          "TWAMP Light test session ID.";
      }
      leaf value {
        type uint32;
        description
          "Delay value.";
      }
      leaf upper-limit-threshold {
        type uint32;
        description
          "The Delay trigger-alarm threshold value.";
      }
      leaf lower-limit-threshold {
        type uint32;
        description
          "The clear-alarm Delay threshold value.";
      }
    }
  }
  augment "/ncs:devices/ncs:device/ncs:netconf-notifications/ncs:received-notifications/ncs:notification/ncs:data" {
    container twoway-delay-exceed {
      presence "";
      config false;
      description
        "The two-way delay of the TWAMP test instance exceeded the upper threshold in three consecutive test intervals.";
      leaf session-id {
        type uint32;
        description
          "TWAMP Light test session ID.";
      }
      leaf value {
        type uint32;
        description
          "Delay value.";
      }
      leaf upper-limit-threshold {
        type uint32;
        description
          "The Delay trigger-alarm threshold value.";
      }
      leaf lower-limit-threshold {
        type uint32;
        description
          "The clear-alarm Delay threshold value.";
      }
    }
  }
  augment "/ncs:devices/ncs:device/ncs:netconf-notifications/ncs:received-notifications/ncs:notification/ncs:data" {
    container sender-session-num-recovery {
      presence "";
      config false;
      description
        "The number of TWAMP sender session is under device capability.";
    }
  }
  augment "/ncs:devices/ncs:device/ncs:netconf-notifications/ncs:received-notifications/ncs:notification/ncs:data" {
    container sender-session-num-exceed {
      presence "";
      config false;
      description
        "The number of TWAMP sender session is out of device capability.";
    }
  }
}
