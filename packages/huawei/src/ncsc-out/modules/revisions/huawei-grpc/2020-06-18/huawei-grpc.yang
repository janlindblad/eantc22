module huawei-grpc {
  // Generated by yanger -t ncs
  tailf:mount-id "huawei-nc-1.0:huawei-nc-1.0";
  tailf:ncs-device-type "netconf";

  namespace "urn:huawei:yang:huawei-grpc";
  prefix hw-grpc;

  import huawei-acl {
    prefix acl;
  }
  import huawei-network-instance {
    prefix ni;
  }
  import huawei-l3vpn {
    prefix l3vpn;
  }
  import huawei-ssl {
    prefix ssl;
  }
  import ietf-inet-types {
    prefix inet;
  }
  import huawei-extension {
    prefix ext;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "GRPC, which is short for Google Remote Procedure Call Protocol, is a high-performance general RPC framework running over HTTP/2 protocols at the transport layer.";

  revision 2020-06-18 {
    description
      "Initial revision.";
    reference "Huawei private.";
  }
  ext:task-name "grpc";

  augment "/ncs:devices/ncs:device/ncs:config" {
    container grpc {
      tailf:ncs-device-type "netconf";
      tailf:display-when "not(../../ncs:module) or ../../ncs:module[ncs:name='huawei-grpc']";
      description
        "Google Remote Procedure Call Protocol.";
      container service {
        must "server-enable='false' or source-address" {
          tailf:xpath-root 3;
        }
        description
          "Configure the gRPC service.";
        leaf dscp {
          type uint8 {
            range "0..63";
          }
          default "0";
          description
            "DSCP marking of packets generated by the telemetry subsystem on the network device.";
        }
        leaf server-enable {
          type boolean;
          default "false";
          description
            "Enable/disable the gRPC service.";
        }
        leaf source-address {
          type inet:ipv4-address-no-zone;
          description
            "IP address listened by the gRPC service. Only the address 0.0.0.0 or valid IP addresses in class A, B, or C are supported.";
        }
        leaf vpn-name {
          when '../source-address' {
            tailf:xpath-root 3;
          }
          type leafref {
            path "/ncs:devices/ncs:device/ncs:config/ni:network-instance/ni:instances/ni:instance/ni:name" {
              tailf:xpath-root 3;
            }
          }
          must "/ni:network-instance/ni:instances/ni:instance[ni:name = current()]/l3vpn:afs/l3vpn:af[l3vpn:type='ipv4-unicast']" {
            tailf:xpath-root 3;
          }
          default "_public_";
          description
            "Name of a VPN instance listened by the gRPC service.";
        }
        leaf server-port {
          type uint32 {
            range "10000..57999";
          }
          default "57400";
          description
            "Number of a port listened by the gRPC service.";
        }
        leaf idle-timeout {
          type uint32 {
            range "1..3600";
          }
          units "s";
          default "10";
          description
            "Idle (RPC is not invoked) timeout period for gRPC service access. After the timeout period expires, the gRPC service is disconnected.";
        }
        leaf acl-number-or-name {
          type leafref {
            path "/ncs:devices/ncs:device/ncs:config/acl:acl/acl:groups/acl:group/acl:identity" {
              tailf:xpath-root 3;
            }
          }
          must "/acl:acl/acl:groups/acl:group[acl:identity=current()]/acl:type='basic' or /acl:acl/acl:groups/acl:group[acl:identity=current()]/acl:type='advance'" {
            tailf:xpath-root 3;
          }
          description
            "Specify the name or number of an ACL to configure an access control connection for the gRPC service.";
        }
        leaf ssl-policy {
          type leafref {
            path "/ncs:devices/ncs:device/ncs:config/ssl:ssl/ssl:ssl-policys/ssl:ssl-policy/ssl:policy-name" {
              tailf:xpath-root 3;
            }
          }
          description
            "Specify the name of an SSL policy to bind an SSL policy to the gRPC server.";
        }
        leaf ssl-policy-peer {
          type boolean;
          default "false";
          description
            "Enable/disable SSL two-way authentication.";
        }
      }
      container service-ipv6 {
        must "server-enable='false' or source-address" {
          tailf:xpath-root 3;
        }
        description
          "Configure the IPv6 gRPC service.";
        leaf dscp {
          type uint8 {
            range "0..63";
          }
          default "0";
          description
            "DSCP marking of packets generated by the telemetry subsystem on the network device.";
        }
        leaf server-enable {
          type boolean;
          default "false";
          description
            "Enable/disable the IPv6 gRPC service.";
        }
        leaf source-address {
          type inet:ipv6-address-no-zone;
          description
            "IPv6 address listened by the IPv6 gRPC service. The multicast address, link-local address, loopback address, IPv4-compatible IPv6 address, and IPv4-mapped IPv6 address are not supported.";
        }
        leaf vpn-name {
          when '../source-address' {
            tailf:xpath-root 3;
          }
          type leafref {
            path "/ncs:devices/ncs:device/ncs:config/ni:network-instance/ni:instances/ni:instance/ni:name" {
              tailf:xpath-root 3;
            }
          }
          must "/ni:network-instance/ni:instances/ni:instance[ni:name = current()]/l3vpn:afs/l3vpn:af[l3vpn:type='ipv6-unicast']" {
            tailf:xpath-root 3;
          }
          default "_public_";
          description
            "Name of a VPN instance listened by the IPv6 gRPC service.";
        }
        leaf server-port {
          type uint32 {
            range "10000..57999";
          }
          default "57400";
          description
            "Number of a port listened by the IPv6 gRPC service.";
        }
        leaf idle-timeout {
          type uint32 {
            range "1..3600";
          }
          units "s";
          default "10";
          description
            "Idle (RPC is not invoked) timeout period for IPv6 gRPC service access. After the timeout period expires, the IPv6 gRPC service is disconnected.";
        }
        leaf acl-number-or-name {
          type leafref {
            path "/ncs:devices/ncs:device/ncs:config/acl:acl/acl:group6s/acl:group6/acl:identity" {
              tailf:xpath-root 3;
            }
          }
          must "/acl:acl/acl:group6s/acl:group6[acl:identity=current()]/acl:type='basic' or /acl:acl/acl:group6s/acl:group6[acl:identity=current()]/acl:type='advance'" {
            tailf:xpath-root 3;
          }
          description
            "Specify the name or number of an ACL6 to configure an access control connection for the IPv6 gRPC service.";
        }
        leaf ssl-policy {
          type leafref {
            path "/ncs:devices/ncs:device/ncs:config/ssl:ssl/ssl:ssl-policys/ssl:ssl-policy/ssl:policy-name" {
              tailf:xpath-root 3;
            }
          }
          description
            "Specify the name of an SSL policy to bind an SSL policy to the IPv6 gRPC server.";
        }
        leaf ssl-policy-peer {
          type boolean;
          default "false";
          description
            "Enable/disable SSL two-way authentication.";
        }
      }
      container client {
        description
          "Configure the gRPC client.";
        leaf ssl-policy {
          type leafref {
            path "/ncs:devices/ncs:device/ncs:config/ssl:ssl/ssl:ssl-policys/ssl:ssl-policy/ssl:policy-name" {
              tailf:xpath-root 3;
            }
          }
          description
            "Specify the name of an SSL policy to bind an SSL policy to the gRPC client.";
        }
        leaf dscp {
          type uint8 {
            range "0..63";
          }
          default "0";
          description
            "DSCP marking of packets generated by the telemetry subsystem on the network device.";
        }
        leaf ssl-verify-cn-name {
          when '../ssl-policy' {
            tailf:xpath-root 3;
          }
          type string {
            length "1..32";
          }
          description
            "Specify a CN name to set the value of the CN field in the SSL verification certificate.";
        }
        leaf ssl-policy-peer {
          type boolean;
          default "false";
          description
            "Enable/disable SSL two-way authentication.";
        }
      }
      container session-car {
        ext:operation-exclude "delete";
        description
          "Configure the GRPC session car.";
        leaf enable {
          type boolean;
          default "true";
          description
            "Enable/disable session car.";
        }
        leaf cir-interval {
          type uint32 {
            range "1..1000000";
          }
          units "kbit/s";
          default "30";
          description
            "Specify the session car cir interval.";
        }
        leaf cbs-interval {
          type uint32 {
            range "1..1000000";
          }
          units "Byte";
          default "3750";
          description
            "Specify the session car cbs interval.";
        }
        leaf pir-interval {
          type uint32 {
            range "1..1000000";
          }
          units "kbit/s";
          default "300";
          description
            "Specify the session car pir interval.";
        }
        leaf pbs-interval {
          type uint32 {
            range "1..1000000";
          }
          units "Byte";
          default "37500";
          description
            "Specify the session car pbs interval.";
        }
      }
    }
  }
  augment "/ncs:devices/ncs:device/ncs:live-status" {
    container grpc {
      tailf:ncs-device-type "netconf";
      tailf:display-when "not(../../ncs:module) or ../../ncs:module[ncs:name='huawei-grpc'] or (../../ncs:live-status-protocol[not(ncs:capability)]) or (../../ncs:live-status-protocol/ncs:capability/ncs:module[.='huawei-grpc'])";
      description
        "Google Remote Procedure Call Protocol.";
      container service {
        // NCS drop must statement
        description
          "Configure the gRPC service.";
        leaf dscp {
          type uint8 {
            range "0..63";
          }
          // NCS drop default statement
          description
            "DSCP marking of packets generated by the telemetry subsystem on the network device.";
        }
        leaf server-enable {
          type boolean;
          // NCS drop default statement
          description
            "Enable/disable the gRPC service.";
        }
        leaf source-address {
          type inet:ipv4-address-no-zone;
          description
            "IP address listened by the gRPC service. Only the address 0.0.0.0 or valid IP addresses in class A, B, or C are supported.";
        }
        leaf vpn-name {
          // NCS drop when statement
          type leafref {
            path "/ncs:devices/ncs:device/ncs:live-status/ni:network-instance/ni:instances/ni:instance/ni:name" {
              tailf:xpath-root 3;
            }
          }
          // NCS drop must statement
          // NCS drop default statement
          description
            "Name of a VPN instance listened by the gRPC service.";
        }
        leaf server-port {
          type uint32 {
            range "10000..57999";
          }
          // NCS drop default statement
          description
            "Number of a port listened by the gRPC service.";
        }
        leaf idle-timeout {
          type uint32 {
            range "1..3600";
          }
          units "s";
          // NCS drop default statement
          description
            "Idle (RPC is not invoked) timeout period for gRPC service access. After the timeout period expires, the gRPC service is disconnected.";
        }
        leaf acl-number-or-name {
          type leafref {
            path "/ncs:devices/ncs:device/ncs:live-status/acl:acl/acl:groups/acl:group/acl:identity" {
              tailf:xpath-root 3;
            }
          }
          // NCS drop must statement
          description
            "Specify the name or number of an ACL to configure an access control connection for the gRPC service.";
        }
        leaf ssl-policy {
          type leafref {
            path "/ncs:devices/ncs:device/ncs:live-status/ssl:ssl/ssl:ssl-policys/ssl:ssl-policy/ssl:policy-name" {
              tailf:xpath-root 3;
            }
          }
          description
            "Specify the name of an SSL policy to bind an SSL policy to the gRPC server.";
        }
        leaf ssl-policy-peer {
          type boolean;
          // NCS drop default statement
          description
            "Enable/disable SSL two-way authentication.";
        }
      }
      container service-ipv6 {
        // NCS drop must statement
        description
          "Configure the IPv6 gRPC service.";
        leaf dscp {
          type uint8 {
            range "0..63";
          }
          // NCS drop default statement
          description
            "DSCP marking of packets generated by the telemetry subsystem on the network device.";
        }
        leaf server-enable {
          type boolean;
          // NCS drop default statement
          description
            "Enable/disable the IPv6 gRPC service.";
        }
        leaf source-address {
          type inet:ipv6-address-no-zone;
          description
            "IPv6 address listened by the IPv6 gRPC service. The multicast address, link-local address, loopback address, IPv4-compatible IPv6 address, and IPv4-mapped IPv6 address are not supported.";
        }
        leaf vpn-name {
          // NCS drop when statement
          type leafref {
            path "/ncs:devices/ncs:device/ncs:live-status/ni:network-instance/ni:instances/ni:instance/ni:name" {
              tailf:xpath-root 3;
            }
          }
          // NCS drop must statement
          // NCS drop default statement
          description
            "Name of a VPN instance listened by the IPv6 gRPC service.";
        }
        leaf server-port {
          type uint32 {
            range "10000..57999";
          }
          // NCS drop default statement
          description
            "Number of a port listened by the IPv6 gRPC service.";
        }
        leaf idle-timeout {
          type uint32 {
            range "1..3600";
          }
          units "s";
          // NCS drop default statement
          description
            "Idle (RPC is not invoked) timeout period for IPv6 gRPC service access. After the timeout period expires, the IPv6 gRPC service is disconnected.";
        }
        leaf acl-number-or-name {
          type leafref {
            path "/ncs:devices/ncs:device/ncs:live-status/acl:acl/acl:group6s/acl:group6/acl:identity" {
              tailf:xpath-root 3;
            }
          }
          // NCS drop must statement
          description
            "Specify the name or number of an ACL6 to configure an access control connection for the IPv6 gRPC service.";
        }
        leaf ssl-policy {
          type leafref {
            path "/ncs:devices/ncs:device/ncs:live-status/ssl:ssl/ssl:ssl-policys/ssl:ssl-policy/ssl:policy-name" {
              tailf:xpath-root 3;
            }
          }
          description
            "Specify the name of an SSL policy to bind an SSL policy to the IPv6 gRPC server.";
        }
        leaf ssl-policy-peer {
          type boolean;
          // NCS drop default statement
          description
            "Enable/disable SSL two-way authentication.";
        }
      }
      container client {
        description
          "Configure the gRPC client.";
        leaf ssl-policy {
          type leafref {
            path "/ncs:devices/ncs:device/ncs:live-status/ssl:ssl/ssl:ssl-policys/ssl:ssl-policy/ssl:policy-name" {
              tailf:xpath-root 3;
            }
          }
          description
            "Specify the name of an SSL policy to bind an SSL policy to the gRPC client.";
        }
        leaf dscp {
          type uint8 {
            range "0..63";
          }
          // NCS drop default statement
          description
            "DSCP marking of packets generated by the telemetry subsystem on the network device.";
        }
        leaf ssl-verify-cn-name {
          // NCS drop when statement
          type string {
            length "1..32";
          }
          description
            "Specify a CN name to set the value of the CN field in the SSL verification certificate.";
        }
        leaf ssl-policy-peer {
          type boolean;
          // NCS drop default statement
          description
            "Enable/disable SSL two-way authentication.";
        }
      }
      container session-car {
        ext:operation-exclude "delete";
        description
          "Configure the GRPC session car.";
        leaf enable {
          type boolean;
          // NCS drop default statement
          description
            "Enable/disable session car.";
        }
        leaf cir-interval {
          type uint32 {
            range "1..1000000";
          }
          units "kbit/s";
          // NCS drop default statement
          description
            "Specify the session car cir interval.";
        }
        leaf cbs-interval {
          type uint32 {
            range "1..1000000";
          }
          units "Byte";
          // NCS drop default statement
          description
            "Specify the session car cbs interval.";
        }
        leaf pir-interval {
          type uint32 {
            range "1..1000000";
          }
          units "kbit/s";
          // NCS drop default statement
          description
            "Specify the session car pir interval.";
        }
        leaf pbs-interval {
          type uint32 {
            range "1..1000000";
          }
          units "Byte";
          // NCS drop default statement
          description
            "Specify the session car pbs interval.";
        }
      }
    }
  }
  augment "/ncs:devices/ncs:template/ncs:ned-id/ncs:config" {
    container grpc {
      description
        "Google Remote Procedure Call Protocol.";
      container service {
        // NCS drop must statement
        description
          "Configure the gRPC service.";
        leaf dscp {
          type string;
          // NCS drop default statement
          description
            "DSCP marking of packets generated by the telemetry subsystem on the network device.";
        }
        leaf server-enable {
          type string;
          // NCS drop default statement
          description
            "Enable/disable the gRPC service.";
        }
        leaf source-address {
          type string;
          description
            "IP address listened by the gRPC service. Only the address 0.0.0.0 or valid IP addresses in class A, B, or C are supported.";
        }
        leaf vpn-name {
          // NCS drop when statement
          type string;
          // NCS drop must statement
          // NCS drop default statement
          description
            "Name of a VPN instance listened by the gRPC service.";
        }
        leaf server-port {
          type string;
          // NCS drop default statement
          description
            "Number of a port listened by the gRPC service.";
        }
        leaf idle-timeout {
          type string;
          units "s";
          // NCS drop default statement
          description
            "Idle (RPC is not invoked) timeout period for gRPC service access. After the timeout period expires, the gRPC service is disconnected.";
        }
        leaf acl-number-or-name {
          type string;
          // NCS drop must statement
          description
            "Specify the name or number of an ACL to configure an access control connection for the gRPC service.";
        }
        leaf ssl-policy {
          type string;
          description
            "Specify the name of an SSL policy to bind an SSL policy to the gRPC server.";
        }
        leaf ssl-policy-peer {
          type string;
          // NCS drop default statement
          description
            "Enable/disable SSL two-way authentication.";
        }
      }
      container service-ipv6 {
        // NCS drop must statement
        description
          "Configure the IPv6 gRPC service.";
        leaf dscp {
          type string;
          // NCS drop default statement
          description
            "DSCP marking of packets generated by the telemetry subsystem on the network device.";
        }
        leaf server-enable {
          type string;
          // NCS drop default statement
          description
            "Enable/disable the IPv6 gRPC service.";
        }
        leaf source-address {
          type string;
          description
            "IPv6 address listened by the IPv6 gRPC service. The multicast address, link-local address, loopback address, IPv4-compatible IPv6 address, and IPv4-mapped IPv6 address are not supported.";
        }
        leaf vpn-name {
          // NCS drop when statement
          type string;
          // NCS drop must statement
          // NCS drop default statement
          description
            "Name of a VPN instance listened by the IPv6 gRPC service.";
        }
        leaf server-port {
          type string;
          // NCS drop default statement
          description
            "Number of a port listened by the IPv6 gRPC service.";
        }
        leaf idle-timeout {
          type string;
          units "s";
          // NCS drop default statement
          description
            "Idle (RPC is not invoked) timeout period for IPv6 gRPC service access. After the timeout period expires, the IPv6 gRPC service is disconnected.";
        }
        leaf acl-number-or-name {
          type string;
          // NCS drop must statement
          description
            "Specify the name or number of an ACL6 to configure an access control connection for the IPv6 gRPC service.";
        }
        leaf ssl-policy {
          type string;
          description
            "Specify the name of an SSL policy to bind an SSL policy to the IPv6 gRPC server.";
        }
        leaf ssl-policy-peer {
          type string;
          // NCS drop default statement
          description
            "Enable/disable SSL two-way authentication.";
        }
      }
      container client {
        description
          "Configure the gRPC client.";
        leaf ssl-policy {
          type string;
          description
            "Specify the name of an SSL policy to bind an SSL policy to the gRPC client.";
        }
        leaf dscp {
          type string;
          // NCS drop default statement
          description
            "DSCP marking of packets generated by the telemetry subsystem on the network device.";
        }
        leaf ssl-verify-cn-name {
          // NCS drop when statement
          type string;
          description
            "Specify a CN name to set the value of the CN field in the SSL verification certificate.";
        }
        leaf ssl-policy-peer {
          type string;
          // NCS drop default statement
          description
            "Enable/disable SSL two-way authentication.";
        }
      }
      container session-car {
        ext:operation-exclude "delete";
        description
          "Configure the GRPC session car.";
        leaf enable {
          type string;
          // NCS drop default statement
          description
            "Enable/disable session car.";
        }
        leaf cir-interval {
          type string;
          units "kbit/s";
          // NCS drop default statement
          description
            "Specify the session car cir interval.";
        }
        leaf cbs-interval {
          type string;
          units "Byte";
          // NCS drop default statement
          description
            "Specify the session car cbs interval.";
        }
        leaf pir-interval {
          type string;
          units "kbit/s";
          // NCS drop default statement
          description
            "Specify the session car pir interval.";
        }
        leaf pbs-interval {
          type string;
          units "Byte";
          // NCS drop default statement
          description
            "Specify the session car pbs interval.";
        }
      }
    }
  }
}
