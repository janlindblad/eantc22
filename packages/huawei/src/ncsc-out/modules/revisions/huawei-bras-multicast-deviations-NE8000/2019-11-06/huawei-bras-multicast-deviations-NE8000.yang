module huawei-bras-multicast-deviations-NE8000 {
  // Generated by yanger -t ncs
  tailf:mount-id "huawei-nc-1.0:huawei-nc-1.0";
  tailf:ncs-device-type "netconf";

  namespace "urn:huawei:yang:huawei-bras-multicast-deviations-NE8000";
  prefix bras-multicast-devs-NE8000;

  import huawei-bras-multicast {
    prefix bras-multicast;
  }
  import huawei-devm {
    prefix devm;
  }
  import huawei-bras-basic-access {
    prefix bras-basic-access;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "This module defines deviation statements for huawei-bras-multicast module.";

  revision 2019-11-06 {
    description
      "Initial revision.";
    reference "Huawei private.";
  }

  deviation "/ncs:devices/ncs:template/ncs:ned-id/ncs:config/devm:devm/devm:mpu-boards/devm:mpu-board/bras-basic-access:bras/bras-multicast:multicast" {
    deviate not-supported;
  }
  deviation "/ncs:devices/ncs:device/ncs:live-status/devm:devm/devm:mpu-boards/devm:mpu-board/bras-basic-access:bras/bras-multicast:multicast" {
    deviate not-supported;
  }
  deviation "/ncs:devices/ncs:device/ncs:config/devm:devm/devm:mpu-boards/devm:mpu-board/bras-basic-access:bras/bras-multicast:multicast" {
    deviate not-supported;
  }
}
