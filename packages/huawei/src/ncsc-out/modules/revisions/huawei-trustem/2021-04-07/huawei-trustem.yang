module huawei-trustem {
  // Generated by yanger -t ncs
  tailf:mount-id "huawei-nc-1.0:huawei-nc-1.0";
  tailf:ncs-device-type "netconf";

  namespace "urn:huawei:yang:huawei-trustem";
  prefix trustem;

  import huawei-extension {
    prefix ext;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Indicate TPM (Trusted Platform Module) environment management.";

  revision 2021-04-07 {
    description
      "Add trust-startup-softwares.";
    reference "Huawei private.";
  }
  revision 2020-04-02 {
    description
      "YANG check.";
    reference "Huawei private.";
  }
  revision 2019-05-27 {
    description
      "Initial revision.";
    reference "Huawei private.";
  }
  ext:task-name "tpm";

  typedef ncs_template_status-type {
    type string;
    description
      "TPM status.";
  }

  typedef ncs_rpc_notif_status-type {
    type enumeration {
      enum "active" {
        value 1;
        description
          "Status active.";
      }
    }
    description
      "TPM status.";
  }

  typedef live_ncs_status-type {
    type enumeration {
      enum "active" {
        value 1;
        description
          "Status active.";
      }
    }
    description
      "TPM status.";
  }

  typedef status-type {
    type enumeration {
      enum "active" {
        value 1;
        description
          "Status active.";
      }
    }
    description
      "TPM status.";
  }

  augment "/ncs:devices/ncs:device/ncs:config" {
    // NCS drop config false container trustem
  }
  augment "/ncs:devices/ncs:device/ncs:live-status" {
    container trustem {
      tailf:ncs-device-type "netconf";
      tailf:display-when "not(../../ncs:module) or ../../ncs:module[ncs:name='huawei-trustem'] or (../../ncs:live-status-protocol[not(ncs:capability)]) or (../../ncs:live-status-protocol/ncs:capability/ncs:module[.='huawei-trustem'])";
      description
        "Indicate trust environment management.";
      container statuss {
        description
          "List of operational state of TPM status information.";
        list status {
          key "slot-id";
          description
            "Operational state of TPM status information.";
          leaf slot-id {
            type string {
              length "1..32";
            }
            description
              "Slot ID of a board.";
          }
          leaf version {
            type string {
              length "1..127";
            }
            description
              "TPM version.";
          }
          leaf manufacturer {
            type string {
              length "1..127";
            }
            description
              "TPM manufacturer.";
          }
          leaf status {
            type live_ncs_status-type;
            description
              "TPM status.";
          }
        }
      }
      container trust-startup-softwares {
        description
          "List of software files information measured by TPM.";
        list trust-startup-software {
          key "name version file";
          description
            "Operational data of software file information measured by TPM.";
          leaf name {
            type string {
              length "1..63";
            }
            description
              "Software file description infomation.";
          }
          leaf version {
            type string {
              length "1..63";
            }
            description
              "Software file version.";
          }
          leaf file {
            type string {
              length "1..255";
            }
            description
              "Software file name on device.";
          }
          leaf checksum {
            type string {
              length "1..127";
            }
            description
              "Hash value of the file.";
          }
        }
      }
    }
  }
  augment "/ncs:devices/ncs:template/ncs:ned-id/ncs:config" {
    // NCS drop config false container trustem
  }
}
