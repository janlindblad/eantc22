module huawei-acl-deviations-NE8000 {
  // Generated by yanger -t ncs
  tailf:mount-id "huawei-nc-1.0:huawei-nc-1.0";
  tailf:ncs-device-type "netconf";

  yang-version 1;
  namespace "urn:huawei:yang:huawei-acl-deviations-NE8000";
  prefix acl-devs-NE8000;

  import huawei-acl {
    prefix acl;
  }
  import huawei-acl-ucl {
    prefix acl-ucl;
  }
  import huawei-extension {
    prefix ext;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Access Control List (ACL). An ACL is used to identify and select data packets through packet attributes. For example, applying an ACL in the firewall can either permit or discard data packets. Applying an ACL in IPsec can encrypt data packets that match ACL rules and forward those that do not match any ACL rule.";

  revision 2019-06-23 {
    description
      "Initial revision.";
    reference "Huawei private.";
  }
  ext:deviation-ext "/acl:acl/acl:groups/acl:group/acl:match-order" {
    ext:deviate-ext "add" {
      ext:operation-exclude "update" {
        when '(../acl:rule-basics/acl:rule-basic) or (../acl:rule-advances/acl:rule-advance) or (../acl:rule-ethernets/acl:rule-ethernet) or (../acl:rule-mplss/acl:rule-mpls) or (../acl-ucl:rule-ucls/acl-ucl:rule-ucl) or (../acl:rule-interfaces/acl:rule-interface)' {
          tailf:xpath-root 3;
        }
        description
          "When an ACL rule exists, this value can not be changed.";
      }
    }
  }
  ext:deviation-ext "/acl:acl/acl:group6s/acl:group6/acl:match-order" {
    ext:deviate-ext "add" {
      ext:operation-exclude "update" {
        when '(../acl:rule-basics/acl:rule-basic) or (../acl:rule-advances/acl:rule-advance) or (../acl-ucl:rule-ucls/acl-ucl:rule-ucl) ' {
          tailf:xpath-root 3;
        }
        description
          "When an ACL rule exists, this value can not be changed.";
      }
    }
  }

  typedef ncs_template_group4-type-deviations {
    type string;
    description
      "Type of a rule group.";
  }

  typedef ncs_rpc_notif_group4-type-deviations {
    type enumeration {
      enum "interface" {
        value 0;
        description
          "Interface ACL.";
      }
      enum "link" {
        value 1;
        description
          "Link ACL.";
      }
      enum "basic" {
        value 2;
        description
          "Basic ACL.";
      }
      enum "advance" {
        value 3;
        description
          "Advanced ACL.";
      }
      enum "mpls" {
        value 7;
        description
          "MPLS ACL.";
      }
      enum "UCL" {
        value 10;
        description
          "UCL.";
      }
    }
    description
      "Type of a rule group.";
  }

  typedef live_ncs_group4-type-deviations {
    type enumeration {
      enum "interface" {
        value 0;
        description
          "Interface ACL.";
      }
      enum "link" {
        value 1;
        description
          "Link ACL.";
      }
      enum "basic" {
        value 2;
        description
          "Basic ACL.";
      }
      enum "advance" {
        value 3;
        description
          "Advanced ACL.";
      }
      enum "mpls" {
        value 7;
        description
          "MPLS ACL.";
      }
      enum "UCL" {
        value 10;
        description
          "UCL.";
      }
    }
    description
      "Type of a rule group.";
  }

  typedef group4-type-deviations {
    type enumeration {
      enum "interface" {
        value 0;
        description
          "Interface ACL.";
      }
      enum "link" {
        value 1;
        description
          "Link ACL.";
      }
      enum "basic" {
        value 2;
        description
          "Basic ACL.";
      }
      enum "advance" {
        value 3;
        description
          "Advanced ACL.";
      }
      enum "mpls" {
        value 7;
        description
          "MPLS ACL.";
      }
      enum "UCL" {
        value 10;
        description
          "UCL.";
      }
    }
    description
      "Type of a rule group.";
  }

  deviation "/ncs:devices/ncs:template/ncs:ned-id/ncs:config/acl:acl/acl:groups/acl:group/acl:type" {
    deviate replace {
      type acl-devs-NE8000:ncs_template_group4-type-deviations;
    }
  }
  deviation "/ncs:devices/ncs:device/ncs:live-status/acl:acl/acl:groups/acl:group/acl:type" {
    deviate replace {
      type acl-devs-NE8000:live_ncs_group4-type-deviations;
    }
  }
  deviation "/ncs:devices/ncs:device/ncs:config/acl:acl/acl:groups/acl:group/acl:type" {
    deviate replace {
      type acl-devs-NE8000:group4-type-deviations;
    }
  }
  deviation "/ncs:devices/ncs:template/ncs:ned-id/ncs:config/acl:acl/acl:group6s/acl:group6/acl:rule-basics/acl:rule-basic/acl:source-ipaddr" {
    deviate add {
      // NCS drop must statement
    }
  }
  deviation "/ncs:devices/ncs:device/ncs:live-status/acl:acl/acl:group6s/acl:group6/acl:rule-basics/acl:rule-basic/acl:source-ipaddr" {
    deviate add {
      // NCS drop must statement
    }
  }
  deviation "/ncs:devices/ncs:device/ncs:config/acl:acl/acl:group6s/acl:group6/acl:rule-basics/acl:rule-basic/acl:source-ipaddr" {
    deviate add {
      must '(../source-ipaddr and ../source-wild) or (../source-ipaddr and ../source-mask-len)' {
        tailf:xpath-root 3;
      }
    }
  }
  deviation "/ncs:devices/ncs:template/ncs:ned-id/ncs:config/acl:acl/acl:groups/acl:group/acl:rule-advances/acl:rule-advance/acl:log-enable" {
    deviate not-supported;
  }
  deviation "/ncs:devices/ncs:device/ncs:live-status/acl:acl/acl:groups/acl:group/acl:rule-advances/acl:rule-advance/acl:log-enable" {
    deviate not-supported;
  }
  deviation "/ncs:devices/ncs:device/ncs:config/acl:acl/acl:groups/acl:group/acl:rule-advances/acl:rule-advance/acl:log-enable" {
    deviate not-supported;
  }
  deviation "/ncs:devices/ncs:template/ncs:ned-id/ncs:config/acl:acl/acl:group6s/acl:group6/acl:rule-advances/acl:rule-advance/acl:log-enable" {
    deviate not-supported;
  }
  deviation "/ncs:devices/ncs:device/ncs:live-status/acl:acl/acl:group6s/acl:group6/acl:rule-advances/acl:rule-advance/acl:log-enable" {
    deviate not-supported;
  }
  deviation "/ncs:devices/ncs:device/ncs:config/acl:acl/acl:group6s/acl:group6/acl:rule-advances/acl:rule-advance/acl:log-enable" {
    deviate not-supported;
  }
}
