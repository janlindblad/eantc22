module huawei-mvpn-forward {
  // Generated by yanger -t ncs
  tailf:mount-id "huawei-nc-1.0:huawei-nc-1.0";
  tailf:ncs-device-type "netconf";

  namespace "urn:huawei:yang:huawei-mvpn-forward";
  prefix mvpn-forward;

  import huawei-network-instance {
    prefix ni;
  }
  import huawei-l3vpn {
    prefix l3vpn;
  }
  import huawei-extension {
    prefix ext;
  }
  import huawei-mvpn {
    prefix mvpn;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Multicast virtual private network.";

  revision 2019-03-26 {
    description
      "Init revision.";
    reference "Huawei private.";
  }
  ext:task-name "mvpn";

  typedef ncs_template_service-class {
    type string;
    description
      "Service type.";
  }

  typedef ncs_template_color {
    type string;
    description
      "Color type.";
  }

  typedef ncs_template_enableflag {
    type string;
    description
      "Enable flag type.";
  }

  typedef ncs_rpc_notif_service-class {
    type enumeration {
      enum "be" {
        value 0;
        description
          "Service type of BE.";
      }
      enum "af1" {
        value 1;
        description
          "Service type of AF1.";
      }
      enum "af2" {
        value 2;
        description
          "Service type of AF2.";
      }
      enum "af3" {
        value 3;
        description
          "Service type of AF3.";
      }
      enum "af4" {
        value 4;
        description
          "Service type of AF4.";
      }
      enum "ef" {
        value 5;
        description
          "Service type of EF.";
      }
      enum "cs6" {
        value 6;
        description
          "Service type of CS6.";
      }
      enum "cs7" {
        value 7;
        description
          "Service type of CS7.";
      }
    }
    description
      "Service type.";
  }

  typedef ncs_rpc_notif_color {
    type enumeration {
      enum "green" {
        value 0;
        description
          "Green.";
      }
      enum "yellow" {
        value 1;
        description
          "Yellow.";
      }
      enum "red" {
        value 2;
        description
          "Red.";
      }
    }
    description
      "Color type.";
  }

  typedef ncs_rpc_notif_enableflag {
    type enumeration {
      enum "true" {
        value 1;
        description
          "Multicast-vpn TTL propagate is enabled.";
      }
      enum "false" {
        value 0;
        description
          "Multicast-vpn TTL propagate is disabled.";
      }
    }
    description
      "Enable flag type.";
  }

  typedef live_ncs_service-class {
    type enumeration {
      enum "be" {
        value 0;
        description
          "Service type of BE.";
      }
      enum "af1" {
        value 1;
        description
          "Service type of AF1.";
      }
      enum "af2" {
        value 2;
        description
          "Service type of AF2.";
      }
      enum "af3" {
        value 3;
        description
          "Service type of AF3.";
      }
      enum "af4" {
        value 4;
        description
          "Service type of AF4.";
      }
      enum "ef" {
        value 5;
        description
          "Service type of EF.";
      }
      enum "cs6" {
        value 6;
        description
          "Service type of CS6.";
      }
      enum "cs7" {
        value 7;
        description
          "Service type of CS7.";
      }
    }
    description
      "Service type.";
  }

  typedef live_ncs_color {
    type enumeration {
      enum "green" {
        value 0;
        description
          "Green.";
      }
      enum "yellow" {
        value 1;
        description
          "Yellow.";
      }
      enum "red" {
        value 2;
        description
          "Red.";
      }
    }
    description
      "Color type.";
  }

  typedef live_ncs_enableflag {
    type enumeration {
      enum "true" {
        value 1;
        description
          "Multicast-vpn TTL propagate is enabled.";
      }
      enum "false" {
        value 0;
        description
          "Multicast-vpn TTL propagate is disabled.";
      }
    }
    description
      "Enable flag type.";
  }

  typedef service-class {
    type enumeration {
      enum "be" {
        value 0;
        description
          "Service type of BE.";
      }
      enum "af1" {
        value 1;
        description
          "Service type of AF1.";
      }
      enum "af2" {
        value 2;
        description
          "Service type of AF2.";
      }
      enum "af3" {
        value 3;
        description
          "Service type of AF3.";
      }
      enum "af4" {
        value 4;
        description
          "Service type of AF4.";
      }
      enum "ef" {
        value 5;
        description
          "Service type of EF.";
      }
      enum "cs6" {
        value 6;
        description
          "Service type of CS6.";
      }
      enum "cs7" {
        value 7;
        description
          "Service type of CS7.";
      }
    }
    description
      "Service type.";
  }

  typedef color {
    type enumeration {
      enum "green" {
        value 0;
        description
          "Green.";
      }
      enum "yellow" {
        value 1;
        description
          "Yellow.";
      }
      enum "red" {
        value 2;
        description
          "Red.";
      }
    }
    description
      "Color type.";
  }

  typedef enableflag {
    type enumeration {
      enum "true" {
        value 1;
        description
          "Multicast-vpn TTL propagate is enabled.";
      }
      enum "false" {
        value 0;
        description
          "Multicast-vpn TTL propagate is disabled.";
      }
    }
    description
      "Enable flag type.";
  }

  augment "/ncs:devices/ncs:device/ncs:config" {
    container mvpn-forward {
      tailf:ncs-device-type "netconf";
      tailf:display-when "not(../../ncs:module) or ../../ncs:module[ncs:name='huawei-mvpn-forward']";
      description
        "Multicast forwarding table.";
      container global {
        description
          "Configure MVPN global configuration.";
        container ttl-propagate {
          description
            "Configure MVPN TTL value.";
          leaf enable {
            type enableflag;
            default "false";
            description
              "Propagate the TTL value used by the private network to the public network.";
          }
        }
        container multicast-vpn-slots {
          description
            "List of MVPN integrated boards.";
          list multicast-vpn-slot {
            key "slot";
            description
              "Configure MVPN integrated board.";
            leaf slot {
              type string {
                length "1..15";
              }
              description
                "Slot number of the board on which MVPN is to be enabled.";
            }
          }
        }
        container ng-mvpn-forward-mode {
          description
            "Configure NGMVPN mode configuration.";
          leaf propagate-enable {
            type enableflag;
            default "false";
            description
              "Config loopback mode.";
          }
        }
      }
    }
  }
  augment "/ncs:devices/ncs:device/ncs:live-status" {
    container mvpn-forward {
      tailf:ncs-device-type "netconf";
      tailf:display-when "not(../../ncs:module) or ../../ncs:module[ncs:name='huawei-mvpn-forward'] or (../../ncs:live-status-protocol[not(ncs:capability)]) or (../../ncs:live-status-protocol/ncs:capability/ncs:module[.='huawei-mvpn-forward'])";
      description
        "Multicast forwarding table.";
      container global {
        description
          "Configure MVPN global configuration.";
        container ttl-propagate {
          description
            "Configure MVPN TTL value.";
          leaf enable {
            type live_ncs_enableflag;
            // NCS drop default statement
            description
              "Propagate the TTL value used by the private network to the public network.";
          }
        }
        container multicast-vpn-slots {
          description
            "List of MVPN integrated boards.";
          list multicast-vpn-slot {
            key "slot";
            description
              "Configure MVPN integrated board.";
            leaf slot {
              type string {
                length "1..15";
              }
              description
                "Slot number of the board on which MVPN is to be enabled.";
            }
          }
        }
        container ng-mvpn-forward-mode {
          description
            "Configure NGMVPN mode configuration.";
          leaf propagate-enable {
            type live_ncs_enableflag;
            // NCS drop default statement
            description
              "Config loopback mode.";
          }
        }
      }
    }
  }
  augment "/ncs:devices/ncs:template/ncs:ned-id/ncs:config" {
    container mvpn-forward {
      description
        "Multicast forwarding table.";
      container global {
        description
          "Configure MVPN global configuration.";
        container ttl-propagate {
          description
            "Configure MVPN TTL value.";
          leaf enable {
            type ncs_template_enableflag;
            // NCS drop default statement
            description
              "Propagate the TTL value used by the private network to the public network.";
          }
        }
        container multicast-vpn-slots {
          description
            "List of MVPN integrated boards.";
          list multicast-vpn-slot {
            // NCS patched for predictable order
            ordered-by user;
            key "slot";
            description
              "Configure MVPN integrated board.";
            leaf slot {
              type string;
              description
                "Slot number of the board on which MVPN is to be enabled.";
            }
          }
        }
        container ng-mvpn-forward-mode {
          description
            "Configure NGMVPN mode configuration.";
          leaf propagate-enable {
            type ncs_template_enableflag;
            // NCS drop default statement
            description
              "Config loopback mode.";
          }
        }
      }
    }
  }
  augment "/ncs:devices/ncs:template/ncs:ned-id/ncs:config/ni:network-instance/ni:instances/ni:instance/l3vpn:afs/l3vpn:af/mvpn:mvpn/mvpn:mvpn-type/mvpn:ng-mvpn/mvpn:ng" {
    description
      "Configure WTR attribute on MVPN template.";
    container multicast-wtr {
      // NCS drop when statement
      description
        "Configure wait time restore.";
      leaf wtr {
        type string;
        units "s";
        // NCS drop default statement
        description
          "Wait time restore.";
      }
    }
  }
  augment "/ncs:devices/ncs:device/ncs:live-status/ni:network-instance/ni:instances/ni:instance/l3vpn:afs/l3vpn:af/mvpn:mvpn/mvpn:mvpn-type/mvpn:ng-mvpn/mvpn:ng" {
    description
      "Configure WTR attribute on MVPN template.";
    container multicast-wtr {
      tailf:ncs-device-type "netconf";
      tailf:display-when "not(../../../../../../../../../../../ncs:module) or ../../../../../../../../../../../ncs:module[ncs:name='huawei-mvpn-forward'] or (../../../../../../../../../../../ncs:live-status-protocol[not(ncs:capability)]) or (../../../../../../../../../../../ncs:live-status-protocol/ncs:capability/ncs:module[.='huawei-mvpn-forward'])";
      // NCS drop when statement
      description
        "Configure wait time restore.";
      leaf wtr {
        type uint16 {
          range "60..1800";
        }
        units "s";
        // NCS drop default statement
        description
          "Wait time restore.";
      }
    }
  }
  augment "/ncs:devices/ncs:device/ncs:config/ni:network-instance/ni:instances/ni:instance/l3vpn:afs/l3vpn:af/mvpn:mvpn/mvpn:mvpn-type/mvpn:ng-mvpn/mvpn:ng" {
    description
      "Configure WTR attribute on MVPN template.";
    container multicast-wtr {
      tailf:ncs-device-type "netconf";
      tailf:display-when "not(../../../../../../../../../../../ncs:module) or ../../../../../../../../../../../ncs:module[ncs:name='huawei-mvpn-forward']";
      when "../../../l3vpn:type='ipv4-unicast' and ../mvpn:is-c-multicast-frr='true'" {
        tailf:xpath-root 3;
      }
      description
        "Configure wait time restore.";
      leaf wtr {
        type uint16 {
          range "60..1800";
        }
        units "s";
        default "600";
        description
          "Wait time restore.";
      }
    }
  }
}
