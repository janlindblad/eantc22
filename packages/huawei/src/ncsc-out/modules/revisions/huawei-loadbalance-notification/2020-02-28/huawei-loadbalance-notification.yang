module huawei-loadbalance-notification {
  // Generated by yanger -t ncs
  tailf:mount-id "huawei-nc-1.0:huawei-nc-1.0";
  tailf:ncs-device-type "netconf";

  yang-version 1;
  namespace "urn:huawei:yang:huawei-loadbalance-notification";
  prefix loadbalance-notification;

  import huawei-extension {
    prefix ext;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Notification of loadbalance-notification.";

  revision 2020-02-28 {
    description
      "Update the type of the nodes.";
    reference "Huawei private.";
  }
  revision 2019-07-08 {
    description
      "Init revision.";
    reference "Huawei private.";
  }
  ext:task-name "forwarding";

  augment "/ncs:devices/ncs:device/ncs:notifications/ncs:received-notifications/ncs:notification/ncs:data" {
    container l2vxlan-deep-hash-alarm-resume {
      presence "";
      config false;
      description
        "A clear alarm was generated because L2vxlan deep hash was disabled or the board was replaced by a board that supports this function.";
      leaf slot {
        type string {
          length "0..15";
        }
        description
          "Slot ID.";
      }
    }
  }
  augment "/ncs:devices/ncs:device/ncs:notifications/ncs:received-notifications/ncs:notification/ncs:data" {
    container l2vxlan-deep-hash-alarm {
      presence "";
      config false;
      description
        "The board did not support L2vxlan deep hash function.";
      leaf slot {
        type string {
          length "0..15";
        }
        description
          "Slot ID.";
      }
    }
  }
  augment "/ncs:devices/ncs:device/ncs:notifications/ncs:received-notifications/ncs:notification/ncs:data" {
    container hash-key-ip-alarm-resume {
      presence "";
      config false;
      description
        "A clear alarm was generated because ECMP based on a specified source or destination IP address was disabled or the board was replaced by a board that supports this function.";
      leaf slot {
        type string {
          length "0..15";
        }
        description
          "Slot ID.";
      }
    }
  }
  augment "/ncs:devices/ncs:device/ncs:notifications/ncs:received-notifications/ncs:notification/ncs:data" {
    container hash-key-ip-alarm {
      presence "";
      config false;
      description
        "The board did not support ECMP based on a specified source or destination IP address.";
      leaf slot {
        type string {
          length "0..15";
        }
        description
          "Slot ID.";
      }
    }
  }
  augment "/ncs:devices/ncs:device/ncs:netconf-notifications/ncs:received-notifications/ncs:notification/ncs:data" {
    container l2vxlan-deep-hash-alarm-resume {
      presence "";
      config false;
      description
        "A clear alarm was generated because L2vxlan deep hash was disabled or the board was replaced by a board that supports this function.";
      leaf slot {
        type string {
          length "0..15";
        }
        description
          "Slot ID.";
      }
    }
  }
  augment "/ncs:devices/ncs:device/ncs:netconf-notifications/ncs:received-notifications/ncs:notification/ncs:data" {
    container l2vxlan-deep-hash-alarm {
      presence "";
      config false;
      description
        "The board did not support L2vxlan deep hash function.";
      leaf slot {
        type string {
          length "0..15";
        }
        description
          "Slot ID.";
      }
    }
  }
  augment "/ncs:devices/ncs:device/ncs:netconf-notifications/ncs:received-notifications/ncs:notification/ncs:data" {
    container hash-key-ip-alarm-resume {
      presence "";
      config false;
      description
        "A clear alarm was generated because ECMP based on a specified source or destination IP address was disabled or the board was replaced by a board that supports this function.";
      leaf slot {
        type string {
          length "0..15";
        }
        description
          "Slot ID.";
      }
    }
  }
  augment "/ncs:devices/ncs:device/ncs:netconf-notifications/ncs:received-notifications/ncs:notification/ncs:data" {
    container hash-key-ip-alarm {
      presence "";
      config false;
      description
        "The board did not support ECMP based on a specified source or destination IP address.";
      leaf slot {
        type string {
          length "0..15";
        }
        description
          "Slot ID.";
      }
    }
  }
}
