module huawei-clocksync-ptpadapt {
  // Generated by yanger -t ncs
  tailf:mount-id "huawei-nc-1.0:huawei-nc-1.0";
  tailf:ncs-device-type "netconf";

  namespace "urn:huawei:yang:huawei-clocksync-ptpadapt";
  prefix clocksync-ptpadapt;

  import ietf-inet-types {
    prefix inet;
  }
  import huawei-network-instance {
    prefix ni;
  }
  import huawei-ifm {
    prefix ifm;
  }
  import huawei-extension {
    prefix ext;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Ptp-adaptive data model define.";

  revision 2020-03-19 {
    description
      "Optimize the must condition of nego-mode and hop-by-hop-mode node.";
    reference "Huawei private.";
  }
  revision 2020-03-14 {
    description
      "Fixed a problem.";
    reference "Huawei private.";
  }
  revision 2020-03-04 {
    description
      "Modify the node description.";
    reference "Huawei private.";
  }
  revision 2019-12-25 {
    description
      "Add reset-ptpa-server-pkt, reset-ptpa-server-pkt action node.";
    reference "Huawei private.";
  }
  revision 2019-05-06 {
    description
      "Initial revision.";
    reference "Huawei private.";
  }
  ext:task-name "clksync";

  typedef ncs_template_server-index {
    type string;
    description
      "Server index.";
  }

  typedef ncs_template_ptpa-nego-mode {
    type string;
    description
      "Negotiation mode type.";
  }

  typedef ncs_template_ptpa-device-type {
    type string;
    description
      "Device type.";
  }

  typedef ncs_template_ptpa-freq-profile {
    type string;
    description
      "Freqprofile type.";
  }

  typedef ncs_template_ptpa-nego-state {
    type string;
    description
      "Negotiation state type.";
  }

  typedef ncs_template_ptpa-nego-error-reason {
    type string;
    description
      "Negotiation error reason.";
  }

  typedef ncs_template_ptpa-server-ptsf-state {
    type string;
    description
      "PTSF state type.";
  }

  typedef ncs_template_phy-ssm-level {
    type string;
    description
      "Ssm level.";
  }

  typedef ncs_template_ptp-time-source {
    type string;
    description
      "Type of ptp time source.";
  }

  typedef ncs_template_ptp-sign-flag {
    type string;
    description
      "Flag of ptp sign.";
  }

  typedef ncs_template_ptpa-trace-source {
    type string;
    description
      "Ptpa trace source type.";
  }

  typedef ncs_rpc_notif_server-index {
    type enumeration {
      enum "server1" {
        value 1;
        description
          "Server1.";
      }
      enum "server2" {
        value 2;
        description
          "Server2.";
      }
    }
    description
      "Server index.";
  }

  typedef ncs_rpc_notif_ptpa-nego-mode {
    type enumeration {
      enum "one-way" {
        value 1;
        description
          "Negotiation mode is one-way.";
      }
      enum "two-way" {
        value 2;
        description
          "Negotiation mode is two-way.";
      }
      enum "acr" {
        value 3;
        description
          "Negotiation mode acr.";
      }
      enum "atr" {
        value 4;
        description
          "Negotiation mode is atr.";
      }
      enum "none" {
        value 99;
        description
          "Negotiation mode is none.";
      }
    }
    description
      "Negotiation mode type.";
  }

  typedef ncs_rpc_notif_ptpa-device-type {
    type enumeration {
      enum "none" {
        value 99;
        description
          "Device type is none.";
      }
      enum "client" {
        value 2;
        description
          "Device type is client.";
      }
      enum "server" {
        value 3;
        description
          "Device type is server.";
      }
    }
    description
      "Device type.";
  }

  typedef ncs_rpc_notif_ptpa-freq-profile {
    type enumeration {
      enum "part" {
        value 0;
        description
          "Freqprofile is part.";
      }
      enum "all" {
        value 1;
        description
          "Freqprofile is all.";
      }
      enum "timeprofile" {
        value 2;
        description
          "Freqprofile is timeprofile.";
      }
    }
    description
      "Freqprofile type.";
  }

  typedef ncs_rpc_notif_ptpa-nego-state {
    type enumeration {
      enum "init" {
        value 0;
        description
          "Negotiation state is init.";
      }
      enum "success" {
        value 1;
        description
          "Negotiation state is success.";
      }
      enum "error" {
        value 2;
        description
          "Negotiation state is error.";
      }
      enum "none" {
        value 3;
        description
          "Negotiation state is none.";
      }
    }
    description
      "Negotiation state type.";
  }

  typedef ncs_rpc_notif_ptpa-nego-error-reason {
    type enumeration {
      enum "delete-link" {
        value 2;
        description
          "Delete-link.";
      }
      enum "announce-timeout" {
        value 3;
        description
          "Announce-timeout.";
      }
      enum "announce-nego-timeout" {
        value 4;
        description
          "Announce-nego-timeout.";
      }
      enum "announce-nego-deny" {
        value 5;
        description
          "Announce-nego-deny.";
      }
      enum "sync-nego-failed" {
        value 6;
        description
          "Sync-nego-failed.";
      }
      enum "sync-nego-deny" {
        value 7;
        description
          "Sync-nego-deny.";
      }
      enum "delay-resp-nego-timeout" {
        value 8;
        description
          "Delayr-esp-nego-timeout.";
      }
      enum "delay-resp-nego-deny" {
        value 9;
        description
          "Delay-resp-nego-deny.";
      }
      enum "if-cannot-support-ptp" {
        value 10;
        description
          "If-cannot-support-ptp.";
      }
      enum "service-mode-notsupport-ptp" {
        value 11;
        description
          "Service-mode-notsupport-ptp.";
      }
      enum "route-unreach" {
        value 12;
        description
          "Route-unreach.";
      }
      enum "bmc-failed" {
        value 13;
        description
          "Bmc-failed.";
      }
      enum "master-synchronization-fault" {
        value 14;
        description
          "Master-synchronization-fault.";
      }
      enum "none" {
        value 15;
        description
          "None.";
      }
    }
    description
      "Negotiation error reason.";
  }

  typedef ncs_rpc_notif_ptpa-server-ptsf-state {
    type enumeration {
      enum "normal" {
        value 1;
        description
          "PTSF state is normal.";
      }
      enum "abnormal" {
        value 0;
        description
          "PTSF state is abnormal.";
      }
    }
    description
      "PTSF state type.";
  }

  typedef ncs_rpc_notif_phy-ssm-level {
    type enumeration {
      enum "none" {
        value 16;
        description
          "NONE.";
      }
      enum "prc" {
        value 2;
        description
          "PRC.";
      }
      enum "ssua" {
        value 4;
        description
          "SSUA.";
      }
      enum "ssub" {
        value 8;
        description
          "SSUB.";
      }
      enum "sec" {
        value 11;
        description
          "SEC.";
      }
      enum "dnu" {
        value 15;
        description
          "DNU.";
      }
      enum "unk" {
        value 0;
        description
          "UNK.";
      }
    }
    description
      "Ssm level.";
  }

  typedef ncs_rpc_notif_ptp-time-source {
    type enumeration {
      enum "atomicclock" {
        value 16;
        description
          "Atomicclock.";
      }
      enum "gps" {
        value 32;
        description
          "Gps.";
      }
      enum "terrestrialradio" {
        value 48;
        description
          "Terrestrialradio.";
      }
      enum "ptp" {
        value 64;
        description
          "Ptp.";
      }
      enum "ntp" {
        value 80;
        description
          "Ntp.";
      }
      enum "handset" {
        value 96;
        description
          "Handset.";
      }
      enum "other" {
        value 144;
        description
          "Other.";
      }
      enum "internaloscillator" {
        value 160;
        description
          "Internaloscillator.";
      }
    }
    description
      "Type of ptp time source.";
  }

  typedef ncs_rpc_notif_ptp-sign-flag {
    type enumeration {
      enum "negative" {
        value 0;
        description
          "Negative.";
      }
      enum "positive" {
        value 1;
        description
          "Positive.";
      }
    }
    description
      "Flag of ptp sign.";
  }

  typedef ncs_rpc_notif_ptpa-trace-source {
    type enumeration {
      enum "local" {
        value 0;
        description
          "Local.";
      }
      enum "server1" {
        value 1;
        description
          "Server1.";
      }
      enum "server2" {
        value 2;
        description
          "Server2.";
      }
    }
    description
      "Ptpa trace source type.";
  }

  typedef live_ncs_server-index {
    type enumeration {
      enum "server1" {
        value 1;
        description
          "Server1.";
      }
      enum "server2" {
        value 2;
        description
          "Server2.";
      }
    }
    description
      "Server index.";
  }

  typedef live_ncs_ptpa-nego-mode {
    type enumeration {
      enum "one-way" {
        value 1;
        description
          "Negotiation mode is one-way.";
      }
      enum "two-way" {
        value 2;
        description
          "Negotiation mode is two-way.";
      }
      enum "acr" {
        value 3;
        description
          "Negotiation mode acr.";
      }
      enum "atr" {
        value 4;
        description
          "Negotiation mode is atr.";
      }
      enum "none" {
        value 99;
        description
          "Negotiation mode is none.";
      }
    }
    description
      "Negotiation mode type.";
  }

  typedef live_ncs_ptpa-device-type {
    type enumeration {
      enum "none" {
        value 99;
        description
          "Device type is none.";
      }
      enum "client" {
        value 2;
        description
          "Device type is client.";
      }
      enum "server" {
        value 3;
        description
          "Device type is server.";
      }
    }
    description
      "Device type.";
  }

  typedef live_ncs_ptpa-freq-profile {
    type enumeration {
      enum "part" {
        value 0;
        description
          "Freqprofile is part.";
      }
      enum "all" {
        value 1;
        description
          "Freqprofile is all.";
      }
      enum "timeprofile" {
        value 2;
        description
          "Freqprofile is timeprofile.";
      }
    }
    description
      "Freqprofile type.";
  }

  typedef live_ncs_ptpa-nego-state {
    type enumeration {
      enum "init" {
        value 0;
        description
          "Negotiation state is init.";
      }
      enum "success" {
        value 1;
        description
          "Negotiation state is success.";
      }
      enum "error" {
        value 2;
        description
          "Negotiation state is error.";
      }
      enum "none" {
        value 3;
        description
          "Negotiation state is none.";
      }
    }
    description
      "Negotiation state type.";
  }

  typedef live_ncs_ptpa-nego-error-reason {
    type enumeration {
      enum "delete-link" {
        value 2;
        description
          "Delete-link.";
      }
      enum "announce-timeout" {
        value 3;
        description
          "Announce-timeout.";
      }
      enum "announce-nego-timeout" {
        value 4;
        description
          "Announce-nego-timeout.";
      }
      enum "announce-nego-deny" {
        value 5;
        description
          "Announce-nego-deny.";
      }
      enum "sync-nego-failed" {
        value 6;
        description
          "Sync-nego-failed.";
      }
      enum "sync-nego-deny" {
        value 7;
        description
          "Sync-nego-deny.";
      }
      enum "delay-resp-nego-timeout" {
        value 8;
        description
          "Delayr-esp-nego-timeout.";
      }
      enum "delay-resp-nego-deny" {
        value 9;
        description
          "Delay-resp-nego-deny.";
      }
      enum "if-cannot-support-ptp" {
        value 10;
        description
          "If-cannot-support-ptp.";
      }
      enum "service-mode-notsupport-ptp" {
        value 11;
        description
          "Service-mode-notsupport-ptp.";
      }
      enum "route-unreach" {
        value 12;
        description
          "Route-unreach.";
      }
      enum "bmc-failed" {
        value 13;
        description
          "Bmc-failed.";
      }
      enum "master-synchronization-fault" {
        value 14;
        description
          "Master-synchronization-fault.";
      }
      enum "none" {
        value 15;
        description
          "None.";
      }
    }
    description
      "Negotiation error reason.";
  }

  typedef live_ncs_ptpa-server-ptsf-state {
    type enumeration {
      enum "normal" {
        value 1;
        description
          "PTSF state is normal.";
      }
      enum "abnormal" {
        value 0;
        description
          "PTSF state is abnormal.";
      }
    }
    description
      "PTSF state type.";
  }

  typedef live_ncs_phy-ssm-level {
    type enumeration {
      enum "none" {
        value 16;
        description
          "NONE.";
      }
      enum "prc" {
        value 2;
        description
          "PRC.";
      }
      enum "ssua" {
        value 4;
        description
          "SSUA.";
      }
      enum "ssub" {
        value 8;
        description
          "SSUB.";
      }
      enum "sec" {
        value 11;
        description
          "SEC.";
      }
      enum "dnu" {
        value 15;
        description
          "DNU.";
      }
      enum "unk" {
        value 0;
        description
          "UNK.";
      }
    }
    description
      "Ssm level.";
  }

  typedef live_ncs_ptp-time-source {
    type enumeration {
      enum "atomicclock" {
        value 16;
        description
          "Atomicclock.";
      }
      enum "gps" {
        value 32;
        description
          "Gps.";
      }
      enum "terrestrialradio" {
        value 48;
        description
          "Terrestrialradio.";
      }
      enum "ptp" {
        value 64;
        description
          "Ptp.";
      }
      enum "ntp" {
        value 80;
        description
          "Ntp.";
      }
      enum "handset" {
        value 96;
        description
          "Handset.";
      }
      enum "other" {
        value 144;
        description
          "Other.";
      }
      enum "internaloscillator" {
        value 160;
        description
          "Internaloscillator.";
      }
    }
    description
      "Type of ptp time source.";
  }

  typedef live_ncs_ptp-sign-flag {
    type enumeration {
      enum "negative" {
        value 0;
        description
          "Negative.";
      }
      enum "positive" {
        value 1;
        description
          "Positive.";
      }
    }
    description
      "Flag of ptp sign.";
  }

  typedef live_ncs_ptpa-trace-source {
    type enumeration {
      enum "local" {
        value 0;
        description
          "Local.";
      }
      enum "server1" {
        value 1;
        description
          "Server1.";
      }
      enum "server2" {
        value 2;
        description
          "Server2.";
      }
    }
    description
      "Ptpa trace source type.";
  }

  typedef server-index {
    type enumeration {
      enum "server1" {
        value 1;
        description
          "Server1.";
      }
      enum "server2" {
        value 2;
        description
          "Server2.";
      }
    }
    description
      "Server index.";
  }

  typedef ptpa-nego-mode {
    type enumeration {
      enum "one-way" {
        value 1;
        description
          "Negotiation mode is one-way.";
      }
      enum "two-way" {
        value 2;
        description
          "Negotiation mode is two-way.";
      }
      enum "acr" {
        value 3;
        description
          "Negotiation mode acr.";
      }
      enum "atr" {
        value 4;
        description
          "Negotiation mode is atr.";
      }
      enum "none" {
        value 99;
        description
          "Negotiation mode is none.";
      }
    }
    description
      "Negotiation mode type.";
  }

  typedef ptpa-device-type {
    type enumeration {
      enum "none" {
        value 99;
        description
          "Device type is none.";
      }
      enum "client" {
        value 2;
        description
          "Device type is client.";
      }
      enum "server" {
        value 3;
        description
          "Device type is server.";
      }
    }
    description
      "Device type.";
  }

  typedef ptpa-freq-profile {
    type enumeration {
      enum "part" {
        value 0;
        description
          "Freqprofile is part.";
      }
      enum "all" {
        value 1;
        description
          "Freqprofile is all.";
      }
      enum "timeprofile" {
        value 2;
        description
          "Freqprofile is timeprofile.";
      }
    }
    description
      "Freqprofile type.";
  }

  typedef ptpa-nego-state {
    type enumeration {
      enum "init" {
        value 0;
        description
          "Negotiation state is init.";
      }
      enum "success" {
        value 1;
        description
          "Negotiation state is success.";
      }
      enum "error" {
        value 2;
        description
          "Negotiation state is error.";
      }
      enum "none" {
        value 3;
        description
          "Negotiation state is none.";
      }
    }
    description
      "Negotiation state type.";
  }

  typedef ptpa-nego-error-reason {
    type enumeration {
      enum "delete-link" {
        value 2;
        description
          "Delete-link.";
      }
      enum "announce-timeout" {
        value 3;
        description
          "Announce-timeout.";
      }
      enum "announce-nego-timeout" {
        value 4;
        description
          "Announce-nego-timeout.";
      }
      enum "announce-nego-deny" {
        value 5;
        description
          "Announce-nego-deny.";
      }
      enum "sync-nego-failed" {
        value 6;
        description
          "Sync-nego-failed.";
      }
      enum "sync-nego-deny" {
        value 7;
        description
          "Sync-nego-deny.";
      }
      enum "delay-resp-nego-timeout" {
        value 8;
        description
          "Delayr-esp-nego-timeout.";
      }
      enum "delay-resp-nego-deny" {
        value 9;
        description
          "Delay-resp-nego-deny.";
      }
      enum "if-cannot-support-ptp" {
        value 10;
        description
          "If-cannot-support-ptp.";
      }
      enum "service-mode-notsupport-ptp" {
        value 11;
        description
          "Service-mode-notsupport-ptp.";
      }
      enum "route-unreach" {
        value 12;
        description
          "Route-unreach.";
      }
      enum "bmc-failed" {
        value 13;
        description
          "Bmc-failed.";
      }
      enum "master-synchronization-fault" {
        value 14;
        description
          "Master-synchronization-fault.";
      }
      enum "none" {
        value 15;
        description
          "None.";
      }
    }
    description
      "Negotiation error reason.";
  }

  typedef ptpa-server-ptsf-state {
    type enumeration {
      enum "normal" {
        value 1;
        description
          "PTSF state is normal.";
      }
      enum "abnormal" {
        value 0;
        description
          "PTSF state is abnormal.";
      }
    }
    description
      "PTSF state type.";
  }

  typedef phy-ssm-level {
    type enumeration {
      enum "none" {
        value 16;
        description
          "NONE.";
      }
      enum "prc" {
        value 2;
        description
          "PRC.";
      }
      enum "ssua" {
        value 4;
        description
          "SSUA.";
      }
      enum "ssub" {
        value 8;
        description
          "SSUB.";
      }
      enum "sec" {
        value 11;
        description
          "SEC.";
      }
      enum "dnu" {
        value 15;
        description
          "DNU.";
      }
      enum "unk" {
        value 0;
        description
          "UNK.";
      }
    }
    description
      "Ssm level.";
  }

  typedef ptp-time-source {
    type enumeration {
      enum "atomicclock" {
        value 16;
        description
          "Atomicclock.";
      }
      enum "gps" {
        value 32;
        description
          "Gps.";
      }
      enum "terrestrialradio" {
        value 48;
        description
          "Terrestrialradio.";
      }
      enum "ptp" {
        value 64;
        description
          "Ptp.";
      }
      enum "ntp" {
        value 80;
        description
          "Ntp.";
      }
      enum "handset" {
        value 96;
        description
          "Handset.";
      }
      enum "other" {
        value 144;
        description
          "Other.";
      }
      enum "internaloscillator" {
        value 160;
        description
          "Internaloscillator.";
      }
    }
    description
      "Type of ptp time source.";
  }

  typedef ptp-sign-flag {
    type enumeration {
      enum "negative" {
        value 0;
        description
          "Negative.";
      }
      enum "positive" {
        value 1;
        description
          "Positive.";
      }
    }
    description
      "Flag of ptp sign.";
  }

  typedef ptpa-trace-source {
    type enumeration {
      enum "local" {
        value 0;
        description
          "Local.";
      }
      enum "server1" {
        value 1;
        description
          "Server1.";
      }
      enum "server2" {
        value 2;
        description
          "Server2.";
      }
    }
    description
      "Ptpa trace source type.";
  }

  augment "/ncs:devices/ncs:device/ncs:rpc" {
    container rpc-reset-ptpa-client-pkt {
      tailf:ncs-device-type "netconf";
      tailf:display-when "not(../../ncs:module) or ../../ncs:module[ncs:name='huawei-clocksync-ptpadapt']";
      tailf:action reset-ptpa-client-pkt {
        tailf:actionpoint ncsproxy {
          tailf:internal;
        }
        description
          "Clear packet statistics.";
        ext:node-ref "/clocksync-ptpadapt:clocksync-ptpadapt/clocksync-ptpadapt:ptpa-clients/clocksync-ptpadapt:ptpa-client";
        input {
          leaf client-id {
            type uint32;
            description
              "Clear packet statistics.";
          }
        }
      }
    }
  }
  augment "/ncs:devices/ncs:device-group/ncs:ned-id/ncs:rpc" {
    container rpc-reset-ptpa-client-pkt {
      tailf:ncs-device-type "netconf";
      tailf:display-when "/ncs:devices/ncs:device[ncs:name=current()/../../../ncs:member]/ncs:module[ncs:name='huawei-clocksync-ptpadapt']";
      tailf:action reset-ptpa-client-pkt {
        tailf:actionpoint ncsproxy {
          tailf:internal;
        }
        description
          "Clear packet statistics.";
        ext:node-ref "/clocksync-ptpadapt:clocksync-ptpadapt/clocksync-ptpadapt:ptpa-clients/clocksync-ptpadapt:ptpa-client";
        input {
          leaf client-id {
            type uint32;
            description
              "Clear packet statistics.";
          }
        }
      }
    }
  }
  augment "/ncs:devices/ncs:device/ncs:rpc" {
    container rpc-reset-ptpa-server-pkt {
      tailf:ncs-device-type "netconf";
      tailf:display-when "not(../../ncs:module) or ../../ncs:module[ncs:name='huawei-clocksync-ptpadapt']";
      tailf:action reset-ptpa-server-pkt {
        tailf:actionpoint ncsproxy {
          tailf:internal;
        }
        description
          "Clear statistics, including packet and timestamp statistics.";
        ext:node-ref "/clocksync-ptpadapt:clocksync-ptpadapt/clocksync-ptpadapt:ptpa-servers/clocksync-ptpadapt:ptpa-server";
        input {
          leaf server-index {
            type ncs_rpc_notif_server-index;
            description
              "Clear statistics, including packet and timestamp statistics.";
          }
        }
      }
    }
  }
  augment "/ncs:devices/ncs:device-group/ncs:ned-id/ncs:rpc" {
    container rpc-reset-ptpa-server-pkt {
      tailf:ncs-device-type "netconf";
      tailf:display-when "/ncs:devices/ncs:device[ncs:name=current()/../../../ncs:member]/ncs:module[ncs:name='huawei-clocksync-ptpadapt']";
      tailf:action reset-ptpa-server-pkt {
        tailf:actionpoint ncsproxy {
          tailf:internal;
        }
        description
          "Clear statistics, including packet and timestamp statistics.";
        ext:node-ref "/clocksync-ptpadapt:clocksync-ptpadapt/clocksync-ptpadapt:ptpa-servers/clocksync-ptpadapt:ptpa-server";
        input {
          leaf server-index {
            type ncs_rpc_notif_server-index;
            description
              "Clear statistics, including packet and timestamp statistics.";
          }
        }
      }
    }
  }
  augment "/ncs:devices/ncs:device/ncs:config" {
    container clocksync-ptpadapt {
      tailf:ncs-device-type "netconf";
      tailf:display-when "not(../../ncs:module) or ../../ncs:module[ncs:name='huawei-clocksync-ptpadapt']";
      description
        "Module of adaptive clock.";
      container ptpa-common {
        description
          "Configure basic information of adaptive clock.";
        leaf enable {
          type boolean;
          default "false";
          description
            "Enable/disable adaptive clock. When the master does not support PTP, the router that enables adaptive clock can retrieve clock information from the server's PTP packets.";
        }
        leaf device-type {
          when "(../enable='true')" {
            tailf:xpath-root 3;
          }
          type ptpa-device-type;
          default "none";
          description
            "Configure the router to work in client or server mode.";
        }
        leaf nego-mode {
          when "(../enable='true')" {
            tailf:xpath-root 3;
          }
          type ptpa-nego-mode;
          must "../enable='true' and ((../device-type='server' and ((../nego-mode='acr' and ../freq-profile!='timeprofile') or (../nego-mode='atr' and ../freq-profile='timeprofile') or ../nego-mode='none') and ../local-ip!='0.0.0.0') or (../device-type='client' and (((../nego-mode='one-way' or ../nego-mode='two-way') and ../freq-profile!='timeprofile') or ../nego-mode='none') and ../local-ip!='0.0.0.0') or (../device-type='none' and ../nego-mode='none'))" {
            tailf:xpath-root 3;
          }
          default "none";
          description
            "Enable or disable PTP adaptive ACR/ATR unicast negotiation.";
        }
        leaf dscp {
          when "(../enable='true')" {
            tailf:xpath-root 3;
          }
          type int32 {
            range "0..63";
          }
          default "56";
          description
            "Configure QoS priority of ptp-adaptive packet.";
        }
        leaf domain {
          when "(../enable='true')" {
            tailf:xpath-root 3;
          }
          type uint32 {
            range "0..255";
          }
          default "0";
          description
            "Configure ptp-adaptive device domain. While profile is configured as 'Support Partly', the default domain value is 0 and domain range is <0-255>. While profile is configured as 'Partly', the default domain value is 4 and domain range is <4-43>.While profile is configured as 'Time Synchronization Protocol', the default domain value is 44 and domain range is <44-63>.";
        }
        leaf local-ip {
          when "(../enable='true')" {
            tailf:xpath-root 3;
          }
          type inet:ipv4-address-no-zone;
          default "0.0.0.0";
          description
            "Local IP address that the client uses for Layer 3 unicast negotiation.";
        }
        leaf req-ann-interval {
          when "(../device-type='none' or ../device-type='client' and ../enable='true')" {
            tailf:xpath-root 3;
          }
          type int32 {
            range "7..14";
          }
          default "11";
          description
            "Interval at which Announce packets are sent by the client to the server. The calculation formula for the interval in seconds is (2 to the power of interval/1024)s.";
        }
        leaf req-sync-interval {
          when "(../device-type='none' or ../device-type='client' and ../enable='true')" {
            tailf:xpath-root 3;
          }
          type int32 {
            range "3..14";
          }
          default "3";
          description
            "Interval at which Sync packets are sent by the client to the server. The calculation formula for the interval in seconds is (2 to the power of interval/1024)s.";
        }
        leaf req-dly-resp-interval {
          when "(../device-type='none' or ../device-type='client' and ../enable='true')" {
            tailf:xpath-root 3;
          }
          type int32 {
            range "3..14";
          }
          default "3";
          description
            "Interval at which DelayResp packets are sent by the client to the server. The calculation formula for the interval in seconds is (2 to the power of interval/1024)s.";
        }
        leaf ann-recv-timeout {
          when "(../device-type='none' or ../device-type='client' and ../enable='true')" {
            tailf:xpath-root 3;
          }
          type int32 {
            range "2..255";
          }
          default "3";
          description
            "Number of times Announce packet receiving times out on the client.";
        }
        leaf ann-duration {
          when "(../device-type='none' or ../device-type='client' and ../enable='true')" {
            tailf:xpath-root 3;
          }
          type int32 {
            range "60..1000";
          }
          units "s";
          default "300";
          description
            "Duration for continuously sending Announce packets.";
        }
        leaf sync-duration {
          when "(../device-type='none' or ../device-type='client' and ../enable='true')" {
            tailf:xpath-root 3;
          }
          type int32 {
            range "60..1000";
          }
          units "s";
          default "300";
          description
            "Duration in which Sync packets are continuously sent.";
        }
        leaf dly-resp-duration {
          when "(../device-type='none' or ../device-type='client' and ../enable='true')" {
            tailf:xpath-root 3;
          }
          type int32 {
            range "60..1000";
          }
          units "s";
          default "300";
          description
            "Duration in which Delay-Resp packets are continuously sent.";
        }
        // NCS drop config false leaf 'trace-source'
        leaf freq-profile {
          when "(../enable='true')" {
            tailf:xpath-root 3;
          }
          type ptpa-freq-profile;
          default "part";
          description
            "By default, ITU-T G.8265.1 is partially supported. You can configure total support for G.8265.1 or G.8275.2.";
        }
        leaf vpn-instance {
          when "(../enable='true')" {
            tailf:xpath-root 3;
          }
          type leafref {
            path "/ncs:devices/ncs:device/ncs:config/ni:network-instance/ni:instances/ni:instance/ni:name" {
              tailf:xpath-root 3;
            }
          }
          description
            "Configure or cancel the VPN instance name bound to the Loopback interface.";
        }
        leaf hop-by-hop-mode {
          when "((../device-type='none' or ../device-type='client') and ../enable='true')" {
            tailf:xpath-root 3;
          }
          type boolean;
          must "../enable='true' and ((../hop-by-hop-mode='true' and (((../nego-mode='atr' or ../nego-mode='none') and ../device-type='client') or (../nego-mode='none' and ../device-type='none')) and ../freq-profile='timeprofile') or ((../device-type='none' or ../device-type='client') and ../hop-by-hop-mode='false'))" {
            tailf:xpath-root 3;
          }
          default "false";
          description
            "Enable/disable 1588 ATR clock hop-by-hop mode.";
        }
      }
      container ptpa-servers {
        when "(../ptpa-common/device-type='client' and ../ptpa-common/enable='true')" {
          tailf:xpath-root 3;
        }
        description
          "List of configure information about the remote server on which negotiation with the client is established.";
        list ptpa-server {
          ext:generated-by "system";
          ext:operation-exclude "create|delete";
          key "server-index";
          unique "server-ip";
          description
            "Configure information about the remote server on which negotiation with the client is established.";
          leaf server-index {
            type server-index;
            description
              "Index of the server, which is used to identify a server.";
          }
          leaf server-ip {
            type inet:ipv4-address-no-zone;
            must "../server-ip!='0.0.0.0'" {
              tailf:xpath-root 3;
            }
            description
              "IP address of the server.";
          }
          // NCS drop config false leaf 'is-cur-trace-source'
          // NCS drop config false leaf 'clock-id'
          // NCS drop config false leaf 'nego-state'
          // NCS drop config false leaf 'error-reason'
          // NCS drop config false container 'bmc-attr'
          // NCS drop config false container 'bmca-attr'
          // NCS drop config false leaf 'parent-clockid'
          // NCS drop config false leaf 'parent-port-num'
          // NCS drop config false leaf 'two-step-flag'
          // NCS drop config false leaf 'steps-removed'
          // NCS drop config false leaf 'time-scale'
          // NCS drop config false leaf 'offset-scaled'
          // NCS drop config false leaf 'time-traceable'
          // NCS drop config false leaf 'frequency-traceable'
          // NCS drop config false leaf 'loss-announce'
          // NCS drop config false leaf 'loss-sync'
          // NCS drop config false leaf 'loss-followup'
          // NCS drop config false leaf 'loss-resp'
          // NCS drop config false container 'server-pkt-statistics'
          container asym-correction {
            description
              "Configure information about asymmetric delay correction.";
            leaf asym-corr-flag {
              type ptp-sign-flag;
              default "negative";
              description
                "Asymmetric delay correction mode, including positive correction and negative correction.";
            }
            leaf asym-corr-value {
              type uint32 {
                range "0..2000000";
              }
              units "ns";
              description
                "Asymmetric delay correction value.";
            }
            // NCS drop config false leaf correction
          }
        }
      }
      // NCS drop config false container 'ptpa-clients'
    }
  }
  augment "/ncs:devices/ncs:device/ncs:live-status" {
    container clocksync-ptpadapt {
      tailf:ncs-device-type "netconf";
      tailf:display-when "not(../../ncs:module) or ../../ncs:module[ncs:name='huawei-clocksync-ptpadapt'] or (../../ncs:live-status-protocol[not(ncs:capability)]) or (../../ncs:live-status-protocol/ncs:capability/ncs:module[.='huawei-clocksync-ptpadapt'])";
      description
        "Module of adaptive clock.";
      container ptpa-common {
        description
          "Configure basic information of adaptive clock.";
        leaf enable {
          type boolean;
          // NCS drop default statement
          description
            "Enable/disable adaptive clock. When the master does not support PTP, the router that enables adaptive clock can retrieve clock information from the server's PTP packets.";
        }
        leaf device-type {
          // NCS drop when statement
          type live_ncs_ptpa-device-type;
          // NCS drop default statement
          description
            "Configure the router to work in client or server mode.";
        }
        leaf nego-mode {
          // NCS drop when statement
          type live_ncs_ptpa-nego-mode;
          // NCS drop must statement
          // NCS drop default statement
          description
            "Enable or disable PTP adaptive ACR/ATR unicast negotiation.";
        }
        leaf dscp {
          // NCS drop when statement
          type int32 {
            range "0..63";
          }
          // NCS drop default statement
          description
            "Configure QoS priority of ptp-adaptive packet.";
        }
        leaf domain {
          // NCS drop when statement
          type uint32 {
            range "0..255";
          }
          // NCS drop default statement
          description
            "Configure ptp-adaptive device domain. While profile is configured as 'Support Partly', the default domain value is 0 and domain range is <0-255>. While profile is configured as 'Partly', the default domain value is 4 and domain range is <4-43>.While profile is configured as 'Time Synchronization Protocol', the default domain value is 44 and domain range is <44-63>.";
        }
        leaf local-ip {
          // NCS drop when statement
          type inet:ipv4-address-no-zone;
          // NCS drop default statement
          description
            "Local IP address that the client uses for Layer 3 unicast negotiation.";
        }
        leaf req-ann-interval {
          // NCS drop when statement
          type int32 {
            range "7..14";
          }
          // NCS drop default statement
          description
            "Interval at which Announce packets are sent by the client to the server. The calculation formula for the interval in seconds is (2 to the power of interval/1024)s.";
        }
        leaf req-sync-interval {
          // NCS drop when statement
          type int32 {
            range "3..14";
          }
          // NCS drop default statement
          description
            "Interval at which Sync packets are sent by the client to the server. The calculation formula for the interval in seconds is (2 to the power of interval/1024)s.";
        }
        leaf req-dly-resp-interval {
          // NCS drop when statement
          type int32 {
            range "3..14";
          }
          // NCS drop default statement
          description
            "Interval at which DelayResp packets are sent by the client to the server. The calculation formula for the interval in seconds is (2 to the power of interval/1024)s.";
        }
        leaf ann-recv-timeout {
          // NCS drop when statement
          type int32 {
            range "2..255";
          }
          // NCS drop default statement
          description
            "Number of times Announce packet receiving times out on the client.";
        }
        leaf ann-duration {
          // NCS drop when statement
          type int32 {
            range "60..1000";
          }
          units "s";
          // NCS drop default statement
          description
            "Duration for continuously sending Announce packets.";
        }
        leaf sync-duration {
          // NCS drop when statement
          type int32 {
            range "60..1000";
          }
          units "s";
          // NCS drop default statement
          description
            "Duration in which Sync packets are continuously sent.";
        }
        leaf dly-resp-duration {
          // NCS drop when statement
          type int32 {
            range "60..1000";
          }
          units "s";
          // NCS drop default statement
          description
            "Duration in which Delay-Resp packets are continuously sent.";
        }
        leaf trace-source {
          type live_ncs_ptpa-trace-source;
          description
            "Current tracing source of the client.";
        }
        leaf freq-profile {
          // NCS drop when statement
          type live_ncs_ptpa-freq-profile;
          // NCS drop default statement
          description
            "By default, ITU-T G.8265.1 is partially supported. You can configure total support for G.8265.1 or G.8275.2.";
        }
        leaf vpn-instance {
          // NCS drop when statement
          type leafref {
            path "/ncs:devices/ncs:device/ncs:live-status/ni:network-instance/ni:instances/ni:instance/ni:name" {
              tailf:xpath-root 3;
            }
          }
          description
            "Configure or cancel the VPN instance name bound to the Loopback interface.";
        }
        leaf hop-by-hop-mode {
          // NCS drop when statement
          type boolean;
          // NCS drop must statement
          // NCS drop default statement
          description
            "Enable/disable 1588 ATR clock hop-by-hop mode.";
        }
      }
      container ptpa-servers {
        // NCS drop when statement
        description
          "List of configure information about the remote server on which negotiation with the client is established.";
        list ptpa-server {
          ext:generated-by "system";
          ext:operation-exclude "create|delete";
          key "server-index";
          unique "server-ip";
          description
            "Configure information about the remote server on which negotiation with the client is established.";
          leaf server-index {
            type live_ncs_server-index;
            description
              "Index of the server, which is used to identify a server.";
          }
          leaf server-ip {
            type inet:ipv4-address-no-zone;
            // NCS drop must statement
            description
              "IP address of the server.";
          }
          leaf is-cur-trace-source {
            type boolean;
            // NCS drop default statement
            description
              "Current tracing source of the client.";
          }
          leaf clock-id {
            type string {
              length "1..50";
            }
            description
              "ID of the clock source on the server side.";
          }
          leaf nego-state {
            type live_ncs_ptpa-nego-state;
            description
              "State negotiated with server.";
          }
          leaf error-reason {
            type live_ncs_ptpa-nego-error-reason;
            description
              "Cause of the clock negotiation failure.";
          }
          container bmc-attr {
            description
              "Statistics of PTP adaptive clock attributes when the PTP frequency profile is not configured.";
            leaf priority1 {
              type uint32;
              // NCS drop default statement
              description
                "Priority1 of the adaptive clock server.";
            }
            leaf priority2 {
              type uint32;
              // NCS drop default statement
              description
                "Priority2 of the adaptive clock server.";
            }
            leaf clock-class {
              type uint32;
              // NCS drop default statement
              description
                "Quality level of the server clock.";
            }
            leaf clock-accuracy {
              type uint32;
              // NCS drop default statement
              description
                "Accuracy of the clock server.";
            }
            leaf time-source {
              type live_ncs_ptp-time-source;
              // NCS drop default statement
              description
                "Clock source type of the adaptive clock server.";
            }
            leaf ptp-sync-uncertain {
              type boolean;
              // NCS drop default statement
              description
                "Synchronization uncertain status of the adaptive clock source.";
            }
          }
          container bmca-attr {
            description
              "Statistics of PTP adaptive attributes when we configure ptp frequency profile.";
            leaf server-ssm {
              type live_ncs_phy-ssm-level;
              // NCS drop default statement
              description
                "SSM level converted from the accuracy of clock signals received by the server.";
            }
            leaf server-priority {
              type uint32;
              // NCS drop default statement
              description
                "Priority of a server. Server1's priority is 1, and Server2's priority is 2.";
            }
            leaf server-ptsf {
              type live_ncs_ptpa-server-ptsf-state;
              // NCS drop default statement
              description
                "Packet timing signals fail.";
            }
          }
          leaf parent-clockid {
            type string {
              length "1..50";
            }
            description
              "Clock ID of the clock server.";
          }
          leaf parent-port-num {
            type uint32;
            description
              "Port number of the clock server.";
          }
          leaf two-step-flag {
            type boolean;
            // NCS drop default statement
            description
              "Two-step flag of clock source Sync packets.";
          }
          leaf steps-removed {
            type uint32;
            description
              "Number of hops to the clock source.";
          }
          leaf time-scale {
            type uint32;
            description
              "Time scale of the clock source.";
          }
          leaf offset-scaled {
            type uint32;
            description
              "Stability of the clock source.";
          }
          leaf time-traceable {
            type boolean;
            // NCS drop default statement
            description
              "Time tracing status at the server side.";
          }
          leaf frequency-traceable {
            type boolean;
            // NCS drop default statement
            description
              "Frequency tracing status at the server side.";
          }
          leaf loss-announce {
            type boolean;
            // NCS drop default statement
            description
              "Announce packet loss status at the server side.";
          }
          leaf loss-sync {
            type boolean;
            // NCS drop default statement
            description
              "Sync packet loss status at the server side.";
          }
          leaf loss-followup {
            type boolean;
            // NCS drop default statement
            description
              "Follow_Up packet loss status at the server side.";
          }
          leaf loss-resp {
            type boolean;
            // NCS drop default statement
            description
              "Resp packet loss status at the server side.";
          }
          container server-pkt-statistics {
            description
              "Client-side packet statistics.";
            leaf rev-signal {
              type uint32;
              description
                "Number of received signaling packets.";
            }
            leaf rev-announce {
              type uint32;
              description
                "Number of received Announce packets.";
            }
            leaf rev-sync {
              type uint32;
              description
                "Number of received Sync packets.";
            }
            leaf rev-delay-resp {
              type uint32;
              description
                "Number of received Delay_Resp packets.";
            }
            leaf rev-followup {
              type uint32;
              description
                "Number of received Follow_Up packets.";
            }
            leaf send-signal {
              type uint32;
              description
                "Number of sent signaling packets.";
            }
            leaf send-delay-req {
              type uint32;
              description
                "Number of sent Delay_Req packets.";
            }
            leaf discard-signal {
              type uint32;
              description
                "Number of dropped signaling packets.";
            }
            leaf discard-announce {
              type uint32;
              description
                "Number of dropped Announce packets.";
            }
            leaf discard-sync {
              type uint32;
              description
                "Number of dropped Sync packets.";
            }
            leaf discard-delay-resp {
              type uint32;
              description
                "Number of dropped Delay_Resp packets.";
            }
            leaf discard-followup {
              type uint32;
              description
                "Number of dropped Follow_Up packets.";
            }
          }
          container asym-correction {
            description
              "Configure information about asymmetric delay correction.";
            leaf asym-corr-flag {
              type live_ncs_ptp-sign-flag;
              // NCS drop default statement
              description
                "Asymmetric delay correction mode, including positive correction and negative correction.";
            }
            leaf asym-corr-value {
              type uint32 {
                range "0..2000000";
              }
              units "ns";
              description
                "Asymmetric delay correction value.";
            }
            leaf correction {
              type int32;
              // NCS drop default statement
              description
                "Automatically measured asymmetric delay correction value. This is a 1588 ATR feature. When link asymmetry exists, the asymmetric delay correction value needs to be measured manually.";
            }
          }
        }
      }
      container ptpa-clients {
        description
          "List of statistics of adaptive clock client information.";
        list ptpa-client {
          key "client-id";
          description
            "Statistics of adaptive clock client information.";
          leaf client-id {
            type uint32;
            description
              "Index of a client, which is used to identify the client.";
          }
          leaf client-ip {
            type inet:ipv4-address-no-zone;
            description
              "Client IP address.";
          }
          leaf clockid {
            type string {
              length "1..50";
            }
            description
              "ID of the clock source on the client side.";
          }
          leaf nego-mode {
            type live_ncs_ptpa-nego-mode;
            description
              "Negotiation mode between server and client.";
          }
          leaf ann-interval {
            type string {
              length "1..50";
            }
            description
              "Interval at which the server sends Announce packets to the client.";
          }
          leaf sync-interval {
            type string {
              length "1..50";
            }
            description
              "Interval at which Sync packets are sent by the server to the client.";
          }
          leaf dly-resp-interval {
            type string {
              length "1..50";
            }
            description
              "Interval at which Delay-Resp packets are sent from the server to the client.";
          }
          leaf ann-duration {
            type int32 {
              range "60..1000";
            }
            // NCS drop default statement
            description
              "Duration in which the server continuously sends Announce packets to the client.";
          }
          leaf sync-duration {
            type int32 {
              range "60..1000";
            }
            // NCS drop default statement
            description
              "Duration in which Sync packets are continuously sent by the server to the client.";
          }
          leaf dly-resp-duration {
            type int32 {
              range "60..1000";
            }
            // NCS drop default statement
            description
              "Duration in which Delay-Resp packets are continuously sent by the server to the client.";
          }
          container client-pkt-statistics {
            description
              "Statistics of various packets sent from the server.";
            leaf rev-signal {
              type uint32;
              description
                "Statistics about the Signaling packets received by the server.";
            }
            leaf rev-delay-req {
              type uint32;
              description
                "Statistics about the Delay_Resp packets received by the server.";
            }
            leaf send-signal {
              type uint32;
              description
                "Statistics about the Signaling packets sent by the server.";
            }
            leaf send-announce {
              type uint32;
              description
                "Statistics about the Announce packets sent by the server.";
            }
            leaf send-sync {
              type uint32;
              description
                "Statistics about the Sync packets sent by the server.";
            }
            leaf send-delay-resp {
              type uint32;
              description
                "Statistics about the Delay_Resp packets sent by the server.";
            }
            leaf discard-signal {
              type uint32;
              description
                "Number of signaling packets dropped on the server.";
            }
            leaf discard-delay-req {
              type uint32;
              description
                "Number of Delay_Req packets dropped on the server.";
            }
          }
        }
      }
    }
  }
  augment "/ncs:devices/ncs:template/ncs:ned-id/ncs:config" {
    container clocksync-ptpadapt {
      description
        "Module of adaptive clock.";
      container ptpa-common {
        description
          "Configure basic information of adaptive clock.";
        leaf enable {
          type string;
          // NCS drop default statement
          description
            "Enable/disable adaptive clock. When the master does not support PTP, the router that enables adaptive clock can retrieve clock information from the server's PTP packets.";
        }
        leaf device-type {
          // NCS drop when statement
          type ncs_template_ptpa-device-type;
          // NCS drop default statement
          description
            "Configure the router to work in client or server mode.";
        }
        leaf nego-mode {
          // NCS drop when statement
          type ncs_template_ptpa-nego-mode;
          // NCS drop must statement
          // NCS drop default statement
          description
            "Enable or disable PTP adaptive ACR/ATR unicast negotiation.";
        }
        leaf dscp {
          // NCS drop when statement
          type string;
          // NCS drop default statement
          description
            "Configure QoS priority of ptp-adaptive packet.";
        }
        leaf domain {
          // NCS drop when statement
          type string;
          // NCS drop default statement
          description
            "Configure ptp-adaptive device domain. While profile is configured as 'Support Partly', the default domain value is 0 and domain range is <0-255>. While profile is configured as 'Partly', the default domain value is 4 and domain range is <4-43>.While profile is configured as 'Time Synchronization Protocol', the default domain value is 44 and domain range is <44-63>.";
        }
        leaf local-ip {
          // NCS drop when statement
          type string;
          // NCS drop default statement
          description
            "Local IP address that the client uses for Layer 3 unicast negotiation.";
        }
        leaf req-ann-interval {
          // NCS drop when statement
          type string;
          // NCS drop default statement
          description
            "Interval at which Announce packets are sent by the client to the server. The calculation formula for the interval in seconds is (2 to the power of interval/1024)s.";
        }
        leaf req-sync-interval {
          // NCS drop when statement
          type string;
          // NCS drop default statement
          description
            "Interval at which Sync packets are sent by the client to the server. The calculation formula for the interval in seconds is (2 to the power of interval/1024)s.";
        }
        leaf req-dly-resp-interval {
          // NCS drop when statement
          type string;
          // NCS drop default statement
          description
            "Interval at which DelayResp packets are sent by the client to the server. The calculation formula for the interval in seconds is (2 to the power of interval/1024)s.";
        }
        leaf ann-recv-timeout {
          // NCS drop when statement
          type string;
          // NCS drop default statement
          description
            "Number of times Announce packet receiving times out on the client.";
        }
        leaf ann-duration {
          // NCS drop when statement
          type string;
          units "s";
          // NCS drop default statement
          description
            "Duration for continuously sending Announce packets.";
        }
        leaf sync-duration {
          // NCS drop when statement
          type string;
          units "s";
          // NCS drop default statement
          description
            "Duration in which Sync packets are continuously sent.";
        }
        leaf dly-resp-duration {
          // NCS drop when statement
          type string;
          units "s";
          // NCS drop default statement
          description
            "Duration in which Delay-Resp packets are continuously sent.";
        }
        // NCS drop config false leaf 'trace-source'
        leaf freq-profile {
          // NCS drop when statement
          type ncs_template_ptpa-freq-profile;
          // NCS drop default statement
          description
            "By default, ITU-T G.8265.1 is partially supported. You can configure total support for G.8265.1 or G.8275.2.";
        }
        leaf vpn-instance {
          // NCS drop when statement
          type string;
          description
            "Configure or cancel the VPN instance name bound to the Loopback interface.";
        }
        leaf hop-by-hop-mode {
          // NCS drop when statement
          type string;
          // NCS drop must statement
          // NCS drop default statement
          description
            "Enable/disable 1588 ATR clock hop-by-hop mode.";
        }
      }
      container ptpa-servers {
        // NCS drop when statement
        description
          "List of configure information about the remote server on which negotiation with the client is established.";
        list ptpa-server {
          // NCS patched for predictable order
          ordered-by user;
          ext:generated-by "system";
          ext:operation-exclude "create|delete";
          key "server-index";
          unique "server-ip";
          description
            "Configure information about the remote server on which negotiation with the client is established.";
          leaf server-index {
            type ncs_template_server-index;
            description
              "Index of the server, which is used to identify a server.";
          }
          leaf server-ip {
            type string;
            // NCS drop must statement
            description
              "IP address of the server.";
          }
          // NCS drop config false leaf 'is-cur-trace-source'
          // NCS drop config false leaf 'clock-id'
          // NCS drop config false leaf 'nego-state'
          // NCS drop config false leaf 'error-reason'
          // NCS drop config false container 'bmc-attr'
          // NCS drop config false container 'bmca-attr'
          // NCS drop config false leaf 'parent-clockid'
          // NCS drop config false leaf 'parent-port-num'
          // NCS drop config false leaf 'two-step-flag'
          // NCS drop config false leaf 'steps-removed'
          // NCS drop config false leaf 'time-scale'
          // NCS drop config false leaf 'offset-scaled'
          // NCS drop config false leaf 'time-traceable'
          // NCS drop config false leaf 'frequency-traceable'
          // NCS drop config false leaf 'loss-announce'
          // NCS drop config false leaf 'loss-sync'
          // NCS drop config false leaf 'loss-followup'
          // NCS drop config false leaf 'loss-resp'
          // NCS drop config false container 'server-pkt-statistics'
          container asym-correction {
            description
              "Configure information about asymmetric delay correction.";
            leaf asym-corr-flag {
              type ncs_template_ptp-sign-flag;
              // NCS drop default statement
              description
                "Asymmetric delay correction mode, including positive correction and negative correction.";
            }
            leaf asym-corr-value {
              type string;
              units "ns";
              description
                "Asymmetric delay correction value.";
            }
            // NCS drop config false leaf correction
          }
        }
      }
      // NCS drop config false container 'ptpa-clients'
    }
  }
  augment "/ncs:devices/ncs:template/ncs:ned-id/ncs:config/ifm:ifm/ifm:interfaces/ifm:interface" {
    description
      "Adaptive clock synchronization ports.";
    container ptpa-ports {
      description
        "Configure adaptive clock synchronization ports information.";
      container ptpa-port {
        description
          "Configure adaptive synchronization port information.";
        leaf ptp-atr-en {
          type string;
          // NCS drop default statement
          description
            "Enable/disable ATR for a port.";
        }
      }
    }
  }
  augment "/ncs:devices/ncs:device/ncs:live-status/ifm:ifm/ifm:interfaces/ifm:interface" {
    description
      "Adaptive clock synchronization ports.";
    container ptpa-ports {
      tailf:ncs-device-type "netconf";
      tailf:display-when "not(../../../../../ncs:module) or ../../../../../ncs:module[ncs:name='huawei-clocksync-ptpadapt'] or (../../../../../ncs:live-status-protocol[not(ncs:capability)]) or (../../../../../ncs:live-status-protocol/ncs:capability/ncs:module[.='huawei-clocksync-ptpadapt'])";
      description
        "Configure adaptive clock synchronization ports information.";
      container ptpa-port {
        description
          "Configure adaptive synchronization port information.";
        leaf ptp-atr-en {
          type boolean;
          // NCS drop default statement
          description
            "Enable/disable ATR for a port.";
        }
      }
    }
  }
  augment "/ncs:devices/ncs:device/ncs:config/ifm:ifm/ifm:interfaces/ifm:interface" {
    description
      "Adaptive clock synchronization ports.";
    container ptpa-ports {
      tailf:ncs-device-type "netconf";
      tailf:display-when "not(../../../../../ncs:module) or ../../../../../ncs:module[ncs:name='huawei-clocksync-ptpadapt']";
      description
        "Configure adaptive clock synchronization ports information.";
      container ptpa-port {
        description
          "Configure adaptive synchronization port information.";
        leaf ptp-atr-en {
          type boolean;
          default "false";
          description
            "Enable/disable ATR for a port.";
        }
      }
    }
  }
}
