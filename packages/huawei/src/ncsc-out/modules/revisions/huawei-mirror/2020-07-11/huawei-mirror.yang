module huawei-mirror {
  // Generated by yanger -t ncs
  tailf:mount-id "huawei-nc-1.0:huawei-nc-1.0";
  tailf:ncs-device-type "netconf";

  namespace "urn:huawei:yang:huawei-mirror";
  prefix mirror;

  import huawei-qos {
    prefix qos;
  }
  import huawei-devm {
    prefix devm;
  }
  import huawei-extension {
    prefix ext;
  }
  import huawei-ifm {
    prefix ifm;
  }
  import huawei-pub-type {
    prefix pub-type;
  }
  import huawei-bd {
    prefix bd;
  }
  import ietf-inet-types {
    prefix inet;
  }
  import huawei-ethernet {
    prefix ethernet;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Network monitor.";

  revision 2020-07-11 {
    description
      "Optimization constraints.";
    reference "Huawei private.";
  }
  revision 2020-02-25 {
    description
      "Optimization constraints.";
    reference "Huawei private.";
  }
  revision 2020-01-19 {
    description
      "Optimization constraints.";
    reference "Huawei private.";
  }
  revision 2020-01-14 {
    description
      "Add global observes container.";
    reference "Huawei private.";
  }
  revision 2019-12-24 {
    description
      "The modifications in the schema file are synchronized to the YANG file.";
    reference "Huawei private.";
  }
  revision 2019-12-13 {
    description
      "The modifications in the schema file are synchronized to the YANG file.";
    reference "Huawei private.";
  }
  revision 2019-11-21 {
    description
      "The modifications in the schema file are synchronized to the YANG file.";
    reference "Huawei private.";
  }
  revision 2019-10-24 {
    description
      "The modifications in the schema file are synchronized to the YANG file.";
    reference "Huawei private.";
  }
  revision 2019-05-04 {
    description
      "Initial revision.";
    reference "Huawei private.";
  }
  ext:task-name "mirror";

  typedef ncs_template_direction-type {
    type string;
    description
      "Direction.";
  }

  typedef ncs_template_without-filter {
    type string;
    description
      "Disable observe filter in observe port.";
  }

  typedef ncs_template_with-linklayer-header {
    type string;
    description
      "With linklayer header observe filter in observe port.";
  }

  typedef ncs_template_pop-label {
    type string;
    description
      "Specify POP MPLS label.";
  }

  typedef ncs_template_mirror-type {
    type string;
    description
      "Mirror type.";
  }

  typedef ncs_template_query-direction-type {
    type string;
    description
      "Direction type.";
  }

  typedef ncs_template_identifier-type {
    type string;
    description
      "Identifier type.";
  }

  typedef ncs_rpc_notif_direction-type {
    type enumeration {
      enum "inbound" {
        value 0;
        description
          "Inbound.";
      }
      enum "outbound" {
        value 1;
        description
          "Outbound.";
      }
    }
    description
      "Direction.";
  }

  typedef ncs_rpc_notif_without-filter {
    type enumeration {
      enum "true" {
        value 1;
        description
          "Enable.";
      }
      enum "false" {
        value 0;
        description
          "Disable.";
      }
    }
    description
      "Disable observe filter in observe port.";
  }

  typedef ncs_rpc_notif_with-linklayer-header {
    type enumeration {
      enum "true" {
        value 1;
        description
          "Enable.";
      }
      enum "false" {
        value 0;
        description
          "Disable.";
      }
    }
    description
      "With linklayer header observe filter in observe port.";
  }

  typedef ncs_rpc_notif_pop-label {
    type enumeration {
      enum "one" {
        value 1;
        description
          "One POP.";
      }
      enum "two" {
        value 2;
        description
          "Two POP.";
      }
      enum "all" {
        value 3;
        description
          "All POP.";
      }
    }
    description
      "Specify POP MPLS label.";
  }

  typedef ncs_rpc_notif_mirror-type {
    type enumeration {
      enum "port" {
        value 0;
        description
          "Port.";
      }
      enum "policy" {
        value 1;
        description
          "Traffic policy.";
      }
    }
    description
      "Mirror type.";
  }

  typedef ncs_rpc_notif_query-direction-type {
    type enumeration {
      enum "in" {
        value 0;
        description
          "In.";
      }
      enum "out" {
        value 1;
        description
          "Out.";
      }
      enum "in-out" {
        value 2;
        description
          "In-Out.";
      }
    }
    description
      "Direction type.";
  }

  typedef ncs_rpc_notif_identifier-type {
    type enumeration {
      enum "none" {
        value 0;
        description
          "None.";
      }
      enum "pe-vid" {
        value 1;
        description
          "PE-VID.";
      }
      enum "ce-vid" {
        value 2;
        description
          "CE-VID.";
      }
      enum "pe-ce-vid" {
        value 3;
        description
          "PE-CE-VID.";
      }
    }
    description
      "Identifier type.";
  }

  typedef live_ncs_direction-type {
    type enumeration {
      enum "inbound" {
        value 0;
        description
          "Inbound.";
      }
      enum "outbound" {
        value 1;
        description
          "Outbound.";
      }
    }
    description
      "Direction.";
  }

  typedef live_ncs_without-filter {
    type enumeration {
      enum "true" {
        value 1;
        description
          "Enable.";
      }
      enum "false" {
        value 0;
        description
          "Disable.";
      }
    }
    description
      "Disable observe filter in observe port.";
  }

  typedef live_ncs_with-linklayer-header {
    type enumeration {
      enum "true" {
        value 1;
        description
          "Enable.";
      }
      enum "false" {
        value 0;
        description
          "Disable.";
      }
    }
    description
      "With linklayer header observe filter in observe port.";
  }

  typedef live_ncs_pop-label {
    type enumeration {
      enum "one" {
        value 1;
        description
          "One POP.";
      }
      enum "two" {
        value 2;
        description
          "Two POP.";
      }
      enum "all" {
        value 3;
        description
          "All POP.";
      }
    }
    description
      "Specify POP MPLS label.";
  }

  typedef live_ncs_mirror-type {
    type enumeration {
      enum "port" {
        value 0;
        description
          "Port.";
      }
      enum "policy" {
        value 1;
        description
          "Traffic policy.";
      }
    }
    description
      "Mirror type.";
  }

  typedef live_ncs_query-direction-type {
    type enumeration {
      enum "in" {
        value 0;
        description
          "In.";
      }
      enum "out" {
        value 1;
        description
          "Out.";
      }
      enum "in-out" {
        value 2;
        description
          "In-Out.";
      }
    }
    description
      "Direction type.";
  }

  typedef live_ncs_identifier-type {
    type enumeration {
      enum "none" {
        value 0;
        description
          "None.";
      }
      enum "pe-vid" {
        value 1;
        description
          "PE-VID.";
      }
      enum "ce-vid" {
        value 2;
        description
          "CE-VID.";
      }
      enum "pe-ce-vid" {
        value 3;
        description
          "PE-CE-VID.";
      }
    }
    description
      "Identifier type.";
  }

  typedef direction-type {
    type enumeration {
      enum "inbound" {
        value 0;
        description
          "Inbound.";
      }
      enum "outbound" {
        value 1;
        description
          "Outbound.";
      }
    }
    description
      "Direction.";
  }

  typedef without-filter {
    type enumeration {
      enum "true" {
        value 1;
        description
          "Enable.";
      }
      enum "false" {
        value 0;
        description
          "Disable.";
      }
    }
    description
      "Disable observe filter in observe port.";
  }

  typedef with-linklayer-header {
    type enumeration {
      enum "true" {
        value 1;
        description
          "Enable.";
      }
      enum "false" {
        value 0;
        description
          "Disable.";
      }
    }
    description
      "With linklayer header observe filter in observe port.";
  }

  typedef pop-label {
    type enumeration {
      enum "one" {
        value 1;
        description
          "One POP.";
      }
      enum "two" {
        value 2;
        description
          "Two POP.";
      }
      enum "all" {
        value 3;
        description
          "All POP.";
      }
    }
    description
      "Specify POP MPLS label.";
  }

  typedef mirror-type {
    type enumeration {
      enum "port" {
        value 0;
        description
          "Port.";
      }
      enum "policy" {
        value 1;
        description
          "Traffic policy.";
      }
    }
    description
      "Mirror type.";
  }

  typedef query-direction-type {
    type enumeration {
      enum "in" {
        value 0;
        description
          "In.";
      }
      enum "out" {
        value 1;
        description
          "Out.";
      }
      enum "in-out" {
        value 2;
        description
          "In-Out.";
      }
    }
    description
      "Direction type.";
  }

  typedef identifier-type {
    type enumeration {
      enum "none" {
        value 0;
        description
          "None.";
      }
      enum "pe-vid" {
        value 1;
        description
          "PE-VID.";
      }
      enum "ce-vid" {
        value 2;
        description
          "CE-VID.";
      }
      enum "pe-ce-vid" {
        value 3;
        description
          "PE-CE-VID.";
      }
    }
    description
      "Identifier type.";
  }

  augment "/ncs:devices/ncs:device/ncs:config" {
    container mirror {
      tailf:ncs-device-type "netconf";
      tailf:display-when "not(../../ncs:module) or ../../ncs:module[ncs:name='huawei-mirror']";
      description
        "Mirror.";
      container statistic-enable {
        presence "create statistic-enable";
        description
          "Enable/disable mirror statistic.";
      }
      container instances {
        description
          "List of mirror instance.";
        list instance {
          key "instance-name";
          description
            "Configure mirror instance.";
          leaf instance-name {
            type string {
              length "1..31";
            }
            description
              "Mirror instance name.";
          }
          container instance-slice {
            presence "create instance mirror slice-size";
            description
              "Enable/disable mirror instance slice.";
            leaf slice-size {
              type uint32 {
                range "64..9600";
              }
              units "Byte";
              mandatory true;
              description
                "Length of packet.";
            }
          }
          container instance-car {
            must '(not(./pir) and not(./pbs)) or (./pbs)' {
              tailf:xpath-root 3;
            }
            must 'not(./pir) or ./pir>=./cir' {
              tailf:xpath-root 3;
            }
            presence "create instance-car";
            description
              "Enable/disable mirror instance car.";
            leaf cir {
              type uint32 {
                range "0..4294967295";
              }
              units "kbit/s";
              mandatory true;
              description
                "Committed information rate.";
            }
            leaf pir {
              type uint32 {
                range "1..4294967295";
              }
              units "kbit/s";
              description
                "Peak information rate.";
            }
            leaf cbs {
              type uint32 {
                range "0..4294967295";
              }
              units "Byte";
              mandatory true;
              description
                "Committed burst size, which has dynamic defaults.";
            }
            leaf pbs {
              type uint32 {
                range "0..4294967295";
              }
              units "Byte";
              description
                "Peak burst size, which has dynamic defaults.";
            }
          }
        }
      }
      container observe-user-define-acls {
        description
          "List of observe user-defined acl.";
        list observe-user-define-acl {
          must 'count(./offsets/offset)>0' {
            tailf:xpath-root 3;
          }
          key "filter-id";
          max-elements 8;
          description
            "Configure observe user-defined acl.";
          leaf filter-id {
            type uint8 {
              range "1..8";
            }
            description
              "Filter index.";
          }
          container offsets {
            description
              "List of observe user-defined offset.";
            list offset {
              key "config-index";
              unique "offset-value";
              min-elements 1;
              max-elements 4;
              description
                "Configure observe user-defined offset.";
              leaf config-index {
                type uint32 {
                  range "1..4";
                }
                description
                  "Offset index. The config-index values in the offset must start at 1 and be consecutive.";
              }
              leaf offset-value {
                type uint32 {
                  range "0..114";
                }
                mandatory true;
                description
                  "Offset.";
              }
              leaf payload-value {
                type pub-type:hex-binary;
                mandatory true;
                description
                  "Payload value, Value range HEX[0,ffffffff].";
              }
              leaf payload-mask {
                type pub-type:hex-binary;
                mandatory true;
                description
                  "Payload mask, Value range HEX[0,ffffffff].";
              }
            }
          }
        }
      }
      // NCS drop config false container 'query-ports'
      // NCS drop config false container 'query-traffic-policy-ports'
    }
  }
  augment "/ncs:devices/ncs:device/ncs:live-status" {
    container mirror {
      tailf:ncs-device-type "netconf";
      tailf:display-when "not(../../ncs:module) or ../../ncs:module[ncs:name='huawei-mirror'] or (../../ncs:live-status-protocol[not(ncs:capability)]) or (../../ncs:live-status-protocol/ncs:capability/ncs:module[.='huawei-mirror'])";
      description
        "Mirror.";
      container statistic-enable {
        presence "create statistic-enable";
        description
          "Enable/disable mirror statistic.";
      }
      container instances {
        description
          "List of mirror instance.";
        list instance {
          key "instance-name";
          description
            "Configure mirror instance.";
          leaf instance-name {
            type string {
              length "1..31";
            }
            description
              "Mirror instance name.";
          }
          container instance-slice {
            presence "create instance mirror slice-size";
            description
              "Enable/disable mirror instance slice.";
            leaf slice-size {
              type uint32 {
                range "64..9600";
              }
              units "Byte";
              // NCS drop mandatory statement
              description
                "Length of packet.";
            }
          }
          container instance-car {
            // NCS drop must statement
            // NCS drop must statement
            presence "create instance-car";
            description
              "Enable/disable mirror instance car.";
            leaf cir {
              type uint32 {
                range "0..4294967295";
              }
              units "kbit/s";
              // NCS drop mandatory statement
              description
                "Committed information rate.";
            }
            leaf pir {
              type uint32 {
                range "1..4294967295";
              }
              units "kbit/s";
              description
                "Peak information rate.";
            }
            leaf cbs {
              type uint32 {
                range "0..4294967295";
              }
              units "Byte";
              // NCS drop mandatory statement
              description
                "Committed burst size, which has dynamic defaults.";
            }
            leaf pbs {
              type uint32 {
                range "0..4294967295";
              }
              units "Byte";
              description
                "Peak burst size, which has dynamic defaults.";
            }
          }
        }
      }
      container observe-user-define-acls {
        description
          "List of observe user-defined acl.";
        list observe-user-define-acl {
          // NCS drop must statement
          key "filter-id";
          // NCS drop max-elements statement
          description
            "Configure observe user-defined acl.";
          leaf filter-id {
            type uint8 {
              range "1..8";
            }
            description
              "Filter index.";
          }
          container offsets {
            description
              "List of observe user-defined offset.";
            list offset {
              key "config-index";
              unique "offset-value";
              // NCS drop min-elements statement
              // NCS drop max-elements statement
              description
                "Configure observe user-defined offset.";
              leaf config-index {
                type uint32 {
                  range "1..4";
                }
                description
                  "Offset index. The config-index values in the offset must start at 1 and be consecutive.";
              }
              leaf offset-value {
                type uint32 {
                  range "0..114";
                }
                // NCS drop mandatory statement
                description
                  "Offset.";
              }
              leaf payload-value {
                type pub-type:live_ncs_hex-binary;
                // NCS drop mandatory statement
                description
                  "Payload value, Value range HEX[0,ffffffff].";
              }
              leaf payload-mask {
                type pub-type:live_ncs_hex-binary;
                // NCS drop mandatory statement
                description
                  "Payload mask, Value range HEX[0,ffffffff].";
              }
            }
          }
        }
      }
      container query-ports {
        description
          "List of query port-mirror infos.";
        list query-port {
          key "if-name";
          description
            "Query port-mirror info state.";
          leaf if-name {
            type leafref {
              path "/ncs:devices/ncs:device/ncs:live-status/ifm:ifm/ifm:interfaces/ifm:interface/ifm:name" {
                tailf:xpath-root 3;
              }
            }
            description
              "Interface name.";
          }
          leaf type {
            type live_ncs_mirror-type;
            description
              "The value 0 indicates port mirroring, and the value 1 indicates flow mirroring.";
          }
          leaf direction {
            type live_ncs_query-direction-type;
            description
              "Direction.";
          }
          leaf in-packets {
            type uint64;
            units "packet";
            description
              "Inbound packets.";
          }
          leaf out-packets {
            type uint64;
            units "packet";
            description
              "Outbound packets.";
          }
          leaf in-drop-packets {
            type uint64;
            units "packet";
            description
              "Inbound Drop Packets.";
          }
          leaf out-drop-packets {
            type uint64;
            units "packet";
            description
              "Outbound Drop Packets.";
          }
          leaf in-bytes {
            type uint64;
            units "Byte";
            description
              "Inbound bytes.";
          }
          leaf out-bytes {
            type uint64;
            units "Byte";
            description
              "Outbound bytes.";
          }
          leaf in-drop-bytes {
            type uint64;
            units "Byte";
            description
              "Inbound Drop Bytes.";
          }
          leaf out-drop-bytes {
            type uint64;
            units "Byte";
            description
              "Outbound Drop Bytes.";
          }
          leaf in-pps {
            type uint64;
            units "pps";
            description
              "Inbound pps.";
          }
          leaf out-pps {
            type uint64;
            units "pps";
            description
              "Outbound pps.";
          }
          leaf in-drop-pps {
            type uint64;
            units "pps";
            description
              "Inbound Drop pps.";
          }
          leaf out-drop-pps {
            type uint64;
            units "pps";
            description
              "Outbound Drop pps.";
          }
          leaf in-bps {
            type uint64;
            units "bit/s";
            description
              "Inbound bps.";
          }
          leaf out-bps {
            type uint64;
            units "bit/s";
            description
              "Outbound bps.";
          }
          leaf in-drop-bps {
            type uint64;
            units "bit/s";
            description
              "Inbound Drop bps.";
          }
          leaf out-drop-bps {
            type uint64;
            units "bit/s";
            description
              "Outbound Drop bps.";
          }
        }
      }
      container query-traffic-policy-ports {
        description
          "List of query traffic policy port.";
        list query-traffic-policy-port {
          key "if-name traffic-policy-name";
          description
            "Query port-mirror for multi traffic policy state.";
          leaf if-name {
            type leafref {
              path "/ncs:devices/ncs:device/ncs:live-status/ifm:ifm/ifm:interfaces/ifm:interface/ifm:name" {
                tailf:xpath-root 3;
              }
            }
            description
              "Interface name.";
          }
          leaf traffic-policy-name {
            type string {
              length "1..127";
            }
            description
              "Traffic policy name.";
          }
          leaf type {
            type live_ncs_mirror-type;
            description
              "The value 0 indicates port mirroring, and the value 1 indicates flow mirroring.";
          }
          leaf direction {
            type live_ncs_query-direction-type;
            description
              "Direction.";
          }
          leaf in-packets {
            type uint64;
            units "packet";
            description
              "Inbound packets.";
          }
          leaf out-packets {
            type uint64;
            units "packet";
            description
              "Outbound packets.";
          }
          leaf in-drop-packets {
            type uint64;
            units "packet";
            description
              "Inbound Drop Packets.";
          }
          leaf out-drop-packets {
            type uint64;
            units "packet";
            description
              "Outbound Drop Packets.";
          }
          leaf in-bytes {
            type uint64;
            units "Byte";
            description
              "Inbound bytes.";
          }
          leaf out-bytes {
            type uint64;
            units "Byte";
            description
              "Outbound bytes.";
          }
          leaf in-drop-bytes {
            type uint64;
            units "Byte";
            description
              "Inbound Drop Bytes.";
          }
          leaf out-drop-bytes {
            type uint64;
            units "Byte";
            description
              "Outbound Drop Bytes.";
          }
          leaf in-pps {
            type uint64;
            units "pps";
            description
              "Inbound pps.";
          }
          leaf out-pps {
            type uint64;
            units "pps";
            description
              "Outbound pps.";
          }
          leaf in-drop-pps {
            type uint64;
            units "pps";
            description
              "Inbound Drop pps.";
          }
          leaf out-drop-pps {
            type uint64;
            units "pps";
            description
              "Outbound Drop pps.";
          }
          leaf in-bps {
            type uint64;
            units "bit/s";
            description
              "Inbound bps.";
          }
          leaf out-bps {
            type uint64;
            units "bit/s";
            description
              "Outbound bps.";
          }
          leaf in-drop-bps {
            type uint64;
            units "bit/s";
            description
              "Inbound Drop bps.";
          }
          leaf out-drop-bps {
            type uint64;
            units "bit/s";
            description
              "Outbound Drop bps.";
          }
        }
      }
    }
  }
  augment "/ncs:devices/ncs:template/ncs:ned-id/ncs:config" {
    container mirror {
      description
        "Mirror.";
      container statistic-enable {
        presence "create statistic-enable";
        description
          "Enable/disable mirror statistic.";
      }
      container instances {
        description
          "List of mirror instance.";
        list instance {
          // NCS patched for predictable order
          ordered-by user;
          key "instance-name";
          description
            "Configure mirror instance.";
          leaf instance-name {
            type string;
            description
              "Mirror instance name.";
          }
          container instance-slice {
            presence "create instance mirror slice-size";
            description
              "Enable/disable mirror instance slice.";
            leaf slice-size {
              type string;
              units "Byte";
              // NCS drop mandatory statement
              description
                "Length of packet.";
            }
          }
          container instance-car {
            // NCS drop must statement
            // NCS drop must statement
            presence "create instance-car";
            description
              "Enable/disable mirror instance car.";
            leaf cir {
              type string;
              units "kbit/s";
              // NCS drop mandatory statement
              description
                "Committed information rate.";
            }
            leaf pir {
              type string;
              units "kbit/s";
              description
                "Peak information rate.";
            }
            leaf cbs {
              type string;
              units "Byte";
              // NCS drop mandatory statement
              description
                "Committed burst size, which has dynamic defaults.";
            }
            leaf pbs {
              type string;
              units "Byte";
              description
                "Peak burst size, which has dynamic defaults.";
            }
          }
        }
      }
      container observe-user-define-acls {
        description
          "List of observe user-defined acl.";
        list observe-user-define-acl {
          // NCS patched for predictable order
          ordered-by user;
          // NCS drop must statement
          key "filter-id";
          // NCS drop max-elements statement
          description
            "Configure observe user-defined acl.";
          leaf filter-id {
            type string;
            description
              "Filter index.";
          }
          container offsets {
            description
              "List of observe user-defined offset.";
            list offset {
              // NCS patched for predictable order
              ordered-by user;
              key "config-index";
              unique "offset-value";
              // NCS drop min-elements statement
              // NCS drop max-elements statement
              description
                "Configure observe user-defined offset.";
              leaf config-index {
                type string;
                description
                  "Offset index. The config-index values in the offset must start at 1 and be consecutive.";
              }
              leaf offset-value {
                type string;
                // NCS drop mandatory statement
                description
                  "Offset.";
              }
              leaf payload-value {
                type pub-type:ncs_template_hex-binary;
                // NCS drop mandatory statement
                description
                  "Payload value, Value range HEX[0,ffffffff].";
              }
              leaf payload-mask {
                type pub-type:ncs_template_hex-binary;
                // NCS drop mandatory statement
                description
                  "Payload mask, Value range HEX[0,ffffffff].";
              }
            }
          }
        }
      }
      // NCS drop config false container 'query-ports'
      // NCS drop config false container 'query-traffic-policy-ports'
    }
  }
  augment "/ncs:devices/ncs:template/ncs:ned-id/ncs:config/devm:devm/devm:mpu-boards/devm:mpu-board" {
    description
      "Observing boards.";
    container mirror {
      description
        "Configure Mirror.";
      container slot-observe {
        presence "create slot-observe";
        description
          "Enable/disable observing board.";
        leaf observe-index {
          type string;
          // NCS drop mandatory statement
          description
            "Observing index.";
        }
      }
      container observe-filters {
        description
          "List of mirror filter rules.";
        list observe-filter {
          // NCS patched for predictable order
          ordered-by user;
          // NCS drop must statement
          key "filter-id";
          // NCS drop max-elements statement
          description
            "Configure mirror filter rule.";
          leaf filter-id {
            type string;
            description
              "User ID number.";
          }
          leaf src-ipaddr {
            type string;
            // NCS drop must statement
            description
              "Source IP.";
          }
          leaf src-ipaddr-mask {
            type string;
            // NCS drop must statement
            description
              "Source IP mask.";
          }
          leaf dst-ipaddr {
            type string;
            // NCS drop must statement
            description
              "Destination IP.";
          }
          leaf dst-ipaddr-mask {
            type string;
            // NCS drop must statement
            description
              "Destination IP mask.";
          }
          leaf src-port {
            type string;
            description
              "Source port.";
          }
          leaf dst-port {
            type string;
            description
              "Destination port.";
          }
          leaf src-macaddr {
            type pub-type:ncs_template_mac-address;
            description
              "Source MAC.";
          }
          leaf pppoe-session-id {
            type string;
            description
              "PPPOE session ID.";
          }
          leaf dst-macaddr {
            type pub-type:ncs_template_mac-address;
            description
              "Destination MAC.";
          }
          leaf vlan {
            type string;
            description
              "VLAN ID.";
          }
          leaf eth-type {
            type pub-type:ncs_template_hex-binary;
            description
              "Ethernet type.";
          }
          choice protocol-type {
            description
              "Protocol type.";
            case ppp {
              description
                "PPP.";
              leaf ppp-protocol {
                type pub-type:ncs_template_hex-binary;
                description
                  "PPP protocol.";
              }
            }
            case ip {
              description
                "IP.";
              leaf ip-protocol {
                type string;
                description
                  "IP protocol.";
              }
            }
          }
        }
      }
    }
  }
  augment "/ncs:devices/ncs:device/ncs:live-status/devm:devm/devm:mpu-boards/devm:mpu-board" {
    description
      "Observing boards.";
    container mirror {
      tailf:ncs-device-type "netconf";
      tailf:display-when "not(../../../../../ncs:module) or ../../../../../ncs:module[ncs:name='huawei-mirror'] or (../../../../../ncs:live-status-protocol[not(ncs:capability)]) or (../../../../../ncs:live-status-protocol/ncs:capability/ncs:module[.='huawei-mirror'])";
      description
        "Configure Mirror.";
      container slot-observe {
        presence "create slot-observe";
        description
          "Enable/disable observing board.";
        leaf observe-index {
          type uint8 {
            range "1..255";
          }
          // NCS drop mandatory statement
          description
            "Observing index.";
        }
      }
      container observe-filters {
        description
          "List of mirror filter rules.";
        list observe-filter {
          // NCS drop must statement
          key "filter-id";
          // NCS drop max-elements statement
          description
            "Configure mirror filter rule.";
          leaf filter-id {
            type uint8 {
              range "0..7";
            }
            description
              "User ID number.";
          }
          leaf src-ipaddr {
            type inet:ipv4-address-no-zone;
            // NCS drop must statement
            description
              "Source IP.";
          }
          leaf src-ipaddr-mask {
            type inet:ipv4-address-no-zone;
            // NCS drop must statement
            description
              "Source IP mask.";
          }
          leaf dst-ipaddr {
            type inet:ipv4-address-no-zone;
            // NCS drop must statement
            description
              "Destination IP.";
          }
          leaf dst-ipaddr-mask {
            type inet:ipv4-address-no-zone;
            // NCS drop must statement
            description
              "Destination IP mask.";
          }
          leaf src-port {
            type uint16;
            description
              "Source port.";
          }
          leaf dst-port {
            type uint16;
            description
              "Destination port.";
          }
          leaf src-macaddr {
            type pub-type:live_ncs_mac-address;
            description
              "Source MAC.";
          }
          leaf pppoe-session-id {
            type uint16 {
              range "1..65535";
            }
            description
              "PPPOE session ID.";
          }
          leaf dst-macaddr {
            type pub-type:live_ncs_mac-address;
            description
              "Destination MAC.";
          }
          leaf vlan {
            type uint16 {
              range "1..4094";
            }
            description
              "VLAN ID.";
          }
          leaf eth-type {
            type pub-type:live_ncs_hex-binary;
            description
              "Ethernet type.";
          }
          choice protocol-type {
            description
              "Protocol type.";
            case ppp {
              description
                "PPP.";
              leaf ppp-protocol {
                type pub-type:live_ncs_hex-binary;
                description
                  "PPP protocol.";
              }
            }
            case ip {
              description
                "IP.";
              leaf ip-protocol {
                type uint32 {
                  range "1..255";
                }
                description
                  "IP protocol.";
              }
            }
          }
        }
      }
    }
  }
  augment "/ncs:devices/ncs:device/ncs:config/devm:devm/devm:mpu-boards/devm:mpu-board" {
    description
      "Observing boards.";
    container mirror {
      tailf:ncs-device-type "netconf";
      tailf:display-when "not(../../../../../ncs:module) or ../../../../../ncs:module[ncs:name='huawei-mirror']";
      description
        "Configure Mirror.";
      container slot-observe {
        presence "create slot-observe";
        description
          "Enable/disable observing board.";
        leaf observe-index {
          type uint8 {
            range "1..255";
          }
          mandatory true;
          description
            "Observing index.";
        }
      }
      container observe-filters {
        description
          "List of mirror filter rules.";
        list observe-filter {
          must './src-ipaddr or ./dst-ipaddr or ./dst-ipaddr or ./src-port or ./dst-port or ./src-macaddr or ./pppoe-session-id or ./dst-macaddr or ./vlan or ./eth-type or ./ppp-protocol or ./ip-protocol' {
            tailf:xpath-root 3;
          }
          key "filter-id";
          max-elements 8;
          description
            "Configure mirror filter rule.";
          leaf filter-id {
            type uint8 {
              range "0..7";
            }
            description
              "User ID number.";
          }
          leaf src-ipaddr {
            type inet:ipv4-address-no-zone;
            must '(../src-ipaddr-mask)' {
              tailf:xpath-root 3;
            }
            description
              "Source IP.";
          }
          leaf src-ipaddr-mask {
            type inet:ipv4-address-no-zone;
            must '(../src-ipaddr)' {
              tailf:xpath-root 3;
            }
            description
              "Source IP mask.";
          }
          leaf dst-ipaddr {
            type inet:ipv4-address-no-zone;
            must '(../dst-ipaddr-mask)' {
              tailf:xpath-root 3;
            }
            description
              "Destination IP.";
          }
          leaf dst-ipaddr-mask {
            type inet:ipv4-address-no-zone;
            must '(../dst-ipaddr)' {
              tailf:xpath-root 3;
            }
            description
              "Destination IP mask.";
          }
          leaf src-port {
            type uint16;
            description
              "Source port.";
          }
          leaf dst-port {
            type uint16;
            description
              "Destination port.";
          }
          leaf src-macaddr {
            type pub-type:mac-address;
            description
              "Source MAC.";
          }
          leaf pppoe-session-id {
            type uint16 {
              range "1..65535";
            }
            description
              "PPPOE session ID.";
          }
          leaf dst-macaddr {
            type pub-type:mac-address;
            description
              "Destination MAC.";
          }
          leaf vlan {
            type uint16 {
              range "1..4094";
            }
            description
              "VLAN ID.";
          }
          leaf eth-type {
            type pub-type:hex-binary {
              length "1..6";
            }
            description
              "Ethernet type.";
          }
          choice protocol-type {
            description
              "Protocol type.";
            case ppp {
              description
                "PPP.";
              leaf ppp-protocol {
                type pub-type:hex-binary {
                  length "1..6";
                }
                description
                  "PPP protocol.";
              }
            }
            case ip {
              description
                "IP.";
              leaf ip-protocol {
                type uint32 {
                  range "1..255";
                }
                description
                  "IP protocol.";
              }
            }
          }
        }
      }
    }
  }
  augment "/ncs:devices/ncs:template/ncs:ned-id/ncs:config/devm:devm/devm:lpu-boards/devm:lpu-board" {
    description
      "Observing boards.";
    container mirror {
      description
        "Configure mirror.";
      container slot-observe {
        presence "create slot-observe";
        description
          "Enable/disable observing board.";
        leaf observe-index {
          type string;
          // NCS drop mandatory statement
          description
            "Observing index.";
        }
      }
      container rate-limit-percent {
        presence "create rate-limit-percent";
        description
          "Enable/disable mirroring rate-value.";
        leaf rate-value {
          type string;
          units "%";
          // NCS drop mandatory statement
          description
            "Rate value.";
        }
      }
      container observe-filters {
        description
          "List of mirror filter rules.";
        list observe-filter {
          // NCS patched for predictable order
          ordered-by user;
          // NCS drop must statement
          key "filter-id";
          // NCS drop max-elements statement
          description
            "Configure mirror filter rule.";
          leaf filter-id {
            type string;
            description
              "User ID number.";
          }
          leaf src-ipaddr {
            type string;
            // NCS drop must statement
            description
              "Source IP.";
          }
          leaf src-ipaddr-mask {
            type string;
            // NCS drop must statement
            description
              "Source IP mask.";
          }
          leaf dst-ipaddr {
            type string;
            // NCS drop must statement
            description
              "Destination IP.";
          }
          leaf dst-ipaddr-mask {
            type string;
            // NCS drop must statement
            description
              "Destination IP mask.";
          }
          leaf src-port {
            type string;
            description
              "Source port.";
          }
          leaf dst-port {
            type string;
            description
              "Destination port.";
          }
          leaf src-macaddr {
            type pub-type:ncs_template_mac-address;
            description
              "Source MAC.";
          }
          leaf pppoe-session-id {
            type string;
            description
              "PPPOE session ID.";
          }
          leaf dst-macaddr {
            type pub-type:ncs_template_mac-address;
            description
              "Destination MAC.";
          }
          leaf vlan {
            type string;
            description
              "VLAN ID.";
          }
          leaf eth-type {
            type pub-type:ncs_template_hex-binary;
            description
              "Ethernet type.";
          }
          choice protocol-type {
            description
              "Protocol type.";
            case ppp {
              description
                "PPP.";
              leaf ppp-protocol {
                type pub-type:ncs_template_hex-binary;
                description
                  "PPP protocol.";
              }
            }
            case ip {
              description
                "IP.";
              leaf ip-protocol {
                type string;
                description
                  "IP protocol.";
              }
            }
          }
        }
      }
    }
  }
  augment "/ncs:devices/ncs:device/ncs:live-status/devm:devm/devm:lpu-boards/devm:lpu-board" {
    description
      "Observing boards.";
    container mirror {
      tailf:ncs-device-type "netconf";
      tailf:display-when "not(../../../../../ncs:module) or ../../../../../ncs:module[ncs:name='huawei-mirror'] or (../../../../../ncs:live-status-protocol[not(ncs:capability)]) or (../../../../../ncs:live-status-protocol/ncs:capability/ncs:module[.='huawei-mirror'])";
      description
        "Configure mirror.";
      container slot-observe {
        presence "create slot-observe";
        description
          "Enable/disable observing board.";
        leaf observe-index {
          type uint8 {
            range "1..255";
          }
          // NCS drop mandatory statement
          description
            "Observing index.";
        }
      }
      container rate-limit-percent {
        presence "create rate-limit-percent";
        description
          "Enable/disable mirroring rate-value.";
        leaf rate-value {
          type uint8 {
            range "1..100";
          }
          units "%";
          // NCS drop mandatory statement
          description
            "Rate value.";
        }
      }
      container observe-filters {
        description
          "List of mirror filter rules.";
        list observe-filter {
          // NCS drop must statement
          key "filter-id";
          // NCS drop max-elements statement
          description
            "Configure mirror filter rule.";
          leaf filter-id {
            type uint8 {
              range "0..7";
            }
            description
              "User ID number.";
          }
          leaf src-ipaddr {
            type inet:ipv4-address-no-zone;
            // NCS drop must statement
            description
              "Source IP.";
          }
          leaf src-ipaddr-mask {
            type inet:ipv4-address-no-zone;
            // NCS drop must statement
            description
              "Source IP mask.";
          }
          leaf dst-ipaddr {
            type inet:ipv4-address-no-zone;
            // NCS drop must statement
            description
              "Destination IP.";
          }
          leaf dst-ipaddr-mask {
            type inet:ipv4-address-no-zone;
            // NCS drop must statement
            description
              "Destination IP mask.";
          }
          leaf src-port {
            type uint16;
            description
              "Source port.";
          }
          leaf dst-port {
            type uint16;
            description
              "Destination port.";
          }
          leaf src-macaddr {
            type pub-type:live_ncs_mac-address;
            description
              "Source MAC.";
          }
          leaf pppoe-session-id {
            type uint16 {
              range "1..65535";
            }
            description
              "PPPOE session ID.";
          }
          leaf dst-macaddr {
            type pub-type:live_ncs_mac-address;
            description
              "Destination MAC.";
          }
          leaf vlan {
            type uint16 {
              range "1..4094";
            }
            description
              "VLAN ID.";
          }
          leaf eth-type {
            type pub-type:live_ncs_hex-binary;
            description
              "Ethernet type.";
          }
          choice protocol-type {
            description
              "Protocol type.";
            case ppp {
              description
                "PPP.";
              leaf ppp-protocol {
                type pub-type:live_ncs_hex-binary;
                description
                  "PPP protocol.";
              }
            }
            case ip {
              description
                "IP.";
              leaf ip-protocol {
                type uint32 {
                  range "1..255";
                }
                description
                  "IP protocol.";
              }
            }
          }
        }
      }
    }
  }
  augment "/ncs:devices/ncs:device/ncs:config/devm:devm/devm:lpu-boards/devm:lpu-board" {
    description
      "Observing boards.";
    container mirror {
      tailf:ncs-device-type "netconf";
      tailf:display-when "not(../../../../../ncs:module) or ../../../../../ncs:module[ncs:name='huawei-mirror']";
      description
        "Configure mirror.";
      container slot-observe {
        presence "create slot-observe";
        description
          "Enable/disable observing board.";
        leaf observe-index {
          type uint8 {
            range "1..255";
          }
          mandatory true;
          description
            "Observing index.";
        }
      }
      container rate-limit-percent {
        presence "create rate-limit-percent";
        description
          "Enable/disable mirroring rate-value.";
        leaf rate-value {
          type uint8 {
            range "1..100";
          }
          units "%";
          mandatory true;
          description
            "Rate value.";
        }
      }
      container observe-filters {
        description
          "List of mirror filter rules.";
        list observe-filter {
          must './src-ipaddr or ./dst-ipaddr or ./dst-ipaddr or ./src-port or ./dst-port or ./src-macaddr or ./pppoe-session-id or ./dst-macaddr or ./vlan or ./eth-type or ./ppp-protocol or ./ip-protocol' {
            tailf:xpath-root 3;
          }
          key "filter-id";
          max-elements 8;
          description
            "Configure mirror filter rule.";
          leaf filter-id {
            type uint8 {
              range "0..7";
            }
            description
              "User ID number.";
          }
          leaf src-ipaddr {
            type inet:ipv4-address-no-zone;
            must '(../src-ipaddr-mask)' {
              tailf:xpath-root 3;
            }
            description
              "Source IP.";
          }
          leaf src-ipaddr-mask {
            type inet:ipv4-address-no-zone;
            must '(../src-ipaddr)' {
              tailf:xpath-root 3;
            }
            description
              "Source IP mask.";
          }
          leaf dst-ipaddr {
            type inet:ipv4-address-no-zone;
            must '(../dst-ipaddr-mask)' {
              tailf:xpath-root 3;
            }
            description
              "Destination IP.";
          }
          leaf dst-ipaddr-mask {
            type inet:ipv4-address-no-zone;
            must '(../dst-ipaddr)' {
              tailf:xpath-root 3;
            }
            description
              "Destination IP mask.";
          }
          leaf src-port {
            type uint16;
            description
              "Source port.";
          }
          leaf dst-port {
            type uint16;
            description
              "Destination port.";
          }
          leaf src-macaddr {
            type pub-type:mac-address;
            description
              "Source MAC.";
          }
          leaf pppoe-session-id {
            type uint16 {
              range "1..65535";
            }
            description
              "PPPOE session ID.";
          }
          leaf dst-macaddr {
            type pub-type:mac-address;
            description
              "Destination MAC.";
          }
          leaf vlan {
            type uint16 {
              range "1..4094";
            }
            description
              "VLAN ID.";
          }
          leaf eth-type {
            type pub-type:hex-binary {
              length "1..6";
            }
            description
              "Ethernet type.";
          }
          choice protocol-type {
            description
              "Protocol type.";
            case ppp {
              description
                "PPP.";
              leaf ppp-protocol {
                type pub-type:hex-binary {
                  length "1..6";
                }
                description
                  "PPP protocol.";
              }
            }
            case ip {
              description
                "IP.";
              leaf ip-protocol {
                type uint32 {
                  range "1..255";
                }
                description
                  "IP protocol.";
              }
            }
          }
        }
      }
    }
  }
  augment "/ncs:devices/ncs:template/ncs:ned-id/ncs:config/qos:qos/qos:global-config" {
    description
      "Observing boards..";
    container mirror {
      description
        "Configure mirror.";
      container to-observe {
        presence "create to-observe";
        description
          "Enable/disable observing board.";
        leaf index {
          type string;
          // NCS drop mandatory statement
          description
            "Observing index.";
        }
      }
    }
  }
  augment "/ncs:devices/ncs:device/ncs:live-status/qos:qos/qos:global-config" {
    description
      "Observing boards..";
    container mirror {
      tailf:ncs-device-type "netconf";
      tailf:display-when "not(../../../../ncs:module) or ../../../../ncs:module[ncs:name='huawei-mirror'] or (../../../../ncs:live-status-protocol[not(ncs:capability)]) or (../../../../ncs:live-status-protocol/ncs:capability/ncs:module[.='huawei-mirror'])";
      description
        "Configure mirror.";
      container to-observe {
        presence "create to-observe";
        description
          "Enable/disable observing board.";
        leaf index {
          type uint8 {
            range "1..8";
          }
          // NCS drop mandatory statement
          description
            "Observing index.";
        }
      }
    }
  }
  augment "/ncs:devices/ncs:device/ncs:config/qos:qos/qos:global-config" {
    description
      "Observing boards..";
    container mirror {
      tailf:ncs-device-type "netconf";
      tailf:display-when "not(../../../../ncs:module) or ../../../../ncs:module[ncs:name='huawei-mirror']";
      description
        "Configure mirror.";
      container to-observe {
        presence "create to-observe";
        description
          "Enable/disable observing board.";
        leaf index {
          type uint8 {
            range "1..8";
          }
          mandatory true;
          description
            "Observing index.";
        }
      }
    }
  }
  augment "/ncs:devices/ncs:template/ncs:ned-id/ncs:config/qos:qos/qos:classifier-template/qos:traffic-behaviors/qos:traffic-behavior" {
    description
      "Mirror.";
    container mirror {
      description
        "Configure Mirror.";
      container mirror-enable {
        presence "create mirror-enable";
        description
          "Enable/disable flow mirroring action.";
      }
      container mirror-slice {
        presence "create mirror-slice";
        description
          "Enable/disable flow mirroring slice action.";
        leaf slice-size {
          type string;
          units "Byte";
          // NCS drop mandatory statement
          description
            "Length of packet.";
        }
      }
      container mirror-car {
        // NCS drop must statement
        // NCS drop must statement
        presence "create mirror-car";
        description
          "Enable/disable flow mirroring car action.";
        leaf cir {
          type string;
          units "kbit/s";
          // NCS drop mandatory statement
          description
            "Committed information rate.";
        }
        leaf pir {
          type string;
          units "kbit/s";
          description
            "Peak information rate.";
        }
        leaf cbs {
          type string;
          units "Byte";
          // NCS drop mandatory statement
          description
            "Committed burst size.";
        }
        leaf pbs {
          type string;
          units "Byte";
          description
            "Peak burst size.";
        }
      }
      container mirror-to {
        presence "create mirror-to";
        description
          "Enable/disable flow mirroring to.";
        leaf observe-index {
          type string;
          // NCS drop mandatory statement
          description
            "Observing index. Enter the observation index value, which is separated by a comma (,) and the index value must be unique. For example, 1 or 1,3,5,7,9.";
        }
      }
    }
  }
  augment "/ncs:devices/ncs:device/ncs:live-status/qos:qos/qos:classifier-template/qos:traffic-behaviors/qos:traffic-behavior" {
    description
      "Mirror.";
    container mirror {
      tailf:ncs-device-type "netconf";
      tailf:display-when "not(../../../../../../ncs:module) or ../../../../../../ncs:module[ncs:name='huawei-mirror'] or (../../../../../../ncs:live-status-protocol[not(ncs:capability)]) or (../../../../../../ncs:live-status-protocol/ncs:capability/ncs:module[.='huawei-mirror'])";
      description
        "Configure Mirror.";
      container mirror-enable {
        presence "create mirror-enable";
        description
          "Enable/disable flow mirroring action.";
      }
      container mirror-slice {
        presence "create mirror-slice";
        description
          "Enable/disable flow mirroring slice action.";
        leaf slice-size {
          type uint32 {
            range "64..9600";
          }
          units "Byte";
          // NCS drop mandatory statement
          description
            "Length of packet.";
        }
      }
      container mirror-car {
        // NCS drop must statement
        // NCS drop must statement
        presence "create mirror-car";
        description
          "Enable/disable flow mirroring car action.";
        leaf cir {
          type uint32 {
            range "0..4294967295";
          }
          units "kbit/s";
          // NCS drop mandatory statement
          description
            "Committed information rate.";
        }
        leaf pir {
          type uint32 {
            range "1..4294967295";
          }
          units "kbit/s";
          description
            "Peak information rate.";
        }
        leaf cbs {
          type uint32 {
            range "0..4294967295";
          }
          units "Byte";
          // NCS drop mandatory statement
          description
            "Committed burst size.";
        }
        leaf pbs {
          type uint32 {
            range "0..4294967295";
          }
          units "Byte";
          description
            "Peak burst size.";
        }
      }
      container mirror-to {
        presence "create mirror-to";
        description
          "Enable/disable flow mirroring to.";
        leaf observe-index {
          type string {
            length "1..50";
            pattern '((25[0-5]|2[0-4]\d|1\d\d|[1-9]\d|[1-9]){1}((,(25[0-5]|2[0-4]\d|1\d\d|[1-9]\d|[1-9])){0,7}))';
          }
          // NCS drop mandatory statement
          description
            "Observing index. Enter the observation index value, which is separated by a comma (,) and the index value must be unique. For example, 1 or 1,3,5,7,9.";
        }
      }
    }
  }
  augment "/ncs:devices/ncs:device/ncs:config/qos:qos/qos:classifier-template/qos:traffic-behaviors/qos:traffic-behavior" {
    description
      "Mirror.";
    container mirror {
      tailf:ncs-device-type "netconf";
      tailf:display-when "not(../../../../../../ncs:module) or ../../../../../../ncs:module[ncs:name='huawei-mirror']";
      description
        "Configure Mirror.";
      container mirror-enable {
        presence "create mirror-enable";
        description
          "Enable/disable flow mirroring action.";
      }
      container mirror-slice {
        presence "create mirror-slice";
        description
          "Enable/disable flow mirroring slice action.";
        leaf slice-size {
          type uint32 {
            range "64..9600";
          }
          units "Byte";
          mandatory true;
          description
            "Length of packet.";
        }
      }
      container mirror-car {
        must '(not(./pir) and not(./pbs)) or (./pbs)' {
          tailf:xpath-root 3;
        }
        must 'not(./pir) or ./pir>=./cir' {
          tailf:xpath-root 3;
        }
        presence "create mirror-car";
        description
          "Enable/disable flow mirroring car action.";
        leaf cir {
          type uint32 {
            range "0..4294967295";
          }
          units "kbit/s";
          mandatory true;
          description
            "Committed information rate.";
        }
        leaf pir {
          type uint32 {
            range "1..4294967295";
          }
          units "kbit/s";
          description
            "Peak information rate.";
        }
        leaf cbs {
          type uint32 {
            range "0..4294967295";
          }
          units "Byte";
          mandatory true;
          description
            "Committed burst size.";
        }
        leaf pbs {
          type uint32 {
            range "0..4294967295";
          }
          units "Byte";
          description
            "Peak burst size.";
        }
      }
      container mirror-to {
        presence "create mirror-to";
        description
          "Enable/disable flow mirroring to.";
        leaf observe-index {
          type string {
            length "1..50";
            pattern '((25[0-5]|2[0-4]\d|1\d\d|[1-9]\d|[1-9]){1}((,(25[0-5]|2[0-4]\d|1\d\d|[1-9]\d|[1-9])){0,7}))';
          }
          mandatory true;
          description
            "Observing index. Enter the observation index value, which is separated by a comma (,) and the index value must be unique. For example, 1 or 1,3,5,7,9.";
        }
      }
    }
  }
  augment "/ncs:devices/ncs:template/ncs:ned-id/ncs:config/ifm:ifm/ifm:interfaces/ifm:interface" {
    description
      "Port-mirror.";
    container mirror {
      description
        "Configure port mirroring.";
      container port-mirrors {
        // NCS drop must statement
        description
          "List of mirroring interfaces.";
        list port-mirror {
          // NCS patched for predictable order
          ordered-by user;
          // NCS drop must statement
          // NCS drop must statement
          // NCS drop must statement
          key "direction cpu-packet";
          description
            "Configure mirroring interface.";
          leaf direction {
            type ncs_template_direction-type;
            description
              "Direction.";
          }
          leaf cpu-packet {
            type string;
            // NCS drop must statement
            description
              "Enable/disable a separate mirroring function for sending CPU packets.";
          }
          choice property {
            description
              "Port mirroring property.";
            case vlan {
              description
                "Virtual LAN.";
              leaf cevlan {
                type pub-type:ncs_template_vlan-range;
                // NCS drop must statement
                // NCS drop must statement
                description
                  "VLAN ID.";
              }
            }
            case user-defined-filter-rule {
              description
                "Mirror user-defined-filter rule.";
              leaf filter-id {
                type string;
                description
                  "Filter index.";
              }
            }
          }
        }
      }
      container port-mirror-slice {
        presence "create port-mirroring slice-size";
        description
          "Enable/disable grab fixed-length packet.";
        leaf slice-size {
          type string;
          units "Byte";
          // NCS drop mandatory statement
          description
            "Length of packet.";
        }
      }
      container without-header {
        // NCS drop when statement
        // NCS drop must statement
        presence "create without-header";
        description
          "Enable/disable specify packet mirroring from layer 3.";
      }
      container port-mirror-car {
        // NCS drop must statement
        // NCS drop must statement
        // NCS drop must statement
        presence "create port-mirror-car";
        description
          "Enable/disable flow mirroring car action.";
        leaf cir {
          type string;
          units "kbit/s";
          // NCS drop mandatory statement
          description
            "Committed information rate.";
        }
        leaf pir {
          type string;
          units "kbit/s";
          description
            "Peak information rate.";
        }
        leaf cbs {
          type string;
          units "Byte";
          // NCS drop mandatory statement
          description
            "Committed burst size.";
        }
        leaf pbs {
          type string;
          units "Byte";
          description
            "Peak burst size.";
        }
      }
      container port-mirror-to {
        // NCS drop must statement
        presence "create port-mirror-to";
        description
          "Enable/disable flow mirroring to.";
        leaf observe-index {
          type string;
          // NCS drop mandatory statement
          description
            "Observing index. Enter the observation index value, which is separated by a comma (,) and the index value must be unique. For example, 1 or 1,3,5,7,9. If mirroring based on no observing port is required, enter null0.";
        }
      }
      container port-fragments {
        // NCS drop when statement
        // NCS drop must statement
        description
          "List of fragment mirroring interfaces.";
        list port-fragment {
          // NCS patched for predictable order
          ordered-by user;
          key "direction";
          description
            "Configure fragment mirroring interface (supported by some subcards).";
          leaf direction {
            type ncs_template_direction-type;
            description
              "Direction.";
          }
        }
      }
      container integrateds {
        // NCS drop must statement
        description
          "List of the port-mirroring to interface command configures port mirroring in integrated mode.";
        list integrated {
          // NCS patched for predictable order
          ordered-by user;
          key "direction cpu-packet";
          description
            "Configure the port-mirroring to interface command configures port mirroring in integrated mode.";
          leaf direction {
            type ncs_template_direction-type;
            description
              "Direction.";
          }
          leaf cpu-packet {
            type string;
            // NCS drop must statement
            // NCS drop must statement
            description
              "Enable/disable a separate mirroring function for sending CPU packets.";
          }
          leaf filter-id {
            type string;
            description
              "User-defined-filter rule number.";
          }
          choice observe-port {
            // NCS drop mandatory statement
            description
              "Observe port.";
            case port-null0 {
              description
                "Specify observing port null0.";
              leaf null0 {
                type empty;
                description
                  "Specify observing port null0.";
              }
            }
            case port-observe {
              description
                "Port observe.";
              leaf if-name {
                type string;
                // NCS drop must statement
                // NCS drop must statement
                description
                  "Name of an observing interface.";
              }
              leaf observe-index {
                type string;
                // NCS drop must statement
                description
                  "Observing index. An index corresponds to only one observing port.";
              }
            }
          }
        }
      }
      container bas-port-mirrors {
        // NCS drop must statement
        description
          "List of QinQ match port mirrors.";
        list bas-port-mirror {
          // NCS patched for predictable order
          ordered-by user;
          // NCS drop must statement
          // NCS drop must statement
          // NCS drop must statement
          // NCS drop must statement
          // NCS drop must statement
          key "direction pevlan-begin pevlan-end cevlan-begin cevlan-end";
          description
            "Configure QinQ match port mirror.";
          leaf direction {
            type ncs_template_direction-type;
            description
              "Direction.";
          }
          leaf pevlan-begin {
            type string;
            description
              "PEVLANBegin.";
          }
          leaf pevlan-end {
            type string;
            description
              "PEVLANEnd.";
          }
          leaf cevlan-begin {
            type string;
            description
              "CEVLANBegin.";
          }
          leaf cevlan-end {
            type string;
            description
              "CEVLANEnd.";
          }
        }
      }
      container evc-l2-port-mirrors {
        description
          "Configure EVC l2 port mirror.";
        choice evc-l2-port-cfg {
          description
            "EVC l2 port cfg.";
          case pub {
            description
              "EVC l2 untag port mirror.";
            container pubs {
              // NCS drop must statement
              description
                "List of EVC l2 port mirror.";
              list pub {
                // NCS patched for predictable order
                ordered-by user;
                // NCS drop must statement
                // NCS drop must statement
                key "direction";
                description
                  "Configure EVC l2 port mirror.";
                leaf direction {
                  type ncs_template_direction-type;
                  description
                    "Direction.";
                }
                leaf instance-name {
                  type string;
                  // NCS drop mandatory statement
                  description
                    "Mirror instance name.";
                }
                leaf group-name {
                  type string;
                  description
                    "Group name.";
                }
              }
            }
          }
          case dot1q-type {
            description
              "EVC l2 dot1q-terminal port mirror.";
            container dot1q-types {
              // NCS drop must statement
              description
                "List of EVC l2 port mirror.";
              list dot1q-type {
                // NCS patched for predictable order
                ordered-by user;
                // NCS drop must statement
                // NCS drop must statement
                // NCS drop must statement
                key "direction vlan-begin vlan-end";
                description
                  "Configure EVC l2 port mirror.";
                leaf direction {
                  type ncs_template_direction-type;
                  description
                    "Direction.";
                }
                leaf vlan-begin {
                  type string;
                  description
                    "CE VLAN begin.";
                }
                leaf vlan-end {
                  type string;
                  description
                    "CE VLAN end.";
                }
                leaf instance-name {
                  type string;
                  // NCS drop mandatory statement
                  description
                    "Mirror instance name.";
                }
                leaf identify {
                  type ncs_template_identifier-type;
                  // NCS drop must statement
                  // NCS drop mandatory statement
                  description
                    "Identify.";
                }
                leaf group-name {
                  type string;
                  description
                    "Group name.";
                }
              }
            }
          }
          case qinq-type {
            description
              "EVC l2 QinQ-terminal port mirror.";
            container qinq-types {
              // NCS drop must statement
              description
                "List of EVC l2 port mirror.";
              list qinq-type {
                // NCS patched for predictable order
                ordered-by user;
                // NCS drop must statement
                // NCS drop must statement
                // NCS drop must statement
                key "direction pevlan cevlan-begin cevlan-end";
                description
                  "Configure EVC l2 port mirror.";
                leaf direction {
                  type ncs_template_direction-type;
                  description
                    "Direction.";
                }
                leaf pevlan {
                  type string;
                  description
                    "PE VLAN.";
                }
                leaf cevlan-begin {
                  type string;
                  description
                    "CE VLAN begin.";
                }
                leaf cevlan-end {
                  type string;
                  description
                    "CE VLAN end.";
                }
                leaf instance-name {
                  type string;
                  // NCS drop mandatory statement
                  description
                    "Mirror instance name.";
                }
                leaf identify {
                  type ncs_template_identifier-type;
                  // NCS drop mandatory statement
                  description
                    "Identify.";
                }
                leaf group-name {
                  type string;
                  description
                    "Group name.";
                }
              }
            }
          }
        }
      }
      container port-observe {
        presence "port-observe";
        description
          "Enable/disable specify observing port index.";
        leaf observe-index {
          type string;
          // NCS drop mandatory statement
          description
            "Observing index. An index corresponds to only one observing port.";
        }
        leaf without-filter {
          type ncs_template_without-filter;
          // NCS drop default statement
          description
            "Disable observe filter in observe port.";
        }
        leaf destination-mac {
          type pub-type:ncs_template_mac-address;
          description
            "The observer port specifies the MAC address.";
        }
        leaf pop-label {
          type ncs_template_pop-label;
          // NCS drop must statement
          description
            "Type of POP MPLS label.";
        }
        leaf sub-extend {
          // NCS drop when statement
          type empty;
          description
            "The MPLS label-POP function enable on sub-interface.";
        }
        leaf with-linklayer-header {
          type ncs_template_with-linklayer-header;
          // NCS drop must statement
          // NCS drop default statement
          description
            "Specify packet mirroring from layer 3.";
        }
      }
    }
  }
  augment "/ncs:devices/ncs:device/ncs:live-status/ifm:ifm/ifm:interfaces/ifm:interface" {
    description
      "Port-mirror.";
    container mirror {
      tailf:ncs-device-type "netconf";
      tailf:display-when "not(../../../../../ncs:module) or ../../../../../ncs:module[ncs:name='huawei-mirror'] or (../../../../../ncs:live-status-protocol[not(ncs:capability)]) or (../../../../../ncs:live-status-protocol/ncs:capability/ncs:module[.='huawei-mirror'])";
      description
        "Configure port mirroring.";
      container port-mirrors {
        // NCS drop must statement
        description
          "List of mirroring interfaces.";
        list port-mirror {
          // NCS drop must statement
          // NCS drop must statement
          // NCS drop must statement
          key "direction cpu-packet";
          description
            "Configure mirroring interface.";
          leaf direction {
            type live_ncs_direction-type;
            description
              "Direction.";
          }
          leaf cpu-packet {
            type boolean;
            // NCS drop must statement
            description
              "Enable/disable a separate mirroring function for sending CPU packets.";
          }
          choice property {
            description
              "Port mirroring property.";
            case vlan {
              description
                "Virtual LAN.";
              leaf cevlan {
                type pub-type:live_ncs_vlan-range;
                // NCS drop must statement
                // NCS drop must statement
                description
                  "VLAN ID.";
              }
            }
            case user-defined-filter-rule {
              description
                "Mirror user-defined-filter rule.";
              leaf filter-id {
                type leafref {
                  path "/ncs:devices/ncs:device/ncs:live-status/mirror:mirror/mirror:observe-user-define-acls/mirror:observe-user-define-acl/mirror:filter-id" {
                    tailf:xpath-root 3;
                  }
                }
                description
                  "Filter index.";
              }
            }
          }
        }
      }
      container port-mirror-slice {
        presence "create port-mirroring slice-size";
        description
          "Enable/disable grab fixed-length packet.";
        leaf slice-size {
          type uint32 {
            range "64..9600";
          }
          units "Byte";
          // NCS drop mandatory statement
          description
            "Length of packet.";
        }
      }
      container without-header {
        // NCS drop when statement
        // NCS drop must statement
        presence "create without-header";
        description
          "Enable/disable specify packet mirroring from layer 3.";
      }
      container port-mirror-car {
        // NCS drop must statement
        // NCS drop must statement
        // NCS drop must statement
        presence "create port-mirror-car";
        description
          "Enable/disable flow mirroring car action.";
        leaf cir {
          type uint32 {
            range "0..4294967295";
          }
          units "kbit/s";
          // NCS drop mandatory statement
          description
            "Committed information rate.";
        }
        leaf pir {
          type uint32 {
            range "1..4294967295";
          }
          units "kbit/s";
          description
            "Peak information rate.";
        }
        leaf cbs {
          type uint32 {
            range "0..4294967295";
          }
          units "Byte";
          // NCS drop mandatory statement
          description
            "Committed burst size.";
        }
        leaf pbs {
          type uint32 {
            range "0..4294967295";
          }
          units "Byte";
          description
            "Peak burst size.";
        }
      }
      container port-mirror-to {
        // NCS drop must statement
        presence "create port-mirror-to";
        description
          "Enable/disable flow mirroring to.";
        leaf observe-index {
          type string {
            length "1..50";
            pattern '(null0)|((25[0-5]|2[0-4]\d|1\d\d|[1-9]\d|[1-9]){1}((,(25[0-5]|2[0-4]\d|1\d\d|[1-9]\d|[1-9])){0,7}))';
          }
          // NCS drop mandatory statement
          description
            "Observing index. Enter the observation index value, which is separated by a comma (,) and the index value must be unique. For example, 1 or 1,3,5,7,9. If mirroring based on no observing port is required, enter null0.";
        }
      }
      container port-fragments {
        // NCS drop when statement
        // NCS drop must statement
        description
          "List of fragment mirroring interfaces.";
        list port-fragment {
          key "direction";
          description
            "Configure fragment mirroring interface (supported by some subcards).";
          leaf direction {
            type live_ncs_direction-type;
            description
              "Direction.";
          }
        }
      }
      container integrateds {
        // NCS drop must statement
        description
          "List of the port-mirroring to interface command configures port mirroring in integrated mode.";
        list integrated {
          key "direction cpu-packet";
          description
            "Configure the port-mirroring to interface command configures port mirroring in integrated mode.";
          leaf direction {
            type live_ncs_direction-type;
            description
              "Direction.";
          }
          leaf cpu-packet {
            type boolean;
            // NCS drop must statement
            // NCS drop must statement
            description
              "Enable/disable a separate mirroring function for sending CPU packets.";
          }
          leaf filter-id {
            type leafref {
              path "/ncs:devices/ncs:device/ncs:live-status/mirror:mirror/mirror:observe-user-define-acls/mirror:observe-user-define-acl/mirror:filter-id" {
                tailf:xpath-root 3;
              }
            }
            description
              "User-defined-filter rule number.";
          }
          choice observe-port {
            // NCS drop mandatory statement
            description
              "Observe port.";
            case port-null0 {
              description
                "Specify observing port null0.";
              leaf null0 {
                type empty;
                description
                  "Specify observing port null0.";
              }
            }
            case port-observe {
              description
                "Port observe.";
              leaf if-name {
                type leafref {
                  path "/ncs:devices/ncs:device/ncs:live-status/ifm:ifm/ifm:interfaces/ifm:interface/ifm:name" {
                    tailf:xpath-root 3;
                  }
                }
                // NCS drop must statement
                // NCS drop must statement
                description
                  "Name of an observing interface.";
              }
              leaf observe-index {
                type uint8 {
                  range "1..255";
                }
                // NCS drop must statement
                description
                  "Observing index. An index corresponds to only one observing port.";
              }
            }
          }
        }
      }
      container bas-port-mirrors {
        // NCS drop must statement
        description
          "List of QinQ match port mirrors.";
        list bas-port-mirror {
          // NCS drop must statement
          // NCS drop must statement
          // NCS drop must statement
          // NCS drop must statement
          // NCS drop must statement
          key "direction pevlan-begin pevlan-end cevlan-begin cevlan-end";
          description
            "Configure QinQ match port mirror.";
          leaf direction {
            type live_ncs_direction-type;
            description
              "Direction.";
          }
          leaf pevlan-begin {
            type uint16 {
              range "1..4094";
            }
            description
              "PEVLANBegin.";
          }
          leaf pevlan-end {
            type uint16 {
              range "1..4094";
            }
            description
              "PEVLANEnd.";
          }
          leaf cevlan-begin {
            type uint16 {
              range "1..4094";
            }
            description
              "CEVLANBegin.";
          }
          leaf cevlan-end {
            type uint16 {
              range "1..4094";
            }
            description
              "CEVLANEnd.";
          }
        }
      }
      container evc-l2-port-mirrors {
        description
          "Configure EVC l2 port mirror.";
        choice evc-l2-port-cfg {
          description
            "EVC l2 port cfg.";
          case pub {
            description
              "EVC l2 untag port mirror.";
            container pubs {
              // NCS drop must statement
              description
                "List of EVC l2 port mirror.";
              list pub {
                // NCS drop must statement
                // NCS drop must statement
                key "direction";
                description
                  "Configure EVC l2 port mirror.";
                leaf direction {
                  type live_ncs_direction-type;
                  description
                    "Direction.";
                }
                leaf instance-name {
                  type leafref {
                    path "/ncs:devices/ncs:device/ncs:live-status/mirror:mirror/mirror:instances/mirror:instance/mirror:instance-name" {
                      tailf:xpath-root 3;
                    }
                  }
                  // NCS drop mandatory statement
                  description
                    "Mirror instance name.";
                }
                leaf group-name {
                  type string {
                    length "1..31";
                  }
                  description
                    "Group name.";
                }
              }
            }
          }
          case dot1q-type {
            description
              "EVC l2 dot1q-terminal port mirror.";
            container dot1q-types {
              // NCS drop must statement
              description
                "List of EVC l2 port mirror.";
              list dot1q-type {
                // NCS drop must statement
                // NCS drop must statement
                // NCS drop must statement
                key "direction vlan-begin vlan-end";
                description
                  "Configure EVC l2 port mirror.";
                leaf direction {
                  type live_ncs_direction-type;
                  description
                    "Direction.";
                }
                leaf vlan-begin {
                  type uint16 {
                    range "1..4094";
                  }
                  description
                    "CE VLAN begin.";
                }
                leaf vlan-end {
                  type uint16 {
                    range "1..4094";
                  }
                  description
                    "CE VLAN end.";
                }
                leaf instance-name {
                  type leafref {
                    path "/ncs:devices/ncs:device/ncs:live-status/mirror:mirror/mirror:instances/mirror:instance/mirror:instance-name" {
                      tailf:xpath-root 3;
                    }
                  }
                  // NCS drop mandatory statement
                  description
                    "Mirror instance name.";
                }
                leaf identify {
                  type live_ncs_identifier-type;
                  // NCS drop must statement
                  // NCS drop mandatory statement
                  description
                    "Identify.";
                }
                leaf group-name {
                  type string {
                    length "1..31";
                  }
                  description
                    "Group name.";
                }
              }
            }
          }
          case qinq-type {
            description
              "EVC l2 QinQ-terminal port mirror.";
            container qinq-types {
              // NCS drop must statement
              description
                "List of EVC l2 port mirror.";
              list qinq-type {
                // NCS drop must statement
                // NCS drop must statement
                // NCS drop must statement
                key "direction pevlan cevlan-begin cevlan-end";
                description
                  "Configure EVC l2 port mirror.";
                leaf direction {
                  type live_ncs_direction-type;
                  description
                    "Direction.";
                }
                leaf pevlan {
                  type uint16 {
                    range "1..4094";
                  }
                  description
                    "PE VLAN.";
                }
                leaf cevlan-begin {
                  type uint16 {
                    range "1..4094";
                  }
                  description
                    "CE VLAN begin.";
                }
                leaf cevlan-end {
                  type uint16 {
                    range "1..4094";
                  }
                  description
                    "CE VLAN end.";
                }
                leaf instance-name {
                  type leafref {
                    path "/ncs:devices/ncs:device/ncs:live-status/mirror:mirror/mirror:instances/mirror:instance/mirror:instance-name" {
                      tailf:xpath-root 3;
                    }
                  }
                  // NCS drop mandatory statement
                  description
                    "Mirror instance name.";
                }
                leaf identify {
                  type live_ncs_identifier-type;
                  // NCS drop mandatory statement
                  description
                    "Identify.";
                }
                leaf group-name {
                  type string {
                    length "1..31";
                  }
                  description
                    "Group name.";
                }
              }
            }
          }
        }
      }
      container port-observe {
        presence "port-observe";
        description
          "Enable/disable specify observing port index.";
        leaf observe-index {
          type uint8 {
            range "1..255";
          }
          // NCS drop mandatory statement
          description
            "Observing index. An index corresponds to only one observing port.";
        }
        leaf without-filter {
          type live_ncs_without-filter;
          // NCS drop default statement
          description
            "Disable observe filter in observe port.";
        }
        leaf destination-mac {
          type pub-type:live_ncs_mac-address;
          description
            "The observer port specifies the MAC address.";
        }
        leaf pop-label {
          type live_ncs_pop-label;
          // NCS drop must statement
          description
            "Type of POP MPLS label.";
        }
        leaf sub-extend {
          // NCS drop when statement
          type empty;
          description
            "The MPLS label-POP function enable on sub-interface.";
        }
        leaf with-linklayer-header {
          type live_ncs_with-linklayer-header;
          // NCS drop must statement
          // NCS drop default statement
          description
            "Specify packet mirroring from layer 3.";
        }
      }
    }
  }
  augment "/ncs:devices/ncs:device/ncs:config/ifm:ifm/ifm:interfaces/ifm:interface" {
    description
      "Port-mirror.";
    container mirror {
      tailf:ncs-device-type "netconf";
      tailf:display-when "not(../../../../../ncs:module) or ../../../../../ncs:module[ncs:name='huawei-mirror']";
      description
        "Configure port mirroring.";
      container port-mirrors {
        must 'not(count(./port-mirror)>0 and (../port-observe or count(../integrateds/integrated)>0))' {
          tailf:xpath-root 3;
        }
        description
          "List of mirroring interfaces.";
        list port-mirror {
          must "((./direction='inbound' and not(../../evc-l2-port-mirrors/pubs/pub[direction='inbound'])) or (./direction='outbound' and not(../../evc-l2-port-mirrors/pubs/pub[direction='outbound'])))" {
            tailf:xpath-root 3;
          }
          must "((./direction='inbound' and not(../../evc-l2-port-mirrors/dot1q-types/dot1q-type[direction='inbound'])) or (./direction='outbound' and not(../../evc-l2-port-mirrors/dot1q-types/dot1q-type[direction='outbound'])))" {
            tailf:xpath-root 3;
          }
          must "((./direction='inbound' and not(../../evc-l2-port-mirrors/qinq-types/qinq-type[direction='inbound'])) or (./direction='outbound' and not(../../evc-l2-port-mirrors/qinq-types/qinq-type[direction='outbound'])))" {
            tailf:xpath-root 3;
          }
          key "direction cpu-packet";
          description
            "Configure mirroring interface.";
          leaf direction {
            type direction-type;
            description
              "Direction.";
          }
          leaf cpu-packet {
            type boolean;
            must "../direction!='outbound' or ../cpu-packet!='true'" {
              tailf:xpath-root 3;
            }
            description
              "Enable/disable a separate mirroring function for sending CPU packets.";
          }
          choice property {
            description
              "Port mirroring property.";
            case vlan {
              description
                "Virtual LAN.";
              leaf cevlan {
                type pub-type:vlan-range;
                must '../../../../ethernet:ethernet/ethernet:main-interface/ethernet:l2-attribute' {
                  tailf:xpath-root 3;
                }
                must "not(../cpu-packet='true')" {
                  tailf:xpath-root 3;
                }
                description
                  "VLAN ID.";
              }
            }
            case user-defined-filter-rule {
              description
                "Mirror user-defined-filter rule.";
              leaf filter-id {
                type leafref {
                  path "/ncs:devices/ncs:device/ncs:config/mirror:mirror/mirror:observe-user-define-acls/mirror:observe-user-define-acl/mirror:filter-id" {
                    tailf:xpath-root 3;
                  }
                }
                description
                  "Filter index.";
              }
            }
          }
        }
      }
      container port-mirror-slice {
        presence "create port-mirroring slice-size";
        description
          "Enable/disable grab fixed-length packet.";
        leaf slice-size {
          type uint32 {
            range "64..9600";
          }
          units "Byte";
          mandatory true;
          description
            "Length of packet.";
        }
      }
      container without-header {
        when '../port-mirrors/port-mirror' {
          tailf:xpath-root 3;
        }
        must "(../port-mirrors/port-mirror[direction='inbound'] and not(../port-mirrors/port-mirror[direction='inbound']/cevlan)) or
(../port-mirrors/port-mirror[direction='outbound'] and not(../port-mirrors/port-mirror[direction='outbound']/cevlan))" {
          tailf:xpath-root 3;
        }
        presence "create without-header";
        description
          "Enable/disable specify packet mirroring from layer 3.";
      }
      container port-mirror-car {
        must 'not(../port-observe)' {
          tailf:xpath-root 3;
        }
        must '(not(./pir) and not(./pbs)) or (./pbs)' {
          tailf:xpath-root 3;
        }
        must 'not(./pir) or ./pir>=./cir' {
          tailf:xpath-root 3;
        }
        presence "create port-mirror-car";
        description
          "Enable/disable flow mirroring car action.";
        leaf cir {
          type uint32 {
            range "0..4294967295";
          }
          units "kbit/s";
          mandatory true;
          description
            "Committed information rate.";
        }
        leaf pir {
          type uint32 {
            range "1..4294967295";
          }
          units "kbit/s";
          description
            "Peak information rate.";
        }
        leaf cbs {
          type uint32 {
            range "0..4294967295";
          }
          units "Byte";
          mandatory true;
          description
            "Committed burst size.";
        }
        leaf pbs {
          type uint32 {
            range "0..4294967295";
          }
          units "Byte";
          description
            "Peak burst size.";
        }
      }
      container port-mirror-to {
        must 'not(../port-observe )' {
          tailf:xpath-root 3;
        }
        presence "create port-mirror-to";
        description
          "Enable/disable flow mirroring to.";
        leaf observe-index {
          type string {
            length "1..50";
            pattern '(null0)|((25[0-5]|2[0-4]\d|1\d\d|[1-9]\d|[1-9]){1}((,(25[0-5]|2[0-4]\d|1\d\d|[1-9]\d|[1-9])){0,7}))';
          }
          mandatory true;
          description
            "Observing index. Enter the observation index value, which is separated by a comma (,) and the index value must be unique. For example, 1 or 1,3,5,7,9. If mirroring based on no observing port is required, enter null0.";
        }
      }
      container port-fragments {
        when "../../ifm:type='Mp-group'" {
          tailf:xpath-root 3;
        }
        must 'not(count(./port-fragment)>0 and (../port-mirrors/port-mirror/cevlan or ../port-observe or count(../integrateds/integrated)>0 or
count(../evc-l2-port-mirrors/pubs/pub)>0 or count(../evc-l2-port-mirrors/dot1q-types/dot1q-type)>0 or count(../evc-l2-port-mirrors/qinq-types/qinq-type)>0))' {
          tailf:xpath-root 3;
        }
        description
          "List of fragment mirroring interfaces.";
        list port-fragment {
          key "direction";
          description
            "Configure fragment mirroring interface (supported by some subcards).";
          leaf direction {
            type direction-type;
            description
              "Direction.";
          }
        }
      }
      container integrateds {
        must 'not(count(./integrated)>0 and (../port-observe or ../port-mirror-to))' {
          tailf:xpath-root 3;
        }
        description
          "List of the port-mirroring to interface command configures port mirroring in integrated mode.";
        list integrated {
          key "direction cpu-packet";
          description
            "Configure the port-mirroring to interface command configures port mirroring in integrated mode.";
          leaf direction {
            type direction-type;
            description
              "Direction.";
          }
          leaf cpu-packet {
            type boolean;
            must "../direction!='outbound' or ../cpu-packet!='true'" {
              tailf:xpath-root 3;
            }
            must "not(../../integrated[direction='inbound'][cpu-packet != current()])" {
              tailf:xpath-root 3;
            }
            description
              "Enable/disable a separate mirroring function for sending CPU packets.";
          }
          leaf filter-id {
            type leafref {
              path "/ncs:devices/ncs:device/ncs:config/mirror:mirror/mirror:observe-user-define-acls/mirror:observe-user-define-acl/mirror:filter-id" {
                tailf:xpath-root 3;
              }
            }
            description
              "User-defined-filter rule number.";
          }
          choice observe-port {
            mandatory true;
            description
              "Observe port.";
            case port-null0 {
              description
                "Specify observing port null0.";
              leaf null0 {
                type empty;
                description
                  "Specify observing port null0.";
              }
            }
            case port-observe {
              description
                "Port observe.";
              leaf if-name {
                type leafref {
                  path "/ncs:devices/ncs:device/ncs:config/ifm:ifm/ifm:interfaces/ifm:interface/ifm:name" {
                    tailf:xpath-root 3;
                  }
                }
                must '../observe-index' {
                  tailf:xpath-root 3;
                }
                must '../../../../ifm:name != current()' {
                  tailf:xpath-root 3;
                }
                description
                  "Name of an observing interface.";
              }
              leaf observe-index {
                type uint8 {
                  range "1..255";
                }
                must '../if-name' {
                  tailf:xpath-root 3;
                }
                description
                  "Observing index. An index corresponds to only one observing port.";
              }
            }
          }
        }
      }
      container bas-port-mirrors {
        must 'not (count(./bas-port-mirror)>0 and (../port-observe or count(../integrateds/integrated)>0 or count(../evc-l2-port-mirrors/pubs/pub)>0
or count(../evc-l2-port-mirrors/dot1q-types/dot1q-type)>0 or count(../evc-l2-port-mirrors/qinq-types/qinq-type)>0))' {
          tailf:xpath-root 3;
        }
        description
          "List of QinQ match port mirrors.";
        list bas-port-mirror {
          must '../../../ethernet:ethernet/ethernet:l3-sub-interface/ethernet:user-vlan-any or ../../../ethernet:ethernet/ethernet:l3-sub-interface/ethernet:user-vlan-common/ethernet:user-vlan-qinqs' {
            tailf:xpath-root 3;
          }
          must './pevlan-begin <= ./pevlan-end' {
            tailf:xpath-root 3;
          }
          must './cevlan-begin <= ./cevlan-end' {
            tailf:xpath-root 3;
          }
          must '(./pevlan-end - ./pevlan-begin + 1) * (./cevlan-end - ./cevlan-begin + 1) <= 4096' {
            tailf:xpath-root 3;
          }
          must "((./direction='inbound' and not(../../port-mirrors/port-mirror[direction='inbound'])) or (./direction='outbound' and not(../../port-mirrors/port-mirror[direction='outbound'])))" {
            tailf:xpath-root 3;
          }
          key "direction pevlan-begin pevlan-end cevlan-begin cevlan-end";
          description
            "Configure QinQ match port mirror.";
          leaf direction {
            type direction-type;
            description
              "Direction.";
          }
          leaf pevlan-begin {
            type uint16 {
              range "1..4094";
            }
            description
              "PEVLANBegin.";
          }
          leaf pevlan-end {
            type uint16 {
              range "1..4094";
            }
            description
              "PEVLANEnd.";
          }
          leaf cevlan-begin {
            type uint16 {
              range "1..4094";
            }
            description
              "CEVLANBegin.";
          }
          leaf cevlan-end {
            type uint16 {
              range "1..4094";
            }
            description
              "CEVLANEnd.";
          }
        }
      }
      container evc-l2-port-mirrors {
        description
          "Configure EVC l2 port mirror.";
        choice evc-l2-port-cfg {
          description
            "EVC l2 port cfg.";
          case pub {
            description
              "EVC l2 untag port mirror.";
            container pubs {
              must 'not(count(./pub)>0 and (../../port-observe))' {
                tailf:xpath-root 3;
              }
              description
                "List of EVC l2 port mirror.";
              list pub {
                must '(../../../../ethernet:ethernet/ethernet:l2-sub-interface/ethernet:default or ../../../../ethernet:ethernet/ethernet:l2-sub-interface/ethernet:untag or
../../../../ethernet:ethernet/ethernet:l2-sub-interface/ethernet:dot1q/ethernet:vlans or ../../../../ethernet:ethernet/ethernet:l2-sub-interface/ethernet:qinqs/ethernet:qinq-vids/ethernet:qinq-vid or
../../../../ethernet:ethernet/ethernet:l2-sub-interface/ethernet:qinqs/ethernet:qinq-vid-ce-default)' {
                  tailf:xpath-root 3;
                }
                must "((./direction='inbound' and not(../../../port-mirrors/port-mirror[direction='inbound'] or ../../../integrateds/integrated[direction='inbound'])) or
(./direction='outbound' and not(../../../port-mirrors/port-mirror[direction='outbound'] or ../../../integrateds/integrated[direction='outbound'])))" {
                  tailf:xpath-root 3;
                }
                key "direction";
                description
                  "Configure EVC l2 port mirror.";
                leaf direction {
                  type direction-type;
                  description
                    "Direction.";
                }
                leaf instance-name {
                  type leafref {
                    path "/ncs:devices/ncs:device/ncs:config/mirror:mirror/mirror:instances/mirror:instance/mirror:instance-name" {
                      tailf:xpath-root 3;
                    }
                  }
                  mandatory true;
                  description
                    "Mirror instance name.";
                }
                leaf group-name {
                  type string {
                    length "1..31";
                  }
                  description
                    "Group name.";
                }
              }
            }
          }
          case dot1q-type {
            description
              "EVC l2 dot1q-terminal port mirror.";
            container dot1q-types {
              must 'not(count(./dot1q-type)>0 and (../../port-observe))' {
                tailf:xpath-root 3;
              }
              description
                "List of EVC l2 port mirror.";
              list dot1q-type {
                must '../../../../ethernet:ethernet/ethernet:l2-sub-interface/ethernet:dot1q/ethernet:vlans' {
                  tailf:xpath-root 3;
                }
                must "((./direction='inbound' and not(../../../port-mirrors/port-mirror[direction='inbound'] or ../../../integrateds/integrated[direction='inbound'] or ../../pubs/pub[direction='inbound'])) or
(./direction='outbound' and not(../../../port-mirrors/port-mirror[direction='outbound'] or ../../../integrateds/integrated[direction='outbound'] or ../../pubs/pub[direction='inbound'])))" {
                  tailf:xpath-root 3;
                }
                must './vlan-begin <= ./vlan-end' {
                  tailf:xpath-root 3;
                }
                key "direction vlan-begin vlan-end";
                description
                  "Configure EVC l2 port mirror.";
                leaf direction {
                  type direction-type;
                  description
                    "Direction.";
                }
                leaf vlan-begin {
                  type uint16 {
                    range "1..4094";
                  }
                  description
                    "CE VLAN begin.";
                }
                leaf vlan-end {
                  type uint16 {
                    range "1..4094";
                  }
                  description
                    "CE VLAN end.";
                }
                leaf instance-name {
                  type leafref {
                    path "/ncs:devices/ncs:device/ncs:config/mirror:mirror/mirror:instances/mirror:instance/mirror:instance-name" {
                      tailf:xpath-root 3;
                    }
                  }
                  mandatory true;
                  description
                    "Mirror instance name.";
                }
                leaf identify {
                  type identifier-type;
                  must "../identify='none' or ../identify='ce-vid'" {
                    tailf:xpath-root 3;
                  }
                  mandatory true;
                  description
                    "Identify.";
                }
                leaf group-name {
                  type string {
                    length "1..31";
                  }
                  description
                    "Group name.";
                }
              }
            }
          }
          case qinq-type {
            description
              "EVC l2 QinQ-terminal port mirror.";
            container qinq-types {
              must 'not(count(./qinq-type)>0 and (../../port-observe))' {
                tailf:xpath-root 3;
              }
              description
                "List of EVC l2 port mirror.";
              list qinq-type {
                must '../../../../ethernet:ethernet/ethernet:l2-sub-interface/ethernet:qinqs/ethernet:qinq-vids/ethernet:qinq-vid' {
                  tailf:xpath-root 3;
                }
                must "((./direction='inbound' and not(../../../port-mirrors/port-mirror[direction='inbound'] or ../../../integrateds/integrated[direction='inbound'] or ../../pubs/pub[direction='inbound'])) or
(./direction='outbound' and not(../../../port-mirrors/port-mirror[direction='outbound'] or ../../../integrateds/integrated[direction='outbound'] or ../../pubs/pub[direction='outbound'])))" {
                  tailf:xpath-root 3;
                }
                must './cevlan-begin <= ./cevlan-end' {
                  tailf:xpath-root 3;
                }
                key "direction pevlan cevlan-begin cevlan-end";
                description
                  "Configure EVC l2 port mirror.";
                leaf direction {
                  type direction-type;
                  description
                    "Direction.";
                }
                leaf pevlan {
                  type uint16 {
                    range "1..4094";
                  }
                  description
                    "PE VLAN.";
                }
                leaf cevlan-begin {
                  type uint16 {
                    range "1..4094";
                  }
                  description
                    "CE VLAN begin.";
                }
                leaf cevlan-end {
                  type uint16 {
                    range "1..4094";
                  }
                  description
                    "CE VLAN end.";
                }
                leaf instance-name {
                  type leafref {
                    path "/ncs:devices/ncs:device/ncs:config/mirror:mirror/mirror:instances/mirror:instance/mirror:instance-name" {
                      tailf:xpath-root 3;
                    }
                  }
                  mandatory true;
                  description
                    "Mirror instance name.";
                }
                leaf identify {
                  type identifier-type;
                  mandatory true;
                  description
                    "Identify.";
                }
                leaf group-name {
                  type string {
                    length "1..31";
                  }
                  description
                    "Group name.";
                }
              }
            }
          }
        }
      }
      container port-observe {
        presence "port-observe";
        description
          "Enable/disable specify observing port index.";
        leaf observe-index {
          type uint8 {
            range "1..255";
          }
          mandatory true;
          description
            "Observing index. An index corresponds to only one observing port.";
        }
        leaf without-filter {
          type without-filter;
          default "false";
          description
            "Disable observe filter in observe port.";
        }
        leaf destination-mac {
          type pub-type:mac-address;
          description
            "The observer port specifies the MAC address.";
        }
        leaf pop-label {
          type pop-label;
          must "not(../destination-mac) and ../../../ifm:class='main-interface'" {
            tailf:xpath-root 3;
          }
          description
            "Type of POP MPLS label.";
        }
        leaf sub-extend {
          when '../pop-label' {
            tailf:xpath-root 3;
          }
          type empty;
          description
            "The MPLS label-POP function enable on sub-interface.";
        }
        leaf with-linklayer-header {
          type with-linklayer-header;
          must "../../../ifm:class='sub-interface' or ../with-linklayer-header='false'" {
            tailf:xpath-root 3;
          }
          default "false";
          description
            "Specify packet mirroring from layer 3.";
        }
      }
    }
  }
  augment "/ncs:devices/ncs:template/ncs:ned-id/ncs:config/bd:bd/bd:instances/bd:instance" {
    description
      "Port mirror under bridge domain.";
    container mirror {
      description
        "Configure mirror.";
      container bd-port-mirrors {
        description
          "List of BD port mirror.";
        list bd-port-mirror {
          // NCS patched for predictable order
          ordered-by user;
          key "direction";
          description
            "Configure BD port mirror.";
          leaf direction {
            type ncs_template_direction-type;
            description
              "Direction.";
          }
          leaf instance-name {
            type string;
            // NCS drop mandatory statement
            description
              "Mirror instance name.";
          }
          leaf group-name {
            type string;
            description
              "Group name.";
          }
        }
      }
    }
  }
  augment "/ncs:devices/ncs:device/ncs:live-status/bd:bd/bd:instances/bd:instance" {
    description
      "Port mirror under bridge domain.";
    container mirror {
      tailf:ncs-device-type "netconf";
      tailf:display-when "not(../../../../../ncs:module) or ../../../../../ncs:module[ncs:name='huawei-mirror'] or (../../../../../ncs:live-status-protocol[not(ncs:capability)]) or (../../../../../ncs:live-status-protocol/ncs:capability/ncs:module[.='huawei-mirror'])";
      description
        "Configure mirror.";
      container bd-port-mirrors {
        description
          "List of BD port mirror.";
        list bd-port-mirror {
          key "direction";
          description
            "Configure BD port mirror.";
          leaf direction {
            type live_ncs_direction-type;
            description
              "Direction.";
          }
          leaf instance-name {
            type leafref {
              path "/ncs:devices/ncs:device/ncs:live-status/mirror:mirror/mirror:instances/mirror:instance/mirror:instance-name" {
                tailf:xpath-root 3;
              }
            }
            // NCS drop mandatory statement
            description
              "Mirror instance name.";
          }
          leaf group-name {
            type string {
              length "1..31";
            }
            description
              "Group name.";
          }
        }
      }
    }
  }
  augment "/ncs:devices/ncs:device/ncs:config/bd:bd/bd:instances/bd:instance" {
    description
      "Port mirror under bridge domain.";
    container mirror {
      tailf:ncs-device-type "netconf";
      tailf:display-when "not(../../../../../ncs:module) or ../../../../../ncs:module[ncs:name='huawei-mirror']";
      description
        "Configure mirror.";
      container bd-port-mirrors {
        description
          "List of BD port mirror.";
        list bd-port-mirror {
          key "direction";
          description
            "Configure BD port mirror.";
          leaf direction {
            type direction-type;
            description
              "Direction.";
          }
          leaf instance-name {
            type leafref {
              path "/ncs:devices/ncs:device/ncs:config/mirror:mirror/mirror:instances/mirror:instance/mirror:instance-name" {
                tailf:xpath-root 3;
              }
            }
            mandatory true;
            description
              "Mirror instance name.";
          }
          leaf group-name {
            type string {
              length "1..31";
            }
            description
              "Group name.";
          }
        }
      }
    }
  }
}
