module huawei-bras-vas {
  // Generated by yanger -t ncs
  tailf:mount-id "huawei-nc-1.0:huawei-nc-1.0";
  tailf:ncs-device-type "netconf";

  namespace "urn:huawei:yang:huawei-bras-vas";
  prefix bras-vas;

  import huawei-pub-type {
    prefix pub-type;
  }
  import huawei-extension {
    prefix ext;
  }
  import huawei-aaa {
    prefix aaa;
  }
  import huawei-radius {
    prefix radius;
  }
  import huawei-qos {
    prefix qos;
  }
  import huawei-bras-basic-access {
    prefix bras-basic-access;
  }
  import huawei-devm {
    prefix devm;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Bras-vas.";

  revision 2020-03-12 {
    description
      "Modify description.";
    reference "Huawei private.";
  }
  revision 2019-03-15 {
    description
      "Init revision.";
    reference "Huawei private.";
  }
  ext:task-name "vas";

  typedef ncs_template_bras-vas-flow-queue-type {
    type string;
    description
      "Type of flow queue.";
  }

  typedef ncs_template_bras-vas-service-source {
    type string;
    description
      "Status of the EDSG accounting copy function.";
  }

  typedef ncs_template_bras-vas-method-type {
    type string;
    description
      "Method type.";
  }

  typedef ncs_template_bras-vas-service-substate {
    type string;
    description
      "Service traffic statistics type. The default value is IPv4. This parameter can be set to IPv6.";
  }

  typedef ncs_template_bras-vas-rate-limit-mode {
    type string;
    description
      "Sets a rate limit mode for EDSG service traffic.";
  }

  typedef ncs_template_bras-vas-out-rate-limit-mode {
    type string;
    description
      "Sets a rate limit mode for EDSG service traffic.";
  }

  typedef ncs_template_bras-vas-service-ip-type {
    type string;
    description
      "Service ip type.";
  }

  typedef ncs_template_bras-vas-policy-type {
    type string;
    description
      "Vas policy type.";
  }

  typedef ncs_template_bras-vas-online-offline-type {
    type string;
    description
      "Online or offline.";
  }

  typedef ncs_template_bras-vas-quota-out-online-offline-type {
    type string;
    description
      "Online or offline.";
  }

  typedef ncs_rpc_notif_bras-vas-flow-queue-type {
    type enumeration {
      enum "be" {
        value 0;
        description
          "Service type BE.";
      }
      enum "af1" {
        value 1;
        description
          "Service type AF1.";
      }
      enum "af2" {
        value 2;
        description
          "Service type AF2.";
      }
      enum "af3" {
        value 3;
        description
          "Service type AF3.";
      }
      enum "af4" {
        value 4;
        description
          "Service type AF4.";
      }
      enum "ef" {
        value 5;
        description
          "Service type EF.";
      }
      enum "cs6" {
        value 6;
        description
          "Service type CS6.";
      }
      enum "cs7" {
        value 7;
        description
          "Service type CS7.";
      }
    }
    description
      "Type of flow queue.";
  }

  typedef ncs_rpc_notif_bras-vas-service-source {
    type enumeration {
      enum "authentication-ack" {
        value 1;
        description
          "Authentication ack.";
      }
      enum "radius" {
        value 2;
        description
          "Radius.";
      }
      enum "diameter" {
        value 3;
        description
          "Diameter.";
      }
      enum "rui" {
        value 4;
        description
          "Rui.";
      }
    }
    description
      "Status of the EDSG accounting copy function.";
  }

  typedef ncs_rpc_notif_bras-vas-method-type {
    type enumeration {
      enum "local" {
        value 1;
        description
          "Local.";
      }
      enum "none" {
        value 2;
        description
          "None.";
      }
      enum "radius" {
        value 3;
        description
          "Radius.";
      }
      enum "cops" {
        value 4;
        description
          "Cops.";
      }
      enum "diameter" {
        value 5;
        description
          "Diameter.";
      }
    }
    description
      "Method type.";
  }

  typedef ncs_rpc_notif_bras-vas-service-substate {
    type enumeration {
      enum "policy-downloading" {
        value 0;
        description
          "Policy downloading.";
      }
      enum "authenticating" {
        value 1;
        description
          "Authenticating.";
      }
      enum "prepaid-initializing" {
        value 2;
        description
          "Prepaid initializing.";
      }
      enum "start-accounting" {
        value 3;
        description
          "Start accounting.";
      }
      enum "accounting" {
        value 4;
        description
          "Accounting.";
      }
      enum "ready" {
        value 5;
        description
          "Ready.";
      }
      enum "flow-query" {
        value 6;
        description
          "Flow query.";
      }
      enum "policy-unloading" {
        value 7;
        description
          "Policy unloading.";
      }
      enum "stop-accounting" {
        value 8;
        description
          "Stop accounting.";
      }
    }
    description
      "Service traffic statistics type. The default value is IPv4. This parameter can be set to IPv6.";
  }

  typedef ncs_rpc_notif_bras-vas-rate-limit-mode {
    type enumeration {
      enum "user-queue" {
        value 0;
        description
          "The rate limit mode is user queue.";
      }
      enum "car" {
        value 1;
        description
          "The rate limit mode is CAR.";
      }
    }
    description
      "Sets a rate limit mode for EDSG service traffic.";
  }

  typedef ncs_rpc_notif_bras-vas-out-rate-limit-mode {
    type enumeration {
      enum "user-queue" {
        value 1;
        description
          "The rate limit mode is user queue.";
      }
      enum "car" {
        value 0;
        description
          "The rate limit mode is CAR.";
      }
    }
    description
      "Sets a rate limit mode for EDSG service traffic.";
  }

  typedef ncs_rpc_notif_bras-vas-service-ip-type {
    type enumeration {
      enum "ipv4" {
        value 0;
        description
          "IPv4.";
      }
      enum "ipv6" {
        value 1;
        description
          "IPv6.";
      }
    }
    description
      "Service ip type.";
  }

  typedef ncs_rpc_notif_bras-vas-policy-type {
    type enumeration {
      enum "daa" {
        value 1;
        description
          "Daa policy.";
      }
      enum "bod" {
        value 2;
        description
          "Bod policy.";
      }
    }
    description
      "Vas policy type.";
  }

  typedef ncs_rpc_notif_bras-vas-online-offline-type {
    type enumeration {
      enum "offline" {
        value 0;
        description
          "Type of offline.";
      }
      enum "online" {
        value 1;
        description
          "Type of online.";
      }
    }
    description
      "Online or offline.";
  }

  typedef ncs_rpc_notif_bras-vas-quota-out-online-offline-type {
    type enumeration {
      enum "offline" {
        value 1;
        description
          "Type of offline.";
      }
      enum "online" {
        value 0;
        description
          "Type of online.";
      }
    }
    description
      "Online or offline.";
  }

  typedef live_ncs_bras-vas-flow-queue-type {
    type enumeration {
      enum "be" {
        value 0;
        description
          "Service type BE.";
      }
      enum "af1" {
        value 1;
        description
          "Service type AF1.";
      }
      enum "af2" {
        value 2;
        description
          "Service type AF2.";
      }
      enum "af3" {
        value 3;
        description
          "Service type AF3.";
      }
      enum "af4" {
        value 4;
        description
          "Service type AF4.";
      }
      enum "ef" {
        value 5;
        description
          "Service type EF.";
      }
      enum "cs6" {
        value 6;
        description
          "Service type CS6.";
      }
      enum "cs7" {
        value 7;
        description
          "Service type CS7.";
      }
    }
    description
      "Type of flow queue.";
  }

  typedef live_ncs_bras-vas-service-source {
    type enumeration {
      enum "authentication-ack" {
        value 1;
        description
          "Authentication ack.";
      }
      enum "radius" {
        value 2;
        description
          "Radius.";
      }
      enum "diameter" {
        value 3;
        description
          "Diameter.";
      }
      enum "rui" {
        value 4;
        description
          "Rui.";
      }
    }
    description
      "Status of the EDSG accounting copy function.";
  }

  typedef live_ncs_bras-vas-method-type {
    type enumeration {
      enum "local" {
        value 1;
        description
          "Local.";
      }
      enum "none" {
        value 2;
        description
          "None.";
      }
      enum "radius" {
        value 3;
        description
          "Radius.";
      }
      enum "cops" {
        value 4;
        description
          "Cops.";
      }
      enum "diameter" {
        value 5;
        description
          "Diameter.";
      }
    }
    description
      "Method type.";
  }

  typedef live_ncs_bras-vas-service-substate {
    type enumeration {
      enum "policy-downloading" {
        value 0;
        description
          "Policy downloading.";
      }
      enum "authenticating" {
        value 1;
        description
          "Authenticating.";
      }
      enum "prepaid-initializing" {
        value 2;
        description
          "Prepaid initializing.";
      }
      enum "start-accounting" {
        value 3;
        description
          "Start accounting.";
      }
      enum "accounting" {
        value 4;
        description
          "Accounting.";
      }
      enum "ready" {
        value 5;
        description
          "Ready.";
      }
      enum "flow-query" {
        value 6;
        description
          "Flow query.";
      }
      enum "policy-unloading" {
        value 7;
        description
          "Policy unloading.";
      }
      enum "stop-accounting" {
        value 8;
        description
          "Stop accounting.";
      }
    }
    description
      "Service traffic statistics type. The default value is IPv4. This parameter can be set to IPv6.";
  }

  typedef live_ncs_bras-vas-rate-limit-mode {
    type enumeration {
      enum "user-queue" {
        value 0;
        description
          "The rate limit mode is user queue.";
      }
      enum "car" {
        value 1;
        description
          "The rate limit mode is CAR.";
      }
    }
    description
      "Sets a rate limit mode for EDSG service traffic.";
  }

  typedef live_ncs_bras-vas-out-rate-limit-mode {
    type enumeration {
      enum "user-queue" {
        value 1;
        description
          "The rate limit mode is user queue.";
      }
      enum "car" {
        value 0;
        description
          "The rate limit mode is CAR.";
      }
    }
    description
      "Sets a rate limit mode for EDSG service traffic.";
  }

  typedef live_ncs_bras-vas-service-ip-type {
    type enumeration {
      enum "ipv4" {
        value 0;
        description
          "IPv4.";
      }
      enum "ipv6" {
        value 1;
        description
          "IPv6.";
      }
    }
    description
      "Service ip type.";
  }

  typedef live_ncs_bras-vas-policy-type {
    type enumeration {
      enum "daa" {
        value 1;
        description
          "Daa policy.";
      }
      enum "bod" {
        value 2;
        description
          "Bod policy.";
      }
    }
    description
      "Vas policy type.";
  }

  typedef live_ncs_bras-vas-online-offline-type {
    type enumeration {
      enum "offline" {
        value 0;
        description
          "Type of offline.";
      }
      enum "online" {
        value 1;
        description
          "Type of online.";
      }
    }
    description
      "Online or offline.";
  }

  typedef live_ncs_bras-vas-quota-out-online-offline-type {
    type enumeration {
      enum "offline" {
        value 1;
        description
          "Type of offline.";
      }
      enum "online" {
        value 0;
        description
          "Type of online.";
      }
    }
    description
      "Online or offline.";
  }

  typedef bras-vas-flow-queue-type {
    type enumeration {
      enum "be" {
        value 0;
        description
          "Service type BE.";
      }
      enum "af1" {
        value 1;
        description
          "Service type AF1.";
      }
      enum "af2" {
        value 2;
        description
          "Service type AF2.";
      }
      enum "af3" {
        value 3;
        description
          "Service type AF3.";
      }
      enum "af4" {
        value 4;
        description
          "Service type AF4.";
      }
      enum "ef" {
        value 5;
        description
          "Service type EF.";
      }
      enum "cs6" {
        value 6;
        description
          "Service type CS6.";
      }
      enum "cs7" {
        value 7;
        description
          "Service type CS7.";
      }
    }
    description
      "Type of flow queue.";
  }

  typedef bras-vas-service-source {
    type enumeration {
      enum "authentication-ack" {
        value 1;
        description
          "Authentication ack.";
      }
      enum "radius" {
        value 2;
        description
          "Radius.";
      }
      enum "diameter" {
        value 3;
        description
          "Diameter.";
      }
      enum "rui" {
        value 4;
        description
          "Rui.";
      }
    }
    description
      "Status of the EDSG accounting copy function.";
  }

  typedef bras-vas-method-type {
    type enumeration {
      enum "local" {
        value 1;
        description
          "Local.";
      }
      enum "none" {
        value 2;
        description
          "None.";
      }
      enum "radius" {
        value 3;
        description
          "Radius.";
      }
      enum "cops" {
        value 4;
        description
          "Cops.";
      }
      enum "diameter" {
        value 5;
        description
          "Diameter.";
      }
    }
    description
      "Method type.";
  }

  typedef bras-vas-service-substate {
    type enumeration {
      enum "policy-downloading" {
        value 0;
        description
          "Policy downloading.";
      }
      enum "authenticating" {
        value 1;
        description
          "Authenticating.";
      }
      enum "prepaid-initializing" {
        value 2;
        description
          "Prepaid initializing.";
      }
      enum "start-accounting" {
        value 3;
        description
          "Start accounting.";
      }
      enum "accounting" {
        value 4;
        description
          "Accounting.";
      }
      enum "ready" {
        value 5;
        description
          "Ready.";
      }
      enum "flow-query" {
        value 6;
        description
          "Flow query.";
      }
      enum "policy-unloading" {
        value 7;
        description
          "Policy unloading.";
      }
      enum "stop-accounting" {
        value 8;
        description
          "Stop accounting.";
      }
    }
    description
      "Service traffic statistics type. The default value is IPv4. This parameter can be set to IPv6.";
  }

  typedef bras-vas-rate-limit-mode {
    type enumeration {
      enum "user-queue" {
        value 0;
        description
          "The rate limit mode is user queue.";
      }
      enum "car" {
        value 1;
        description
          "The rate limit mode is CAR.";
      }
    }
    description
      "Sets a rate limit mode for EDSG service traffic.";
  }

  typedef bras-vas-out-rate-limit-mode {
    type enumeration {
      enum "user-queue" {
        value 1;
        description
          "The rate limit mode is user queue.";
      }
      enum "car" {
        value 0;
        description
          "The rate limit mode is CAR.";
      }
    }
    description
      "Sets a rate limit mode for EDSG service traffic.";
  }

  typedef bras-vas-service-ip-type {
    type enumeration {
      enum "ipv4" {
        value 0;
        description
          "IPv4.";
      }
      enum "ipv6" {
        value 1;
        description
          "IPv6.";
      }
    }
    description
      "Service ip type.";
  }

  typedef bras-vas-policy-type {
    type enumeration {
      enum "daa" {
        value 1;
        description
          "Daa policy.";
      }
      enum "bod" {
        value 2;
        description
          "Bod policy.";
      }
    }
    description
      "Vas policy type.";
  }

  typedef bras-vas-online-offline-type {
    type enumeration {
      enum "offline" {
        value 0;
        description
          "Type of offline.";
      }
      enum "online" {
        value 1;
        description
          "Type of online.";
      }
    }
    description
      "Online or offline.";
  }

  typedef bras-vas-quota-out-online-offline-type {
    type enumeration {
      enum "offline" {
        value 1;
        description
          "Type of offline.";
      }
      enum "online" {
        value 0;
        description
          "Type of online.";
      }
    }
    description
      "Online or offline.";
  }

  grouping ncs_template_rate-limit-type {
    description
      "Configures the inbound and outbound rate for the service policy template.";
    leaf cir {
      type string;
      units "kbit/s";
      // NCS drop mandatory statement
      description
        "Specifies committed information rate.";
    }
    leaf pir {
      type string;
      units "kbit/s";
      // NCS drop must statement
      description
        "Specifies the peak information rate.";
    }
    leaf cbs {
      type string;
      units "kbit/s";
      description
        "Specifies the committed burst size.";
    }
    leaf pbs {
      type string;
      units "kbit/s";
      // NCS drop must statement
      description
        "Specifies the peak burst size.";
    }
    leaf flow-queue-pbs {
      // NCS drop when statement
      type string;
      units "Byte";
      // NCS drop must statement
      description
        "Specifies the peak burst size of flow queue.";
    }
  }

  grouping ncs_template_bras-vas-user-traffic-type {
    description
      "Configures the inbound and outbound rate for the service policy template.";
    leaf cs7 {
      type string;
      // NCS drop default statement
      description
        "Enable/disable a service class is CS7.";
    }
    leaf cs6 {
      type string;
      // NCS drop default statement
      description
        "Enable/disable a service class is CS6.";
    }
    leaf ef {
      type string;
      // NCS drop default statement
      description
        "Enable/disable a service class is EF.";
    }
    leaf af4 {
      type string;
      // NCS drop default statement
      description
        "Enable/disable a service class is AF4.";
    }
    leaf af3 {
      type string;
      // NCS drop default statement
      description
        "Enable/disable a service class is AF3.";
    }
    leaf af2 {
      type string;
      // NCS drop default statement
      description
        "Enable/disable a service class is AF2.";
    }
    leaf af1 {
      type string;
      // NCS drop default statement
      description
        "Enable/disable a service class is AF1.";
    }
    leaf be {
      type string;
      // NCS drop default statement
      description
        "Enable/disable a service class is BE.";
    }
  }

  grouping ncs_template_remote-policy-cache-type {
    description
      "Display information about a specified EDSG service cache policy in CU.";
    leaf service-policy-index {
      type string;
      description
        "The service policy index.";
    }
    leaf reference-count {
      type string;
      description
        "The reference count.";
    }
  }

  grouping ncs_template_edsg-time-range-info-type {
    description
      "Display edsg time-range information.";
    leaf updated-success-users {
      type string;
      description
        "Number Of Users That Success To Be Updated.";
    }
    leaf updated-failed-users {
      type string;
      description
        "Number Of Users That Fail To Be Updated.";
    }
    leaf to-be-update-users {
      type string;
      description
        "Number Of Users To Be Updated.";
    }
    leaf total-updated-users {
      type string;
      description
        "Total Number Of Updated Users.";
    }
  }

  grouping ncs_template_updated-fail-statistic-type {
    description
      "Failed to update statistic resource for the service.";
    leaf sq-resource-fail-num {
      type string;
      description
        "Failed to Apply SQ Resource For The Service.";
    }
    leaf car-res-fail-num {
      type string;
      description
        "Failed to Apply CAR Resource For The Service.";
    }
    leaf stat-res-fail-num {
      type string;
      description
        "Failed to Apply Statistic Resource For The Service.";
    }
  }

  grouping ncs_template_user-id-bod-or-daa-statistic-type {
    description
      "Display BOD or DAA type information about value-added services based on a specified user ID.";
    leaf service-name {
      type string;
      description
        "Name of a service.";
    }
    leaf service-ip-type {
      type ncs_template_bras-vas-service-ip-type;
      description
        "Service traffic statistics type. The default value is IPv4. This parameter can be set to IPv6.";
    }
    leaf account-method {
      type ncs_template_bras-vas-method-type;
      description
        "Accounting method.";
    }
    leaf normal-server-group {
      type string;
      description
        "Name of the policy server that delivers a service policy.";
    }
    leaf up-committed-rate {
      type string;
      description
        "Upstream committed information rate.";
    }
    leaf up-peak-rate {
      type string;
      description
        "Upstream peak information rate.";
    }
    leaf up-committed-burst-size {
      type string;
      description
        "Upstream committed burst size.";
    }
    leaf up-peak-burst-size {
      type string;
      description
        "Upstream peak burst size.";
    }
    leaf down-committed-rate {
      type string;
      description
        "Downstream CIR.";
    }
    leaf down-peak-rate {
      type string;
      description
        "Downstream PIR.";
    }
    leaf down-committed-burst-rate {
      type string;
      description
        "Downstream CBS.";
    }
    leaf down-peak-burst-size {
      type string;
      description
        "Downstream PBS.";
    }
    leaf service-source-ip {
      type string;
      description
        "Source IP of a service.";
    }
    leaf service-type {
      type string;
      description
        "Type of a service.";
    }
    leaf account-start-time {
      type string;
      description
        "Time when the accounting starts.";
    }
    leaf two-level-acct-server-group {
      type string;
      description
        "Radius server group of two level accounting.";
    }
    leaf physical-acct-server-group {
      type string;
      description
        "Radius server group of physical account.";
    }
    leaf up-flow-packets-high {
      type string;
      units "packet";
      description
        "Number of upstream accounting high packets.";
    }
    leaf up-flow-packets-low {
      type string;
      units "packet";
      description
        "Number of upstream accounting low packets.";
    }
    leaf up-flow-bytes-high {
      type string;
      units "Byte";
      description
        "Number of upstream accounting high bytes.";
    }
    leaf up-flow-bytes-low {
      type string;
      units "Byte";
      description
        "Number of upstream accounting low bytes.";
    }
    leaf down-flow-packets-high {
      type string;
      units "packet";
      description
        "Number of downstream accounting high packets.";
    }
    leaf down-flow-packets-low {
      type string;
      units "packet";
      description
        "Number of downstream accounting low packets.";
    }
    leaf down-flow-bytes-high {
      type string;
      units "Byte";
      description
        "Number of downstream accounting high bytes.";
    }
    leaf down-flow-bytes-low {
      type string;
      units "Byte";
      description
        "Number of downstream accounting low bytes.";
    }
    leaf ipv6-up-flow-packets-high {
      type string;
      units "packet";
      description
        "Number of upstream IPv6 accounting high packets.";
    }
    leaf ipv6-up-flow-packets-low {
      type string;
      units "packet";
      description
        "Number of upstream IPv6 accounting low packets.";
    }
    leaf ipv6-up-flow-bytes-high {
      type string;
      units "Byte";
      description
        "Number of upstream IPv6 accounting high bytes.";
    }
    leaf ipv6-up-flow-bytes-low {
      type string;
      units "Byte";
      description
        "Number of upstream IPv6 accounting low bytes.";
    }
    leaf ipv6-down-flow-packets-high {
      type string;
      units "packet";
      description
        "Number of downstream IPv6 accounting high packets.";
    }
    leaf ipv6-down-flow-packets-low {
      type string;
      units "packet";
      description
        "Number of downstream IPv6 accounting low packets.";
    }
    leaf ipv6-down-flow-bytes-high {
      type string;
      units "Byte";
      description
        "Number of downstream IPv6 accounting high bytes.";
    }
    leaf ipv6-down-flow-bytes-low {
      type string;
      units "Byte";
      description
        "Number of downstream IPv6 accounting low bytes.";
    }
    leaf local-up-flow-packets-high {
      type string;
      units "packet";
      description
        "Number of upstream accounting high packets.";
    }
    leaf local-up-flow-packets-low {
      type string;
      units "packet";
      description
        "Number of upstream accounting low packets.";
    }
    leaf local-up-flow-bytes-high {
      type string;
      units "Byte";
      description
        "Number of upstream accounting high bytes.";
    }
    leaf local-up-flow-bytes-low {
      type string;
      units "Byte";
      description
        "Number of upstream accounting low bytes.";
    }
    leaf local-down-flow-packets-high {
      type string;
      units "packet";
      description
        "Number of downstream accounting high packets.";
    }
    leaf local-down-flow-packets-low {
      type string;
      units "packet";
      description
        "Number of downstream accounting low packets.";
    }
    leaf local-down-flow-bytes-high {
      type string;
      units "Byte";
      description
        "Number of downstream accounting high bytes.";
    }
    leaf local-down-flow-bytes-low {
      type string;
      units "Byte";
      description
        "Number of downstream accounting low bytes.";
    }
    leaf remote-up-flow-packets-high {
      type string;
      units "packet";
      description
        "Number of RUI-backed up upstream accounting high packets.";
    }
    leaf remote-up-flow-packets-low {
      type string;
      units "packet";
      description
        "Number of RUI-backed up upstream accounting low packets.";
    }
    leaf remote-up-flow-bytes-high {
      type string;
      units "Byte";
      description
        "Number of RUI-backed up downstream accounting high bytes.";
    }
    leaf remote-up-flow-bytes-low {
      type string;
      units "Byte";
      description
        "Number of RUI-backed up downstream accounting low bytes.";
    }
    leaf remote-down-flow-packets-high {
      type string;
      units "packet";
      description
        "Number of RUI-backed up downstream accounting high packets.";
    }
    leaf remote-down-flow-packets-low {
      type string;
      units "packet";
      description
        "Number of RUI-backed up downstream accounting low packets.";
    }
    leaf remote-down-flow-bytes-high {
      type string;
      units "Byte";
      description
        "Number of RUI-backed up downstream accounting high bytes.";
    }
    leaf remote-down-flow-bytes-low {
      type string;
      units "Byte";
      description
        "Number of RUI-backed up downstream accounting low bytes.";
    }
    leaf local-v6-up-flow-packets-high {
      type string;
      units "packet";
      description
        "Number of IPv6 upstream accounting high packets.";
    }
    leaf local-v6-up-flow-packets-low {
      type string;
      units "packet";
      description
        "Number of IPv6 upstream accounting low packets.";
    }
    leaf local-v6-up-flow-bytes-high {
      type string;
      units "Byte";
      description
        "Number of IPv6 upstream accounting high bytes.";
    }
    leaf local-v6-up-flow-bytes-low {
      type string;
      units "Byte";
      description
        "Number of IPv6 upstream accounting low bytes.";
    }
    leaf local-v6-down-flow-packets-high {
      type string;
      units "packet";
      description
        "Number of IPv6 downstream accounting high packets.";
    }
    leaf local-v6-down-flow-packets-low {
      type string;
      units "packet";
      description
        "Number of IPv6 downstream accounting low packets.";
    }
    leaf local-v6-down-flow-bytes-high {
      type string;
      units "Byte";
      description
        "Number of IPv6 downstream accounting high bytes.";
    }
    leaf local-v6-down-flow-bytes-low {
      type string;
      units "Byte";
      description
        "Number of IPv6 downstream accounting low bytes.";
    }
    leaf remote-v6-up-flow-packets-high {
      type string;
      units "packet";
      description
        "Number of RUI-backed IPv6 upstream accounting high packets.";
    }
    leaf remote-v6-up-flow-packets-low {
      type string;
      units "packet";
      description
        "Number of RUI-backed IPv6 upstream accounting low packets.";
    }
    leaf remote-v6-up-flow-bytes-high {
      type string;
      units "Byte";
      description
        "Number of RUI-backed IPv6 upstream accounting high bytes.";
    }
    leaf remote-v6-up-flow-bytes-low {
      type string;
      units "Byte";
      description
        "Number of RUI-backed IPv6 upstream accounting low bytes.";
    }
    leaf remote-v6-down-flow-packets-high {
      type string;
      units "packet";
      description
        "Number of RUI-backed IPv6 downstream accounting high packets.";
    }
    leaf remote-v6-down-flow-packets-low {
      type string;
      units "packet";
      description
        "Number of RUI-backed IPv6 downstream accounting low packets.";
    }
    leaf remote-v6-down-flow-bytes-high {
      type string;
      units "Byte";
      description
        "Number of RUI-backed IPv6 downstream accounting high bytes.";
    }
    leaf remote-v6-down-flow-bytes-low {
      type string;
      units "Byte";
      description
        "Number of RUI-backed IPv6 downstream accounting low bytes.";
    }
    leaf multicast-down-packets {
      type string;
      units "packet";
      description
        "Number of multicast downstream accounting packets.";
    }
    leaf multicast-down-bytes {
      type string;
      units "Byte";
      description
        "Number of multicast downstream accounting bytes.";
    }
    leaf time-remind {
      type string;
      units "s";
      description
        "Time remind.";
    }
    leaf flow-remained-high {
      type string;
      units "Byte";
      description
        "Flow remained high byte.";
    }
    leaf flow-remained-low {
      type string;
      units "Byte";
      description
        "Flow remained low byte.";
    }
    leaf idle-cut-time {
      type string;
      units "s";
      description
        "Idle-cut time. The device checks whether a user is in idle state every 120s.";
    }
    leaf idle-cut-rate {
      type string;
      units "1/60 kB/s";
      description
        "Idle-cut rate. The device checks whether a user is in idle state every 120s.";
    }
    leaf idle-cut-minute {
      type string;
      units "min";
      description
        "Idle-cut minute. The device checks whether a user is in idle state every 120s.";
    }
    leaf idle-cut-second {
      type string;
      units "s";
      description
        "Idle-cut second. The device checks whether a user is in idle state every 120s.";
    }
  }

  grouping ncs_rpc_notif_rate-limit-type {
    description
      "Configures the inbound and outbound rate for the service policy template.";
    leaf cir {
      type uint32 {
        range "0..4294967294";
      }
      units "kbit/s";
      mandatory true;
      description
        "Specifies committed information rate.";
    }
    leaf pir {
      type uint32 {
        range "0..4294967294";
      }
      units "kbit/s";
      must 'not(../pir) or (../pir and ../pir >=../cir)' {
        tailf:xpath-root 3;
      }
      description
        "Specifies the peak information rate.";
    }
    leaf cbs {
      type uint32 {
        range "0..4294967294";
      }
      units "kbit/s";
      description
        "Specifies the committed burst size.";
    }
    leaf pbs {
      type uint32 {
        range "0..4294967294";
      }
      units "kbit/s";
      must 'not(../pbs) or (../cbs and ../pbs and ../pbs >=../cbs)' {
        tailf:xpath-root 3;
      }
      description
        "Specifies the peak burst size.";
    }
    leaf flow-queue-pbs {
      when '../cbs' {
        tailf:xpath-root 3;
      }
      type uint32 {
        range "1..4194304";
      }
      units "Byte";
      must '../flow-queue-pbs>=../cbs' {
        tailf:xpath-root 3;
      }
      description
        "Specifies the peak burst size of flow queue.";
    }
  }

  grouping ncs_rpc_notif_bras-vas-user-traffic-type {
    description
      "Configures the inbound and outbound rate for the service policy template.";
    leaf cs7 {
      type boolean;
      default "false";
      description
        "Enable/disable a service class is CS7.";
    }
    leaf cs6 {
      type boolean;
      default "false";
      description
        "Enable/disable a service class is CS6.";
    }
    leaf ef {
      type boolean;
      default "false";
      description
        "Enable/disable a service class is EF.";
    }
    leaf af4 {
      type boolean;
      default "false";
      description
        "Enable/disable a service class is AF4.";
    }
    leaf af3 {
      type boolean;
      default "false";
      description
        "Enable/disable a service class is AF3.";
    }
    leaf af2 {
      type boolean;
      default "false";
      description
        "Enable/disable a service class is AF2.";
    }
    leaf af1 {
      type boolean;
      default "false";
      description
        "Enable/disable a service class is AF1.";
    }
    leaf be {
      type boolean;
      default "false";
      description
        "Enable/disable a service class is BE.";
    }
  }

  grouping ncs_rpc_notif_remote-policy-cache-type {
    description
      "Display information about a specified EDSG service cache policy in CU.";
    leaf service-policy-index {
      type uint32;
      description
        "The service policy index.";
    }
    leaf reference-count {
      type uint32;
      description
        "The reference count.";
    }
  }

  grouping ncs_rpc_notif_edsg-time-range-info-type {
    description
      "Display edsg time-range information.";
    leaf updated-success-users {
      type uint32;
      description
        "Number Of Users That Success To Be Updated.";
    }
    leaf updated-failed-users {
      type uint32;
      description
        "Number Of Users That Fail To Be Updated.";
    }
    leaf to-be-update-users {
      type uint32;
      description
        "Number Of Users To Be Updated.";
    }
    leaf total-updated-users {
      type uint32;
      description
        "Total Number Of Updated Users.";
    }
  }

  grouping ncs_rpc_notif_updated-fail-statistic-type {
    description
      "Failed to update statistic resource for the service.";
    leaf sq-resource-fail-num {
      type uint32;
      description
        "Failed to Apply SQ Resource For The Service.";
    }
    leaf car-res-fail-num {
      type uint32;
      description
        "Failed to Apply CAR Resource For The Service.";
    }
    leaf stat-res-fail-num {
      type uint32;
      description
        "Failed to Apply Statistic Resource For The Service.";
    }
  }

  grouping ncs_rpc_notif_user-id-bod-or-daa-statistic-type {
    description
      "Display BOD or DAA type information about value-added services based on a specified user ID.";
    leaf service-name {
      type string {
        length "1..200";
      }
      description
        "Name of a service.";
    }
    leaf service-ip-type {
      type ncs_rpc_notif_bras-vas-service-ip-type;
      description
        "Service traffic statistics type. The default value is IPv4. This parameter can be set to IPv6.";
    }
    leaf account-method {
      type ncs_rpc_notif_bras-vas-method-type;
      description
        "Accounting method.";
    }
    leaf normal-server-group {
      type string {
        length "1..34";
      }
      description
        "Name of the policy server that delivers a service policy.";
    }
    leaf up-committed-rate {
      type string {
        length "1..19";
      }
      description
        "Upstream committed information rate.";
    }
    leaf up-peak-rate {
      type string {
        length "1..19";
      }
      description
        "Upstream peak information rate.";
    }
    leaf up-committed-burst-size {
      type string {
        length "1..19";
      }
      description
        "Upstream committed burst size.";
    }
    leaf up-peak-burst-size {
      type string {
        length "1..19";
      }
      description
        "Upstream peak burst size.";
    }
    leaf down-committed-rate {
      type string {
        length "1..19";
      }
      description
        "Downstream CIR.";
    }
    leaf down-peak-rate {
      type string {
        length "1..19";
      }
      description
        "Downstream PIR.";
    }
    leaf down-committed-burst-rate {
      type string {
        length "1..19";
      }
      description
        "Downstream CBS.";
    }
    leaf down-peak-burst-size {
      type string {
        length "1..19";
      }
      description
        "Downstream PBS.";
    }
    leaf service-source-ip {
      type uint32;
      description
        "Source IP of a service.";
    }
    leaf service-type {
      type string {
        length "1..40";
      }
      description
        "Type of a service.";
    }
    leaf account-start-time {
      type string {
        length "1..31";
      }
      description
        "Time when the accounting starts.";
    }
    leaf two-level-acct-server-group {
      type string {
        length "1..34";
      }
      description
        "Radius server group of two level accounting.";
    }
    leaf physical-acct-server-group {
      type string {
        length "1..34";
      }
      description
        "Radius server group of physical account.";
    }
    leaf up-flow-packets-high {
      type uint32;
      units "packet";
      description
        "Number of upstream accounting high packets.";
    }
    leaf up-flow-packets-low {
      type uint32;
      units "packet";
      description
        "Number of upstream accounting low packets.";
    }
    leaf up-flow-bytes-high {
      type uint32;
      units "Byte";
      description
        "Number of upstream accounting high bytes.";
    }
    leaf up-flow-bytes-low {
      type uint32;
      units "Byte";
      description
        "Number of upstream accounting low bytes.";
    }
    leaf down-flow-packets-high {
      type uint32;
      units "packet";
      description
        "Number of downstream accounting high packets.";
    }
    leaf down-flow-packets-low {
      type uint32;
      units "packet";
      description
        "Number of downstream accounting low packets.";
    }
    leaf down-flow-bytes-high {
      type uint32;
      units "Byte";
      description
        "Number of downstream accounting high bytes.";
    }
    leaf down-flow-bytes-low {
      type uint32;
      units "Byte";
      description
        "Number of downstream accounting low bytes.";
    }
    leaf ipv6-up-flow-packets-high {
      type uint32;
      units "packet";
      description
        "Number of upstream IPv6 accounting high packets.";
    }
    leaf ipv6-up-flow-packets-low {
      type uint32;
      units "packet";
      description
        "Number of upstream IPv6 accounting low packets.";
    }
    leaf ipv6-up-flow-bytes-high {
      type uint32;
      units "Byte";
      description
        "Number of upstream IPv6 accounting high bytes.";
    }
    leaf ipv6-up-flow-bytes-low {
      type uint32;
      units "Byte";
      description
        "Number of upstream IPv6 accounting low bytes.";
    }
    leaf ipv6-down-flow-packets-high {
      type uint32;
      units "packet";
      description
        "Number of downstream IPv6 accounting high packets.";
    }
    leaf ipv6-down-flow-packets-low {
      type uint32;
      units "packet";
      description
        "Number of downstream IPv6 accounting low packets.";
    }
    leaf ipv6-down-flow-bytes-high {
      type uint32;
      units "Byte";
      description
        "Number of downstream IPv6 accounting high bytes.";
    }
    leaf ipv6-down-flow-bytes-low {
      type uint32;
      units "Byte";
      description
        "Number of downstream IPv6 accounting low bytes.";
    }
    leaf local-up-flow-packets-high {
      type uint32;
      units "packet";
      description
        "Number of upstream accounting high packets.";
    }
    leaf local-up-flow-packets-low {
      type uint32;
      units "packet";
      description
        "Number of upstream accounting low packets.";
    }
    leaf local-up-flow-bytes-high {
      type uint32;
      units "Byte";
      description
        "Number of upstream accounting high bytes.";
    }
    leaf local-up-flow-bytes-low {
      type uint32;
      units "Byte";
      description
        "Number of upstream accounting low bytes.";
    }
    leaf local-down-flow-packets-high {
      type uint32;
      units "packet";
      description
        "Number of downstream accounting high packets.";
    }
    leaf local-down-flow-packets-low {
      type uint32;
      units "packet";
      description
        "Number of downstream accounting low packets.";
    }
    leaf local-down-flow-bytes-high {
      type uint32;
      units "Byte";
      description
        "Number of downstream accounting high bytes.";
    }
    leaf local-down-flow-bytes-low {
      type uint32;
      units "Byte";
      description
        "Number of downstream accounting low bytes.";
    }
    leaf remote-up-flow-packets-high {
      type uint32;
      units "packet";
      description
        "Number of RUI-backed up upstream accounting high packets.";
    }
    leaf remote-up-flow-packets-low {
      type uint32;
      units "packet";
      description
        "Number of RUI-backed up upstream accounting low packets.";
    }
    leaf remote-up-flow-bytes-high {
      type uint32;
      units "Byte";
      description
        "Number of RUI-backed up downstream accounting high bytes.";
    }
    leaf remote-up-flow-bytes-low {
      type uint32;
      units "Byte";
      description
        "Number of RUI-backed up downstream accounting low bytes.";
    }
    leaf remote-down-flow-packets-high {
      type uint32;
      units "packet";
      description
        "Number of RUI-backed up downstream accounting high packets.";
    }
    leaf remote-down-flow-packets-low {
      type uint32;
      units "packet";
      description
        "Number of RUI-backed up downstream accounting low packets.";
    }
    leaf remote-down-flow-bytes-high {
      type uint32;
      units "Byte";
      description
        "Number of RUI-backed up downstream accounting high bytes.";
    }
    leaf remote-down-flow-bytes-low {
      type uint32;
      units "Byte";
      description
        "Number of RUI-backed up downstream accounting low bytes.";
    }
    leaf local-v6-up-flow-packets-high {
      type uint32;
      units "packet";
      description
        "Number of IPv6 upstream accounting high packets.";
    }
    leaf local-v6-up-flow-packets-low {
      type uint32;
      units "packet";
      description
        "Number of IPv6 upstream accounting low packets.";
    }
    leaf local-v6-up-flow-bytes-high {
      type uint32;
      units "Byte";
      description
        "Number of IPv6 upstream accounting high bytes.";
    }
    leaf local-v6-up-flow-bytes-low {
      type uint32;
      units "Byte";
      description
        "Number of IPv6 upstream accounting low bytes.";
    }
    leaf local-v6-down-flow-packets-high {
      type uint32;
      units "packet";
      description
        "Number of IPv6 downstream accounting high packets.";
    }
    leaf local-v6-down-flow-packets-low {
      type uint32;
      units "packet";
      description
        "Number of IPv6 downstream accounting low packets.";
    }
    leaf local-v6-down-flow-bytes-high {
      type uint32;
      units "Byte";
      description
        "Number of IPv6 downstream accounting high bytes.";
    }
    leaf local-v6-down-flow-bytes-low {
      type uint32;
      units "Byte";
      description
        "Number of IPv6 downstream accounting low bytes.";
    }
    leaf remote-v6-up-flow-packets-high {
      type uint32;
      units "packet";
      description
        "Number of RUI-backed IPv6 upstream accounting high packets.";
    }
    leaf remote-v6-up-flow-packets-low {
      type uint32;
      units "packet";
      description
        "Number of RUI-backed IPv6 upstream accounting low packets.";
    }
    leaf remote-v6-up-flow-bytes-high {
      type uint32;
      units "Byte";
      description
        "Number of RUI-backed IPv6 upstream accounting high bytes.";
    }
    leaf remote-v6-up-flow-bytes-low {
      type uint32;
      units "Byte";
      description
        "Number of RUI-backed IPv6 upstream accounting low bytes.";
    }
    leaf remote-v6-down-flow-packets-high {
      type uint32;
      units "packet";
      description
        "Number of RUI-backed IPv6 downstream accounting high packets.";
    }
    leaf remote-v6-down-flow-packets-low {
      type uint32;
      units "packet";
      description
        "Number of RUI-backed IPv6 downstream accounting low packets.";
    }
    leaf remote-v6-down-flow-bytes-high {
      type uint32;
      units "Byte";
      description
        "Number of RUI-backed IPv6 downstream accounting high bytes.";
    }
    leaf remote-v6-down-flow-bytes-low {
      type uint32;
      units "Byte";
      description
        "Number of RUI-backed IPv6 downstream accounting low bytes.";
    }
    leaf multicast-down-packets {
      type uint64;
      units "packet";
      description
        "Number of multicast downstream accounting packets.";
    }
    leaf multicast-down-bytes {
      type uint64;
      units "Byte";
      description
        "Number of multicast downstream accounting bytes.";
    }
    leaf time-remind {
      type uint32;
      units "s";
      description
        "Time remind.";
    }
    leaf flow-remained-high {
      type uint32;
      units "Byte";
      description
        "Flow remained high byte.";
    }
    leaf flow-remained-low {
      type uint32;
      units "Byte";
      description
        "Flow remained low byte.";
    }
    leaf idle-cut-time {
      type uint32;
      units "s";
      description
        "Idle-cut time. The device checks whether a user is in idle state every 120s.";
    }
    leaf idle-cut-rate {
      type uint32;
      units "1/60 kB/s";
      description
        "Idle-cut rate. The device checks whether a user is in idle state every 120s.";
    }
    leaf idle-cut-minute {
      type uint32;
      units "min";
      description
        "Idle-cut minute. The device checks whether a user is in idle state every 120s.";
    }
    leaf idle-cut-second {
      type uint32;
      units "s";
      description
        "Idle-cut second. The device checks whether a user is in idle state every 120s.";
    }
  }

  grouping live_ncs_rate-limit-type {
    description
      "Configures the inbound and outbound rate for the service policy template.";
    leaf cir {
      type uint32 {
        range "0..4294967294";
      }
      units "kbit/s";
      // NCS drop mandatory statement
      description
        "Specifies committed information rate.";
    }
    leaf pir {
      type uint32 {
        range "0..4294967294";
      }
      units "kbit/s";
      // NCS drop must statement
      description
        "Specifies the peak information rate.";
    }
    leaf cbs {
      type uint32 {
        range "0..4294967294";
      }
      units "kbit/s";
      description
        "Specifies the committed burst size.";
    }
    leaf pbs {
      type uint32 {
        range "0..4294967294";
      }
      units "kbit/s";
      // NCS drop must statement
      description
        "Specifies the peak burst size.";
    }
    leaf flow-queue-pbs {
      // NCS drop when statement
      type uint32 {
        range "1..4194304";
      }
      units "Byte";
      // NCS drop must statement
      description
        "Specifies the peak burst size of flow queue.";
    }
  }

  grouping live_ncs_bras-vas-user-traffic-type {
    description
      "Configures the inbound and outbound rate for the service policy template.";
    leaf cs7 {
      type boolean;
      // NCS drop default statement
      description
        "Enable/disable a service class is CS7.";
    }
    leaf cs6 {
      type boolean;
      // NCS drop default statement
      description
        "Enable/disable a service class is CS6.";
    }
    leaf ef {
      type boolean;
      // NCS drop default statement
      description
        "Enable/disable a service class is EF.";
    }
    leaf af4 {
      type boolean;
      // NCS drop default statement
      description
        "Enable/disable a service class is AF4.";
    }
    leaf af3 {
      type boolean;
      // NCS drop default statement
      description
        "Enable/disable a service class is AF3.";
    }
    leaf af2 {
      type boolean;
      // NCS drop default statement
      description
        "Enable/disable a service class is AF2.";
    }
    leaf af1 {
      type boolean;
      // NCS drop default statement
      description
        "Enable/disable a service class is AF1.";
    }
    leaf be {
      type boolean;
      // NCS drop default statement
      description
        "Enable/disable a service class is BE.";
    }
  }

  grouping live_ncs_remote-policy-cache-type {
    description
      "Display information about a specified EDSG service cache policy in CU.";
    leaf service-policy-index {
      type uint32;
      description
        "The service policy index.";
    }
    leaf reference-count {
      type uint32;
      description
        "The reference count.";
    }
  }

  grouping live_ncs_edsg-time-range-info-type {
    description
      "Display edsg time-range information.";
    leaf updated-success-users {
      type uint32;
      description
        "Number Of Users That Success To Be Updated.";
    }
    leaf updated-failed-users {
      type uint32;
      description
        "Number Of Users That Fail To Be Updated.";
    }
    leaf to-be-update-users {
      type uint32;
      description
        "Number Of Users To Be Updated.";
    }
    leaf total-updated-users {
      type uint32;
      description
        "Total Number Of Updated Users.";
    }
  }

  grouping live_ncs_updated-fail-statistic-type {
    description
      "Failed to update statistic resource for the service.";
    leaf sq-resource-fail-num {
      type uint32;
      description
        "Failed to Apply SQ Resource For The Service.";
    }
    leaf car-res-fail-num {
      type uint32;
      description
        "Failed to Apply CAR Resource For The Service.";
    }
    leaf stat-res-fail-num {
      type uint32;
      description
        "Failed to Apply Statistic Resource For The Service.";
    }
  }

  grouping live_ncs_user-id-bod-or-daa-statistic-type {
    description
      "Display BOD or DAA type information about value-added services based on a specified user ID.";
    leaf service-name {
      type string {
        length "1..200";
      }
      description
        "Name of a service.";
    }
    leaf service-ip-type {
      type live_ncs_bras-vas-service-ip-type;
      description
        "Service traffic statistics type. The default value is IPv4. This parameter can be set to IPv6.";
    }
    leaf account-method {
      type live_ncs_bras-vas-method-type;
      description
        "Accounting method.";
    }
    leaf normal-server-group {
      type string {
        length "1..34";
      }
      description
        "Name of the policy server that delivers a service policy.";
    }
    leaf up-committed-rate {
      type string {
        length "1..19";
      }
      description
        "Upstream committed information rate.";
    }
    leaf up-peak-rate {
      type string {
        length "1..19";
      }
      description
        "Upstream peak information rate.";
    }
    leaf up-committed-burst-size {
      type string {
        length "1..19";
      }
      description
        "Upstream committed burst size.";
    }
    leaf up-peak-burst-size {
      type string {
        length "1..19";
      }
      description
        "Upstream peak burst size.";
    }
    leaf down-committed-rate {
      type string {
        length "1..19";
      }
      description
        "Downstream CIR.";
    }
    leaf down-peak-rate {
      type string {
        length "1..19";
      }
      description
        "Downstream PIR.";
    }
    leaf down-committed-burst-rate {
      type string {
        length "1..19";
      }
      description
        "Downstream CBS.";
    }
    leaf down-peak-burst-size {
      type string {
        length "1..19";
      }
      description
        "Downstream PBS.";
    }
    leaf service-source-ip {
      type uint32;
      description
        "Source IP of a service.";
    }
    leaf service-type {
      type string {
        length "1..40";
      }
      description
        "Type of a service.";
    }
    leaf account-start-time {
      type string {
        length "1..31";
      }
      description
        "Time when the accounting starts.";
    }
    leaf two-level-acct-server-group {
      type string {
        length "1..34";
      }
      description
        "Radius server group of two level accounting.";
    }
    leaf physical-acct-server-group {
      type string {
        length "1..34";
      }
      description
        "Radius server group of physical account.";
    }
    leaf up-flow-packets-high {
      type uint32;
      units "packet";
      description
        "Number of upstream accounting high packets.";
    }
    leaf up-flow-packets-low {
      type uint32;
      units "packet";
      description
        "Number of upstream accounting low packets.";
    }
    leaf up-flow-bytes-high {
      type uint32;
      units "Byte";
      description
        "Number of upstream accounting high bytes.";
    }
    leaf up-flow-bytes-low {
      type uint32;
      units "Byte";
      description
        "Number of upstream accounting low bytes.";
    }
    leaf down-flow-packets-high {
      type uint32;
      units "packet";
      description
        "Number of downstream accounting high packets.";
    }
    leaf down-flow-packets-low {
      type uint32;
      units "packet";
      description
        "Number of downstream accounting low packets.";
    }
    leaf down-flow-bytes-high {
      type uint32;
      units "Byte";
      description
        "Number of downstream accounting high bytes.";
    }
    leaf down-flow-bytes-low {
      type uint32;
      units "Byte";
      description
        "Number of downstream accounting low bytes.";
    }
    leaf ipv6-up-flow-packets-high {
      type uint32;
      units "packet";
      description
        "Number of upstream IPv6 accounting high packets.";
    }
    leaf ipv6-up-flow-packets-low {
      type uint32;
      units "packet";
      description
        "Number of upstream IPv6 accounting low packets.";
    }
    leaf ipv6-up-flow-bytes-high {
      type uint32;
      units "Byte";
      description
        "Number of upstream IPv6 accounting high bytes.";
    }
    leaf ipv6-up-flow-bytes-low {
      type uint32;
      units "Byte";
      description
        "Number of upstream IPv6 accounting low bytes.";
    }
    leaf ipv6-down-flow-packets-high {
      type uint32;
      units "packet";
      description
        "Number of downstream IPv6 accounting high packets.";
    }
    leaf ipv6-down-flow-packets-low {
      type uint32;
      units "packet";
      description
        "Number of downstream IPv6 accounting low packets.";
    }
    leaf ipv6-down-flow-bytes-high {
      type uint32;
      units "Byte";
      description
        "Number of downstream IPv6 accounting high bytes.";
    }
    leaf ipv6-down-flow-bytes-low {
      type uint32;
      units "Byte";
      description
        "Number of downstream IPv6 accounting low bytes.";
    }
    leaf local-up-flow-packets-high {
      type uint32;
      units "packet";
      description
        "Number of upstream accounting high packets.";
    }
    leaf local-up-flow-packets-low {
      type uint32;
      units "packet";
      description
        "Number of upstream accounting low packets.";
    }
    leaf local-up-flow-bytes-high {
      type uint32;
      units "Byte";
      description
        "Number of upstream accounting high bytes.";
    }
    leaf local-up-flow-bytes-low {
      type uint32;
      units "Byte";
      description
        "Number of upstream accounting low bytes.";
    }
    leaf local-down-flow-packets-high {
      type uint32;
      units "packet";
      description
        "Number of downstream accounting high packets.";
    }
    leaf local-down-flow-packets-low {
      type uint32;
      units "packet";
      description
        "Number of downstream accounting low packets.";
    }
    leaf local-down-flow-bytes-high {
      type uint32;
      units "Byte";
      description
        "Number of downstream accounting high bytes.";
    }
    leaf local-down-flow-bytes-low {
      type uint32;
      units "Byte";
      description
        "Number of downstream accounting low bytes.";
    }
    leaf remote-up-flow-packets-high {
      type uint32;
      units "packet";
      description
        "Number of RUI-backed up upstream accounting high packets.";
    }
    leaf remote-up-flow-packets-low {
      type uint32;
      units "packet";
      description
        "Number of RUI-backed up upstream accounting low packets.";
    }
    leaf remote-up-flow-bytes-high {
      type uint32;
      units "Byte";
      description
        "Number of RUI-backed up downstream accounting high bytes.";
    }
    leaf remote-up-flow-bytes-low {
      type uint32;
      units "Byte";
      description
        "Number of RUI-backed up downstream accounting low bytes.";
    }
    leaf remote-down-flow-packets-high {
      type uint32;
      units "packet";
      description
        "Number of RUI-backed up downstream accounting high packets.";
    }
    leaf remote-down-flow-packets-low {
      type uint32;
      units "packet";
      description
        "Number of RUI-backed up downstream accounting low packets.";
    }
    leaf remote-down-flow-bytes-high {
      type uint32;
      units "Byte";
      description
        "Number of RUI-backed up downstream accounting high bytes.";
    }
    leaf remote-down-flow-bytes-low {
      type uint32;
      units "Byte";
      description
        "Number of RUI-backed up downstream accounting low bytes.";
    }
    leaf local-v6-up-flow-packets-high {
      type uint32;
      units "packet";
      description
        "Number of IPv6 upstream accounting high packets.";
    }
    leaf local-v6-up-flow-packets-low {
      type uint32;
      units "packet";
      description
        "Number of IPv6 upstream accounting low packets.";
    }
    leaf local-v6-up-flow-bytes-high {
      type uint32;
      units "Byte";
      description
        "Number of IPv6 upstream accounting high bytes.";
    }
    leaf local-v6-up-flow-bytes-low {
      type uint32;
      units "Byte";
      description
        "Number of IPv6 upstream accounting low bytes.";
    }
    leaf local-v6-down-flow-packets-high {
      type uint32;
      units "packet";
      description
        "Number of IPv6 downstream accounting high packets.";
    }
    leaf local-v6-down-flow-packets-low {
      type uint32;
      units "packet";
      description
        "Number of IPv6 downstream accounting low packets.";
    }
    leaf local-v6-down-flow-bytes-high {
      type uint32;
      units "Byte";
      description
        "Number of IPv6 downstream accounting high bytes.";
    }
    leaf local-v6-down-flow-bytes-low {
      type uint32;
      units "Byte";
      description
        "Number of IPv6 downstream accounting low bytes.";
    }
    leaf remote-v6-up-flow-packets-high {
      type uint32;
      units "packet";
      description
        "Number of RUI-backed IPv6 upstream accounting high packets.";
    }
    leaf remote-v6-up-flow-packets-low {
      type uint32;
      units "packet";
      description
        "Number of RUI-backed IPv6 upstream accounting low packets.";
    }
    leaf remote-v6-up-flow-bytes-high {
      type uint32;
      units "Byte";
      description
        "Number of RUI-backed IPv6 upstream accounting high bytes.";
    }
    leaf remote-v6-up-flow-bytes-low {
      type uint32;
      units "Byte";
      description
        "Number of RUI-backed IPv6 upstream accounting low bytes.";
    }
    leaf remote-v6-down-flow-packets-high {
      type uint32;
      units "packet";
      description
        "Number of RUI-backed IPv6 downstream accounting high packets.";
    }
    leaf remote-v6-down-flow-packets-low {
      type uint32;
      units "packet";
      description
        "Number of RUI-backed IPv6 downstream accounting low packets.";
    }
    leaf remote-v6-down-flow-bytes-high {
      type uint32;
      units "Byte";
      description
        "Number of RUI-backed IPv6 downstream accounting high bytes.";
    }
    leaf remote-v6-down-flow-bytes-low {
      type uint32;
      units "Byte";
      description
        "Number of RUI-backed IPv6 downstream accounting low bytes.";
    }
    leaf multicast-down-packets {
      type uint64;
      units "packet";
      description
        "Number of multicast downstream accounting packets.";
    }
    leaf multicast-down-bytes {
      type uint64;
      units "Byte";
      description
        "Number of multicast downstream accounting bytes.";
    }
    leaf time-remind {
      type uint32;
      units "s";
      description
        "Time remind.";
    }
    leaf flow-remained-high {
      type uint32;
      units "Byte";
      description
        "Flow remained high byte.";
    }
    leaf flow-remained-low {
      type uint32;
      units "Byte";
      description
        "Flow remained low byte.";
    }
    leaf idle-cut-time {
      type uint32;
      units "s";
      description
        "Idle-cut time. The device checks whether a user is in idle state every 120s.";
    }
    leaf idle-cut-rate {
      type uint32;
      units "1/60 kB/s";
      description
        "Idle-cut rate. The device checks whether a user is in idle state every 120s.";
    }
    leaf idle-cut-minute {
      type uint32;
      units "min";
      description
        "Idle-cut minute. The device checks whether a user is in idle state every 120s.";
    }
    leaf idle-cut-second {
      type uint32;
      units "s";
      description
        "Idle-cut second. The device checks whether a user is in idle state every 120s.";
    }
  }

  grouping rate-limit-type {
    description
      "Configures the inbound and outbound rate for the service policy template.";
    leaf cir {
      type uint32 {
        range "0..4294967294";
      }
      units "kbit/s";
      mandatory true;
      description
        "Specifies committed information rate.";
    }
    leaf pir {
      type uint32 {
        range "0..4294967294";
      }
      units "kbit/s";
      must 'not(../pir) or (../pir and ../pir >=../cir)' {
        tailf:xpath-root 3;
      }
      description
        "Specifies the peak information rate.";
    }
    leaf cbs {
      type uint32 {
        range "0..4294967294";
      }
      units "kbit/s";
      description
        "Specifies the committed burst size.";
    }
    leaf pbs {
      type uint32 {
        range "0..4294967294";
      }
      units "kbit/s";
      must 'not(../pbs) or (../cbs and ../pbs and ../pbs >=../cbs)' {
        tailf:xpath-root 3;
      }
      description
        "Specifies the peak burst size.";
    }
    leaf flow-queue-pbs {
      when '../cbs' {
        tailf:xpath-root 3;
      }
      type uint32 {
        range "1..4194304";
      }
      units "Byte";
      must '../flow-queue-pbs>=../cbs' {
        tailf:xpath-root 3;
      }
      description
        "Specifies the peak burst size of flow queue.";
    }
  }

  grouping bras-vas-user-traffic-type {
    description
      "Configures the inbound and outbound rate for the service policy template.";
    leaf cs7 {
      type boolean;
      default "false";
      description
        "Enable/disable a service class is CS7.";
    }
    leaf cs6 {
      type boolean;
      default "false";
      description
        "Enable/disable a service class is CS6.";
    }
    leaf ef {
      type boolean;
      default "false";
      description
        "Enable/disable a service class is EF.";
    }
    leaf af4 {
      type boolean;
      default "false";
      description
        "Enable/disable a service class is AF4.";
    }
    leaf af3 {
      type boolean;
      default "false";
      description
        "Enable/disable a service class is AF3.";
    }
    leaf af2 {
      type boolean;
      default "false";
      description
        "Enable/disable a service class is AF2.";
    }
    leaf af1 {
      type boolean;
      default "false";
      description
        "Enable/disable a service class is AF1.";
    }
    leaf be {
      type boolean;
      default "false";
      description
        "Enable/disable a service class is BE.";
    }
  }

  grouping remote-policy-cache-type {
    description
      "Display information about a specified EDSG service cache policy in CU.";
    leaf service-policy-index {
      type uint32;
      description
        "The service policy index.";
    }
    leaf reference-count {
      type uint32;
      description
        "The reference count.";
    }
  }

  grouping edsg-time-range-info-type {
    description
      "Display edsg time-range information.";
    leaf updated-success-users {
      type uint32;
      description
        "Number Of Users That Success To Be Updated.";
    }
    leaf updated-failed-users {
      type uint32;
      description
        "Number Of Users That Fail To Be Updated.";
    }
    leaf to-be-update-users {
      type uint32;
      description
        "Number Of Users To Be Updated.";
    }
    leaf total-updated-users {
      type uint32;
      description
        "Total Number Of Updated Users.";
    }
  }

  grouping updated-fail-statistic-type {
    description
      "Failed to update statistic resource for the service.";
    leaf sq-resource-fail-num {
      type uint32;
      description
        "Failed to Apply SQ Resource For The Service.";
    }
    leaf car-res-fail-num {
      type uint32;
      description
        "Failed to Apply CAR Resource For The Service.";
    }
    leaf stat-res-fail-num {
      type uint32;
      description
        "Failed to Apply Statistic Resource For The Service.";
    }
  }

  grouping user-id-bod-or-daa-statistic-type {
    description
      "Display BOD or DAA type information about value-added services based on a specified user ID.";
    leaf service-name {
      type string {
        length "1..200";
      }
      description
        "Name of a service.";
    }
    leaf service-ip-type {
      type bras-vas-service-ip-type;
      description
        "Service traffic statistics type. The default value is IPv4. This parameter can be set to IPv6.";
    }
    leaf account-method {
      type bras-vas-method-type;
      description
        "Accounting method.";
    }
    leaf normal-server-group {
      type string {
        length "1..34";
      }
      description
        "Name of the policy server that delivers a service policy.";
    }
    leaf up-committed-rate {
      type string {
        length "1..19";
      }
      description
        "Upstream committed information rate.";
    }
    leaf up-peak-rate {
      type string {
        length "1..19";
      }
      description
        "Upstream peak information rate.";
    }
    leaf up-committed-burst-size {
      type string {
        length "1..19";
      }
      description
        "Upstream committed burst size.";
    }
    leaf up-peak-burst-size {
      type string {
        length "1..19";
      }
      description
        "Upstream peak burst size.";
    }
    leaf down-committed-rate {
      type string {
        length "1..19";
      }
      description
        "Downstream CIR.";
    }
    leaf down-peak-rate {
      type string {
        length "1..19";
      }
      description
        "Downstream PIR.";
    }
    leaf down-committed-burst-rate {
      type string {
        length "1..19";
      }
      description
        "Downstream CBS.";
    }
    leaf down-peak-burst-size {
      type string {
        length "1..19";
      }
      description
        "Downstream PBS.";
    }
    leaf service-source-ip {
      type uint32;
      description
        "Source IP of a service.";
    }
    leaf service-type {
      type string {
        length "1..40";
      }
      description
        "Type of a service.";
    }
    leaf account-start-time {
      type string {
        length "1..31";
      }
      description
        "Time when the accounting starts.";
    }
    leaf two-level-acct-server-group {
      type string {
        length "1..34";
      }
      description
        "Radius server group of two level accounting.";
    }
    leaf physical-acct-server-group {
      type string {
        length "1..34";
      }
      description
        "Radius server group of physical account.";
    }
    leaf up-flow-packets-high {
      type uint32;
      units "packet";
      description
        "Number of upstream accounting high packets.";
    }
    leaf up-flow-packets-low {
      type uint32;
      units "packet";
      description
        "Number of upstream accounting low packets.";
    }
    leaf up-flow-bytes-high {
      type uint32;
      units "Byte";
      description
        "Number of upstream accounting high bytes.";
    }
    leaf up-flow-bytes-low {
      type uint32;
      units "Byte";
      description
        "Number of upstream accounting low bytes.";
    }
    leaf down-flow-packets-high {
      type uint32;
      units "packet";
      description
        "Number of downstream accounting high packets.";
    }
    leaf down-flow-packets-low {
      type uint32;
      units "packet";
      description
        "Number of downstream accounting low packets.";
    }
    leaf down-flow-bytes-high {
      type uint32;
      units "Byte";
      description
        "Number of downstream accounting high bytes.";
    }
    leaf down-flow-bytes-low {
      type uint32;
      units "Byte";
      description
        "Number of downstream accounting low bytes.";
    }
    leaf ipv6-up-flow-packets-high {
      type uint32;
      units "packet";
      description
        "Number of upstream IPv6 accounting high packets.";
    }
    leaf ipv6-up-flow-packets-low {
      type uint32;
      units "packet";
      description
        "Number of upstream IPv6 accounting low packets.";
    }
    leaf ipv6-up-flow-bytes-high {
      type uint32;
      units "Byte";
      description
        "Number of upstream IPv6 accounting high bytes.";
    }
    leaf ipv6-up-flow-bytes-low {
      type uint32;
      units "Byte";
      description
        "Number of upstream IPv6 accounting low bytes.";
    }
    leaf ipv6-down-flow-packets-high {
      type uint32;
      units "packet";
      description
        "Number of downstream IPv6 accounting high packets.";
    }
    leaf ipv6-down-flow-packets-low {
      type uint32;
      units "packet";
      description
        "Number of downstream IPv6 accounting low packets.";
    }
    leaf ipv6-down-flow-bytes-high {
      type uint32;
      units "Byte";
      description
        "Number of downstream IPv6 accounting high bytes.";
    }
    leaf ipv6-down-flow-bytes-low {
      type uint32;
      units "Byte";
      description
        "Number of downstream IPv6 accounting low bytes.";
    }
    leaf local-up-flow-packets-high {
      type uint32;
      units "packet";
      description
        "Number of upstream accounting high packets.";
    }
    leaf local-up-flow-packets-low {
      type uint32;
      units "packet";
      description
        "Number of upstream accounting low packets.";
    }
    leaf local-up-flow-bytes-high {
      type uint32;
      units "Byte";
      description
        "Number of upstream accounting high bytes.";
    }
    leaf local-up-flow-bytes-low {
      type uint32;
      units "Byte";
      description
        "Number of upstream accounting low bytes.";
    }
    leaf local-down-flow-packets-high {
      type uint32;
      units "packet";
      description
        "Number of downstream accounting high packets.";
    }
    leaf local-down-flow-packets-low {
      type uint32;
      units "packet";
      description
        "Number of downstream accounting low packets.";
    }
    leaf local-down-flow-bytes-high {
      type uint32;
      units "Byte";
      description
        "Number of downstream accounting high bytes.";
    }
    leaf local-down-flow-bytes-low {
      type uint32;
      units "Byte";
      description
        "Number of downstream accounting low bytes.";
    }
    leaf remote-up-flow-packets-high {
      type uint32;
      units "packet";
      description
        "Number of RUI-backed up upstream accounting high packets.";
    }
    leaf remote-up-flow-packets-low {
      type uint32;
      units "packet";
      description
        "Number of RUI-backed up upstream accounting low packets.";
    }
    leaf remote-up-flow-bytes-high {
      type uint32;
      units "Byte";
      description
        "Number of RUI-backed up downstream accounting high bytes.";
    }
    leaf remote-up-flow-bytes-low {
      type uint32;
      units "Byte";
      description
        "Number of RUI-backed up downstream accounting low bytes.";
    }
    leaf remote-down-flow-packets-high {
      type uint32;
      units "packet";
      description
        "Number of RUI-backed up downstream accounting high packets.";
    }
    leaf remote-down-flow-packets-low {
      type uint32;
      units "packet";
      description
        "Number of RUI-backed up downstream accounting low packets.";
    }
    leaf remote-down-flow-bytes-high {
      type uint32;
      units "Byte";
      description
        "Number of RUI-backed up downstream accounting high bytes.";
    }
    leaf remote-down-flow-bytes-low {
      type uint32;
      units "Byte";
      description
        "Number of RUI-backed up downstream accounting low bytes.";
    }
    leaf local-v6-up-flow-packets-high {
      type uint32;
      units "packet";
      description
        "Number of IPv6 upstream accounting high packets.";
    }
    leaf local-v6-up-flow-packets-low {
      type uint32;
      units "packet";
      description
        "Number of IPv6 upstream accounting low packets.";
    }
    leaf local-v6-up-flow-bytes-high {
      type uint32;
      units "Byte";
      description
        "Number of IPv6 upstream accounting high bytes.";
    }
    leaf local-v6-up-flow-bytes-low {
      type uint32;
      units "Byte";
      description
        "Number of IPv6 upstream accounting low bytes.";
    }
    leaf local-v6-down-flow-packets-high {
      type uint32;
      units "packet";
      description
        "Number of IPv6 downstream accounting high packets.";
    }
    leaf local-v6-down-flow-packets-low {
      type uint32;
      units "packet";
      description
        "Number of IPv6 downstream accounting low packets.";
    }
    leaf local-v6-down-flow-bytes-high {
      type uint32;
      units "Byte";
      description
        "Number of IPv6 downstream accounting high bytes.";
    }
    leaf local-v6-down-flow-bytes-low {
      type uint32;
      units "Byte";
      description
        "Number of IPv6 downstream accounting low bytes.";
    }
    leaf remote-v6-up-flow-packets-high {
      type uint32;
      units "packet";
      description
        "Number of RUI-backed IPv6 upstream accounting high packets.";
    }
    leaf remote-v6-up-flow-packets-low {
      type uint32;
      units "packet";
      description
        "Number of RUI-backed IPv6 upstream accounting low packets.";
    }
    leaf remote-v6-up-flow-bytes-high {
      type uint32;
      units "Byte";
      description
        "Number of RUI-backed IPv6 upstream accounting high bytes.";
    }
    leaf remote-v6-up-flow-bytes-low {
      type uint32;
      units "Byte";
      description
        "Number of RUI-backed IPv6 upstream accounting low bytes.";
    }
    leaf remote-v6-down-flow-packets-high {
      type uint32;
      units "packet";
      description
        "Number of RUI-backed IPv6 downstream accounting high packets.";
    }
    leaf remote-v6-down-flow-packets-low {
      type uint32;
      units "packet";
      description
        "Number of RUI-backed IPv6 downstream accounting low packets.";
    }
    leaf remote-v6-down-flow-bytes-high {
      type uint32;
      units "Byte";
      description
        "Number of RUI-backed IPv6 downstream accounting high bytes.";
    }
    leaf remote-v6-down-flow-bytes-low {
      type uint32;
      units "Byte";
      description
        "Number of RUI-backed IPv6 downstream accounting low bytes.";
    }
    leaf multicast-down-packets {
      type uint64;
      units "packet";
      description
        "Number of multicast downstream accounting packets.";
    }
    leaf multicast-down-bytes {
      type uint64;
      units "Byte";
      description
        "Number of multicast downstream accounting bytes.";
    }
    leaf time-remind {
      type uint32;
      units "s";
      description
        "Time remind.";
    }
    leaf flow-remained-high {
      type uint32;
      units "Byte";
      description
        "Flow remained high byte.";
    }
    leaf flow-remained-low {
      type uint32;
      units "Byte";
      description
        "Flow remained low byte.";
    }
    leaf idle-cut-time {
      type uint32;
      units "s";
      description
        "Idle-cut time. The device checks whether a user is in idle state every 120s.";
    }
    leaf idle-cut-rate {
      type uint32;
      units "1/60 kB/s";
      description
        "Idle-cut rate. The device checks whether a user is in idle state every 120s.";
    }
    leaf idle-cut-minute {
      type uint32;
      units "min";
      description
        "Idle-cut minute. The device checks whether a user is in idle state every 120s.";
    }
    leaf idle-cut-second {
      type uint32;
      units "s";
      description
        "Idle-cut second. The device checks whether a user is in idle state every 120s.";
    }
  }

  augment "/ncs:devices/ncs:device/ncs:config" {
    container bras-vas {
      tailf:ncs-device-type "netconf";
      tailf:display-when "not(../../ncs:module) or ../../ncs:module[ncs:name='huawei-bras-vas']";
      description
        "Bras value-added services.";
      container global {
        description
          "Configure value-added-service.";
        container value-added-service {
          description
            "Configure value-added-service enable list.";
          leaf enable {
            type boolean;
            default "false";
            description
              "Enable/disable value-added-service.";
          }
        }
        container account-individual {
          description
            "Configure account individual.";
          leaf enable {
            type boolean;
            default "false";
            description
              "Enable/disable account individual.";
          }
        }
        container policy-name-case-sensitive {
          description
            "Configure service policy name case sensitive.";
          leaf enable {
            type boolean;
            default "false";
            description
              "Enable/disable service policy name case sensitive.";
          }
        }
        container quota-out {
          description
            "Configure the Quota type.";
          leaf quota-type {
            type bras-vas-quota-out-online-offline-type;
            default "online";
            description
              "Quota type.";
          }
          leaf diameter-link-down {
            type bras-vas-quota-out-online-offline-type;
            default "online";
            description
              "Quota type of diameter link down.";
          }
        }
        container daa-resource-insufficient {
          description
            "Configure Resource Application Failures Policy.";
          leaf type {
            type enumeration {
              enum "online" {
                value 0;
                description
                  "By default, DAA users remain online after they fail to apply for resources.";
              }
              enum "inbound-offline" {
                value 1;
                description
                  "Log out DAA users who fail to apply for upstream resources.";
              }
              enum "outbound-offline" {
                value 2;
                description
                  "Log out DAA users who fail to apply for downstream resources.";
              }
              enum "inbound-or-outbound-offline" {
                value 3;
                description
                  "Log out DAA users who fail to apply for upstream or downstream resources.";
              }
              enum "both-offline" {
                value 4;
                description
                  "Log out DAA users who fail to apply for both upstream and downstream resources.";
              }
            }
            default "online";
            description
              "Policy Upon Resource Application Failures.";
          }
        }
        container edsg-queue {
          description
            "Configure delayed EDSG user activation.";
          leaf enable {
            type boolean;
            default "false";
            description
              "Enable/disable a device to adjust the access rate of users who go online by configuring the edsg service to enter the activation queue and suspend the activation.";
          }
        }
        // NCS drop config false container 'edsg-run-info'
        container edsg-centralized-ds-lite {
          description
            "Configure value-added services on the centralized DS-Lite device.";
          leaf enable {
            type boolean;
            default "false";
            description
              "Enable/disable the function of matching EDSG services based on inner IPv4 packets.";
          }
        }
        container daa-report-dropped-flow {
          description
            "Configure the function to report DAA users whose packets are dropped.";
          leaf enable {
            type boolean;
            default "false";
            description
              "Enable/disable the function to report DAA users whose packets are dropped.";
          }
        }
      }
      container vas-policys {
        description
          "List of the vas Policy.";
        list vas-policy {
          key "name";
          description
            "Configure a vas policy.";
          leaf name {
            type string {
              length "1..63";
              pattern '[!-~]{1,63}';
              pattern "([^A-Z\"%'*/:<>\\?@|]{1,63})";
            }
            must "../name != '-' and ../name != '--'" {
              tailf:xpath-root 3;
            }
            description
              "Vas policy name.";
            ext:case-sensitivity "lower-only";
          }
          leaf type {
            ext:operation-exclude "update";
            type bras-vas-policy-type;
            mandatory true;
            description
              "Vas policy type.";
          }
          container qos-profile {
            when "../type='bod'" {
              tailf:xpath-root 3;
            }
            description
              "Configure qos profile.";
            leaf name {
              type leafref {
                path "/ncs:devices/ncs:device/ncs:config/qos:qos/qos:queue-scheduler-template/qos:profiles/qos:profile/qos:name" {
                  tailf:xpath-root 3;
                }
              }
              must "/qos:qos/qos:queue-scheduler-template/qos:profiles/qos:profile[qos:name=current()]/qos:mode='normal'" {
                tailf:xpath-root 3;
              }
              description
                "Name of qos profile.";
            }
          }
          container accounting-scheme {
            description
              "Configure accounting scheme.";
            leaf name {
              type leafref {
                path "/ncs:devices/ncs:device/ncs:config/aaa:aaa/aaa:accounting-schemes/aaa:accounting-scheme/aaa:acct-scheme-name" {
                  tailf:xpath-root 3;
                }
              }
              default "default1";
              description
                "Name of accounting scheme.";
            }
          }
          container daa-service-enable {
            when "not(../type='bod')" {
              tailf:xpath-root 3;
            }
            description
              "Configure daa service.";
            leaf user-accounting-together {
              type boolean;
              default "false";
              description
                "Enable/disable the DAA service traffic counts into user traffic.";
            }
            leaf traffic-separate {
              type boolean;
              default "false";
              description
                "Enable/disable the DAA service separate function.";
            }
            leaf tariff-queue-mapping {
              type boolean;
              default "false";
              description
                "Enable/disable priority scheduling based on tariff levels.";
            }
            leaf accounting-together {
              type boolean;
              default "false";
              description
                "Enable/disable uniform accounting for DAA services.";
            }
          }
          container bind-user-group {
            description
              "Configure an ACL user group to a value-added service policy.";
            leaf name {
              type leafref {
                path "/ncs:devices/ncs:device/ncs:config/bras-basic-access:bras-basic-access/bras-basic-access:user-groups/bras-basic-access:user-group/bras-basic-access:name" {
                  tailf:xpath-root 3;
                }
              }
              description
                "Specifies the name of a user group, and the user group must not be added to a user group list or a domain without binding nat instance.";
            }
          }
          container bind-tariff-levels {
            when "../type='daa'" {
              tailf:xpath-root 3;
            }
            description
              "List of the tariff level for DAA accounting.";
            list bind-tariff-level {
              key "tariff-level";
              description
                "Configure a tariff level for DAA accounting.";
              leaf tariff-level {
                type uint8 {
                  range "1..8";
                }
                description
                  "Tariff level for DAA accounting.";
              }
              leaf qos-profile-name {
                type leafref {
                  path "/ncs:devices/ncs:device/ncs:config/qos:qos/qos:queue-scheduler-template/qos:profiles/qos:profile/qos:name" {
                    tailf:xpath-root 3;
                  }
                }
                must "/qos:qos/qos:queue-scheduler-template/qos:profiles/qos:profile[qos:name=current()]/qos:mode='normal'" {
                  tailf:xpath-root 3;
                }
                mandatory true;
                description
                  "Specifies the name of a bound QoS profile.";
              }
            }
          }
          container tariff-level-accountings {
            when "../type='daa'" {
              tailf:xpath-root 3;
            }
            description
              "List of the accounting status or IP type for a DAA tariff level.";
            list tariff-level-accounting {
              must "./accounting-off = 'true' or ./ip-type-ipv6 = 'true'" {
                tailf:xpath-root 3;
              }
              key "level";
              description
                "Configure the accounting status or IP type for a DAA tariff level.";
              leaf level {
                type uint8 {
                  range "1..8";
                }
                description
                  "Specifies a DAA tariff level.";
              }
              leaf accounting-off {
                type boolean;
                default "false";
                description
                  "Enable/disable the accounting status of a DAA tariff level as disabled.";
              }
              leaf ip-type-ipv6 {
                type boolean;
                default "false";
                description
                  "Enable/disable an IP type for a DAA tariff level as IPv6.";
              }
            }
          }
          container user-traffic-statistic {
            when "../type='daa'" {
              tailf:xpath-root 3;
            }
            description
              "Configure the statistics mode for user traffic. After CAR is performed on a DAA service flow, packets in the DAA service flow are re-marked with different priorities and are scheduled into SQs. In SQ-based traffic statistics, however, DAA traffic and non-DAA traffic are not differentiated. Specify the FQs of which traffic statistics are collected as user traffic statistics.";
            container inbound {
              description
                "Configure the statistics mode for user traffic when SQ scheduling is applied to DAA services.";
              uses bras-vas-user-traffic-type;
            }
            container outbound {
              description
                "Configure the statistics mode for user traffic when SQ scheduling is applied to DAA services.";
              uses bras-vas-user-traffic-type;
            }
          }
          container accounting-service-policy {
            when "../type='daa'" {
              tailf:xpath-root 3;
            }
            description
              "Configure user traffic from to match a DAA service policy.";
            leaf inbound {
              type enumeration {
                enum "disable" {
                  value 0;
                  description
                    "Disables user traffic from matching a DAA service policy.";
                }
                enum "enable" {
                  value 1;
                  description
                    "Enables user traffic from to match a DAA service policy.";
                }
                enum "auto" {
                  value 2;
                  description
                    "Automatically matches user traffic with a DAA service policy.";
                }
              }
              default "enable";
              description
                "Upstream user traffic.";
            }
            leaf outbound {
              type enumeration {
                enum "disable" {
                  value 0;
                  description
                    "Disables user traffic from matching a DAA service policy.";
                }
                enum "enable" {
                  value 1;
                  description
                    "Enables user traffic from to match a DAA service policy.";
                }
                enum "auto" {
                  value 2;
                  description
                    "Automatically matches user traffic with a DAA service policy.";
                }
              }
              default "enable";
              description
                "Downstream user traffic.";
            }
          }
          container rate-limit-mode {
            when "../type='daa'" {
              tailf:xpath-root 3;
            }
            description
              "Configure a QoS rate limit mode for downstream DAA services on a board with the eTM subcard installed.";
            leaf outbond {
              type bras-vas-out-rate-limit-mode;
              description
                "QoS Rate Limit Mode.";
            }
          }
          // NCS drop config false container 'policy-info'
        }
      }
      container hw-policy-name-attribute {
        description
          "Configure the HW-Policy-Name attribute to carry the EDSG service policy name.";
        leaf support-edsg {
          type boolean;
          default "false";
          description
            "Enable/disable the HW-Policy-Name attribute to carry the EDSG service policy name.";
        }
      }
      container accounting-merge-cache {
        description
          "Configure a post-merging accounting packet that fails to be sent for value-added services to enter the accounting packet cache. By default, a post-merging accounting packet that fails to be sent for value-added services is disabled from entering the accounting packet cache.";
        leaf enable {
          type boolean;
          default "false";
          description
            "Enable/disable a post-merging accounting packet that fails to be sent for value-added services to enter the accounting packet cache.";
        }
      }
      container bod-portal-reserved {
        description
          "Configure portal reserved when the type of value added service is bod.";
        leaf enable {
          type boolean;
          default "false";
          description
            "Enable/disable portal reserved when the type of value added service is bod.";
        }
      }
      container service-policy-download {
        presence "service-policy-download.";
        description
          "Configure a mode in which an EDSG service policy is obtained.";
        leaf download-type {
          type enumeration {
            enum "local" {
              value 0;
              description
                "Local configuration.";
            }
            enum "radius" {
              value 1;
              description
                "Download from an RADIUS server.";
            }
            enum "local-radius" {
              value 2;
              description
                "First from the local configuration and then from an RADIUS server.";
            }
            enum "radius-local" {
              value 3;
              description
                "First from an RADIUS server and then from the local configuration.";
            }
          }
          default "local";
          description
            "Sets a mode in which an EDSG service policy is obtained.";
        }
        leaf radius-server-group-name {
          when "../download-type ='radius' or ../download-type ='local-radius' or ../download-type ='radius-local'" {
            tailf:xpath-root 3;
          }
          type leafref {
            path "/ncs:devices/ncs:device/ncs:config/radius:radius/radius:radius-server-groups/radius:radius-server-group/radius:name" {
              tailf:xpath-root 3;
            }
          }
          mandatory true;
          description
            "Specifies the name of a RADIUS server group.";
        }
        leaf password {
          when "../download-type ='radius' or ../download-type ='local-radius' or ../download-type ='radius-local'" {
            tailf:xpath-root 3;
          }
          type pub-type:password-extend {
            length "1..128";
          }
          mandatory true;
          description
            "Specifies an unencrypted/encrypted password.";
        }
      }
      container service-groups {
        description
          "List of the service group.";
        list service-group {
          key "name";
          max-elements 4096;
          description
            "Configure a service group.";
          leaf name {
            type string {
              length "1..31";
            }
            must "../name!='a' and ../name!='an' and ../name!='any'" {
              tailf:xpath-root 3;
            }
            description
              "Service group name.";
          }
          // NCS drop config false container 'service-group-status'
        }
      }
      container coa-hw-policy-name {
        description
          "Configure DAA or EDSG service templates delivered by the RADIUS server through Huawei proprietary attributes in COA messages.";
        leaf daa-same-policy-reply-ack {
          type boolean;
          default "false";
          description
            "Enable/disable a device to reply with an ACK message when the RADIUS server uses a COA message's HW-Policy-Name (26-95) attribute to deliver the same DAA service policy as that configured on the device in uniform accounting scenarios.";
        }
        leaf daa-coexist-with-user {
          type boolean;
          default "false";
          description
            "Enable/disable the user attributes also to take effect if ehty are delivered with a DAA template in the HW-Policy-Name (26-95) attribute through the same COA message which may also carry other DAA service attributes.";
        }
      }
      container prepaid-profiles {
        description
          "List of the prepaid service templates.";
        list prepaid-profile {
          key "name";
          max-elements 1024;
          description
            "Configure a prepaid service template.";
          leaf name {
            type string {
              length "1..31";
              pattern '[a-z0-9._-]{1,31}';
            }
            must "../name != '-' and ../name != '--'" {
              tailf:xpath-root 3;
            }
            description
              "Specifies the name of a prepaid service template.";
            ext:case-sensitivity "lower-only";
          }
          container accounting-scheme {
            description
              "Configure the accounting scheme for the current pre-paid profile. The scheme must be a configured accounting scheme.";
            leaf name {
              type leafref {
                path "/ncs:devices/ncs:device/ncs:config/aaa:aaa/aaa:accounting-schemes/aaa:accounting-scheme/aaa:acct-scheme-name" {
                  tailf:xpath-root 3;
                }
              }
              default "default1";
              description
                "Specifies the name of the accounting scheme adopted by the pre-paid profile.";
            }
          }
          container authen-scheme {
            description
              "Configure the authentication scheme for the current pre-paid profile. The scheme must be a configured authentication scheme.";
            leaf name {
              type leafref {
                path "/ncs:devices/ncs:device/ncs:config/aaa:aaa/aaa:authentication-schemes/aaa:authentication-scheme/aaa:authen-scheme-name" {
                  tailf:xpath-root 3;
                }
              }
              default "default1";
              description
                "Specifies the name of the authentication scheme.";
            }
          }
          container password {
            description
              "Configure the password used for the quotas application sent to the server by the prepaid services.";
            leaf password {
              type pub-type:password-extend {
                length "1..128";
              }
              description
                "The password is a string ranging from 1 to 16 characters for a simple password and 1 to 128 characters for a ciphertext password.";
            }
          }
          container threshold {
            description
              "Configure the threshold that determines when the pre-paid service sends the application for quotas.";
            leaf time-value {
              type uint32;
              units "s";
              default "0";
              description
                "Uses a certain period of time as the threshold.";
            }
            leaf volume-value {
              type uint32;
              default "0";
              description
                "Uses a certain quantity of volume as the threshold.";
            }
            leaf volume-unit {
              type enumeration {
                enum "bytes" {
                  value 1;
                  description
                    "The unit is bytes.";
                }
                enum "kbytes" {
                  value 2;
                  description
                    "The unit is kbytes.";
                }
                enum "mbytes" {
                  value 3;
                  description
                    "The unit is mbytes.";
                }
              }
              default "bytes";
              description
                "Unit of the volume.";
            }
          }
          container service-volume-quota-apply {
            description
              "Configure the traffic direction to which the EDSG service quota applies.";
            leaf direction {
              type enumeration {
                enum "both" {
                  value 0;
                  description
                    "The direction is both inbound and outbound.";
                }
                enum "inbound" {
                  value 1;
                  description
                    "The direction is inbound.";
                }
                enum "outbound" {
                  value 2;
                  description
                    "The direction is outbound.";
                }
              }
              default "both";
              description
                "The direction of volume Apply.";
            }
          }
          // NCS drop config false container 'profile-info'
        }
      }
      container edsg-accounting-interim {
        description
          "Configure a device to send a real-time accounting packet carrying the HW-Acct-Update-Address (26-159) attribute with a value of 1 for EDSG services when the user address changes. By default, when the user address changes, a device does not send a real-time accounting packet carrying the HW-Acct-Update-Address (26-159) attribute with a value of 1 for EDSG services.";
        leaf send-update-user-ip-enable {
          type boolean;
          default "false";
          description
            "Enable/disable a device to send a real-time accounting packet carrying the HW-Acct-Update-Address (26-159) attribute with a value of 1 for EDSG services when the user address changes.";
        }
      }
      container edsg-coexist-attribute {
        description
          "Configure a specified attribute to take effect upon delivery in EDSG service scenarios.";
        leaf filter-id {
          type boolean;
          default "false";
          description
            "Enable/disable the attribute of filter-id.";
        }
        leaf traffic-policy {
          type boolean;
          default "false";
          description
            "Enable/disable the attribute of traffic-Policy.";
        }
        leaf hw-data-filter {
          type boolean;
          default "false";
          description
            "Enable/disable the attribute of HW-Data-Filter.";
        }
        leaf class {
          type boolean;
          default "false";
          description
            "Enable/disable the attribute of class.";
        }
      }
      container service-record {
        description
          "Configure the service activation failure or deactivation record.";
        leaf active-fail {
          type boolean;
          default "true";
          description
            "Enable/disable the service activation failure record function.";
        }
        leaf deactive {
          type boolean;
          default "true";
          description
            "Enable/disable the service deactivation record function.";
        }
      }
      container traffic-policy {
        description
          "Configure a DAA traffic policy globally.";
        leaf name {
          type leafref {
            path "/ncs:devices/ncs:device/ncs:config/qos:qos/qos:classifier-template/qos:traffic-policys/qos:traffic-policy/qos:name" {
              tailf:xpath-root 3;
            }
          }
          description
            "Specifies the name of a DAA traffic policy.";
        }
      }
      container policy-cache-update-interval {
        description
          "Configure an interval at which the downloaded EDSG service policy template is updated.";
        leaf interval {
          type uint16 {
            range "5..65535";
          }
          units "min";
          description
            "Specifies the interval at which the downloaded EDSG service policy template is updated.";
        }
      }
      container service-no-server-policy {
        description
          "Configure an activation policy for RADIUS servers when an EDSG service policy is not bound to any RADIUS server group.";
        leaf server-activation-mode {
          type bras-vas-online-offline-type;
          default "offline";
          description
            "Configures an activation policy for RADIUS servers when an EDSG service policy is not bound to any RADIUS server group.";
        }
      }
      container tariff-queue-mapping {
        presence "Tariff queue mapping.";
        description
          "Configure the queue scheduling can be performed on different value-added services to ensure that services with higher priorities are forwarded first. It is used to configure the mapping relationship between tariff levels of DAA and flow queues.";
        leaf-list tariff-level {
          ext:generated-by "system";
          ext:operation-exclude "create|delete";
          type bras-vas-flow-queue-type;
          min-elements 8;
          max-elements 8;
          ordered-by user;
          description
            "Configure a packet type.";
        }
      }
      container service-policys {
        description
          "List of the value-added service policy templates.";
        list service-policy {
          key "name";
          max-elements 4096;
          description
            "Configure a value-added service policy template.";
          leaf name {
            type string {
              length "1..64";
              pattern '[a-zA-Z0-9._-]{1,64}';
            }
            must "../name != '-' and ../name != '--'" {
              tailf:xpath-root 3;
            }
            description
              "Specify the name of a value-added service policy. When the node of policy-name-case-sensitive is enabled, the service policy name is case-sensitive. When the node of policy-name-case-sensitive is disabled, the service policy name cannot contain uppercase letters.";
          }
          leaf mode {
            ext:operation-exclude "update";
            type enumeration {
              enum "edsg" {
                value 0;
                description
                  "Indicates an enhanced dynamic service gateway (EDSG) service policy.";
              }
              enum "portal" {
                value 1;
                description
                  "Indicates a portal service policy.";
              }
              enum "mirror" {
                value 4;
                description
                  "Indicates a mirror service policy.";
              }
            }
            mandatory true;
            description
              "Indicates a service policy. This leaf cannot be modified. If you need to modify it, delete the policy and then create a new type of policy.";
          }
          container service-group {
            presence "Service-group.";
            description
              "Configure a service group for a service policy.";
            leaf group-name {
              type leafref {
                path "../../../../service-groups/service-group/name";
              }
              mandatory true;
              description
                "Specifies the name of a service group.";
            }
            leaf direction {
              when "../../mode='edsg'" {
                tailf:xpath-root 3;
              }
              type enumeration {
                enum "inbound" {
                  value 1;
                  description
                    "Inbound.";
                }
                enum "outbound" {
                  value 2;
                  description
                    "Outbound.";
                }
                enum "both" {
                  value 3;
                  description
                    "Both.";
                }
              }
              default "both";
              description
                "Indicates the direction for a service group.";
            }
            leaf priority {
              when "../../mode='edsg'" {
                tailf:xpath-root 3;
              }
              type uint32 {
                range "0..1000";
              }
              default "0";
              description
                "Specifies a priority value that a service matches.";
            }
          }
          container accounting-scheme {
            when "../mode='edsg'" {
              tailf:xpath-root 3;
            }
            description
              "Configure the accounting scheme for the current service policy. The scheme must be a configured accounting scheme.";
            leaf name {
              type leafref {
                path "/ncs:devices/ncs:device/ncs:config/aaa:aaa/aaa:accounting-schemes/aaa:accounting-scheme/aaa:acct-scheme-name" {
                  tailf:xpath-root 3;
                }
              }
              default "default1";
              description
                "Specifies the name of the accounting scheme adopted by the pre-paid profile.";
            }
          }
          container radius-server-group {
            when "../mode='edsg'" {
              tailf:xpath-root 3;
            }
            description
              "Configure the RADIUS server group for service policy. The server group must be a configured server group.";
            leaf name {
              type leafref {
                path "/ncs:devices/ncs:device/ncs:config/radius:radius/radius:radius-server-groups/radius:radius-server-group/radius:name" {
                  tailf:xpath-root 3;
                }
              }
              description
                "Specifies the name of the RADIUS server group.";
            }
          }
          container traffic-match {
            when "../mode='edsg'" {
              tailf:xpath-root 3;
            }
            description
              "Configure EDSG service traffic to match a user group.";
            leaf direction {
              type enumeration {
                enum "none" {
                  value 0;
                  description
                    "None.";
                }
                enum "inbound" {
                  value 1;
                  description
                    "Specifies inbound direction of reporting dropped SQ traffic.";
                }
                enum "outbound" {
                  value 2;
                  description
                    "Specifies outbound direction of reporting dropped SQ traffic.";
                }
                enum "both" {
                  value 3;
                  description
                    "Specifies inbound and outbound direction of reporting dropped SQ traffic.";
                }
              }
              default "none";
              description
                "Indicates stream direction of EDSG service traffic.";
            }
          }
          container statistic-ip-type {
            when "../mode='edsg'" {
              tailf:xpath-root 3;
            }
            description
              "Configure a statistic IP type for EDSG services. The default statistic type is IPv4 for EDSG services.";
            leaf type {
              type bras-vas-service-ip-type;
              default "ipv4";
              description
                "Statistic IP type for EDSG services.";
            }
          }
          container service-class {
            when "../mode='edsg'" {
              tailf:xpath-root 3;
            }
            description
              "Configure upstream or downstream service classes.";
            leaf inbound-class {
              type bras-vas-flow-queue-type;
              description
                "Specifies a service class of inbound direction.";
            }
            leaf outbound-class {
              type bras-vas-flow-queue-type;
              description
                "Specifies a service class of outbound direction.";
            }
          }
          container authentication-scheme {
            when "../mode='edsg'" {
              tailf:xpath-root 3;
            }
            description
              "Configure an authentication scheme for the current service policy. The scheme must be a configured authentication scheme.";
            leaf name {
              type leafref {
                path "/ncs:devices/ncs:device/ncs:config/aaa:aaa/aaa:authentication-schemes/aaa:authentication-scheme/aaa:authen-scheme-name" {
                  tailf:xpath-root 3;
                }
              }
              description
                "Specifies the name of the authentication scheme.";
            }
          }
          container rate-limit {
            when "../mode='edsg'" {
              tailf:xpath-root 3;
            }
            description
              "Configure the inbound and outbound rate for the service policy template.";
            container inbound {
              presence "Create inbound rate-limit.";
              description
                "Configure the inbound rate for the service policy template.";
              uses rate-limit-type;
            }
            container outbound {
              presence "Create outbound rate-limit.";
              description
                "Configure the outbound rate for the service policy template.";
              uses rate-limit-type;
            }
          }
          container diameter-monitor-key {
            when "../mode='edsg'" {
              tailf:xpath-root 3;
            }
            description
              "Configure the Characters monitoring key values for the policy business.";
            leaf key {
              type uint32 {
                range "1..4294967294";
              }
              description
                "Monitoring key values for the policy business.";
            }
          }
          // NCS drop config false container 'policy-info'
        }
      }
      container mirror-service-policy-rules {
        description
          "List of the mapping relation between service policy and option82.";
        list mirror-service-policy-rule {
          key "number";
          description
            "Configure the mapping relation between service policy and option82.";
          leaf number {
            type uint32 {
              range "0..65535";
            }
            description
              "The number of the rule.";
          }
          leaf service-policy-name {
            type leafref {
              path "../../../service-policys/service-policy/name";
            }
            must "../../../service-policys/service-policy[name=current()]/mode='mirror'" {
              tailf:xpath-root 3;
            }
            must '../../../service-policys/service-policy[name=current()]/service-group/group-name' {
              tailf:xpath-root 3;
            }
            mandatory true;
            description
              "The name of a service policy.";
          }
          leaf option82-type {
            type enumeration {
              enum "circuit-id" {
                value 1;
                description
                  "Circuit id.";
              }
              enum "remote-id" {
                value 2;
                description
                  "Remote id.";
              }
            }
            mandatory true;
            description
              "The type of option82 attribute.";
          }
          leaf option82-value {
            type string {
              length "1..198";
            }
            mandatory true;
            description
              "The information of option82.";
          }
          leaf part-match {
            type boolean;
            default "false";
            description
              "Enable/disable supporting the part matching.";
          }
        }
      }
      // NCS drop config false container 'vas-user-id-states'
      // NCS drop config false container 'edsg-user-infos'
      // NCS drop config false container 'user-id-daa-states'
      // NCS drop config false container 'user-id-bod-states'
      // NCS drop config false container 'vas-edsg-user-id-informations'
      // NCS drop config false container 'edsg-time-range-state'
      // NCS drop config false container 'updated-fail-statistic'
      // NCS drop config false container 'remote-policy-caches'
      // NCS drop config false container 'vas-daa-user-id-infos'
    }
  }
  augment "/ncs:devices/ncs:device/ncs:live-status" {
    container bras-vas {
      tailf:ncs-device-type "netconf";
      tailf:display-when "not(../../ncs:module) or ../../ncs:module[ncs:name='huawei-bras-vas'] or (../../ncs:live-status-protocol[not(ncs:capability)]) or (../../ncs:live-status-protocol/ncs:capability/ncs:module[.='huawei-bras-vas'])";
      description
        "Bras value-added services.";
      container global {
        description
          "Configure value-added-service.";
        container value-added-service {
          description
            "Configure value-added-service enable list.";
          leaf enable {
            type boolean;
            // NCS drop default statement
            description
              "Enable/disable value-added-service.";
          }
        }
        container account-individual {
          description
            "Configure account individual.";
          leaf enable {
            type boolean;
            // NCS drop default statement
            description
              "Enable/disable account individual.";
          }
        }
        container policy-name-case-sensitive {
          description
            "Configure service policy name case sensitive.";
          leaf enable {
            type boolean;
            // NCS drop default statement
            description
              "Enable/disable service policy name case sensitive.";
          }
        }
        container quota-out {
          description
            "Configure the Quota type.";
          leaf quota-type {
            type live_ncs_bras-vas-quota-out-online-offline-type;
            // NCS drop default statement
            description
              "Quota type.";
          }
          leaf diameter-link-down {
            type live_ncs_bras-vas-quota-out-online-offline-type;
            // NCS drop default statement
            description
              "Quota type of diameter link down.";
          }
        }
        container daa-resource-insufficient {
          description
            "Configure Resource Application Failures Policy.";
          leaf type {
            type enumeration {
              enum "online" {
                value 0;
                description
                  "By default, DAA users remain online after they fail to apply for resources.";
              }
              enum "inbound-offline" {
                value 1;
                description
                  "Log out DAA users who fail to apply for upstream resources.";
              }
              enum "outbound-offline" {
                value 2;
                description
                  "Log out DAA users who fail to apply for downstream resources.";
              }
              enum "inbound-or-outbound-offline" {
                value 3;
                description
                  "Log out DAA users who fail to apply for upstream or downstream resources.";
              }
              enum "both-offline" {
                value 4;
                description
                  "Log out DAA users who fail to apply for both upstream and downstream resources.";
              }
            }
            // NCS drop default statement
            description
              "Policy Upon Resource Application Failures.";
          }
        }
        container edsg-queue {
          description
            "Configure delayed EDSG user activation.";
          leaf enable {
            type boolean;
            // NCS drop default statement
            description
              "Enable/disable a device to adjust the access rate of users who go online by configuring the edsg service to enter the activation queue and suspend the activation.";
          }
        }
        container edsg-run-info {
          description
            "Statistics of the global service policy configuration.";
          leaf edsg-run-service-number {
            type uint32;
            description
              "Number of EDSG resources that are in use, this item is displayed only if the EDSG function license is deactivated.";
          }
        }
        container edsg-centralized-ds-lite {
          description
            "Configure value-added services on the centralized DS-Lite device.";
          leaf enable {
            type boolean;
            // NCS drop default statement
            description
              "Enable/disable the function of matching EDSG services based on inner IPv4 packets.";
          }
        }
        container daa-report-dropped-flow {
          description
            "Configure the function to report DAA users whose packets are dropped.";
          leaf enable {
            type boolean;
            // NCS drop default statement
            description
              "Enable/disable the function to report DAA users whose packets are dropped.";
          }
        }
      }
      container vas-policys {
        description
          "List of the vas Policy.";
        list vas-policy {
          key "name";
          description
            "Configure a vas policy.";
          leaf name {
            type string {
              length "1..63";
              pattern '[!-~]{1,63}';
              pattern "([^A-Z\"%'*/:<>\\?@|]{1,63})";
            }
            // NCS drop must statement
            description
              "Vas policy name.";
            ext:case-sensitivity "lower-only";
          }
          leaf type {
            ext:operation-exclude "update";
            type live_ncs_bras-vas-policy-type;
            // NCS drop mandatory statement
            description
              "Vas policy type.";
          }
          container qos-profile {
            // NCS drop when statement
            description
              "Configure qos profile.";
            leaf name {
              type leafref {
                path "/ncs:devices/ncs:device/ncs:live-status/qos:qos/qos:queue-scheduler-template/qos:profiles/qos:profile/qos:name" {
                  tailf:xpath-root 3;
                }
              }
              // NCS drop must statement
              description
                "Name of qos profile.";
            }
          }
          container accounting-scheme {
            description
              "Configure accounting scheme.";
            leaf name {
              type leafref {
                path "/ncs:devices/ncs:device/ncs:live-status/aaa:aaa/aaa:accounting-schemes/aaa:accounting-scheme/aaa:acct-scheme-name" {
                  tailf:xpath-root 3;
                }
              }
              // NCS drop default statement
              description
                "Name of accounting scheme.";
            }
          }
          container daa-service-enable {
            // NCS drop when statement
            description
              "Configure daa service.";
            leaf user-accounting-together {
              type boolean;
              // NCS drop default statement
              description
                "Enable/disable the DAA service traffic counts into user traffic.";
            }
            leaf traffic-separate {
              type boolean;
              // NCS drop default statement
              description
                "Enable/disable the DAA service separate function.";
            }
            leaf tariff-queue-mapping {
              type boolean;
              // NCS drop default statement
              description
                "Enable/disable priority scheduling based on tariff levels.";
            }
            leaf accounting-together {
              type boolean;
              // NCS drop default statement
              description
                "Enable/disable uniform accounting for DAA services.";
            }
          }
          container bind-user-group {
            description
              "Configure an ACL user group to a value-added service policy.";
            leaf name {
              type leafref {
                path "/ncs:devices/ncs:device/ncs:live-status/bras-basic-access:bras-basic-access/bras-basic-access:user-groups/bras-basic-access:user-group/bras-basic-access:name" {
                  tailf:xpath-root 3;
                }
              }
              description
                "Specifies the name of a user group, and the user group must not be added to a user group list or a domain without binding nat instance.";
            }
          }
          container bind-tariff-levels {
            // NCS drop when statement
            description
              "List of the tariff level for DAA accounting.";
            list bind-tariff-level {
              key "tariff-level";
              description
                "Configure a tariff level for DAA accounting.";
              leaf tariff-level {
                type uint8 {
                  range "1..8";
                }
                description
                  "Tariff level for DAA accounting.";
              }
              leaf qos-profile-name {
                type leafref {
                  path "/ncs:devices/ncs:device/ncs:live-status/qos:qos/qos:queue-scheduler-template/qos:profiles/qos:profile/qos:name" {
                    tailf:xpath-root 3;
                  }
                }
                // NCS drop must statement
                // NCS drop mandatory statement
                description
                  "Specifies the name of a bound QoS profile.";
              }
            }
          }
          container tariff-level-accountings {
            // NCS drop when statement
            description
              "List of the accounting status or IP type for a DAA tariff level.";
            list tariff-level-accounting {
              // NCS drop must statement
              key "level";
              description
                "Configure the accounting status or IP type for a DAA tariff level.";
              leaf level {
                type uint8 {
                  range "1..8";
                }
                description
                  "Specifies a DAA tariff level.";
              }
              leaf accounting-off {
                type boolean;
                // NCS drop default statement
                description
                  "Enable/disable the accounting status of a DAA tariff level as disabled.";
              }
              leaf ip-type-ipv6 {
                type boolean;
                // NCS drop default statement
                description
                  "Enable/disable an IP type for a DAA tariff level as IPv6.";
              }
            }
          }
          container user-traffic-statistic {
            // NCS drop when statement
            description
              "Configure the statistics mode for user traffic. After CAR is performed on a DAA service flow, packets in the DAA service flow are re-marked with different priorities and are scheduled into SQs. In SQ-based traffic statistics, however, DAA traffic and non-DAA traffic are not differentiated. Specify the FQs of which traffic statistics are collected as user traffic statistics.";
            container inbound {
              description
                "Configure the statistics mode for user traffic when SQ scheduling is applied to DAA services.";
              uses live_ncs_bras-vas-user-traffic-type;
            }
            container outbound {
              description
                "Configure the statistics mode for user traffic when SQ scheduling is applied to DAA services.";
              uses live_ncs_bras-vas-user-traffic-type;
            }
          }
          container accounting-service-policy {
            // NCS drop when statement
            description
              "Configure user traffic from to match a DAA service policy.";
            leaf inbound {
              type enumeration {
                enum "disable" {
                  value 0;
                  description
                    "Disables user traffic from matching a DAA service policy.";
                }
                enum "enable" {
                  value 1;
                  description
                    "Enables user traffic from to match a DAA service policy.";
                }
                enum "auto" {
                  value 2;
                  description
                    "Automatically matches user traffic with a DAA service policy.";
                }
              }
              // NCS drop default statement
              description
                "Upstream user traffic.";
            }
            leaf outbound {
              type enumeration {
                enum "disable" {
                  value 0;
                  description
                    "Disables user traffic from matching a DAA service policy.";
                }
                enum "enable" {
                  value 1;
                  description
                    "Enables user traffic from to match a DAA service policy.";
                }
                enum "auto" {
                  value 2;
                  description
                    "Automatically matches user traffic with a DAA service policy.";
                }
              }
              // NCS drop default statement
              description
                "Downstream user traffic.";
            }
          }
          container rate-limit-mode {
            // NCS drop when statement
            description
              "Configure a QoS rate limit mode for downstream DAA services on a board with the eTM subcard installed.";
            leaf outbond {
              type live_ncs_bras-vas-out-rate-limit-mode;
              description
                "QoS Rate Limit Mode.";
            }
          }
          container policy-info {
            description
              "Statistics of a specified DAA or BOD value-added service policy.";
            leaf used-number {
              type uint32 {
                range "0..4294967295";
              }
              description
                "Number of services that reference a value-added service policy.";
            }
            leaf user-number {
              type uint32 {
                range "0..4294967295";
              }
              description
                "Number of users for whom a value-added service policy is used.";
            }
          }
        }
      }
      container hw-policy-name-attribute {
        description
          "Configure the HW-Policy-Name attribute to carry the EDSG service policy name.";
        leaf support-edsg {
          type boolean;
          // NCS drop default statement
          description
            "Enable/disable the HW-Policy-Name attribute to carry the EDSG service policy name.";
        }
      }
      container accounting-merge-cache {
        description
          "Configure a post-merging accounting packet that fails to be sent for value-added services to enter the accounting packet cache. By default, a post-merging accounting packet that fails to be sent for value-added services is disabled from entering the accounting packet cache.";
        leaf enable {
          type boolean;
          // NCS drop default statement
          description
            "Enable/disable a post-merging accounting packet that fails to be sent for value-added services to enter the accounting packet cache.";
        }
      }
      container bod-portal-reserved {
        description
          "Configure portal reserved when the type of value added service is bod.";
        leaf enable {
          type boolean;
          // NCS drop default statement
          description
            "Enable/disable portal reserved when the type of value added service is bod.";
        }
      }
      container service-policy-download {
        presence "service-policy-download.";
        description
          "Configure a mode in which an EDSG service policy is obtained.";
        leaf download-type {
          type enumeration {
            enum "local" {
              value 0;
              description
                "Local configuration.";
            }
            enum "radius" {
              value 1;
              description
                "Download from an RADIUS server.";
            }
            enum "local-radius" {
              value 2;
              description
                "First from the local configuration and then from an RADIUS server.";
            }
            enum "radius-local" {
              value 3;
              description
                "First from an RADIUS server and then from the local configuration.";
            }
          }
          // NCS drop default statement
          description
            "Sets a mode in which an EDSG service policy is obtained.";
        }
        leaf radius-server-group-name {
          // NCS drop when statement
          type leafref {
            path "/ncs:devices/ncs:device/ncs:live-status/radius:radius/radius:radius-server-groups/radius:radius-server-group/radius:name" {
              tailf:xpath-root 3;
            }
          }
          // NCS drop mandatory statement
          description
            "Specifies the name of a RADIUS server group.";
        }
        leaf password {
          // NCS drop when statement
          type pub-type:live_ncs_password-extend;
          // NCS drop mandatory statement
          description
            "Specifies an unencrypted/encrypted password.";
        }
      }
      container service-groups {
        description
          "List of the service group.";
        list service-group {
          key "name";
          // NCS drop max-elements statement
          description
            "Configure a service group.";
          leaf name {
            type string {
              length "1..31";
            }
            // NCS drop must statement
            description
              "Service group name.";
          }
          container service-group-status {
            description
              "Operational state of service-group.";
            leaf is-used {
              type enumeration {
                enum "no" {
                  value 0;
                  description
                    "The service-group is unused.";
                }
                enum "yes" {
                  value 1;
                  description
                    "The service-group is used.";
                }
              }
              description
                "Whether the service-group is used or not.";
            }
            leaf group-type {
              type string {
                length "1..19";
              }
              description
                "The type of service-group.";
            }
          }
        }
      }
      container coa-hw-policy-name {
        description
          "Configure DAA or EDSG service templates delivered by the RADIUS server through Huawei proprietary attributes in COA messages.";
        leaf daa-same-policy-reply-ack {
          type boolean;
          // NCS drop default statement
          description
            "Enable/disable a device to reply with an ACK message when the RADIUS server uses a COA message's HW-Policy-Name (26-95) attribute to deliver the same DAA service policy as that configured on the device in uniform accounting scenarios.";
        }
        leaf daa-coexist-with-user {
          type boolean;
          // NCS drop default statement
          description
            "Enable/disable the user attributes also to take effect if ehty are delivered with a DAA template in the HW-Policy-Name (26-95) attribute through the same COA message which may also carry other DAA service attributes.";
        }
      }
      container prepaid-profiles {
        description
          "List of the prepaid service templates.";
        list prepaid-profile {
          key "name";
          // NCS drop max-elements statement
          description
            "Configure a prepaid service template.";
          leaf name {
            type string {
              length "1..31";
              pattern '[a-z0-9._-]{1,31}';
            }
            // NCS drop must statement
            description
              "Specifies the name of a prepaid service template.";
            ext:case-sensitivity "lower-only";
          }
          container accounting-scheme {
            description
              "Configure the accounting scheme for the current pre-paid profile. The scheme must be a configured accounting scheme.";
            leaf name {
              type leafref {
                path "/ncs:devices/ncs:device/ncs:live-status/aaa:aaa/aaa:accounting-schemes/aaa:accounting-scheme/aaa:acct-scheme-name" {
                  tailf:xpath-root 3;
                }
              }
              // NCS drop default statement
              description
                "Specifies the name of the accounting scheme adopted by the pre-paid profile.";
            }
          }
          container authen-scheme {
            description
              "Configure the authentication scheme for the current pre-paid profile. The scheme must be a configured authentication scheme.";
            leaf name {
              type leafref {
                path "/ncs:devices/ncs:device/ncs:live-status/aaa:aaa/aaa:authentication-schemes/aaa:authentication-scheme/aaa:authen-scheme-name" {
                  tailf:xpath-root 3;
                }
              }
              // NCS drop default statement
              description
                "Specifies the name of the authentication scheme.";
            }
          }
          container password {
            description
              "Configure the password used for the quotas application sent to the server by the prepaid services.";
            leaf password {
              type pub-type:live_ncs_password-extend;
              description
                "The password is a string ranging from 1 to 16 characters for a simple password and 1 to 128 characters for a ciphertext password.";
            }
          }
          container threshold {
            description
              "Configure the threshold that determines when the pre-paid service sends the application for quotas.";
            leaf time-value {
              type uint32;
              units "s";
              // NCS drop default statement
              description
                "Uses a certain period of time as the threshold.";
            }
            leaf volume-value {
              type uint32;
              // NCS drop default statement
              description
                "Uses a certain quantity of volume as the threshold.";
            }
            leaf volume-unit {
              type enumeration {
                enum "bytes" {
                  value 1;
                  description
                    "The unit is bytes.";
                }
                enum "kbytes" {
                  value 2;
                  description
                    "The unit is kbytes.";
                }
                enum "mbytes" {
                  value 3;
                  description
                    "The unit is mbytes.";
                }
              }
              // NCS drop default statement
              description
                "Unit of the volume.";
            }
          }
          container service-volume-quota-apply {
            description
              "Configure the traffic direction to which the EDSG service quota applies.";
            leaf direction {
              type enumeration {
                enum "both" {
                  value 0;
                  description
                    "The direction is both inbound and outbound.";
                }
                enum "inbound" {
                  value 1;
                  description
                    "The direction is inbound.";
                }
                enum "outbound" {
                  value 2;
                  description
                    "The direction is outbound.";
                }
              }
              // NCS drop default statement
              description
                "The direction of volume Apply.";
            }
          }
          container profile-info {
            description
              "Operational state of prepaid profile.";
            leaf reference-count {
              type uint32;
              description
                "Number of times that a prepaid profile is referenced by service instances.";
            }
          }
        }
      }
      container edsg-accounting-interim {
        description
          "Configure a device to send a real-time accounting packet carrying the HW-Acct-Update-Address (26-159) attribute with a value of 1 for EDSG services when the user address changes. By default, when the user address changes, a device does not send a real-time accounting packet carrying the HW-Acct-Update-Address (26-159) attribute with a value of 1 for EDSG services.";
        leaf send-update-user-ip-enable {
          type boolean;
          // NCS drop default statement
          description
            "Enable/disable a device to send a real-time accounting packet carrying the HW-Acct-Update-Address (26-159) attribute with a value of 1 for EDSG services when the user address changes.";
        }
      }
      container edsg-coexist-attribute {
        description
          "Configure a specified attribute to take effect upon delivery in EDSG service scenarios.";
        leaf filter-id {
          type boolean;
          // NCS drop default statement
          description
            "Enable/disable the attribute of filter-id.";
        }
        leaf traffic-policy {
          type boolean;
          // NCS drop default statement
          description
            "Enable/disable the attribute of traffic-Policy.";
        }
        leaf hw-data-filter {
          type boolean;
          // NCS drop default statement
          description
            "Enable/disable the attribute of HW-Data-Filter.";
        }
        leaf class {
          type boolean;
          // NCS drop default statement
          description
            "Enable/disable the attribute of class.";
        }
      }
      container service-record {
        description
          "Configure the service activation failure or deactivation record.";
        leaf active-fail {
          type boolean;
          // NCS drop default statement
          description
            "Enable/disable the service activation failure record function.";
        }
        leaf deactive {
          type boolean;
          // NCS drop default statement
          description
            "Enable/disable the service deactivation record function.";
        }
      }
      container traffic-policy {
        description
          "Configure a DAA traffic policy globally.";
        leaf name {
          type leafref {
            path "/ncs:devices/ncs:device/ncs:live-status/qos:qos/qos:classifier-template/qos:traffic-policys/qos:traffic-policy/qos:name" {
              tailf:xpath-root 3;
            }
          }
          description
            "Specifies the name of a DAA traffic policy.";
        }
      }
      container policy-cache-update-interval {
        description
          "Configure an interval at which the downloaded EDSG service policy template is updated.";
        leaf interval {
          type uint16 {
            range "5..65535";
          }
          units "min";
          description
            "Specifies the interval at which the downloaded EDSG service policy template is updated.";
        }
      }
      container service-no-server-policy {
        description
          "Configure an activation policy for RADIUS servers when an EDSG service policy is not bound to any RADIUS server group.";
        leaf server-activation-mode {
          type live_ncs_bras-vas-online-offline-type;
          // NCS drop default statement
          description
            "Configures an activation policy for RADIUS servers when an EDSG service policy is not bound to any RADIUS server group.";
        }
      }
      container tariff-queue-mapping {
        presence "Tariff queue mapping.";
        description
          "Configure the queue scheduling can be performed on different value-added services to ensure that services with higher priorities are forwarded first. It is used to configure the mapping relationship between tariff levels of DAA and flow queues.";
        leaf-list tariff-level {
          ext:generated-by "system";
          ext:operation-exclude "create|delete";
          type live_ncs_bras-vas-flow-queue-type;
          // NCS drop min-elements statement
          // NCS drop max-elements statement
          ordered-by user;
          description
            "Configure a packet type.";
        }
      }
      container service-policys {
        description
          "List of the value-added service policy templates.";
        list service-policy {
          key "name";
          // NCS drop max-elements statement
          description
            "Configure a value-added service policy template.";
          leaf name {
            type string {
              length "1..64";
              pattern '[a-zA-Z0-9._-]{1,64}';
            }
            // NCS drop must statement
            description
              "Specify the name of a value-added service policy. When the node of policy-name-case-sensitive is enabled, the service policy name is case-sensitive. When the node of policy-name-case-sensitive is disabled, the service policy name cannot contain uppercase letters.";
          }
          leaf mode {
            ext:operation-exclude "update";
            type enumeration {
              enum "edsg" {
                value 0;
                description
                  "Indicates an enhanced dynamic service gateway (EDSG) service policy.";
              }
              enum "portal" {
                value 1;
                description
                  "Indicates a portal service policy.";
              }
              enum "mirror" {
                value 4;
                description
                  "Indicates a mirror service policy.";
              }
            }
            // NCS drop mandatory statement
            description
              "Indicates a service policy. This leaf cannot be modified. If you need to modify it, delete the policy and then create a new type of policy.";
          }
          container service-group {
            presence "Service-group.";
            description
              "Configure a service group for a service policy.";
            leaf group-name {
              type leafref {
                path "../../../../service-groups/service-group/name";
              }
              // NCS drop mandatory statement
              description
                "Specifies the name of a service group.";
            }
            leaf direction {
              // NCS drop when statement
              type enumeration {
                enum "inbound" {
                  value 1;
                  description
                    "Inbound.";
                }
                enum "outbound" {
                  value 2;
                  description
                    "Outbound.";
                }
                enum "both" {
                  value 3;
                  description
                    "Both.";
                }
              }
              // NCS drop default statement
              description
                "Indicates the direction for a service group.";
            }
            leaf priority {
              // NCS drop when statement
              type uint32 {
                range "0..1000";
              }
              // NCS drop default statement
              description
                "Specifies a priority value that a service matches.";
            }
          }
          container accounting-scheme {
            // NCS drop when statement
            description
              "Configure the accounting scheme for the current service policy. The scheme must be a configured accounting scheme.";
            leaf name {
              type leafref {
                path "/ncs:devices/ncs:device/ncs:live-status/aaa:aaa/aaa:accounting-schemes/aaa:accounting-scheme/aaa:acct-scheme-name" {
                  tailf:xpath-root 3;
                }
              }
              // NCS drop default statement
              description
                "Specifies the name of the accounting scheme adopted by the pre-paid profile.";
            }
          }
          container radius-server-group {
            // NCS drop when statement
            description
              "Configure the RADIUS server group for service policy. The server group must be a configured server group.";
            leaf name {
              type leafref {
                path "/ncs:devices/ncs:device/ncs:live-status/radius:radius/radius:radius-server-groups/radius:radius-server-group/radius:name" {
                  tailf:xpath-root 3;
                }
              }
              description
                "Specifies the name of the RADIUS server group.";
            }
          }
          container traffic-match {
            // NCS drop when statement
            description
              "Configure EDSG service traffic to match a user group.";
            leaf direction {
              type enumeration {
                enum "none" {
                  value 0;
                  description
                    "None.";
                }
                enum "inbound" {
                  value 1;
                  description
                    "Specifies inbound direction of reporting dropped SQ traffic.";
                }
                enum "outbound" {
                  value 2;
                  description
                    "Specifies outbound direction of reporting dropped SQ traffic.";
                }
                enum "both" {
                  value 3;
                  description
                    "Specifies inbound and outbound direction of reporting dropped SQ traffic.";
                }
              }
              // NCS drop default statement
              description
                "Indicates stream direction of EDSG service traffic.";
            }
          }
          container statistic-ip-type {
            // NCS drop when statement
            description
              "Configure a statistic IP type for EDSG services. The default statistic type is IPv4 for EDSG services.";
            leaf type {
              type live_ncs_bras-vas-service-ip-type;
              // NCS drop default statement
              description
                "Statistic IP type for EDSG services.";
            }
          }
          container service-class {
            // NCS drop when statement
            description
              "Configure upstream or downstream service classes.";
            leaf inbound-class {
              type live_ncs_bras-vas-flow-queue-type;
              description
                "Specifies a service class of inbound direction.";
            }
            leaf outbound-class {
              type live_ncs_bras-vas-flow-queue-type;
              description
                "Specifies a service class of outbound direction.";
            }
          }
          container authentication-scheme {
            // NCS drop when statement
            description
              "Configure an authentication scheme for the current service policy. The scheme must be a configured authentication scheme.";
            leaf name {
              type leafref {
                path "/ncs:devices/ncs:device/ncs:live-status/aaa:aaa/aaa:authentication-schemes/aaa:authentication-scheme/aaa:authen-scheme-name" {
                  tailf:xpath-root 3;
                }
              }
              description
                "Specifies the name of the authentication scheme.";
            }
          }
          container rate-limit {
            // NCS drop when statement
            description
              "Configure the inbound and outbound rate for the service policy template.";
            container inbound {
              presence "Create inbound rate-limit.";
              description
                "Configure the inbound rate for the service policy template.";
              uses live_ncs_rate-limit-type;
            }
            container outbound {
              presence "Create outbound rate-limit.";
              description
                "Configure the outbound rate for the service policy template.";
              uses live_ncs_rate-limit-type;
            }
          }
          container diameter-monitor-key {
            // NCS drop when statement
            description
              "Configure the Characters monitoring key values for the policy business.";
            leaf key {
              type uint32 {
                range "1..4294967294";
              }
              description
                "Monitoring key values for the policy business.";
            }
          }
          container policy-info {
            description
              "Statistics of the value-added-service policy.";
            leaf reference-count {
              type uint32 {
                range "0..4294967295";
              }
              description
                "Number of services that reference a service policy.";
            }
          }
        }
      }
      container mirror-service-policy-rules {
        description
          "List of the mapping relation between service policy and option82.";
        list mirror-service-policy-rule {
          key "number";
          description
            "Configure the mapping relation between service policy and option82.";
          leaf number {
            type uint32 {
              range "0..65535";
            }
            description
              "The number of the rule.";
          }
          leaf service-policy-name {
            type leafref {
              path "../../../service-policys/service-policy/name";
            }
            // NCS drop must statement
            // NCS drop must statement
            // NCS drop mandatory statement
            description
              "The name of a service policy.";
          }
          leaf option82-type {
            type enumeration {
              enum "circuit-id" {
                value 1;
                description
                  "Circuit id.";
              }
              enum "remote-id" {
                value 2;
                description
                  "Remote id.";
              }
            }
            // NCS drop mandatory statement
            description
              "The type of option82 attribute.";
          }
          leaf option82-value {
            type string {
              length "1..198";
            }
            // NCS drop mandatory statement
            description
              "The information of option82.";
          }
          leaf part-match {
            type boolean;
            // NCS drop default statement
            description
              "Enable/disable supporting the part matching.";
          }
        }
      }
      container vas-user-id-states {
        description
          "List of the value-added service user IDs.";
        list vas-user-id-state {
          key "service-type user-id";
          description
            "Statistics of the value-added service user IDs.";
          leaf service-type {
            type enumeration {
              enum "bod" {
                value 0;
                description
                  "BOD service type.";
              }
              enum "daa" {
                value 1;
                description
                  "DAA service type.";
              }
              enum "service" {
                value 2;
                description
                  "Display entries of users for whom value-added services are configured.";
              }
              enum "without-service" {
                value 3;
                description
                  "Display entries of users for whom no value-added services are configured.";
              }
              enum "edsg" {
                value 4;
                description
                  "Display EDSG user entries.";
              }
              enum "edsg-radius" {
                value 5;
                description
                  "Delivered by the RADIUS server.";
              }
              enum "edsg-diameter" {
                value 6;
                description
                  "Delivered by the Diameter server.";
              }
              enum "daa-inbound" {
                value 7;
                description
                  "Inbound direction.";
              }
              enum "daa-outbound" {
                value 8;
                description
                  "Outbound direction.";
              }
              enum "daa-with-droped-flow" {
                value 9;
                description
                  "Display DAA users whose packets are dropped.";
              }
            }
            description
              "User table type.";
          }
          leaf user-id {
            type uint32 {
              range "0..4294967295";
            }
            description
              "ID of a user.";
          }
          leaf service-policy-name {
            // NCS drop when statement
            type string {
              length "1..63";
            }
            description
              "Name of a DAA service policy.";
            ext:support-filter "true";
          }
        }
      }
      container edsg-user-infos {
        description
          "List of the VAS user IDs of a specified EDSG service.";
        list edsg-user-info {
          key "user-id service-index";
          description
            "Statistics of the VAS user IDs of a specified EDSG service.";
          leaf user-id {
            type uint32 {
              range "0..4294967295";
            }
            description
              "User access ID.";
          }
          leaf service-index {
            type uint32 {
              range "0..4095";
            }
            description
              "Index of a service.";
          }
          leaf service-name {
            type string {
              length "1..200";
            }
            description
              "Name of a service.";
            ext:support-filter "true";
          }
          leaf service-ip-type {
            type enumeration {
              enum "ipv4" {
                value 0;
                description
                  "IPv4.";
              }
              enum "ipv6" {
                value 1;
                description
                  "IPv6.";
              }
            }
            description
              "Service traffic statistics type.";
          }
          leaf service-state {
            type string {
              length "1..31";
            }
            description
              "Service status.";
          }
          leaf service-sub-state {
            type live_ncs_bras-vas-service-substate;
            description
              "Service sub-state.";
          }
          leaf reserve-policy-name {
            type string {
              length "1..200";
            }
            description
              "Name of the service policy that has been replaced with the service policy delivered using a CoA message.";
          }
          leaf service-group {
            type string {
              length "1..31";
            }
            description
              "Service group.";
          }
          leaf service-group-index {
            type uint16 {
              range "0..65535";
            }
            description
              "Index of a service group.";
          }
          leaf service-group-priority {
            type uint16 {
              range "0..65535";
            }
            description
              "Priority of a service group.";
          }
          leaf inbound-service-class {
            type string {
              length "1..3";
            }
            description
              "Inbound service class.";
          }
          leaf outbound-service-class {
            type string {
              length "1..3";
            }
            description
              "Outbound service class.";
          }
          leaf authen-method {
            type live_ncs_bras-vas-method-type;
            description
              "Authentication method.";
          }
          leaf account-method {
            type live_ncs_bras-vas-method-type;
            description
              "Accounting method.";
          }
          leaf radius-server-group {
            type string {
              length "1..32";
            }
            description
              "RADIUS server group.";
          }
          leaf account-copy-state {
            type enumeration {
              enum "service" {
                value 0;
                description
                  "Service.";
              }
              enum "prepaid" {
                value 1;
                description
                  "Prepaid.";
              }
              enum "close" {
                value 2;
                description
                  "Close.";
              }
            }
            description
              "Status of the EDSG accounting copy function.";
          }
          leaf account-copy-group {
            type string {
              length "1..32";
            }
            description
              "RADIUS server group to which EDSG accounting packets are copied.";
          }
          leaf account-session-id {
            type string {
              length "1..44";
            }
            description
              "Accounting session ID.";
          }
          leaf service-online-time {
            type string {
              length "1..8";
            }
            description
              "Service online duration.";
          }
          leaf real-time-accout-interval {
            type uint32 {
              range "0..4294967295";
            }
            units "s";
            description
              "Real time accounting interval.";
          }
          leaf up-committed-rate {
            type string {
              length "1..19";
            }
            description
              "Upstream committed information rate.";
          }
          leaf up-peak-rate {
            type string {
              length "1..19";
            }
            description
              "Upstream peak information rate.";
          }
          leaf up-committed-burst-size {
            type string {
              length "1..19";
            }
            description
              "Upstream committed burst size.";
          }
          leaf up-peak-burst-size {
            type string {
              length "1..19";
            }
            description
              "Upstream peak burst size.";
          }
          leaf down-committed-rate {
            type string {
              length "1..19";
            }
            description
              "Downstream CIR.";
          }
          leaf down-peak-rate {
            type string {
              length "1..19";
            }
            description
              "Downstream PIR.";
          }
          leaf down-committed-burst-rate {
            type string {
              length "1..19";
            }
            description
              "Downstream CBS.";
          }
          leaf down-peak-burst-size {
            type string {
              length "1..19";
            }
            description
              "Downstream PBS.";
          }
          leaf up-flow-packets-high {
            type uint32 {
              range "0..4294967295";
            }
            units "packet";
            description
              "Number of upstream accounting high packets.";
          }
          leaf up-flow-packets-low {
            type uint32 {
              range "0..4294967295";
            }
            units "packet";
            description
              "Number of upstream accounting low packets.";
          }
          leaf up-flow-bytes-high {
            type uint32 {
              range "0..4294967295";
            }
            units "Byte";
            description
              "Number of upstream accounting high bytes.";
          }
          leaf up-flow-bytes-low {
            type uint32 {
              range "0..4294967295";
            }
            units "Byte";
            description
              "Number of upstream accounting low bytes.";
          }
          leaf down-flow-packets-high {
            type uint32 {
              range "0..4294967295";
            }
            units "packet";
            description
              "Number of downstream accounting high packets.";
          }
          leaf down-flow-packets-low {
            type uint32 {
              range "0..4294967295";
            }
            units "packet";
            description
              "Number of downstream accounting low packets.";
          }
          leaf down-flow-bytes-high {
            type uint32 {
              range "0..4294967295";
            }
            units "Byte";
            description
              "Number of downstream accounting high bytes.";
          }
          leaf down-flow-bytes-low {
            type uint32 {
              range "0..4294967295";
            }
            units "Byte";
            description
              "Number of downstream accounting low bytes.";
          }
          leaf local-up-flow-packets-high {
            type uint32 {
              range "0..4294967295";
            }
            units "packet";
            description
              "Number of upstream accounting high packets.";
          }
          leaf local-up-flow-packets-low {
            type uint32 {
              range "0..4294967295";
            }
            units "packet";
            description
              "Number of upstream accounting low packets.";
          }
          leaf local-up-flow-bytes-high {
            type uint32 {
              range "0..4294967295";
            }
            units "Byte";
            description
              "Number of upstream accounting high bytes.";
          }
          leaf local-up-flow-bytes-low {
            type uint32 {
              range "0..4294967295";
            }
            units "Byte";
            description
              "Number of upstream accounting low bytes.";
          }
          leaf local-down-flow-packets-high {
            type uint32 {
              range "0..4294967295";
            }
            units "packet";
            description
              "Number of downstream accounting high packets.";
          }
          leaf local-down-flow-packets-low {
            type uint32 {
              range "0..4294967295";
            }
            units "packet";
            description
              "Number of downstream accounting low packets.";
          }
          leaf local-down-flow-bytes-high {
            type uint32 {
              range "0..4294967295";
            }
            units "Byte";
            description
              "Number of downstream accounting high bytes.";
          }
          leaf local-down-flow-bytes-low {
            type uint32 {
              range "0..4294967295";
            }
            units "Byte";
            description
              "Number of downstream accounting low bytes.";
          }
          leaf remote-up-flow-packets-high {
            type uint32 {
              range "0..4294967295";
            }
            units "packet";
            description
              "Number of RUI-backed up upstream accounting high packets.";
          }
          leaf remote-up-flow-packets-low {
            type uint32 {
              range "0..4294967295";
            }
            units "packet";
            description
              "Number of RUI-backed up upstream accounting low packets.";
          }
          leaf remote-up-flow-bytes-high {
            type uint32 {
              range "0..4294967295";
            }
            units "Byte";
            description
              "Number of RUI-backed up downstream accounting high packets.";
          }
          leaf remote-up-flow-bytes-low {
            type uint32 {
              range "0..4294967295";
            }
            units "Byte";
            description
              "Number of RUI-backed up downstream accounting low packets.";
          }
          leaf remote-down-flow-packets-high {
            type uint32 {
              range "0..4294967295";
            }
            units "packet";
            description
              "Number of RUI-backed up downstream accounting high packets.";
          }
          leaf remote-down-flow-packets-low {
            type uint32 {
              range "0..4294967295";
            }
            units "packet";
            description
              "Number of RUI-backed up downstream accounting low packets.";
          }
          leaf remote-down-flow-bytes-high {
            type uint32 {
              range "0..4294967295";
            }
            units "Byte";
            description
              "Number of RUI-backed up downstream accounting high bytes.";
          }
          leaf remote-down-flow-bytes-low {
            type uint32 {
              range "0..4294967295";
            }
            units "Byte";
            description
              "Number of RUI-backed up downstream accounting low bytes.";
          }
          leaf prepaid-state {
            type string {
              length "1..11";
            }
            description
              "Prepaid status.";
          }
          leaf prepaid-account-method {
            type live_ncs_bras-vas-method-type;
            description
              "Prepaid accounting method.";
          }
          leaf volume-quota-high {
            type uint32 {
              range "0..4294967295";
            }
            units "Byte/s";
            description
              "Traffic volume quota high.";
          }
          leaf volume-quota-low {
            type uint32 {
              range "0..4294967295";
            }
            units "Byte/s";
            description
              "Traffic volume quota low.";
          }
          leaf volume-threshold-high {
            type uint32 {
              range "0..4294967295";
            }
            units "Byte/s";
            description
              "Traffic volume threshold high.";
          }
          leaf volume-threshold-low {
            type uint32 {
              range "0..4294967295";
            }
            units "Byte/s";
            description
              "Traffic volume threshold low.";
          }
          leaf time-quota {
            type uint32 {
              range "0..4294967295";
            }
            units "s";
            description
              "Traffic volume quota.";
          }
          leaf time-threshold {
            type uint32 {
              range "0..4294967295";
            }
            units "s";
            description
              "Traffic volume threshold.";
          }
          leaf idle-time-out {
            type uint32 {
              range "0..4294967295";
            }
            units "s";
            description
              "Idle timeout.";
          }
          leaf http-redirect-profile {
            type string {
              length "1..32";
            }
            description
              "Name of the redirection profile configured for EDSG services.";
          }
          leaf http-redirect-enable {
            type boolean;
            description
              "Whether captive portal is enabled for EDSG services.";
          }
          leaf http-redirect-profile-portal {
            type string {
              length "1..32";
            }
            description
              "Name of the redirection profile configured for captive portal for EDSG services.";
          }
          leaf http-service-index {
            type uint8 {
              range "0..255";
            }
            description
              "Index of an EDSG service for which captive portal is enabled.";
          }
          leaf service-source {
            type live_ncs_bras-vas-service-source;
            description
              "Service source.";
          }
          leaf diameter-monitor-key {
            type uint32 {
              range "0..4294967295";
            }
            description
              "Diameter monitoring key in the service policy.";
          }
          leaf inbound-match-user-group {
            type boolean;
            description
              "Whether upstream EDSG service traffic matches a user group.";
          }
          leaf outbound-match-user-group {
            type boolean;
            description
              "Whether downstream EDSG service traffic matches a user group.";
          }
          leaf time-range-template {
            type string {
              length "1..32";
            }
            description
              "Name of the time range template that takes effect.";
          }
          leaf rui-state {
            type enumeration {
              enum "master" {
                value 1;
                description
                  "Master.";
              }
              enum "slave" {
                value 2;
                description
                  "Slave.";
              }
              enum "none" {
                value 3;
                description
                  "None.";
              }
            }
            description
              "RUI status of the EDSG service.";
          }
          leaf rui-backup-online-time {
            type uint32 {
              range "0..4294967295";
            }
            units "s";
            description
              "Online duration of the EDSG service when the slave RUI device activates the EDSG service.";
          }
        }
      }
      container user-id-daa-states {
        description
          "List of DAA type information about value-added services based on a specified user ID.";
        list user-id-daa-state {
          key "user-id tariff-level";
          description
            "Statistics of DAA type information about value-added services based on a specified user ID.";
          leaf user-id {
            type uint32;
            description
              "User access ID.";
          }
          leaf tariff-level {
            type uint32 {
              range "1..8";
            }
            description
              "Tariff level.";
          }
          uses live_ncs_user-id-bod-or-daa-statistic-type;
        }
      }
      container user-id-bod-states {
        description
          "List of BOD type information about value-added services based on a specified user ID.";
        list user-id-bod-state {
          key "user-id";
          description
            "Statistics of BOD type information about value-added services based on a specified user ID.";
          leaf user-id {
            type uint32;
            description
              "User access ID.";
          }
          uses live_ncs_user-id-bod-or-daa-statistic-type;
        }
      }
      container vas-edsg-user-id-informations {
        description
          "List of the VAS EDSG service of a specified user ID.";
        list vas-edsg-user-id-information {
          key "user-access-index";
          description
            "Statistics of the VAS EDSG service of a specified user ID.";
          leaf user-access-index {
            type uint32 {
              range "0..4294967295";
            }
            description
              "Index of an access user.";
          }
          leaf user-name {
            type string {
              length "1..253";
            }
            description
              "Name of a user.";
          }
          leaf traffic-rate-mode {
            type enumeration {
              enum "together" {
                value 0;
                description
                  "Together.";
              }
              enum "separate" {
                value 1;
                description
                  "Separate.";
              }
            }
            description
              "Rate limit mode.";
          }
          leaf traffic-statistic-mode {
            type enumeration {
              enum "together" {
                value 0;
                description
                  "Together.";
              }
              enum "separate" {
                value 1;
                description
                  "Separate.";
              }
            }
            description
              "Statistics mode.";
          }
          leaf inbound-rate-limit-mode {
            type live_ncs_bras-vas-rate-limit-mode;
            description
              "Inbound rate limit mode.";
          }
          leaf outbound-rate-limit-mode {
            type live_ncs_bras-vas-rate-limit-mode;
            description
              "Outbound rate limit mode.";
          }
          leaf service-change-mode {
            type enumeration {
              enum "stop-start" {
                value 0;
                description
                  "Stop-start.";
              }
              enum "update" {
                value 1;
                description
                  "Update.";
              }
            }
            description
              "Service change mode.";
          }
          leaf stop-accounting-merge {
            type boolean;
            // NCS drop default statement
            description
              "Stop accounting merge.";
          }
          leaf interim-accounting-merge {
            type boolean;
            // NCS drop default statement
            description
              "Interim accounting merge.";
          }
          leaf interim-interval {
            type uint16 {
              range "0..65535";
            }
            units "min";
            description
              "Merged interim accounting interval.";
          }
          leaf interim-hash {
            type boolean;
            // NCS drop default statement
            description
              "Merged interim accounting hash.";
          }
          leaf inbound-family-schedule {
            type boolean;
            // NCS drop default statement
            description
              "Whether EDSG unified scheduling is enabled for upstream family users.";
          }
          leaf outbound-family-schedule {
            type boolean;
            // NCS drop default statement
            description
              "Whether EDSG unified scheduling is enabled for downstream family users.";
          }
          container user-id-edsg-service-briefs {
            description
              "List of the VAS EDSG service of a specified user ID.";
            list user-id-edsg-service-brief {
              key "service-index";
              description
                "Statistics of the VAS EDSG service of a specified user ID.";
              leaf service-index {
                type uint32 {
                  range "0..4294967295";
                }
                description
                  "Index of a service.";
              }
              leaf service-name {
                type string {
                  length "1..200";
                }
                description
                  "Name of a service.";
              }
              leaf service-state {
                type string {
                  length "1..31";
                }
                description
                  "State of a service.";
              }
            }
          }
        }
      }
      container edsg-time-range-state {
        description
          "Statistics of the edsg time-range.";
        uses live_ncs_edsg-time-range-info-type;
      }
      container updated-fail-statistic {
        description
          "Statistics of update fail record.";
        uses live_ncs_updated-fail-statistic-type;
      }
      container remote-policy-caches {
        description
          "List of the specified EDSG service cache policy.";
        list remote-policy-cache {
          key "service-policy-name";
          // NCS drop max-elements statement
          description
            "Statistics of a specified EDSG service cache policy.";
          leaf service-policy-name {
            type string {
              length "1..200";
            }
            description
              "Specify the name of a remote policy cache.";
          }
          uses live_ncs_remote-policy-cache-type;
        }
      }
      container vas-daa-user-id-infos {
        description
          "List of the dropped DAA service traffic of a specified user ID.";
        list vas-daa-user-id-info {
          key "user-access-index";
          description
            "Statistics of the dropped DAA service traffic of a specified user ID.";
          leaf user-access-index {
            type uint32 {
              range "0..4294967295";
            }
            description
              "Index of an access user.";
          }
          leaf user-state {
            type uint8;
            description
              "State of a user.";
          }
          leaf user-name {
            type string {
              length "1..253";
            }
            description
              "Name of a user.";
          }
          leaf user-service-number {
            type uint8;
            description
              "Number of user services.";
          }
          leaf cops-server-name {
            type string {
              length "1..63";
            }
            description
              "Name of a cops server.";
          }
          leaf direction {
            type string {
              length "1..15";
            }
            description
              "Direction of DAA service traffic.";
          }
          leaf outbound-rate-limit-mode {
            type string {
              length "1..15";
            }
            description
              "Rate limiting mode of downstream DAA service traffic.";
          }
          leaf dropped-flow-upstream-high {
            type uint32;
            units "packet";
            description
              "High-order number of packets dropped in the upstream direction.";
          }
          leaf dropped-flow-upstream-low {
            type uint32;
            units "packet";
            description
              "Low-order number of packets dropped in the upstream direction.";
          }
          leaf dropped-flow-downstream-high {
            type uint32;
            units "packet";
            description
              "High-order number of packets dropped in the downstream direction.";
          }
          leaf dropped-flow-downstream-low {
            type uint32;
            units "packet";
            description
              "Low-order number of packets dropped in the downstream direction.";
          }
          leaf tariff-level1 {
            type uint8;
            description
              "DAA tariff level 1.";
          }
          leaf tariff-level2 {
            type uint8;
            description
              "DAA tariff level 2.";
          }
          leaf tariff-level3 {
            type uint8;
            description
              "DAA tariff level 3.";
          }
          leaf tariff-level4 {
            type uint8;
            description
              "DAA tariff level 4.";
          }
          leaf tariff-level5 {
            type uint8;
            description
              "DAA tariff level 5.";
          }
          leaf tariff-level6 {
            type uint8;
            description
              "DAA tariff level 6.";
          }
          leaf tariff-level7 {
            type uint8;
            description
              "DAA tariff level 7.";
          }
          leaf tariff-level8 {
            type uint8;
            description
              "DAA tariff level 8.";
          }
        }
      }
    }
  }
  augment "/ncs:devices/ncs:template/ncs:ned-id/ncs:config" {
    container bras-vas {
      description
        "Bras value-added services.";
      container global {
        description
          "Configure value-added-service.";
        container value-added-service {
          description
            "Configure value-added-service enable list.";
          leaf enable {
            type string;
            // NCS drop default statement
            description
              "Enable/disable value-added-service.";
          }
        }
        container account-individual {
          description
            "Configure account individual.";
          leaf enable {
            type string;
            // NCS drop default statement
            description
              "Enable/disable account individual.";
          }
        }
        container policy-name-case-sensitive {
          description
            "Configure service policy name case sensitive.";
          leaf enable {
            type string;
            // NCS drop default statement
            description
              "Enable/disable service policy name case sensitive.";
          }
        }
        container quota-out {
          description
            "Configure the Quota type.";
          leaf quota-type {
            type ncs_template_bras-vas-quota-out-online-offline-type;
            // NCS drop default statement
            description
              "Quota type.";
          }
          leaf diameter-link-down {
            type ncs_template_bras-vas-quota-out-online-offline-type;
            // NCS drop default statement
            description
              "Quota type of diameter link down.";
          }
        }
        container daa-resource-insufficient {
          description
            "Configure Resource Application Failures Policy.";
          leaf type {
            type string;
            // NCS drop default statement
            description
              "Policy Upon Resource Application Failures.";
          }
        }
        container edsg-queue {
          description
            "Configure delayed EDSG user activation.";
          leaf enable {
            type string;
            // NCS drop default statement
            description
              "Enable/disable a device to adjust the access rate of users who go online by configuring the edsg service to enter the activation queue and suspend the activation.";
          }
        }
        // NCS drop config false container 'edsg-run-info'
        container edsg-centralized-ds-lite {
          description
            "Configure value-added services on the centralized DS-Lite device.";
          leaf enable {
            type string;
            // NCS drop default statement
            description
              "Enable/disable the function of matching EDSG services based on inner IPv4 packets.";
          }
        }
        container daa-report-dropped-flow {
          description
            "Configure the function to report DAA users whose packets are dropped.";
          leaf enable {
            type string;
            // NCS drop default statement
            description
              "Enable/disable the function to report DAA users whose packets are dropped.";
          }
        }
      }
      container vas-policys {
        description
          "List of the vas Policy.";
        list vas-policy {
          // NCS patched for predictable order
          ordered-by user;
          key "name";
          description
            "Configure a vas policy.";
          leaf name {
            type string;
            // NCS drop must statement
            description
              "Vas policy name.";
            ext:case-sensitivity "lower-only";
          }
          leaf type {
            ext:operation-exclude "update";
            type ncs_template_bras-vas-policy-type;
            // NCS drop mandatory statement
            description
              "Vas policy type.";
          }
          container qos-profile {
            // NCS drop when statement
            description
              "Configure qos profile.";
            leaf name {
              type string;
              // NCS drop must statement
              description
                "Name of qos profile.";
            }
          }
          container accounting-scheme {
            description
              "Configure accounting scheme.";
            leaf name {
              type string;
              // NCS drop default statement
              description
                "Name of accounting scheme.";
            }
          }
          container daa-service-enable {
            // NCS drop when statement
            description
              "Configure daa service.";
            leaf user-accounting-together {
              type string;
              // NCS drop default statement
              description
                "Enable/disable the DAA service traffic counts into user traffic.";
            }
            leaf traffic-separate {
              type string;
              // NCS drop default statement
              description
                "Enable/disable the DAA service separate function.";
            }
            leaf tariff-queue-mapping {
              type string;
              // NCS drop default statement
              description
                "Enable/disable priority scheduling based on tariff levels.";
            }
            leaf accounting-together {
              type string;
              // NCS drop default statement
              description
                "Enable/disable uniform accounting for DAA services.";
            }
          }
          container bind-user-group {
            description
              "Configure an ACL user group to a value-added service policy.";
            leaf name {
              type string;
              description
                "Specifies the name of a user group, and the user group must not be added to a user group list or a domain without binding nat instance.";
            }
          }
          container bind-tariff-levels {
            // NCS drop when statement
            description
              "List of the tariff level for DAA accounting.";
            list bind-tariff-level {
              // NCS patched for predictable order
              ordered-by user;
              key "tariff-level";
              description
                "Configure a tariff level for DAA accounting.";
              leaf tariff-level {
                type string;
                description
                  "Tariff level for DAA accounting.";
              }
              leaf qos-profile-name {
                type string;
                // NCS drop must statement
                // NCS drop mandatory statement
                description
                  "Specifies the name of a bound QoS profile.";
              }
            }
          }
          container tariff-level-accountings {
            // NCS drop when statement
            description
              "List of the accounting status or IP type for a DAA tariff level.";
            list tariff-level-accounting {
              // NCS patched for predictable order
              ordered-by user;
              // NCS drop must statement
              key "level";
              description
                "Configure the accounting status or IP type for a DAA tariff level.";
              leaf level {
                type string;
                description
                  "Specifies a DAA tariff level.";
              }
              leaf accounting-off {
                type string;
                // NCS drop default statement
                description
                  "Enable/disable the accounting status of a DAA tariff level as disabled.";
              }
              leaf ip-type-ipv6 {
                type string;
                // NCS drop default statement
                description
                  "Enable/disable an IP type for a DAA tariff level as IPv6.";
              }
            }
          }
          container user-traffic-statistic {
            // NCS drop when statement
            description
              "Configure the statistics mode for user traffic. After CAR is performed on a DAA service flow, packets in the DAA service flow are re-marked with different priorities and are scheduled into SQs. In SQ-based traffic statistics, however, DAA traffic and non-DAA traffic are not differentiated. Specify the FQs of which traffic statistics are collected as user traffic statistics.";
            container inbound {
              description
                "Configure the statistics mode for user traffic when SQ scheduling is applied to DAA services.";
              uses ncs_template_bras-vas-user-traffic-type;
            }
            container outbound {
              description
                "Configure the statistics mode for user traffic when SQ scheduling is applied to DAA services.";
              uses ncs_template_bras-vas-user-traffic-type;
            }
          }
          container accounting-service-policy {
            // NCS drop when statement
            description
              "Configure user traffic from to match a DAA service policy.";
            leaf inbound {
              type string;
              // NCS drop default statement
              description
                "Upstream user traffic.";
            }
            leaf outbound {
              type string;
              // NCS drop default statement
              description
                "Downstream user traffic.";
            }
          }
          container rate-limit-mode {
            // NCS drop when statement
            description
              "Configure a QoS rate limit mode for downstream DAA services on a board with the eTM subcard installed.";
            leaf outbond {
              type ncs_template_bras-vas-out-rate-limit-mode;
              description
                "QoS Rate Limit Mode.";
            }
          }
          // NCS drop config false container 'policy-info'
        }
      }
      container hw-policy-name-attribute {
        description
          "Configure the HW-Policy-Name attribute to carry the EDSG service policy name.";
        leaf support-edsg {
          type string;
          // NCS drop default statement
          description
            "Enable/disable the HW-Policy-Name attribute to carry the EDSG service policy name.";
        }
      }
      container accounting-merge-cache {
        description
          "Configure a post-merging accounting packet that fails to be sent for value-added services to enter the accounting packet cache. By default, a post-merging accounting packet that fails to be sent for value-added services is disabled from entering the accounting packet cache.";
        leaf enable {
          type string;
          // NCS drop default statement
          description
            "Enable/disable a post-merging accounting packet that fails to be sent for value-added services to enter the accounting packet cache.";
        }
      }
      container bod-portal-reserved {
        description
          "Configure portal reserved when the type of value added service is bod.";
        leaf enable {
          type string;
          // NCS drop default statement
          description
            "Enable/disable portal reserved when the type of value added service is bod.";
        }
      }
      container service-policy-download {
        presence "service-policy-download.";
        description
          "Configure a mode in which an EDSG service policy is obtained.";
        leaf download-type {
          type string;
          // NCS drop default statement
          description
            "Sets a mode in which an EDSG service policy is obtained.";
        }
        leaf radius-server-group-name {
          // NCS drop when statement
          type string;
          // NCS drop mandatory statement
          description
            "Specifies the name of a RADIUS server group.";
        }
        leaf password {
          // NCS drop when statement
          type pub-type:ncs_template_password-extend;
          // NCS drop mandatory statement
          description
            "Specifies an unencrypted/encrypted password.";
        }
      }
      container service-groups {
        description
          "List of the service group.";
        list service-group {
          // NCS patched for predictable order
          ordered-by user;
          key "name";
          // NCS drop max-elements statement
          description
            "Configure a service group.";
          leaf name {
            type string;
            // NCS drop must statement
            description
              "Service group name.";
          }
          // NCS drop config false container 'service-group-status'
        }
      }
      container coa-hw-policy-name {
        description
          "Configure DAA or EDSG service templates delivered by the RADIUS server through Huawei proprietary attributes in COA messages.";
        leaf daa-same-policy-reply-ack {
          type string;
          // NCS drop default statement
          description
            "Enable/disable a device to reply with an ACK message when the RADIUS server uses a COA message's HW-Policy-Name (26-95) attribute to deliver the same DAA service policy as that configured on the device in uniform accounting scenarios.";
        }
        leaf daa-coexist-with-user {
          type string;
          // NCS drop default statement
          description
            "Enable/disable the user attributes also to take effect if ehty are delivered with a DAA template in the HW-Policy-Name (26-95) attribute through the same COA message which may also carry other DAA service attributes.";
        }
      }
      container prepaid-profiles {
        description
          "List of the prepaid service templates.";
        list prepaid-profile {
          // NCS patched for predictable order
          ordered-by user;
          key "name";
          // NCS drop max-elements statement
          description
            "Configure a prepaid service template.";
          leaf name {
            type string;
            // NCS drop must statement
            description
              "Specifies the name of a prepaid service template.";
            ext:case-sensitivity "lower-only";
          }
          container accounting-scheme {
            description
              "Configure the accounting scheme for the current pre-paid profile. The scheme must be a configured accounting scheme.";
            leaf name {
              type string;
              // NCS drop default statement
              description
                "Specifies the name of the accounting scheme adopted by the pre-paid profile.";
            }
          }
          container authen-scheme {
            description
              "Configure the authentication scheme for the current pre-paid profile. The scheme must be a configured authentication scheme.";
            leaf name {
              type string;
              // NCS drop default statement
              description
                "Specifies the name of the authentication scheme.";
            }
          }
          container password {
            description
              "Configure the password used for the quotas application sent to the server by the prepaid services.";
            leaf password {
              type pub-type:ncs_template_password-extend;
              description
                "The password is a string ranging from 1 to 16 characters for a simple password and 1 to 128 characters for a ciphertext password.";
            }
          }
          container threshold {
            description
              "Configure the threshold that determines when the pre-paid service sends the application for quotas.";
            leaf time-value {
              type string;
              units "s";
              // NCS drop default statement
              description
                "Uses a certain period of time as the threshold.";
            }
            leaf volume-value {
              type string;
              // NCS drop default statement
              description
                "Uses a certain quantity of volume as the threshold.";
            }
            leaf volume-unit {
              type string;
              // NCS drop default statement
              description
                "Unit of the volume.";
            }
          }
          container service-volume-quota-apply {
            description
              "Configure the traffic direction to which the EDSG service quota applies.";
            leaf direction {
              type string;
              // NCS drop default statement
              description
                "The direction of volume Apply.";
            }
          }
          // NCS drop config false container 'profile-info'
        }
      }
      container edsg-accounting-interim {
        description
          "Configure a device to send a real-time accounting packet carrying the HW-Acct-Update-Address (26-159) attribute with a value of 1 for EDSG services when the user address changes. By default, when the user address changes, a device does not send a real-time accounting packet carrying the HW-Acct-Update-Address (26-159) attribute with a value of 1 for EDSG services.";
        leaf send-update-user-ip-enable {
          type string;
          // NCS drop default statement
          description
            "Enable/disable a device to send a real-time accounting packet carrying the HW-Acct-Update-Address (26-159) attribute with a value of 1 for EDSG services when the user address changes.";
        }
      }
      container edsg-coexist-attribute {
        description
          "Configure a specified attribute to take effect upon delivery in EDSG service scenarios.";
        leaf filter-id {
          type string;
          // NCS drop default statement
          description
            "Enable/disable the attribute of filter-id.";
        }
        leaf traffic-policy {
          type string;
          // NCS drop default statement
          description
            "Enable/disable the attribute of traffic-Policy.";
        }
        leaf hw-data-filter {
          type string;
          // NCS drop default statement
          description
            "Enable/disable the attribute of HW-Data-Filter.";
        }
        leaf class {
          type string;
          // NCS drop default statement
          description
            "Enable/disable the attribute of class.";
        }
      }
      container service-record {
        description
          "Configure the service activation failure or deactivation record.";
        leaf active-fail {
          type string;
          // NCS drop default statement
          description
            "Enable/disable the service activation failure record function.";
        }
        leaf deactive {
          type string;
          // NCS drop default statement
          description
            "Enable/disable the service deactivation record function.";
        }
      }
      container traffic-policy {
        description
          "Configure a DAA traffic policy globally.";
        leaf name {
          type string;
          description
            "Specifies the name of a DAA traffic policy.";
        }
      }
      container policy-cache-update-interval {
        description
          "Configure an interval at which the downloaded EDSG service policy template is updated.";
        leaf interval {
          type string;
          units "min";
          description
            "Specifies the interval at which the downloaded EDSG service policy template is updated.";
        }
      }
      container service-no-server-policy {
        description
          "Configure an activation policy for RADIUS servers when an EDSG service policy is not bound to any RADIUS server group.";
        leaf server-activation-mode {
          type ncs_template_bras-vas-online-offline-type;
          // NCS drop default statement
          description
            "Configures an activation policy for RADIUS servers when an EDSG service policy is not bound to any RADIUS server group.";
        }
      }
      container tariff-queue-mapping {
        presence "Tariff queue mapping.";
        description
          "Configure the queue scheduling can be performed on different value-added services to ensure that services with higher priorities are forwarded first. It is used to configure the mapping relationship between tariff levels of DAA and flow queues.";
        leaf-list tariff-level {
          // NCS patched for predictable order
          ordered-by user;
          ext:generated-by "system";
          ext:operation-exclude "create|delete";
          type ncs_template_bras-vas-flow-queue-type;
          // NCS drop min-elements statement
          // NCS drop max-elements statement
          description
            "Configure a packet type.";
        }
      }
      container service-policys {
        description
          "List of the value-added service policy templates.";
        list service-policy {
          // NCS patched for predictable order
          ordered-by user;
          key "name";
          // NCS drop max-elements statement
          description
            "Configure a value-added service policy template.";
          leaf name {
            type string;
            // NCS drop must statement
            description
              "Specify the name of a value-added service policy. When the node of policy-name-case-sensitive is enabled, the service policy name is case-sensitive. When the node of policy-name-case-sensitive is disabled, the service policy name cannot contain uppercase letters.";
          }
          leaf mode {
            ext:operation-exclude "update";
            type string;
            // NCS drop mandatory statement
            description
              "Indicates a service policy. This leaf cannot be modified. If you need to modify it, delete the policy and then create a new type of policy.";
          }
          container service-group {
            presence "Service-group.";
            description
              "Configure a service group for a service policy.";
            leaf group-name {
              type string;
              // NCS drop mandatory statement
              description
                "Specifies the name of a service group.";
            }
            leaf direction {
              // NCS drop when statement
              type string;
              // NCS drop default statement
              description
                "Indicates the direction for a service group.";
            }
            leaf priority {
              // NCS drop when statement
              type string;
              // NCS drop default statement
              description
                "Specifies a priority value that a service matches.";
            }
          }
          container accounting-scheme {
            // NCS drop when statement
            description
              "Configure the accounting scheme for the current service policy. The scheme must be a configured accounting scheme.";
            leaf name {
              type string;
              // NCS drop default statement
              description
                "Specifies the name of the accounting scheme adopted by the pre-paid profile.";
            }
          }
          container radius-server-group {
            // NCS drop when statement
            description
              "Configure the RADIUS server group for service policy. The server group must be a configured server group.";
            leaf name {
              type string;
              description
                "Specifies the name of the RADIUS server group.";
            }
          }
          container traffic-match {
            // NCS drop when statement
            description
              "Configure EDSG service traffic to match a user group.";
            leaf direction {
              type string;
              // NCS drop default statement
              description
                "Indicates stream direction of EDSG service traffic.";
            }
          }
          container statistic-ip-type {
            // NCS drop when statement
            description
              "Configure a statistic IP type for EDSG services. The default statistic type is IPv4 for EDSG services.";
            leaf type {
              type ncs_template_bras-vas-service-ip-type;
              // NCS drop default statement
              description
                "Statistic IP type for EDSG services.";
            }
          }
          container service-class {
            // NCS drop when statement
            description
              "Configure upstream or downstream service classes.";
            leaf inbound-class {
              type ncs_template_bras-vas-flow-queue-type;
              description
                "Specifies a service class of inbound direction.";
            }
            leaf outbound-class {
              type ncs_template_bras-vas-flow-queue-type;
              description
                "Specifies a service class of outbound direction.";
            }
          }
          container authentication-scheme {
            // NCS drop when statement
            description
              "Configure an authentication scheme for the current service policy. The scheme must be a configured authentication scheme.";
            leaf name {
              type string;
              description
                "Specifies the name of the authentication scheme.";
            }
          }
          container rate-limit {
            // NCS drop when statement
            description
              "Configure the inbound and outbound rate for the service policy template.";
            container inbound {
              presence "Create inbound rate-limit.";
              description
                "Configure the inbound rate for the service policy template.";
              uses ncs_template_rate-limit-type;
            }
            container outbound {
              presence "Create outbound rate-limit.";
              description
                "Configure the outbound rate for the service policy template.";
              uses ncs_template_rate-limit-type;
            }
          }
          container diameter-monitor-key {
            // NCS drop when statement
            description
              "Configure the Characters monitoring key values for the policy business.";
            leaf key {
              type string;
              description
                "Monitoring key values for the policy business.";
            }
          }
          // NCS drop config false container 'policy-info'
        }
      }
      container mirror-service-policy-rules {
        description
          "List of the mapping relation between service policy and option82.";
        list mirror-service-policy-rule {
          // NCS patched for predictable order
          ordered-by user;
          key "number";
          description
            "Configure the mapping relation between service policy and option82.";
          leaf number {
            type string;
            description
              "The number of the rule.";
          }
          leaf service-policy-name {
            type string;
            // NCS drop must statement
            // NCS drop must statement
            // NCS drop mandatory statement
            description
              "The name of a service policy.";
          }
          leaf option82-type {
            type string;
            // NCS drop mandatory statement
            description
              "The type of option82 attribute.";
          }
          leaf option82-value {
            type string;
            // NCS drop mandatory statement
            description
              "The information of option82.";
          }
          leaf part-match {
            type string;
            // NCS drop default statement
            description
              "Enable/disable supporting the part matching.";
          }
        }
      }
      // NCS drop config false container 'vas-user-id-states'
      // NCS drop config false container 'edsg-user-infos'
      // NCS drop config false container 'user-id-daa-states'
      // NCS drop config false container 'user-id-bod-states'
      // NCS drop config false container 'vas-edsg-user-id-informations'
      // NCS drop config false container 'edsg-time-range-state'
      // NCS drop config false container 'updated-fail-statistic'
      // NCS drop config false container 'remote-policy-caches'
      // NCS drop config false container 'vas-daa-user-id-infos'
    }
  }
  augment "/ncs:devices/ncs:template/ncs:ned-id/ncs:config/qos:qos/qos:classifier-template/qos:traffic-behaviors/qos:traffic-behavior" {
    description
      "Adds vas configuration to qos traffic-behavior model.";
    container bas {
      description
        "Configure traffic behavior.";
      container vas {
        // NCS drop must statement
        description
          "Configure vas in qos traffic-behavior model.";
        container daa-accounting {
          description
            "Configure a tariff level for DAA accounting.";
          leaf tariff-level {
            type string;
            description
              "Configures a tariff level for DAA accounting.";
          }
          leaf tariff-statistic-enable {
            type string;
            // NCS drop default statement
            description
              "Enable/disable Traffic Statistics Collection.";
          }
        }
        container service-class-edsg {
          description
            "Configure the service queue level is not used in the traffic behavior to overwrite the original queue level.";
          leaf keep-queue-level {
            type string;
            // NCS drop default statement
            description
              "Enable/disable the service class for Enhanced dynamic service gateway.";
          }
        }
        container car-for-daa {
          description
            "Configure CAR for DAA service traffic.";
          leaf enable {
            type string;
            // NCS drop default statement
            description
              "Enable/disable CAR for DAA service traffic.";
          }
        }
      }
    }
  }
  augment "/ncs:devices/ncs:device/ncs:live-status/qos:qos/qos:classifier-template/qos:traffic-behaviors/qos:traffic-behavior" {
    description
      "Adds vas configuration to qos traffic-behavior model.";
    container bas {
      tailf:ncs-device-type "netconf";
      tailf:display-when "not(../../../../../../ncs:module) or ../../../../../../ncs:module[ncs:name='huawei-bras-vas'] or (../../../../../../ncs:live-status-protocol[not(ncs:capability)]) or (../../../../../../ncs:live-status-protocol/ncs:capability/ncs:module[.='huawei-bras-vas'])";
      description
        "Configure traffic behavior.";
      container vas {
        // NCS drop must statement
        description
          "Configure vas in qos traffic-behavior model.";
        container daa-accounting {
          description
            "Configure a tariff level for DAA accounting.";
          leaf tariff-level {
            type uint8 {
              range "1..8";
            }
            description
              "Configures a tariff level for DAA accounting.";
          }
          leaf tariff-statistic-enable {
            type boolean;
            // NCS drop default statement
            description
              "Enable/disable Traffic Statistics Collection.";
          }
        }
        container service-class-edsg {
          description
            "Configure the service queue level is not used in the traffic behavior to overwrite the original queue level.";
          leaf keep-queue-level {
            type boolean;
            // NCS drop default statement
            description
              "Enable/disable the service class for Enhanced dynamic service gateway.";
          }
        }
        container car-for-daa {
          description
            "Configure CAR for DAA service traffic.";
          leaf enable {
            type boolean;
            // NCS drop default statement
            description
              "Enable/disable CAR for DAA service traffic.";
          }
        }
      }
    }
  }
  augment "/ncs:devices/ncs:device/ncs:config/qos:qos/qos:classifier-template/qos:traffic-behaviors/qos:traffic-behavior" {
    description
      "Adds vas configuration to qos traffic-behavior model.";
    container bas {
      tailf:ncs-device-type "netconf";
      tailf:display-when "not(../../../../../../ncs:module) or ../../../../../../ncs:module[ncs:name='huawei-bras-vas']";
      description
        "Configure traffic behavior.";
      container vas {
        must "not(./service-class-edsg/keep-queue-level = 'true' and (./daa-accounting/tariff-level or ./daa-accounting/tariff-statistic-enable = 'true' or ./car-for-daa/enable = 'true'))" {
          tailf:xpath-root 3;
        }
        description
          "Configure vas in qos traffic-behavior model.";
        container daa-accounting {
          description
            "Configure a tariff level for DAA accounting.";
          leaf tariff-level {
            type uint8 {
              range "1..8";
            }
            description
              "Configures a tariff level for DAA accounting.";
          }
          leaf tariff-statistic-enable {
            type boolean;
            default "false";
            description
              "Enable/disable Traffic Statistics Collection.";
          }
        }
        container service-class-edsg {
          description
            "Configure the service queue level is not used in the traffic behavior to overwrite the original queue level.";
          leaf keep-queue-level {
            type boolean;
            default "false";
            description
              "Enable/disable the service class for Enhanced dynamic service gateway.";
          }
        }
        container car-for-daa {
          description
            "Configure CAR for DAA service traffic.";
          leaf enable {
            type boolean;
            default "false";
            description
              "Enable/disable CAR for DAA service traffic.";
          }
        }
      }
    }
  }
  augment "/ncs:devices/ncs:template/ncs:ned-id/ncs:config/radius:radius/radius:radius-server-groups/radius:radius-server-group" {
    description
      "Adds vas configuration to radius group model.";
    container bras-vas {
      description
        "Configure value-added service attributes to be sent to the RADIUS server.";
      container attribute-vas {
        description
          "Configure value-added service attributes to be sent to the RADIUS server.";
        leaf agent-circuit-id {
          type string;
          // NCS drop default statement
          description
            "Enable/disable the DSL FORUM No. 1 attribute, which represents the agent circuit ID.";
        }
        leaf agent-remote-id {
          type string;
          // NCS drop default statement
          description
            "Enable/disable the DSL FORUM No. 2 attribute, which represents the agent remote circuit ID.";
        }
      }
      container policy-no-exist {
        description
          "Configure a policy for access users if the policy name carried in the HUAWEI-95 attribute delivered by the RADIUS server does not exist.";
        leaf action {
          type ncs_template_bras-vas-online-offline-type;
          // NCS drop default statement
          description
            "Configures a policy for access users if the policy name carried in the HUAWEI-95 attribute delivered by the RADIUS server does not exist.";
        }
      }
    }
  }
  augment "/ncs:devices/ncs:device/ncs:live-status/radius:radius/radius:radius-server-groups/radius:radius-server-group" {
    description
      "Adds vas configuration to radius group model.";
    container bras-vas {
      tailf:ncs-device-type "netconf";
      tailf:display-when "not(../../../../../ncs:module) or ../../../../../ncs:module[ncs:name='huawei-bras-vas'] or (../../../../../ncs:live-status-protocol[not(ncs:capability)]) or (../../../../../ncs:live-status-protocol/ncs:capability/ncs:module[.='huawei-bras-vas'])";
      description
        "Configure value-added service attributes to be sent to the RADIUS server.";
      container attribute-vas {
        description
          "Configure value-added service attributes to be sent to the RADIUS server.";
        leaf agent-circuit-id {
          type boolean;
          // NCS drop default statement
          description
            "Enable/disable the DSL FORUM No. 1 attribute, which represents the agent circuit ID.";
        }
        leaf agent-remote-id {
          type boolean;
          // NCS drop default statement
          description
            "Enable/disable the DSL FORUM No. 2 attribute, which represents the agent remote circuit ID.";
        }
      }
      container policy-no-exist {
        description
          "Configure a policy for access users if the policy name carried in the HUAWEI-95 attribute delivered by the RADIUS server does not exist.";
        leaf action {
          type live_ncs_bras-vas-online-offline-type;
          // NCS drop default statement
          description
            "Configures a policy for access users if the policy name carried in the HUAWEI-95 attribute delivered by the RADIUS server does not exist.";
        }
      }
    }
  }
  augment "/ncs:devices/ncs:device/ncs:config/radius:radius/radius:radius-server-groups/radius:radius-server-group" {
    description
      "Adds vas configuration to radius group model.";
    container bras-vas {
      tailf:ncs-device-type "netconf";
      tailf:display-when "not(../../../../../ncs:module) or ../../../../../ncs:module[ncs:name='huawei-bras-vas']";
      description
        "Configure value-added service attributes to be sent to the RADIUS server.";
      container attribute-vas {
        description
          "Configure value-added service attributes to be sent to the RADIUS server.";
        leaf agent-circuit-id {
          type boolean;
          default "false";
          description
            "Enable/disable the DSL FORUM No. 1 attribute, which represents the agent circuit ID.";
        }
        leaf agent-remote-id {
          type boolean;
          default "false";
          description
            "Enable/disable the DSL FORUM No. 2 attribute, which represents the agent remote circuit ID.";
        }
      }
      container policy-no-exist {
        description
          "Configure a policy for access users if the policy name carried in the HUAWEI-95 attribute delivered by the RADIUS server does not exist.";
        leaf action {
          type bras-vas-online-offline-type;
          default "offline";
          description
            "Configures a policy for access users if the policy name carried in the HUAWEI-95 attribute delivered by the RADIUS server does not exist.";
        }
      }
    }
  }
  augment "/ncs:devices/ncs:template/ncs:ned-id/ncs:config/aaa:aaa/aaa:domains/aaa:domain/bras-basic-access:bas" {
    description
      "Adds vas configuration to aaa domain model.";
    container vas {
      description
        "Configure vas in aaa domain model.";
      container service-rate-limit-mode {
        description
          "Configure a rate limit mode for EDSG service traffic.";
        leaf inbound {
          type ncs_template_bras-vas-rate-limit-mode;
          // NCS drop default statement
          description
            "Configuring the upstream rate limit mode.";
        }
        leaf outbound {
          type ncs_template_bras-vas-rate-limit-mode;
          // NCS drop default statement
          description
            "Configuring the downstream rate limit mode.";
        }
      }
      container edsg-traffic-mode {
        description
          "Configure EDSG service rate limiting and traffic statistics policies. By default, the rate of service traffic is separately limited and is not affected by user bandwidth. Only user traffic is counted as user traffic.";
        leaf rate-limit-and-traffic-static {
          type string;
          // NCS drop default statement
          description
            "Configures EDSG service rate limiting mode.";
        }
      }
      container billing-server-type {
        description
          "Configure the accounting server type. By default, Router considers all accounting servers supporting the dynamic policy.";
        leaf type {
          type string;
          // NCS drop default statement
          description
            "Configures the accounting server type.";
        }
      }
      container daa-coexist-qos-profile {
        description
          "Configure the QoS profile attribute to take effect when DAA services are dynamically modified.";
        leaf enable {
          type string;
          // NCS drop default statement
          description
            "Enable/disable the QoS profile attribute to take effect when DAA services are dynamically modified.";
        }
      }
      container daa-match-direction {
        description
          "Configure the upstream or downstream traffic of users that go online through an AAA domain against DAA services.";
        leaf inbound {
          type string;
          // NCS drop default statement
          description
            "Enable/disable the DAA service matching function of upstream traffic of users that go online through domain.";
        }
        leaf outbound {
          type string;
          // NCS drop default statement
          description
            "Enable/disable the DAA service matching function of downstream traffic of users that go online through domain.";
        }
      }
      container family-schedule {
        description
          "Configure EDSG services to support HQoS scheduling for home users.";
        leaf inbound {
          type string;
          // NCS drop default statement
          description
            "Enable/disable upstream traffic for home users.";
        }
        leaf outbound {
          type string;
          // NCS drop default statement
          description
            "Enable/disable downstream traffic for home users.";
        }
      }
      container traffic-match-user-group {
        description
          "Configure EDSG service traffic to match a user group.";
        leaf direction {
          type string;
          description
            "Indicates upstream or downstream EDSG service traffic.";
        }
      }
      container account-type {
        // NCS drop must statement
        description
          "Configure a value-added service accounting mode. default accounting, none accounting, and RADIUS accounting can be adopted for the value-added services. If no accounting mode is specified, the default accounting mode is adopted.";
        leaf type {
          type string;
          // NCS drop default statement
          description
            "Configures a value-added service accounting mode. default accounting, none accounting, and RADIUS accounting can be adopted for the value-added services.";
        }
        leaf radius-server-group-name {
          // NCS drop when statement
          type string;
          description
            "Specifies the name of the RADIUS server group. The server group must be a configured RADIUS server group.";
        }
      }
      container vas-policy {
        description
          "Configure the value-added service policy used by the domain.";
        leaf name {
          type string;
          // NCS drop must statement
          description
            "Specifies the name of the service policy used by the domain. The policy must be a configured service policy.";
        }
      }
    }
  }
  augment "/ncs:devices/ncs:device/ncs:live-status/aaa:aaa/aaa:domains/aaa:domain/bras-basic-access:bas" {
    description
      "Adds vas configuration to aaa domain model.";
    container vas {
      tailf:ncs-device-type "netconf";
      tailf:display-when "not(../../../../../../ncs:module) or ../../../../../../ncs:module[ncs:name='huawei-bras-vas'] or (../../../../../../ncs:live-status-protocol[not(ncs:capability)]) or (../../../../../../ncs:live-status-protocol/ncs:capability/ncs:module[.='huawei-bras-vas'])";
      description
        "Configure vas in aaa domain model.";
      container service-rate-limit-mode {
        description
          "Configure a rate limit mode for EDSG service traffic.";
        leaf inbound {
          type live_ncs_bras-vas-rate-limit-mode;
          // NCS drop default statement
          description
            "Configuring the upstream rate limit mode.";
        }
        leaf outbound {
          type live_ncs_bras-vas-rate-limit-mode;
          // NCS drop default statement
          description
            "Configuring the downstream rate limit mode.";
        }
      }
      container edsg-traffic-mode {
        description
          "Configure EDSG service rate limiting and traffic statistics policies. By default, the rate of service traffic is separately limited and is not affected by user bandwidth. Only user traffic is counted as user traffic.";
        leaf rate-limit-and-traffic-static {
          type enumeration {
            enum "default-mode" {
              value 0;
              description
                "By default, the rate of service traffic is separately limited and is not affected by user bandwidth. Only user traffic is counted as user traffic.";
            }
            enum "separate" {
              value 1;
              description
                "Performs separate rate limiting on service traffic.";
            }
            enum "together" {
              value 2;
              description
                "Performs rate limiting on service traffic and then user traffic.";
            }
          }
          // NCS drop default statement
          description
            "Configures EDSG service rate limiting mode.";
        }
      }
      container billing-server-type {
        description
          "Configure the accounting server type. By default, Router considers all accounting servers supporting the dynamic policy.";
        leaf type {
          type enumeration {
            enum "dynamic" {
              value 1;
              description
                "Specifies the dynamic policy switch mode.";
            }
            enum "normal" {
              value 2;
              description
                "Specifies the normal policy switch mode.";
            }
          }
          // NCS drop default statement
          description
            "Configures the accounting server type.";
        }
      }
      container daa-coexist-qos-profile {
        description
          "Configure the QoS profile attribute to take effect when DAA services are dynamically modified.";
        leaf enable {
          type boolean;
          // NCS drop default statement
          description
            "Enable/disable the QoS profile attribute to take effect when DAA services are dynamically modified.";
        }
      }
      container daa-match-direction {
        description
          "Configure the upstream or downstream traffic of users that go online through an AAA domain against DAA services.";
        leaf inbound {
          type boolean;
          // NCS drop default statement
          description
            "Enable/disable the DAA service matching function of upstream traffic of users that go online through domain.";
        }
        leaf outbound {
          type boolean;
          // NCS drop default statement
          description
            "Enable/disable the DAA service matching function of downstream traffic of users that go online through domain.";
        }
      }
      container family-schedule {
        description
          "Configure EDSG services to support HQoS scheduling for home users.";
        leaf inbound {
          type boolean;
          // NCS drop default statement
          description
            "Enable/disable upstream traffic for home users.";
        }
        leaf outbound {
          type boolean;
          // NCS drop default statement
          description
            "Enable/disable downstream traffic for home users.";
        }
      }
      container traffic-match-user-group {
        description
          "Configure EDSG service traffic to match a user group.";
        leaf direction {
          type enumeration {
            enum "both" {
              value 0;
              description
                "Indicates both upstream and downstream EDSG service traffic.";
            }
            enum "inbound" {
              value 1;
              description
                "Indicates upstream EDSG service traffic.";
            }
            enum "outbound" {
              value 2;
              description
                "Indicates downstream EDSG service traffic.";
            }
          }
          description
            "Indicates upstream or downstream EDSG service traffic.";
        }
      }
      container account-type {
        // NCS drop must statement
        description
          "Configure a value-added service accounting mode. default accounting, none accounting, and RADIUS accounting can be adopted for the value-added services. If no accounting mode is specified, the default accounting mode is adopted.";
        leaf type {
          type enumeration {
            enum "default" {
              value 1;
              description
                "Default accounting.";
            }
            enum "none" {
              value 2;
              description
                "None accounting.";
            }
            enum "radius" {
              value 3;
              description
                "RADIUS accounting.";
            }
          }
          // NCS drop default statement
          description
            "Configures a value-added service accounting mode. default accounting, none accounting, and RADIUS accounting can be adopted for the value-added services.";
        }
        leaf radius-server-group-name {
          // NCS drop when statement
          type leafref {
            path "/ncs:devices/ncs:device/ncs:live-status/radius:radius/radius:radius-server-groups/radius:radius-server-group/radius:name" {
              tailf:xpath-root 3;
            }
          }
          description
            "Specifies the name of the RADIUS server group. The server group must be a configured RADIUS server group.";
        }
      }
      container vas-policy {
        description
          "Configure the value-added service policy used by the domain.";
        leaf name {
          type leafref {
            path "/ncs:devices/ncs:device/ncs:live-status/bras-vas:bras-vas/bras-vas:vas-policys/bras-vas:vas-policy/bras-vas:name" {
              tailf:xpath-root 3;
            }
          }
          // NCS drop must statement
          description
            "Specifies the name of the service policy used by the domain. The policy must be a configured service policy.";
        }
      }
    }
  }
  augment "/ncs:devices/ncs:device/ncs:config/aaa:aaa/aaa:domains/aaa:domain/bras-basic-access:bas" {
    description
      "Adds vas configuration to aaa domain model.";
    container vas {
      tailf:ncs-device-type "netconf";
      tailf:display-when "not(../../../../../../ncs:module) or ../../../../../../ncs:module[ncs:name='huawei-bras-vas']";
      description
        "Configure vas in aaa domain model.";
      container service-rate-limit-mode {
        description
          "Configure a rate limit mode for EDSG service traffic.";
        leaf inbound {
          type bras-vas-rate-limit-mode;
          default "car";
          description
            "Configuring the upstream rate limit mode.";
        }
        leaf outbound {
          type bras-vas-rate-limit-mode;
          default "car";
          description
            "Configuring the downstream rate limit mode.";
        }
      }
      container edsg-traffic-mode {
        description
          "Configure EDSG service rate limiting and traffic statistics policies. By default, the rate of service traffic is separately limited and is not affected by user bandwidth. Only user traffic is counted as user traffic.";
        leaf rate-limit-and-traffic-static {
          type enumeration {
            enum "default-mode" {
              value 0;
              description
                "By default, the rate of service traffic is separately limited and is not affected by user bandwidth. Only user traffic is counted as user traffic.";
            }
            enum "separate" {
              value 1;
              description
                "Performs separate rate limiting on service traffic.";
            }
            enum "together" {
              value 2;
              description
                "Performs rate limiting on service traffic and then user traffic.";
            }
          }
          default "default-mode";
          description
            "Configures EDSG service rate limiting mode.";
        }
      }
      container billing-server-type {
        description
          "Configure the accounting server type. By default, Router considers all accounting servers supporting the dynamic policy.";
        leaf type {
          type enumeration {
            enum "dynamic" {
              value 1;
              description
                "Specifies the dynamic policy switch mode.";
            }
            enum "normal" {
              value 2;
              description
                "Specifies the normal policy switch mode.";
            }
          }
          default "dynamic";
          description
            "Configures the accounting server type.";
        }
      }
      container daa-coexist-qos-profile {
        description
          "Configure the QoS profile attribute to take effect when DAA services are dynamically modified.";
        leaf enable {
          type boolean;
          default "false";
          description
            "Enable/disable the QoS profile attribute to take effect when DAA services are dynamically modified.";
        }
      }
      container daa-match-direction {
        description
          "Configure the upstream or downstream traffic of users that go online through an AAA domain against DAA services.";
        leaf inbound {
          type boolean;
          default "false";
          description
            "Enable/disable the DAA service matching function of upstream traffic of users that go online through domain.";
        }
        leaf outbound {
          type boolean;
          default "false";
          description
            "Enable/disable the DAA service matching function of downstream traffic of users that go online through domain.";
        }
      }
      container family-schedule {
        description
          "Configure EDSG services to support HQoS scheduling for home users.";
        leaf inbound {
          type boolean;
          default "false";
          description
            "Enable/disable upstream traffic for home users.";
        }
        leaf outbound {
          type boolean;
          default "false";
          description
            "Enable/disable downstream traffic for home users.";
        }
      }
      container traffic-match-user-group {
        description
          "Configure EDSG service traffic to match a user group.";
        leaf direction {
          type enumeration {
            enum "both" {
              value 0;
              description
                "Indicates both upstream and downstream EDSG service traffic.";
            }
            enum "inbound" {
              value 1;
              description
                "Indicates upstream EDSG service traffic.";
            }
            enum "outbound" {
              value 2;
              description
                "Indicates downstream EDSG service traffic.";
            }
          }
          description
            "Indicates upstream or downstream EDSG service traffic.";
        }
      }
      container account-type {
        must "../account-type/radius-server-group-name or not(../account-type/type='radius')" {
          tailf:xpath-root 3;
        }
        description
          "Configure a value-added service accounting mode. default accounting, none accounting, and RADIUS accounting can be adopted for the value-added services. If no accounting mode is specified, the default accounting mode is adopted.";
        leaf type {
          type enumeration {
            enum "default" {
              value 1;
              description
                "Default accounting.";
            }
            enum "none" {
              value 2;
              description
                "None accounting.";
            }
            enum "radius" {
              value 3;
              description
                "RADIUS accounting.";
            }
          }
          default "default";
          description
            "Configures a value-added service accounting mode. default accounting, none accounting, and RADIUS accounting can be adopted for the value-added services.";
        }
        leaf radius-server-group-name {
          when "../type='radius'" {
            tailf:xpath-root 3;
          }
          type leafref {
            path "/ncs:devices/ncs:device/ncs:config/radius:radius/radius:radius-server-groups/radius:radius-server-group/radius:name" {
              tailf:xpath-root 3;
            }
          }
          description
            "Specifies the name of the RADIUS server group. The server group must be a configured RADIUS server group.";
        }
      }
      container vas-policy {
        description
          "Configure the value-added service policy used by the domain.";
        leaf name {
          type leafref {
            path "/ncs:devices/ncs:device/ncs:config/bras-vas:bras-vas/bras-vas:vas-policys/bras-vas:vas-policy/bras-vas:name" {
              tailf:xpath-root 3;
            }
          }
          must "/bras-vas:bras-vas/bras-vas:vas-policys/bras-vas:vas-policy[bras-vas:name=current()]/bras-vas:type='daa'" {
            tailf:xpath-root 3;
          }
          description
            "Specifies the name of the service policy used by the domain. The policy must be a configured service policy.";
        }
      }
    }
  }
  augment "/ncs:devices/ncs:template/ncs:ned-id/ncs:config/devm:devm/devm:lpu-boards/devm:lpu-board/bras-basic-access:bras" {
    description
      "Bras devm configuration.";
    container vas {
      description
        "Configure vas devm.";
      container statistic-frequency {
        description
          "Configure a board to read EDSG service traffic statistics at a configured rate.";
        leaf flow-read-speed {
          type string;
          // NCS drop default statement
          description
            "Sets the number of EDSG services for which traffic statistics are collected every 200 ms.";
        }
      }
    }
  }
  augment "/ncs:devices/ncs:device/ncs:live-status/devm:devm/devm:lpu-boards/devm:lpu-board/bras-basic-access:bras" {
    description
      "Bras devm configuration.";
    container vas {
      tailf:ncs-device-type "netconf";
      tailf:display-when "not(../../../../../../ncs:module) or ../../../../../../ncs:module[ncs:name='huawei-bras-vas'] or (../../../../../../ncs:live-status-protocol[not(ncs:capability)]) or (../../../../../../ncs:live-status-protocol/ncs:capability/ncs:module[.='huawei-bras-vas'])";
      description
        "Configure vas devm.";
      container statistic-frequency {
        description
          "Configure a board to read EDSG service traffic statistics at a configured rate.";
        leaf flow-read-speed {
          type uint32 {
            range "52..500";
          }
          // NCS drop default statement
          description
            "Sets the number of EDSG services for which traffic statistics are collected every 200 ms.";
        }
      }
    }
  }
  augment "/ncs:devices/ncs:device/ncs:config/devm:devm/devm:lpu-boards/devm:lpu-board/bras-basic-access:bras" {
    description
      "Bras devm configuration.";
    container vas {
      tailf:ncs-device-type "netconf";
      tailf:display-when "not(../../../../../../ncs:module) or ../../../../../../ncs:module[ncs:name='huawei-bras-vas']";
      description
        "Configure vas devm.";
      container statistic-frequency {
        description
          "Configure a board to read EDSG service traffic statistics at a configured rate.";
        leaf flow-read-speed {
          type uint32 {
            range "52..500";
          }
          default "52";
          description
            "Sets the number of EDSG services for which traffic statistics are collected every 200 ms.";
        }
      }
    }
  }
  augment "/ncs:devices/ncs:template/ncs:ned-id/ncs:config/devm:devm/devm:mpu-boards/devm:mpu-board/bras-basic-access:bras" {
    description
      "Bras devm configuration.";
    container vas {
      description
        "Configure vas devm.";
      container statistic-frequency {
        description
          "Configure a board to read EDSG service traffic statistics at a configured rate.";
        leaf flow-read-speed {
          type string;
          // NCS drop default statement
          description
            "Sets the number of EDSG services for which traffic statistics are collected every 200 ms.";
        }
      }
    }
  }
  augment "/ncs:devices/ncs:device/ncs:live-status/devm:devm/devm:mpu-boards/devm:mpu-board/bras-basic-access:bras" {
    description
      "Bras devm configuration.";
    container vas {
      tailf:ncs-device-type "netconf";
      tailf:display-when "not(../../../../../../ncs:module) or ../../../../../../ncs:module[ncs:name='huawei-bras-vas'] or (../../../../../../ncs:live-status-protocol[not(ncs:capability)]) or (../../../../../../ncs:live-status-protocol/ncs:capability/ncs:module[.='huawei-bras-vas'])";
      description
        "Configure vas devm.";
      container statistic-frequency {
        description
          "Configure a board to read EDSG service traffic statistics at a configured rate.";
        leaf flow-read-speed {
          type uint32 {
            range "52..500";
          }
          // NCS drop default statement
          description
            "Sets the number of EDSG services for which traffic statistics are collected every 200 ms.";
        }
      }
    }
  }
  augment "/ncs:devices/ncs:device/ncs:config/devm:devm/devm:mpu-boards/devm:mpu-board/bras-basic-access:bras" {
    description
      "Bras devm configuration.";
    container vas {
      tailf:ncs-device-type "netconf";
      tailf:display-when "not(../../../../../../ncs:module) or ../../../../../../ncs:module[ncs:name='huawei-bras-vas']";
      description
        "Configure vas devm.";
      container statistic-frequency {
        description
          "Configure a board to read EDSG service traffic statistics at a configured rate.";
        leaf flow-read-speed {
          type uint32 {
            range "52..500";
          }
          default "52";
          description
            "Sets the number of EDSG services for which traffic statistics are collected every 200 ms.";
        }
      }
    }
  }
}
