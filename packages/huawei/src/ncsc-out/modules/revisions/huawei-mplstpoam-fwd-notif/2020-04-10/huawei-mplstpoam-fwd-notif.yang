module huawei-mplstpoam-fwd-notif {
  // Generated by yanger -t ncs
  tailf:mount-id "huawei-nc-1.0:huawei-nc-1.0";
  tailf:ncs-device-type "netconf";

  yang-version 1;
  namespace "urn:huawei:yang:huawei-mplstpoam-fwd-notif";
  prefix mplstpoam-fwd-notif;

  import ietf-inet-types {
    prefix inet;
  }
  import huawei-l2vpn {
    prefix l2vpn;
  }
  import huawei-extension {
    prefix ext;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Notification of MPLS-TP OAM.";

  revision 2020-04-10 {
    description
      "Initial revision.";
    reference "Huawei private.";
  }
  ext:task-name "tpoam";

  augment "/ncs:devices/ncs:device/ncs:notifications/ncs:received-notifications/ncs:notification/ncs:data" {
    container tpoam-tunnel-not-support-resume {
      presence "";
      config false;
      description
        "The alarm that MPLS-TP OAM for PW does not support the current public tunnel is resumed.";
      leaf vc-id {
        type uint32;
        description
          "Identifier of the layer 2 virtual circuit.";
      }
      leaf vc-type {
        type l2vpn:ncs_rpc_notif_encapsulation-type;
        description
          "Encapsulation type of a L2VPN instance.";
      }
      leaf peer-addr {
        type inet:ipv4-address-no-zone;
        description
          "Peer IP address.";
      }
    }
  }
  augment "/ncs:devices/ncs:device/ncs:notifications/ncs:received-notifications/ncs:notification/ncs:data" {
    container tpoam-tunnel-not-support {
      presence "";
      config false;
      description
        "MPLS-TP OAM for PW does not support the current public tunnel.";
      leaf vc-id {
        type uint32;
        description
          "Identifier of the layer 2 virtual circuit.";
      }
      leaf vc-type {
        type l2vpn:ncs_rpc_notif_encapsulation-type;
        description
          "Encapsulation type of a L2VPN instance.";
      }
      leaf peer-addr {
        type inet:ipv4-address-no-zone;
        description
          "Peer IP address.";
      }
    }
  }
  augment "/ncs:devices/ncs:device/ncs:netconf-notifications/ncs:received-notifications/ncs:notification/ncs:data" {
    container tpoam-tunnel-not-support-resume {
      presence "";
      config false;
      description
        "The alarm that MPLS-TP OAM for PW does not support the current public tunnel is resumed.";
      leaf vc-id {
        type uint32;
        description
          "Identifier of the layer 2 virtual circuit.";
      }
      leaf vc-type {
        type l2vpn:ncs_rpc_notif_encapsulation-type;
        description
          "Encapsulation type of a L2VPN instance.";
      }
      leaf peer-addr {
        type inet:ipv4-address-no-zone;
        description
          "Peer IP address.";
      }
    }
  }
  augment "/ncs:devices/ncs:device/ncs:netconf-notifications/ncs:received-notifications/ncs:notification/ncs:data" {
    container tpoam-tunnel-not-support {
      presence "";
      config false;
      description
        "MPLS-TP OAM for PW does not support the current public tunnel.";
      leaf vc-id {
        type uint32;
        description
          "Identifier of the layer 2 virtual circuit.";
      }
      leaf vc-type {
        type l2vpn:ncs_rpc_notif_encapsulation-type;
        description
          "Encapsulation type of a L2VPN instance.";
      }
      leaf peer-addr {
        type inet:ipv4-address-no-zone;
        description
          "Peer IP address.";
      }
    }
  }
}
