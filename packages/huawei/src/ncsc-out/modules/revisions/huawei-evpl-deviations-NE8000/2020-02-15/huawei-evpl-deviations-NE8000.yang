module huawei-evpl-deviations-NE8000 {
  // Generated by yanger -t ncs
  tailf:mount-id "huawei-nc-1.0:huawei-nc-1.0";
  tailf:ncs-device-type "netconf";

  yang-version 1;
  namespace "urn:huawei:yang:huawei-evpl-deviations-NE8000";
  prefix evpl-devs-NE8000;

  import huawei-evpl {
    prefix evpl;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Management of EVPL.";

  revision 2020-02-15 {
    description
      "Init revision.";
    reference "Huawei private.";
  }

  deviation "/ncs:devices/ncs:template/ncs:ned-id/ncs:config/evpl:evpl/evpl:instances/evpl:instance/evpl:evpl-statistics" {
    deviate not-supported;
  }
  deviation "/ncs:devices/ncs:device/ncs:live-status/evpl:evpl/evpl:instances/evpl:instance/evpl:evpl-statistics" {
    deviate not-supported;
  }
  deviation "/ncs:devices/ncs:device/ncs:config/evpl:evpl/evpl:instances/evpl:instance/evpl:evpl-statistics" {
    deviate not-supported;
  }
}
