module huawei-vty-deviations-NE8000 {
  // Generated by yanger -t ncs
  tailf:mount-id "huawei-nc-1.0:huawei-nc-1.0";
  tailf:ncs-device-type "netconf";

  namespace "urn:huawei:yang:huawei-vty-deviations-NE8000";
  prefix vty-devs-NE8000;

  import huawei-vty {
    prefix vty;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "VTY.";

  revision 2019-05-01 {
    description
      "Init revision.";
    reference "Huawei private.";
  }

  typedef ncs_template_vty-authmode-type-deviations {
    type string;
    description
      "Vty and tty authentication mode type.";
  }

  typedef ncs_rpc_notif_vty-authmode-type-deviations {
    type enumeration {
      enum "password" {
        value 2;
        description
          "VTY authentication mode password.";
      }
      enum "aaa" {
        value 3;
        description
          "VTY authentication mode aaa.";
      }
      enum "init" {
        value 4;
        description
          "Undo authentication mode.";
      }
    }
    description
      "Vty and tty authentication mode type.";
  }

  typedef live_ncs_vty-authmode-type-deviations {
    type enumeration {
      enum "password" {
        value 2;
        description
          "VTY authentication mode password.";
      }
      enum "aaa" {
        value 3;
        description
          "VTY authentication mode aaa.";
      }
      enum "init" {
        value 4;
        description
          "Undo authentication mode.";
      }
    }
    description
      "Vty and tty authentication mode type.";
  }

  typedef vty-authmode-type-deviations {
    type enumeration {
      enum "password" {
        value 2;
        description
          "VTY authentication mode password.";
      }
      enum "aaa" {
        value 3;
        description
          "VTY authentication mode aaa.";
      }
      enum "init" {
        value 4;
        description
          "Undo authentication mode.";
      }
    }
    description
      "Vty and tty authentication mode type.";
  }

  deviation "/ncs:devices/ncs:template/ncs:ned-id/ncs:config/vty:vty/vty:lines/vty:line/vty:auth-mode" {
    deviate replace {
      type vty-devs-NE8000:ncs_template_vty-authmode-type-deviations;
    }
  }
  deviation "/ncs:devices/ncs:device/ncs:live-status/vty:vty/vty:lines/vty:line/vty:auth-mode" {
    deviate replace {
      type vty-devs-NE8000:live_ncs_vty-authmode-type-deviations;
    }
  }
  deviation "/ncs:devices/ncs:device/ncs:config/vty:vty/vty:lines/vty:line/vty:auth-mode" {
    deviate replace {
      type vty-devs-NE8000:vty-authmode-type-deviations;
    }
  }
}
