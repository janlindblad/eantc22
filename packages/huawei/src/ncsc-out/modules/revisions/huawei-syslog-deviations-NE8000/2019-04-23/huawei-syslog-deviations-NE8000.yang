module huawei-syslog-deviations-NE8000 {
  // Generated by yanger -t ncs
  tailf:mount-id "huawei-nc-1.0:huawei-nc-1.0";
  tailf:ncs-device-type "netconf";

  namespace "urn:huawei:yang:huawei-syslog-deviations-NE8000";
  prefix syslog-devs-NE8000;

  import huawei-syslog {
    prefix syslog;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Deviation of syslog module.";

  revision 2019-04-23 {
    description
      "Init revision.";
    reference "Huawei private.";
  }

  typedef ncs_template_logfile-type-deviations {
    type string;
    description
      "The type of log.";
  }

  typedef ncs_rpc_notif_logfile-type-deviations {
    type enumeration {
      enum "log" {
        value 1;
        description
          "Log logfile.";
      }
      enum "security" {
        value 3;
        description
          "Security logfile.";
      }
      enum "debug" {
        value 6;
        description
          "Debug logfile.";
      }
    }
    description
      "The type of log.";
  }

  typedef live_ncs_logfile-type-deviations {
    type enumeration {
      enum "log" {
        value 1;
        description
          "Log logfile.";
      }
      enum "security" {
        value 3;
        description
          "Security logfile.";
      }
      enum "debug" {
        value 6;
        description
          "Debug logfile.";
      }
    }
    description
      "The type of log.";
  }

  typedef logfile-type-deviations {
    type enumeration {
      enum "log" {
        value 1;
        description
          "Log logfile.";
      }
      enum "security" {
        value 3;
        description
          "Security logfile.";
      }
      enum "debug" {
        value 6;
        description
          "Debug logfile.";
      }
    }
    description
      "The type of log.";
  }

  deviation "/ncs:devices/ncs:template/ncs:ned-id/ncs:config/syslog:syslog/syslog:domain-servers/syslog:domain-server/syslog:is-brief-format" {
    deviate not-supported;
  }
  deviation "/ncs:devices/ncs:device/ncs:live-status/syslog:syslog/syslog:domain-servers/syslog:domain-server/syslog:is-brief-format" {
    deviate not-supported;
  }
  deviation "/ncs:devices/ncs:device/ncs:config/syslog:syslog/syslog:domain-servers/syslog:domain-server/syslog:is-brief-format" {
    deviate not-supported;
  }
  deviation "/ncs:devices/ncs:template/ncs:ned-id/ncs:config/syslog:syslog/syslog:servers/syslog:server/syslog:host-name" {
    deviate not-supported;
  }
  deviation "/ncs:devices/ncs:device/ncs:live-status/syslog:syslog/syslog:servers/syslog:server/syslog:host-name" {
    deviate not-supported;
  }
  deviation "/ncs:devices/ncs:device/ncs:config/syslog:syslog/syslog:servers/syslog:server/syslog:host-name" {
    deviate not-supported;
  }
  deviation "/ncs:devices/ncs:template/ncs:ned-id/ncs:config/syslog:syslog/syslog:servers/syslog:server/syslog:is-activated" {
    deviate not-supported;
  }
  deviation "/ncs:devices/ncs:device/ncs:live-status/syslog:syslog/syslog:servers/syslog:server/syslog:is-activated" {
    deviate not-supported;
  }
  deviation "/ncs:devices/ncs:device/ncs:config/syslog:syslog/syslog:servers/syslog:server/syslog:is-activated" {
    deviate not-supported;
  }
  deviation "/ncs:devices/ncs:template/ncs:ned-id/ncs:config/syslog:syslog/syslog:servers/syslog:server/syslog:facility-mask" {
    deviate not-supported;
  }
  deviation "/ncs:devices/ncs:device/ncs:live-status/syslog:syslog/syslog:servers/syslog:server/syslog:facility-mask" {
    deviate not-supported;
  }
  deviation "/ncs:devices/ncs:device/ncs:config/syslog:syslog/syslog:servers/syslog:server/syslog:facility-mask" {
    deviate not-supported;
  }
  deviation "/ncs:devices/ncs:template/ncs:ned-id/ncs:config/syslog:syslog/syslog:servers/syslog:server/syslog:severity-mask" {
    deviate not-supported;
  }
  deviation "/ncs:devices/ncs:device/ncs:live-status/syslog:syslog/syslog:servers/syslog:server/syslog:severity-mask" {
    deviate not-supported;
  }
  deviation "/ncs:devices/ncs:device/ncs:config/syslog:syslog/syslog:servers/syslog:server/syslog:severity-mask" {
    deviate not-supported;
  }
  deviation "/ncs:devices/ncs:template/ncs:ned-id/ncs:config/syslog:syslog/syslog:servers/syslog:server/syslog:is-brief-format" {
    deviate not-supported;
  }
  deviation "/ncs:devices/ncs:device/ncs:live-status/syslog:syslog/syslog:servers/syslog:server/syslog:is-brief-format" {
    deviate not-supported;
  }
  deviation "/ncs:devices/ncs:device/ncs:config/syslog:syslog/syslog:servers/syslog:server/syslog:is-brief-format" {
    deviate not-supported;
  }
  deviation "/ncs:devices/ncs:template/ncs:ned-id/ncs:config/syslog:syslog/syslog:global-parameter/syslog:character-set" {
    deviate not-supported;
  }
  deviation "/ncs:devices/ncs:device/ncs:live-status/syslog:syslog/syslog:global-parameter/syslog:character-set" {
    deviate not-supported;
  }
  deviation "/ncs:devices/ncs:device/ncs:config/syslog:syslog/syslog:global-parameter/syslog:character-set" {
    deviate not-supported;
  }
  deviation "/ncs:devices/ncs:template/ncs:ned-id/ncs:config/syslog:syslog/syslog:logfiles/syslog:logfile/syslog:logfile-type" {
    deviate replace {
      type syslog-devs-NE8000:ncs_template_logfile-type-deviations;
    }
  }
  deviation "/ncs:devices/ncs:device/ncs:live-status/syslog:syslog/syslog:logfiles/syslog:logfile/syslog:logfile-type" {
    deviate replace {
      type syslog-devs-NE8000:live_ncs_logfile-type-deviations;
    }
  }
  deviation "/ncs:devices/ncs:device/ncs:config/syslog:syslog/syslog:logfiles/syslog:logfile/syslog:logfile-type" {
    deviate replace {
      type syslog-devs-NE8000:logfile-type-deviations;
    }
  }
}
