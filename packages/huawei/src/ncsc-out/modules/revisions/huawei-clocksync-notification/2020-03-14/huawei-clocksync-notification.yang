module huawei-clocksync-notification {
  // Generated by yanger -t ncs
  tailf:mount-id "huawei-nc-1.0:huawei-nc-1.0";
  tailf:ncs-device-type "netconf";

  yang-version 1;
  namespace "urn:huawei:yang:huawei-clocksync-notification";
  prefix clocksync-notification;

  import ietf-inet-types {
    prefix inet;
  }
  import huawei-extension {
    prefix ext;
  }
  import huawei-ifm {
    prefix ifm;
  }
  import huawei-clocksync-1588v2 {
    prefix clocksync-1588v2;
  }
  import huawei-clocksync-phy {
    prefix clocksync-phy;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Notification of clocksync-notification.";

  revision 2020-03-14 {
    description
      "Modify the node description.";
    reference "Huawei private.";
  }
  revision 2020-03-04 {
    description
      "Modify the node description and add gnss-model-type.";
    reference "Huawei private.";
  }
  revision 2020-01-16 {
    description
      "Initial revision.";
    reference "Huawei private.";
  }
  ext:task-name "clksync";

  typedef ncs_template_clock-lock-state {
    type string;
    description
      "Clock lock state.";
  }

  typedef ncs_template_cluster-sync-type {
    type string;
    description
      "Inter-chassis synchronization type.";
  }

  typedef ncs_template_cluster-topo-type {
    type string;
    description
      "Inter-chassis synchronization topo type.";
  }

  typedef ncs_template_cluster-link-type {
    type string;
    description
      "Inter-chassis synchronization link type.";
  }

  typedef ncs_template_cluster-sync-topo-state {
    type string;
    description
      "Inter-chassis synchronization topo status.";
  }

  typedef ncs_template_clock-pll-id {
    type string;
    description
      "The id of pll.";
  }

  typedef ncs_template_clock-lock-mode {
    type string;
    description
      "Lock mode of system clock.";
  }

  typedef ncs_template_clock-src-type {
    type string;
    description
      "Index of the clock source type.";
  }

  typedef ncs_template_clock-src-state {
    type string;
    description
      "The state of the current clock source.";
  }

  typedef ncs_template_fre-check-result {
    type string;
    description
      "Result of the check of frequency.";
  }

  typedef ncs_template_sync-state {
    type string;
    description
      "State of synchoronization.";
  }

  typedef ncs_template_time-port-state {
    type string;
    description
      "Port status of the external Time.";
  }

  typedef ncs_template_ext-time-port-type {
    type string;
    description
      "Port type of the external Time.";
  }

  typedef ncs_template_ptp-packet-type {
    type string;
    description
      "The packet type.";
  }

  typedef ncs_template_clock-sync-state {
    type string;
    description
      "Indicate that the status of the equipment.";
  }

  typedef ncs_template_clock-ssm-level {
    type string;
    description
      "SSM level type.";
  }

  typedef ncs_template_ptpa-ptsf-type {
    type string;
    description
      "The PTSF type of PTP adaptive clock synchronization.";
  }

  typedef ncs_template_ptpa-ptsf-state {
    type string;
    description
      "The PTSF state of PTP adaptive clock synchronization.";
  }

  typedef ncs_template_ptp-port-status {
    type string;
    description
      "State of ptp port.";
  }

  typedef ncs_template_ptpa-client-state {
    type string;
    description
      "Indicate the client status.";
  }

  typedef ncs_template_ptpa-nego-state {
    type string;
    description
      "Indicates the negotiation status of the client with server.";
  }

  typedef ncs_template_ptpa-nego-fail-reason {
    type string;
    description
      "Indicates causes of the negotiation failure.";
  }

  typedef ncs_template_ptpa-server-id {
    type string;
    description
      "Indicates the server ID.";
  }

  typedef ncs_template_ptpa-sync-server-src {
    type string;
    description
      "Clock source that the client has traced.";
  }

  typedef ncs_template_gnss-model-type {
    type string;
    description
      "Type of gnss model.";
  }

  typedef ncs_rpc_notif_clock-lock-state {
    type enumeration {
      enum "unlock" {
        value 0;
        description
          "Clock not in locked state.";
      }
      enum "lock" {
        value 1;
        description
          "Clock in locked state.";
      }
    }
    description
      "Clock lock state.";
  }

  typedef ncs_rpc_notif_cluster-sync-type {
    type enumeration {
      enum "frequency" {
        value 1;
        description
          "Inter-chassis synchronization type is frequency.";
      }
      enum "time" {
        value 2;
        description
          "Inter-chassis synchronization type is time.";
      }
    }
    description
      "Inter-chassis synchronization type.";
  }

  typedef ncs_rpc_notif_cluster-topo-type {
    type enumeration {
      enum "inlink" {
        value 1;
        description
          "Synchronization topo type is interlink.";
      }
      enum "extinject" {
        value 2;
        description
          "Synchronization topo type is externInject.";
      }
    }
    description
      "Inter-chassis synchronization topo type.";
  }

  typedef ncs_rpc_notif_cluster-link-type {
    type enumeration {
      enum "bits" {
        value 1;
        description
          "Synchronization link type is bits.";
      }
      enum "port" {
        value 2;
        description
          "Synchronization link type is port.";
      }
    }
    description
      "Inter-chassis synchronization link type.";
  }

  typedef ncs_rpc_notif_cluster-sync-topo-state {
    type enumeration {
      enum "fail" {
        value 1;
        description
          "Topo status is fail.";
      }
      enum "success" {
        value 2;
        description
          "Topo status is success.";
      }
    }
    description
      "Inter-chassis synchronization topo status.";
  }

  typedef ncs_rpc_notif_clock-pll-id {
    type enumeration {
      enum "system" {
        value 1;
        description
          "Pll id is system.";
      }
      enum "sync2m1" {
        value 2;
        description
          "Pll id is sync2M1.";
      }
      enum "sync2m2" {
        value 3;
        description
          "Pll id is sync2M2.";
      }
    }
    description
      "The id of pll.";
  }

  typedef ncs_rpc_notif_clock-lock-mode {
    type enumeration {
      enum "freerun" {
        value 0;
        description
          "Lock mode is freerun.";
      }
      enum "fastlock" {
        value 1;
        description
          "Lock mode is fastlock.";
      }
      enum "lock" {
        value 2;
        description
          "Lock mode is lock.";
      }
      enum "hold" {
        value 3;
        description
          "Lock mode is hold.";
      }
    }
    description
      "Lock mode of system clock.";
  }

  typedef ncs_rpc_notif_clock-src-type {
    type enumeration {
      enum "bits" {
        value 1;
        description
          "Clock source type is bits.";
      }
      enum "ptp" {
        value 2;
        description
          "Clock source type is ptp.";
      }
      enum "interface" {
        value 3;
        description
          "Clock source type is interface.";
      }
      enum "cesacr" {
        value 4;
        description
          "Clock source type is cesacr.";
      }
    }
    description
      "Index of the clock source type.";
  }

  typedef ncs_rpc_notif_clock-src-state {
    type enumeration {
      enum "initial" {
        value 0;
        description
          "Clock source state is initial.";
      }
      enum "normal" {
        value 1;
        description
          "Clock source state is normal.";
      }
      enum "abnormal" {
        value 2;
        description
          "Clock source state is abnormal.";
      }
      enum "wtr" {
        value 3;
        description
          "Clock source state is wtr.";
      }
      enum "holdoff" {
        value 4;
        description
          "Clock source state is holdoff.";
      }
    }
    description
      "The state of the current clock source.";
  }

  typedef ncs_rpc_notif_fre-check-result {
    type enumeration {
      enum "abnormal" {
        value 0;
        description
          "Frequency check is abnormal.";
      }
      enum "normal" {
        value 1;
        description
          "Frequency check is normal.";
      }
    }
    description
      "Result of the check of frequency.";
  }

  typedef ncs_rpc_notif_sync-state {
    type enumeration {
      enum "normal" {
        value 0;
        description
          "The state is normal.";
      }
      enum "abnormal" {
        value 1;
        description
          "The state is abnormal.";
      }
    }
    description
      "State of synchoronization.";
  }

  typedef ncs_rpc_notif_time-port-state {
    type enumeration {
      enum "normal" {
        value 0;
        description
          "Port state is normal.";
      }
      enum "portdown" {
        value 1;
        description
          "Port state is portdown.";
      }
    }
    description
      "Port status of the external Time.";
  }

  typedef ncs_rpc_notif_ext-time-port-type {
    type enumeration {
      enum "bits0" {
        value 0;
        description
          "The external time port type is bits0.";
      }
      enum "bits1" {
        value 1;
        description
          "The external time port type is bits1.";
      }
      enum "bits2" {
        value 2;
        description
          "The external time port type is bits2.";
      }
      enum "bits1slot4" {
        value 1025;
        description
          "The external time port type is bits1slot4.";
      }
      enum "bits1slot5" {
        value 1281;
        description
          "The external time port type is bits1slot5.";
      }
      enum "bits1slot6" {
        value 1537;
        description
          "The external time port type is bits1slot6.";
      }
      enum "bits1slot7" {
        value 1793;
        description
          "The external time port type is bits1slot7.";
      }
      enum "bits1slot8" {
        value 2049;
        description
          "The external time port type is bits1slot8.";
      }
      enum "bits1slot9" {
        value 2305;
        description
          "The external time port type is bits1slot9.";
      }
      enum "bits1slot10" {
        value 2561;
        description
          "The external time port type is bits1slot10.";
      }
      enum "bits1slot11" {
        value 2817;
        description
          "The external time port type is bits1slot11.";
      }
      enum "bits1slot12" {
        value 3073;
        description
          "The external time port type is bits1slot12.";
      }
      enum "bits1slot15" {
        value 3841;
        description
          "The external time port type is bits1slot15.";
      }
      enum "bits1slot16" {
        value 4097;
        description
          "The external time port type is bits1slot16.";
      }
      enum "bits1slot17" {
        value 4353;
        description
          "The external time port type is bits1slot17.";
      }
      enum "bits1slot18" {
        value 4609;
        description
          "The external time port type is bits1slot18.";
      }
      enum "bits1slot19" {
        value 4865;
        description
          "The external time port type is bits1slot19.";
      }
      enum "bits1slot20" {
        value 5121;
        description
          "The external time port type is bits1slot20.";
      }
      enum "bits1slot21" {
        value 5377;
        description
          "The external time port type is bits1slot21.";
      }
      enum "bits1slot22" {
        value 5633;
        description
          "The external time port type is bits1slot22.";
      }
    }
    description
      "Port type of the external Time.";
  }

  typedef ncs_rpc_notif_ptp-packet-type {
    type enumeration {
      enum "announce" {
        value 8;
        description
          "The packet type is announce.";
      }
      enum "sync" {
        value 1;
        description
          "The packet type is sync.";
      }
      enum "delay-resp" {
        value 6;
        description
          "The packet type is delay-resp.";
      }
      enum "pdelay-resp" {
        value 4;
        description
          "The packet type is pdelay-resp.";
      }
    }
    description
      "The packet type.";
  }

  typedef ncs_rpc_notif_clock-sync-state {
    type enumeration {
      enum "unsync" {
        value 1;
        description
          "The status is unsynchoronization.";
      }
      enum "sync" {
        value 2;
        description
          "The status is synchoronization.";
      }
    }
    description
      "Indicate that the status of the equipment.";
  }

  typedef ncs_rpc_notif_clock-ssm-level {
    type enumeration {
      enum "unk" {
        value 0;
        description
          "Unknown SSM level (UNK).";
      }
      enum "prc" {
        value 2;
        description
          "SSM level of the G.811 clock (PRC).";
      }
      enum "ssua" {
        value 4;
        description
          "G.812 transit clock (SSUA).";
      }
      enum "ssub" {
        value 8;
        description
          "G.812 local clock (SSUB).";
      }
      enum "sec" {
        value 11;
        description
          "SDH (sec).";
      }
      enum "dnu" {
        value 15;
        description
          "The quality level of the clock source is unavailable (DNU).";
      }
      enum "invaild" {
        value 255;
        description
          "Invalid SSM level.";
      }
    }
    description
      "SSM level type.";
  }

  typedef ncs_rpc_notif_ptpa-ptsf-type {
    type enumeration {
      enum "loss-announce" {
        value 1;
        description
          "The PTSF type is loss-announce.";
      }
      enum "loss-sync-followup" {
        value 2;
        description
          "The PTSF type is loss-Sync-followup.";
      }
      enum "loss-resp" {
        value 3;
        description
          "The PTSF type is loss-resp.";
      }
      enum "unusable" {
        value 4;
        description
          "The PTSF type is unusable.";
      }
    }
    description
      "The PTSF type of PTP adaptive clock synchronization.";
  }

  typedef ncs_rpc_notif_ptpa-ptsf-state {
    type enumeration {
      enum "true" {
        value 1;
        description
          "The PTSF state is true.";
      }
      enum "false" {
        value 2;
        description
          "The PTSF state is false.";
      }
    }
    description
      "The PTSF state of PTP adaptive clock synchronization.";
  }

  typedef ncs_rpc_notif_ptp-port-status {
    type enumeration {
      enum "master" {
        value 1;
        description
          "Master.";
      }
      enum "slave" {
        value 2;
        description
          "Slave.";
      }
      enum "passive" {
        value 3;
        description
          "Passive.";
      }
      enum "listening" {
        value 4;
        description
          "Listening.";
      }
      enum "faulty" {
        value 5;
        description
          "Faulty.";
      }
      enum "initializing" {
        value 6;
        description
          "Initializing.";
      }
      enum "premaster" {
        value 7;
        description
          "Premaster.";
      }
      enum "disabled" {
        value 8;
        description
          "Disabled.";
      }
      enum "uncalibrated" {
        value 9;
        description
          "Uncalibrated.";
      }
    }
    description
      "State of ptp port.";
  }

  typedef ncs_rpc_notif_ptpa-client-state {
    type enumeration {
      enum "added" {
        value 0;
        description
          "The client status is connected.";
      }
      enum "deleted" {
        value 1;
        description
          "The client status is disconnected.";
      }
    }
    description
      "Indicate the client status.";
  }

  typedef ncs_rpc_notif_ptpa-nego-state {
    type enumeration {
      enum "init" {
        value 0;
        description
          "The Initial state.";
      }
      enum "success" {
        value 1;
        description
          "Negotiation successful.";
      }
      enum "error" {
        value 2;
        description
          "Negotiation failure.";
      }
      enum "none" {
        value 3;
        description
          "Indicates that the server IP address is unavailable.";
      }
    }
    description
      "Indicates the negotiation status of the client with server.";
  }

  typedef ncs_rpc_notif_ptpa-nego-fail-reason {
    type enumeration {
      enum "none" {
        value 0;
        description
          "None.";
      }
      enum "delete-link" {
        value 1;
        description
          "Delete link.";
      }
      enum "announce-timeout" {
        value 2;
        description
          "Announce timeout.";
      }
      enum "announce-nego-timeout" {
        value 3;
        description
          "Announce negotiation timeout.";
      }
      enum "announce-nego-deny" {
        value 4;
        description
          "Announce timeout.";
      }
      enum "sync-nego-failed" {
        value 5;
        description
          "Announce negotiation timeout.";
      }
      enum "sync-nego-timeout" {
        value 6;
        description
          "Announce negotiation timeout.";
      }
      enum "delayresp-nego-timeout" {
        value 7;
        description
          "Delay response negotiation timeout.";
      }
      enum "delayresp-nego-deny" {
        value 8;
        description
          "Delay response negotiation deny.";
      }
      enum "if-not-support" {
        value 9;
        description
          "Interface not support.";
      }
      enum "service-mode-not-support" {
        value 10;
        description
          "Service mode not support.";
      }
      enum "route-unreach" {
        value 11;
        description
          "Route unreach.";
      }
      enum "bmc-failed" {
        value 12;
        description
          "BMC failed.";
      }
      enum "master-sync-fault" {
        value 13;
        description
          "Master synchronization fault.";
      }
    }
    description
      "Indicates causes of the negotiation failure.";
  }

  typedef ncs_rpc_notif_ptpa-server-id {
    type enumeration {
      enum "server1" {
        value 1;
        description
          "Server1.";
      }
      enum "server2" {
        value 2;
        description
          "Server2.";
      }
    }
    description
      "Indicates the server ID.";
  }

  typedef ncs_rpc_notif_ptpa-sync-server-src {
    type enumeration {
      enum "local" {
        value 0;
        description
          "Clock source is Local.";
      }
      enum "server1" {
        value 1;
        description
          "Clock source is server1.";
      }
      enum "server2" {
        value 2;
        description
          "Clock source is server2.";
      }
    }
    description
      "Clock source that the client has traced.";
  }

  typedef ncs_rpc_notif_gnss-model-type {
    type enumeration {
      enum "none" {
        value 0;
        description
          "None.";
      }
      enum "gps" {
        value 1;
        description
          "Gps.";
      }
      enum "glonass" {
        value 2;
        description
          "Glonass.";
      }
      enum "beidou" {
        value 3;
        description
          "Beidou.";
      }
      enum "gps-glonass" {
        value 4;
        description
          "Gps-glonass.";
      }
      enum "gps-beidou" {
        value 5;
        description
          "Gps-beidou.";
      }
    }
    description
      "Type of gnss model.";
  }

  typedef live_ncs_clock-lock-state {
    type enumeration {
      enum "unlock" {
        value 0;
        description
          "Clock not in locked state.";
      }
      enum "lock" {
        value 1;
        description
          "Clock in locked state.";
      }
    }
    description
      "Clock lock state.";
  }

  typedef live_ncs_cluster-sync-type {
    type enumeration {
      enum "frequency" {
        value 1;
        description
          "Inter-chassis synchronization type is frequency.";
      }
      enum "time" {
        value 2;
        description
          "Inter-chassis synchronization type is time.";
      }
    }
    description
      "Inter-chassis synchronization type.";
  }

  typedef live_ncs_cluster-topo-type {
    type enumeration {
      enum "inlink" {
        value 1;
        description
          "Synchronization topo type is interlink.";
      }
      enum "extinject" {
        value 2;
        description
          "Synchronization topo type is externInject.";
      }
    }
    description
      "Inter-chassis synchronization topo type.";
  }

  typedef live_ncs_cluster-link-type {
    type enumeration {
      enum "bits" {
        value 1;
        description
          "Synchronization link type is bits.";
      }
      enum "port" {
        value 2;
        description
          "Synchronization link type is port.";
      }
    }
    description
      "Inter-chassis synchronization link type.";
  }

  typedef live_ncs_cluster-sync-topo-state {
    type enumeration {
      enum "fail" {
        value 1;
        description
          "Topo status is fail.";
      }
      enum "success" {
        value 2;
        description
          "Topo status is success.";
      }
    }
    description
      "Inter-chassis synchronization topo status.";
  }

  typedef live_ncs_clock-pll-id {
    type enumeration {
      enum "system" {
        value 1;
        description
          "Pll id is system.";
      }
      enum "sync2m1" {
        value 2;
        description
          "Pll id is sync2M1.";
      }
      enum "sync2m2" {
        value 3;
        description
          "Pll id is sync2M2.";
      }
    }
    description
      "The id of pll.";
  }

  typedef live_ncs_clock-lock-mode {
    type enumeration {
      enum "freerun" {
        value 0;
        description
          "Lock mode is freerun.";
      }
      enum "fastlock" {
        value 1;
        description
          "Lock mode is fastlock.";
      }
      enum "lock" {
        value 2;
        description
          "Lock mode is lock.";
      }
      enum "hold" {
        value 3;
        description
          "Lock mode is hold.";
      }
    }
    description
      "Lock mode of system clock.";
  }

  typedef live_ncs_clock-src-type {
    type enumeration {
      enum "bits" {
        value 1;
        description
          "Clock source type is bits.";
      }
      enum "ptp" {
        value 2;
        description
          "Clock source type is ptp.";
      }
      enum "interface" {
        value 3;
        description
          "Clock source type is interface.";
      }
      enum "cesacr" {
        value 4;
        description
          "Clock source type is cesacr.";
      }
    }
    description
      "Index of the clock source type.";
  }

  typedef live_ncs_clock-src-state {
    type enumeration {
      enum "initial" {
        value 0;
        description
          "Clock source state is initial.";
      }
      enum "normal" {
        value 1;
        description
          "Clock source state is normal.";
      }
      enum "abnormal" {
        value 2;
        description
          "Clock source state is abnormal.";
      }
      enum "wtr" {
        value 3;
        description
          "Clock source state is wtr.";
      }
      enum "holdoff" {
        value 4;
        description
          "Clock source state is holdoff.";
      }
    }
    description
      "The state of the current clock source.";
  }

  typedef live_ncs_fre-check-result {
    type enumeration {
      enum "abnormal" {
        value 0;
        description
          "Frequency check is abnormal.";
      }
      enum "normal" {
        value 1;
        description
          "Frequency check is normal.";
      }
    }
    description
      "Result of the check of frequency.";
  }

  typedef live_ncs_sync-state {
    type enumeration {
      enum "normal" {
        value 0;
        description
          "The state is normal.";
      }
      enum "abnormal" {
        value 1;
        description
          "The state is abnormal.";
      }
    }
    description
      "State of synchoronization.";
  }

  typedef live_ncs_time-port-state {
    type enumeration {
      enum "normal" {
        value 0;
        description
          "Port state is normal.";
      }
      enum "portdown" {
        value 1;
        description
          "Port state is portdown.";
      }
    }
    description
      "Port status of the external Time.";
  }

  typedef live_ncs_ext-time-port-type {
    type enumeration {
      enum "bits0" {
        value 0;
        description
          "The external time port type is bits0.";
      }
      enum "bits1" {
        value 1;
        description
          "The external time port type is bits1.";
      }
      enum "bits2" {
        value 2;
        description
          "The external time port type is bits2.";
      }
      enum "bits1slot4" {
        value 1025;
        description
          "The external time port type is bits1slot4.";
      }
      enum "bits1slot5" {
        value 1281;
        description
          "The external time port type is bits1slot5.";
      }
      enum "bits1slot6" {
        value 1537;
        description
          "The external time port type is bits1slot6.";
      }
      enum "bits1slot7" {
        value 1793;
        description
          "The external time port type is bits1slot7.";
      }
      enum "bits1slot8" {
        value 2049;
        description
          "The external time port type is bits1slot8.";
      }
      enum "bits1slot9" {
        value 2305;
        description
          "The external time port type is bits1slot9.";
      }
      enum "bits1slot10" {
        value 2561;
        description
          "The external time port type is bits1slot10.";
      }
      enum "bits1slot11" {
        value 2817;
        description
          "The external time port type is bits1slot11.";
      }
      enum "bits1slot12" {
        value 3073;
        description
          "The external time port type is bits1slot12.";
      }
      enum "bits1slot15" {
        value 3841;
        description
          "The external time port type is bits1slot15.";
      }
      enum "bits1slot16" {
        value 4097;
        description
          "The external time port type is bits1slot16.";
      }
      enum "bits1slot17" {
        value 4353;
        description
          "The external time port type is bits1slot17.";
      }
      enum "bits1slot18" {
        value 4609;
        description
          "The external time port type is bits1slot18.";
      }
      enum "bits1slot19" {
        value 4865;
        description
          "The external time port type is bits1slot19.";
      }
      enum "bits1slot20" {
        value 5121;
        description
          "The external time port type is bits1slot20.";
      }
      enum "bits1slot21" {
        value 5377;
        description
          "The external time port type is bits1slot21.";
      }
      enum "bits1slot22" {
        value 5633;
        description
          "The external time port type is bits1slot22.";
      }
    }
    description
      "Port type of the external Time.";
  }

  typedef live_ncs_ptp-packet-type {
    type enumeration {
      enum "announce" {
        value 8;
        description
          "The packet type is announce.";
      }
      enum "sync" {
        value 1;
        description
          "The packet type is sync.";
      }
      enum "delay-resp" {
        value 6;
        description
          "The packet type is delay-resp.";
      }
      enum "pdelay-resp" {
        value 4;
        description
          "The packet type is pdelay-resp.";
      }
    }
    description
      "The packet type.";
  }

  typedef live_ncs_clock-sync-state {
    type enumeration {
      enum "unsync" {
        value 1;
        description
          "The status is unsynchoronization.";
      }
      enum "sync" {
        value 2;
        description
          "The status is synchoronization.";
      }
    }
    description
      "Indicate that the status of the equipment.";
  }

  typedef live_ncs_clock-ssm-level {
    type enumeration {
      enum "unk" {
        value 0;
        description
          "Unknown SSM level (UNK).";
      }
      enum "prc" {
        value 2;
        description
          "SSM level of the G.811 clock (PRC).";
      }
      enum "ssua" {
        value 4;
        description
          "G.812 transit clock (SSUA).";
      }
      enum "ssub" {
        value 8;
        description
          "G.812 local clock (SSUB).";
      }
      enum "sec" {
        value 11;
        description
          "SDH (sec).";
      }
      enum "dnu" {
        value 15;
        description
          "The quality level of the clock source is unavailable (DNU).";
      }
      enum "invaild" {
        value 255;
        description
          "Invalid SSM level.";
      }
    }
    description
      "SSM level type.";
  }

  typedef live_ncs_ptpa-ptsf-type {
    type enumeration {
      enum "loss-announce" {
        value 1;
        description
          "The PTSF type is loss-announce.";
      }
      enum "loss-sync-followup" {
        value 2;
        description
          "The PTSF type is loss-Sync-followup.";
      }
      enum "loss-resp" {
        value 3;
        description
          "The PTSF type is loss-resp.";
      }
      enum "unusable" {
        value 4;
        description
          "The PTSF type is unusable.";
      }
    }
    description
      "The PTSF type of PTP adaptive clock synchronization.";
  }

  typedef live_ncs_ptpa-ptsf-state {
    type enumeration {
      enum "true" {
        value 1;
        description
          "The PTSF state is true.";
      }
      enum "false" {
        value 2;
        description
          "The PTSF state is false.";
      }
    }
    description
      "The PTSF state of PTP adaptive clock synchronization.";
  }

  typedef live_ncs_ptp-port-status {
    type enumeration {
      enum "master" {
        value 1;
        description
          "Master.";
      }
      enum "slave" {
        value 2;
        description
          "Slave.";
      }
      enum "passive" {
        value 3;
        description
          "Passive.";
      }
      enum "listening" {
        value 4;
        description
          "Listening.";
      }
      enum "faulty" {
        value 5;
        description
          "Faulty.";
      }
      enum "initializing" {
        value 6;
        description
          "Initializing.";
      }
      enum "premaster" {
        value 7;
        description
          "Premaster.";
      }
      enum "disabled" {
        value 8;
        description
          "Disabled.";
      }
      enum "uncalibrated" {
        value 9;
        description
          "Uncalibrated.";
      }
    }
    description
      "State of ptp port.";
  }

  typedef live_ncs_ptpa-client-state {
    type enumeration {
      enum "added" {
        value 0;
        description
          "The client status is connected.";
      }
      enum "deleted" {
        value 1;
        description
          "The client status is disconnected.";
      }
    }
    description
      "Indicate the client status.";
  }

  typedef live_ncs_ptpa-nego-state {
    type enumeration {
      enum "init" {
        value 0;
        description
          "The Initial state.";
      }
      enum "success" {
        value 1;
        description
          "Negotiation successful.";
      }
      enum "error" {
        value 2;
        description
          "Negotiation failure.";
      }
      enum "none" {
        value 3;
        description
          "Indicates that the server IP address is unavailable.";
      }
    }
    description
      "Indicates the negotiation status of the client with server.";
  }

  typedef live_ncs_ptpa-nego-fail-reason {
    type enumeration {
      enum "none" {
        value 0;
        description
          "None.";
      }
      enum "delete-link" {
        value 1;
        description
          "Delete link.";
      }
      enum "announce-timeout" {
        value 2;
        description
          "Announce timeout.";
      }
      enum "announce-nego-timeout" {
        value 3;
        description
          "Announce negotiation timeout.";
      }
      enum "announce-nego-deny" {
        value 4;
        description
          "Announce timeout.";
      }
      enum "sync-nego-failed" {
        value 5;
        description
          "Announce negotiation timeout.";
      }
      enum "sync-nego-timeout" {
        value 6;
        description
          "Announce negotiation timeout.";
      }
      enum "delayresp-nego-timeout" {
        value 7;
        description
          "Delay response negotiation timeout.";
      }
      enum "delayresp-nego-deny" {
        value 8;
        description
          "Delay response negotiation deny.";
      }
      enum "if-not-support" {
        value 9;
        description
          "Interface not support.";
      }
      enum "service-mode-not-support" {
        value 10;
        description
          "Service mode not support.";
      }
      enum "route-unreach" {
        value 11;
        description
          "Route unreach.";
      }
      enum "bmc-failed" {
        value 12;
        description
          "BMC failed.";
      }
      enum "master-sync-fault" {
        value 13;
        description
          "Master synchronization fault.";
      }
    }
    description
      "Indicates causes of the negotiation failure.";
  }

  typedef live_ncs_ptpa-server-id {
    type enumeration {
      enum "server1" {
        value 1;
        description
          "Server1.";
      }
      enum "server2" {
        value 2;
        description
          "Server2.";
      }
    }
    description
      "Indicates the server ID.";
  }

  typedef live_ncs_ptpa-sync-server-src {
    type enumeration {
      enum "local" {
        value 0;
        description
          "Clock source is Local.";
      }
      enum "server1" {
        value 1;
        description
          "Clock source is server1.";
      }
      enum "server2" {
        value 2;
        description
          "Clock source is server2.";
      }
    }
    description
      "Clock source that the client has traced.";
  }

  typedef live_ncs_gnss-model-type {
    type enumeration {
      enum "none" {
        value 0;
        description
          "None.";
      }
      enum "gps" {
        value 1;
        description
          "Gps.";
      }
      enum "glonass" {
        value 2;
        description
          "Glonass.";
      }
      enum "beidou" {
        value 3;
        description
          "Beidou.";
      }
      enum "gps-glonass" {
        value 4;
        description
          "Gps-glonass.";
      }
      enum "gps-beidou" {
        value 5;
        description
          "Gps-beidou.";
      }
    }
    description
      "Type of gnss model.";
  }

  typedef clock-lock-state {
    type enumeration {
      enum "unlock" {
        value 0;
        description
          "Clock not in locked state.";
      }
      enum "lock" {
        value 1;
        description
          "Clock in locked state.";
      }
    }
    description
      "Clock lock state.";
  }

  typedef cluster-sync-type {
    type enumeration {
      enum "frequency" {
        value 1;
        description
          "Inter-chassis synchronization type is frequency.";
      }
      enum "time" {
        value 2;
        description
          "Inter-chassis synchronization type is time.";
      }
    }
    description
      "Inter-chassis synchronization type.";
  }

  typedef cluster-topo-type {
    type enumeration {
      enum "inlink" {
        value 1;
        description
          "Synchronization topo type is interlink.";
      }
      enum "extinject" {
        value 2;
        description
          "Synchronization topo type is externInject.";
      }
    }
    description
      "Inter-chassis synchronization topo type.";
  }

  typedef cluster-link-type {
    type enumeration {
      enum "bits" {
        value 1;
        description
          "Synchronization link type is bits.";
      }
      enum "port" {
        value 2;
        description
          "Synchronization link type is port.";
      }
    }
    description
      "Inter-chassis synchronization link type.";
  }

  typedef cluster-sync-topo-state {
    type enumeration {
      enum "fail" {
        value 1;
        description
          "Topo status is fail.";
      }
      enum "success" {
        value 2;
        description
          "Topo status is success.";
      }
    }
    description
      "Inter-chassis synchronization topo status.";
  }

  typedef clock-pll-id {
    type enumeration {
      enum "system" {
        value 1;
        description
          "Pll id is system.";
      }
      enum "sync2m1" {
        value 2;
        description
          "Pll id is sync2M1.";
      }
      enum "sync2m2" {
        value 3;
        description
          "Pll id is sync2M2.";
      }
    }
    description
      "The id of pll.";
  }

  typedef clock-lock-mode {
    type enumeration {
      enum "freerun" {
        value 0;
        description
          "Lock mode is freerun.";
      }
      enum "fastlock" {
        value 1;
        description
          "Lock mode is fastlock.";
      }
      enum "lock" {
        value 2;
        description
          "Lock mode is lock.";
      }
      enum "hold" {
        value 3;
        description
          "Lock mode is hold.";
      }
    }
    description
      "Lock mode of system clock.";
  }

  typedef clock-src-type {
    type enumeration {
      enum "bits" {
        value 1;
        description
          "Clock source type is bits.";
      }
      enum "ptp" {
        value 2;
        description
          "Clock source type is ptp.";
      }
      enum "interface" {
        value 3;
        description
          "Clock source type is interface.";
      }
      enum "cesacr" {
        value 4;
        description
          "Clock source type is cesacr.";
      }
    }
    description
      "Index of the clock source type.";
  }

  typedef clock-src-state {
    type enumeration {
      enum "initial" {
        value 0;
        description
          "Clock source state is initial.";
      }
      enum "normal" {
        value 1;
        description
          "Clock source state is normal.";
      }
      enum "abnormal" {
        value 2;
        description
          "Clock source state is abnormal.";
      }
      enum "wtr" {
        value 3;
        description
          "Clock source state is wtr.";
      }
      enum "holdoff" {
        value 4;
        description
          "Clock source state is holdoff.";
      }
    }
    description
      "The state of the current clock source.";
  }

  typedef fre-check-result {
    type enumeration {
      enum "abnormal" {
        value 0;
        description
          "Frequency check is abnormal.";
      }
      enum "normal" {
        value 1;
        description
          "Frequency check is normal.";
      }
    }
    description
      "Result of the check of frequency.";
  }

  typedef sync-state {
    type enumeration {
      enum "normal" {
        value 0;
        description
          "The state is normal.";
      }
      enum "abnormal" {
        value 1;
        description
          "The state is abnormal.";
      }
    }
    description
      "State of synchoronization.";
  }

  typedef time-port-state {
    type enumeration {
      enum "normal" {
        value 0;
        description
          "Port state is normal.";
      }
      enum "portdown" {
        value 1;
        description
          "Port state is portdown.";
      }
    }
    description
      "Port status of the external Time.";
  }

  typedef ext-time-port-type {
    type enumeration {
      enum "bits0" {
        value 0;
        description
          "The external time port type is bits0.";
      }
      enum "bits1" {
        value 1;
        description
          "The external time port type is bits1.";
      }
      enum "bits2" {
        value 2;
        description
          "The external time port type is bits2.";
      }
      enum "bits1slot4" {
        value 1025;
        description
          "The external time port type is bits1slot4.";
      }
      enum "bits1slot5" {
        value 1281;
        description
          "The external time port type is bits1slot5.";
      }
      enum "bits1slot6" {
        value 1537;
        description
          "The external time port type is bits1slot6.";
      }
      enum "bits1slot7" {
        value 1793;
        description
          "The external time port type is bits1slot7.";
      }
      enum "bits1slot8" {
        value 2049;
        description
          "The external time port type is bits1slot8.";
      }
      enum "bits1slot9" {
        value 2305;
        description
          "The external time port type is bits1slot9.";
      }
      enum "bits1slot10" {
        value 2561;
        description
          "The external time port type is bits1slot10.";
      }
      enum "bits1slot11" {
        value 2817;
        description
          "The external time port type is bits1slot11.";
      }
      enum "bits1slot12" {
        value 3073;
        description
          "The external time port type is bits1slot12.";
      }
      enum "bits1slot15" {
        value 3841;
        description
          "The external time port type is bits1slot15.";
      }
      enum "bits1slot16" {
        value 4097;
        description
          "The external time port type is bits1slot16.";
      }
      enum "bits1slot17" {
        value 4353;
        description
          "The external time port type is bits1slot17.";
      }
      enum "bits1slot18" {
        value 4609;
        description
          "The external time port type is bits1slot18.";
      }
      enum "bits1slot19" {
        value 4865;
        description
          "The external time port type is bits1slot19.";
      }
      enum "bits1slot20" {
        value 5121;
        description
          "The external time port type is bits1slot20.";
      }
      enum "bits1slot21" {
        value 5377;
        description
          "The external time port type is bits1slot21.";
      }
      enum "bits1slot22" {
        value 5633;
        description
          "The external time port type is bits1slot22.";
      }
    }
    description
      "Port type of the external Time.";
  }

  typedef ptp-packet-type {
    type enumeration {
      enum "announce" {
        value 8;
        description
          "The packet type is announce.";
      }
      enum "sync" {
        value 1;
        description
          "The packet type is sync.";
      }
      enum "delay-resp" {
        value 6;
        description
          "The packet type is delay-resp.";
      }
      enum "pdelay-resp" {
        value 4;
        description
          "The packet type is pdelay-resp.";
      }
    }
    description
      "The packet type.";
  }

  typedef clock-sync-state {
    type enumeration {
      enum "unsync" {
        value 1;
        description
          "The status is unsynchoronization.";
      }
      enum "sync" {
        value 2;
        description
          "The status is synchoronization.";
      }
    }
    description
      "Indicate that the status of the equipment.";
  }

  typedef clock-ssm-level {
    type enumeration {
      enum "unk" {
        value 0;
        description
          "Unknown SSM level (UNK).";
      }
      enum "prc" {
        value 2;
        description
          "SSM level of the G.811 clock (PRC).";
      }
      enum "ssua" {
        value 4;
        description
          "G.812 transit clock (SSUA).";
      }
      enum "ssub" {
        value 8;
        description
          "G.812 local clock (SSUB).";
      }
      enum "sec" {
        value 11;
        description
          "SDH (sec).";
      }
      enum "dnu" {
        value 15;
        description
          "The quality level of the clock source is unavailable (DNU).";
      }
      enum "invaild" {
        value 255;
        description
          "Invalid SSM level.";
      }
    }
    description
      "SSM level type.";
  }

  typedef ptpa-ptsf-type {
    type enumeration {
      enum "loss-announce" {
        value 1;
        description
          "The PTSF type is loss-announce.";
      }
      enum "loss-sync-followup" {
        value 2;
        description
          "The PTSF type is loss-Sync-followup.";
      }
      enum "loss-resp" {
        value 3;
        description
          "The PTSF type is loss-resp.";
      }
      enum "unusable" {
        value 4;
        description
          "The PTSF type is unusable.";
      }
    }
    description
      "The PTSF type of PTP adaptive clock synchronization.";
  }

  typedef ptpa-ptsf-state {
    type enumeration {
      enum "true" {
        value 1;
        description
          "The PTSF state is true.";
      }
      enum "false" {
        value 2;
        description
          "The PTSF state is false.";
      }
    }
    description
      "The PTSF state of PTP adaptive clock synchronization.";
  }

  typedef ptp-port-status {
    type enumeration {
      enum "master" {
        value 1;
        description
          "Master.";
      }
      enum "slave" {
        value 2;
        description
          "Slave.";
      }
      enum "passive" {
        value 3;
        description
          "Passive.";
      }
      enum "listening" {
        value 4;
        description
          "Listening.";
      }
      enum "faulty" {
        value 5;
        description
          "Faulty.";
      }
      enum "initializing" {
        value 6;
        description
          "Initializing.";
      }
      enum "premaster" {
        value 7;
        description
          "Premaster.";
      }
      enum "disabled" {
        value 8;
        description
          "Disabled.";
      }
      enum "uncalibrated" {
        value 9;
        description
          "Uncalibrated.";
      }
    }
    description
      "State of ptp port.";
  }

  typedef ptpa-client-state {
    type enumeration {
      enum "added" {
        value 0;
        description
          "The client status is connected.";
      }
      enum "deleted" {
        value 1;
        description
          "The client status is disconnected.";
      }
    }
    description
      "Indicate the client status.";
  }

  typedef ptpa-nego-state {
    type enumeration {
      enum "init" {
        value 0;
        description
          "The Initial state.";
      }
      enum "success" {
        value 1;
        description
          "Negotiation successful.";
      }
      enum "error" {
        value 2;
        description
          "Negotiation failure.";
      }
      enum "none" {
        value 3;
        description
          "Indicates that the server IP address is unavailable.";
      }
    }
    description
      "Indicates the negotiation status of the client with server.";
  }

  typedef ptpa-nego-fail-reason {
    type enumeration {
      enum "none" {
        value 0;
        description
          "None.";
      }
      enum "delete-link" {
        value 1;
        description
          "Delete link.";
      }
      enum "announce-timeout" {
        value 2;
        description
          "Announce timeout.";
      }
      enum "announce-nego-timeout" {
        value 3;
        description
          "Announce negotiation timeout.";
      }
      enum "announce-nego-deny" {
        value 4;
        description
          "Announce timeout.";
      }
      enum "sync-nego-failed" {
        value 5;
        description
          "Announce negotiation timeout.";
      }
      enum "sync-nego-timeout" {
        value 6;
        description
          "Announce negotiation timeout.";
      }
      enum "delayresp-nego-timeout" {
        value 7;
        description
          "Delay response negotiation timeout.";
      }
      enum "delayresp-nego-deny" {
        value 8;
        description
          "Delay response negotiation deny.";
      }
      enum "if-not-support" {
        value 9;
        description
          "Interface not support.";
      }
      enum "service-mode-not-support" {
        value 10;
        description
          "Service mode not support.";
      }
      enum "route-unreach" {
        value 11;
        description
          "Route unreach.";
      }
      enum "bmc-failed" {
        value 12;
        description
          "BMC failed.";
      }
      enum "master-sync-fault" {
        value 13;
        description
          "Master synchronization fault.";
      }
    }
    description
      "Indicates causes of the negotiation failure.";
  }

  typedef ptpa-server-id {
    type enumeration {
      enum "server1" {
        value 1;
        description
          "Server1.";
      }
      enum "server2" {
        value 2;
        description
          "Server2.";
      }
    }
    description
      "Indicates the server ID.";
  }

  typedef ptpa-sync-server-src {
    type enumeration {
      enum "local" {
        value 0;
        description
          "Clock source is Local.";
      }
      enum "server1" {
        value 1;
        description
          "Clock source is server1.";
      }
      enum "server2" {
        value 2;
        description
          "Clock source is server2.";
      }
    }
    description
      "Clock source that the client has traced.";
  }

  typedef gnss-model-type {
    type enumeration {
      enum "none" {
        value 0;
        description
          "None.";
      }
      enum "gps" {
        value 1;
        description
          "Gps.";
      }
      enum "glonass" {
        value 2;
        description
          "Glonass.";
      }
      enum "beidou" {
        value 3;
        description
          "Beidou.";
      }
      enum "gps-glonass" {
        value 4;
        description
          "Gps-glonass.";
      }
      enum "gps-beidou" {
        value 5;
        description
          "Gps-beidou.";
      }
    }
    description
      "Type of gnss model.";
  }

  augment "/ncs:devices/ncs:device/ncs:notifications/ncs:received-notifications/ncs:notification/ncs:data" {
    container ptp-pdv-limit-exceed {
      presence "";
      config false;
      description
        "The value of State can be: normal(0), indicating that 1588 ACR/ATR PDV data performance is normal. limitExceed(1), indicating that 1588 ACR/ATR PDV data performance exceeds the threshold.";
      leaf state {
        type uint32;
        description
          "1588 ACR/ATR PDV data threshold-crossing event occurred.";
      }
    }
  }
  augment "/ncs:devices/ncs:device/ncs:notifications/ncs:received-notifications/ncs:notification/ncs:data" {
    container ptp-adaptive-trace-source-change {
      presence "";
      config false;
      description
        "The clock source traced by the client changed.";
      leaf old-trace-source {
        type ncs_rpc_notif_ptpa-sync-server-src;
        description
          "Historical clock source that the client has traced.";
      }
      leaf trace-source {
        type ncs_rpc_notif_ptpa-sync-server-src;
        description
          "Current clock source that the client is synchroniazation.";
      }
    }
  }
  augment "/ncs:devices/ncs:device/ncs:notifications/ncs:received-notifications/ncs:notification/ncs:data" {
    container ptp-adaptive-nego-info-change {
      presence "";
      config false;
      description
        "The negotiation status of the client with server 1 and with server 2 changed.";
      leaf server-id {
        type ncs_rpc_notif_ptpa-server-id;
        description
          "Indicates the server ID.";
      }
      leaf nego-state {
        type ncs_rpc_notif_ptpa-nego-state;
        description
          "Indicates the negotiation status of the client with server.";
      }
      leaf error-reason {
        type ncs_rpc_notif_ptpa-nego-fail-reason;
        description
          "Indicates causes of the negotiation failure.";
      }
    }
  }
  augment "/ncs:devices/ncs:device/ncs:notifications/ncs:received-notifications/ncs:notification/ncs:data" {
    container ptp-adaptive-client-list-change {
      presence "";
      config false;
      description
        "The status of the client list was refreshed.";
      leaf client-ip-list {
        type inet:ipv4-address-no-zone;
        description
          "Indicates the IP address of the client.";
      }
      leaf client-ip-change-flag {
        type ncs_rpc_notif_ptpa-client-state;
        description
          "Indicate the client status.";
      }
      leaf client-index {
        type uint32;
        description
          "Indicates the Index of the client.";
      }
      leaf client-id {
        type uint32;
        description
          "Indicates the ID of the client.";
      }
    }
  }
  augment "/ncs:devices/ncs:device/ncs:notifications/ncs:received-notifications/ncs:notification/ncs:data" {
    container ptp-port-state-change {
      presence "";
      config false;
      description
        "The alarm was generated when the interface status changed.";
      leaf ifindex {
        type int32;
        description
          "Interface index.";
      }
      leaf ifname {
        type string;
        description
          "Name of the port whose state has changed.";
      }
      leaf port-state {
        type ncs_rpc_notif_ptp-port-status;
        description
          "Current status of the interface.";
      }
      leaf old-port-state {
        type ncs_rpc_notif_ptp-port-status;
        description
          "Old status of the interface.";
      }
    }
  }
  augment "/ncs:devices/ncs:device/ncs:notifications/ncs:received-notifications/ncs:notification/ncs:data" {
    container ptp-port-bmc-info-change {
      presence "";
      config false;
      description
        "The PTP port clock source information is changed. The clock source ID, clock source port number, or clock source's hop count received on a port was changed.";
      leaf ifindex {
        type int32;
        description
          "Port index.";
      }
      leaf ifname {
        type string;
        description
          "Port name.";
      }
      leaf clock-id {
        type string {
          length "16";
        }
        description
          "Clock source ID received on a port.";
      }
      leaf port-num {
        type int32;
        description
          "Clock source port number received on a port.";
      }
      leaf steps {
        type int32;
        description
          "Clock source's hop count received on a port.";
      }
      leaf master-clock-id {
        type string {
          length "16";
        }
        description
          "ID of the current master clock source.";
      }
    }
  }
  augment "/ncs:devices/ncs:device/ncs:notifications/ncs:received-notifications/ncs:notification/ncs:data" {
    container ptp-passive-fiber-length-change {
      presence "";
      config false;
      description
        "The optical fiber length on the Passive port was changed.";
      leaf ifindex {
        type int32;
        description
          "Index of the current port.";
      }
      leaf ifname {
        type string;
        description
          "Name of the current port.";
      }
      leaf change-value {
        type int32;
        description
          "New time offset caused by the fiber length change of the current port.";
      }
      leaf value-flag {
        type clocksync-1588v2:ncs_rpc_notif_ptp-sign-flag;
        description
          "Positive or negative sign of the new time offset.";
      }
    }
  }
  augment "/ncs:devices/ncs:device/ncs:notifications/ncs:received-notifications/ncs:notification/ncs:data" {
    container ptp-clock-source-change {
      presence "";
      config false;
      description
        "This trap was generated when the clock source changed.";
      leaf old-clock-id {
        type string {
          length "16";
        }
        description
          "Indicates the ID of the old master clock.";
      }
      leaf clock-id {
        type string {
          length "16";
        }
        description
          "Indicates the ID of the current master clock.";
      }
      leaf ifindex {
        type uint32;
        description
          "Indicates the port index of the current clock source.";
      }
      leaf old-port-num {
        type int32;
        description
          "Indicates the port number of the original clock source.";
      }
      leaf port-num {
        type int32;
        description
          "Indicates the port number of the current clock source.";
      }
      leaf old-ifname {
        type string;
        description
          "Indicates the port name of the original clock source.";
      }
      leaf ifname {
        type string;
        description
          "Indicates the port name of the current clock source.";
      }
    }
  }
  augment "/ncs:devices/ncs:device/ncs:notifications/ncs:received-notifications/ncs:notification/ncs:data" {
    container ptp-adaptive-ptsf-state-change {
      presence "";
      config false;
      description
        "The PTSF status of PTP adaptive clock synchronization is changed.";
      leaf server-index {
        type int32;
        description
          "Server index for the PTSF status change.";
      }
      leaf ptsf-type {
        type ncs_rpc_notif_ptpa-ptsf-type;
        description
          "PTSF type.";
      }
      leaf ptsf-state {
        type ncs_rpc_notif_ptpa-ptsf-state;
        description
          "New PTSF status.";
      }
    }
  }
  augment "/ncs:devices/ncs:device/ncs:notifications/ncs:received-notifications/ncs:notification/ncs:data" {
    container clock-source-switch {
      presence "";
      config false;
      description
        "The working mode of the system clock changed.";
      leaf chassis-id {
        type int32;
        description
          "Indicates the ID of the chassis where the clock source resides, The value is 1 in single chassis scenarios.";
      }
      leaf pll-id {
        type ncs_rpc_notif_clock-pll-id;
        description
          "Indicates the clock source type ID.";
      }
      leaf old-source-name {
        type string {
          length "1..63";
        }
        description
          "Indicates the last clock source name.";
      }
      leaf source-name {
        type string {
          length "1..63";
        }
        description
          "Indicates the current clock source name.";
      }
      leaf chassis-index {
        type int32;
        description
          "Indicates the index of the chassis where the clock source resides,.The value is 1 in single chassis scenarios.";
      }
      leaf src-type {
        type ncs_rpc_notif_clock-pll-id;
        description
          "Indicates the type of clock source selection.";
      }
      leaf src-mode {
        type clocksync-phy:ncs_rpc_notif_source-selection-mode;
        description
          "Indicates the mode of clock source selection.";
      }
    }
  }
  augment "/ncs:devices/ncs:device/ncs:notifications/ncs:received-notifications/ncs:notification/ncs:data" {
    container clock-source-ssm-change {
      presence "";
      config false;
      description
        "The SSM level of the clock source was changed.";
      leaf chassis-id {
        type uint32;
        description
          "Chassis ID. The value is 1 in single chassis scenarios.";
      }
      leaf source-name {
        type string {
          length "1..63";
        }
        description
          "Name of the current clock source.";
      }
      leaf old-ssm {
        type ncs_rpc_notif_clock-ssm-level;
        description
          "SSM level before the change.";
      }
      leaf ssm {
        type ncs_rpc_notif_clock-ssm-level;
        description
          "Current SSM level.";
      }
    }
  }
  augment "/ncs:devices/ncs:device/ncs:notifications/ncs:received-notifications/ncs:notification/ncs:data" {
    container clock-gnss-model-change {
      presence "";
      config false;
      description
        "Gnss model change notification.";
      leaf ifindex {
        type int32;
        description
          "Specifies the index of the port on which the working mode is changed.";
      }
      leaf ifname {
        type string;
        description
          "Specifies the name of the port on which the working mode is changed.";
      }
      leaf model {
        type ncs_rpc_notif_gnss-model-type;
        must "(../model='gps' or ../model='glonass' or ../model='beidou' or ../model='gps-glonass' or ../model='gps-beidou')" {
          tailf:xpath-root 6;
        }
        description
          "Specifies the new working mode.";
      }
      leaf old-model {
        type ncs_rpc_notif_gnss-model-type;
        must "(../old-model='gps' or ../old-model='glonass' or ../old-model='beidou' or ../old-model='gps-glonass' or ../old-model='gps-beidou')" {
          tailf:xpath-root 6;
        }
        description
          "Specifies the old working mode.";
      }
    }
  }
  augment "/ncs:devices/ncs:device/ncs:notifications/ncs:received-notifications/ncs:notification/ncs:data" {
    container clock-source-sys-clk-lock-mode-change {
      presence "";
      config false;
      description
        "The working mode of the system clock changed.";
      leaf chassis-id {
        type int32;
        description
          "Indicates the ID of the chassis where the clock source resides, The index is always 1 for a single chassis.";
      }
      leaf old-lock-mode {
        type uint32 {
          range "0..3";
        }
        description
          "Indicates the old lock mode of the clock source.";
      }
      leaf attr-chassis-index {
        type int32;
        description
          "Index of the chassis where the clock source is located. In the case of a single chassis, the index is 1.";
      }
      leaf lock-mode {
        type ncs_rpc_notif_clock-lock-mode;
        description
          "Indicates the lock mode of the system clock.";
      }
    }
  }
  augment "/ncs:devices/ncs:device/ncs:notifications/ncs:received-notifications/ncs:notification/ncs:data" {
    container clock-source-state-change {
      presence "";
      config false;
      description
        "The status of the clock source changed.";
      leaf chassis-id {
        type int32;
        description
          "Chassis ID. In the case of a single chassis, the value is 1.";
      }
      leaf source-name {
        type string {
          length "1..63";
        }
        description
          "Name of the current clock source.";
      }
      leaf old-source-state {
        type ncs_rpc_notif_clock-src-state;
        description
          "Clock source state before the change.";
      }
      leaf chassis-index {
        type int32;
        description
          "Index of the chassis where the clock source is located. In the case of a single chassis, the index is 1.";
      }
      leaf source-type-index {
        type ncs_rpc_notif_clock-src-type;
        description
          "Index of the interface type.";
      }
      leaf source-index {
        type uint32;
        description
          "Index of the clock source.";
      }
      leaf source-state {
        type ncs_rpc_notif_clock-src-state;
        description
          "Status of the current clock source.";
      }
    }
  }
  augment "/ncs:devices/ncs:device/ncs:notifications/ncs:received-notifications/ncs:notification/ncs:data" {
    container clock-ces-acr-master-pw-change {
      presence "";
      config false;
      description
        "The master PW in the CES ACR clock domain changed.";
      leaf slot {
        type uint32;
        description
          "Slot ID of the clock source.";
      }
      leaf card {
        type uint32;
        description
          "Card ID of the clock source.";
      }
      leaf domain {
        type uint32;
        description
          "Clock source recovery domain.";
      }
      leaf old-pw-name {
        type string {
          length "1..63";
        }
        description
          "Name of the old master PW of CES ACR clock source.";
      }
      leaf pw-name {
        type string {
          length "1..63";
        }
        description
          "Name of the new master PW of CES ACR clock source.";
      }
    }
  }
  augment "/ncs:devices/ncs:device/ncs:notifications/ncs:received-notifications/ncs:notification/ncs:data" {
    container ptp-time-sync-resume {
      presence "";
      config false;
      description
        "Time source traced status is normal.";
      leaf sync-status {
        type ncs_rpc_notif_clock-sync-state;
        description
          "Indicate that the status of the equipment is synchronization or unsynchoronization.";
      }
    }
  }
  augment "/ncs:devices/ncs:device/ncs:notifications/ncs:received-notifications/ncs:notification/ncs:data" {
    container ptp-time-sync-faulty {
      presence "";
      config false;
      description
        "Time source traced status is faulty.";
      leaf sync-status {
        type ncs_rpc_notif_clock-sync-state;
        description
          "Indicate that the status of the equipment is synchronization or unsynchoronization.";
      }
    }
  }
  augment "/ncs:devices/ncs:device/ncs:notifications/ncs:received-notifications/ncs:notification/ncs:data" {
    container ptp-time-offset-sum-over-resume {
      presence "";
      config false;
      description
        "The ptp time offset sum is normal.";
      leaf offset-sum {
        type uint32;
        description
          "Accumulated and peak time offset values.";
      }
      leaf threshold {
        type uint32;
        description
          "Threshold of the sum of time offset.";
      }
    }
  }
  augment "/ncs:devices/ncs:device/ncs:notifications/ncs:received-notifications/ncs:notification/ncs:data" {
    container ptp-time-offset-sum-over {
      presence "";
      config false;
      description
        "The ptp time offset sum is abnormal.";
      leaf offset-sum {
        type uint32;
        description
          "Accumulated and peak time offset values.";
      }
      leaf threshold {
        type uint32;
        description
          "Threshold of the sum of time offset.";
      }
    }
  }
  augment "/ncs:devices/ncs:device/ncs:notifications/ncs:received-notifications/ncs:notification/ncs:data" {
    container ptp-time-lock-fail-resume {
      presence "";
      config false;
      description
        "Time lock is resumed at present.";
      leaf lock-status {
        type ncs_rpc_notif_clock-lock-state;
        description
          "Time lock status.";
      }
    }
  }
  augment "/ncs:devices/ncs:device/ncs:notifications/ncs:received-notifications/ncs:notification/ncs:data" {
    container ptp-time-lock-fail {
      presence "";
      config false;
      description
        "The time lock status is failed.";
      leaf lock-status {
        type ncs_rpc_notif_clock-lock-state;
        description
          "Time lock status.";
      }
    }
  }
  augment "/ncs:devices/ncs:device/ncs:notifications/ncs:received-notifications/ncs:notification/ncs:data" {
    container ptp-standard-time-offset-over-resume {
      presence "";
      config false;
      description
        "The ptp standard time offset is normal.";
      leaf offset {
        type uint32;
        description
          "The standard time offset.";
      }
      leaf threshold {
        type uint32;
        description
          "Threshold of the standard time offset.";
      }
    }
  }
  augment "/ncs:devices/ncs:device/ncs:notifications/ncs:received-notifications/ncs:notification/ncs:data" {
    container ptp-standard-time-offset-over {
      presence "";
      config false;
      description
        "The ptp standard time offset is abnormal.";
      leaf offset {
        type uint32;
        description
          "The standard time offset.";
      }
      leaf threshold {
        type uint32;
        description
          "Threshold of the standard time offset.";
      }
    }
  }
  augment "/ncs:devices/ncs:device/ncs:notifications/ncs:received-notifications/ncs:notification/ncs:data" {
    container ptp-ring-fiber-length-change-resume {
      presence "";
      config false;
      description
        "The length change value of the ring-network optical fiber is determined.";
      leaf ifindex {
        type uint32;
        description
          "Index of the current port.";
      }
      leaf ifname {
        type string;
        description
          "Name of the current port.";
      }
      leaf change-value {
        type uint32;
        description
          "New time deviation value of the current port caused by the change of optical fiber length. (unit:ns)";
      }
      leaf value-flag {
        type clocksync-1588v2:ncs_rpc_notif_ptp-sign-flag;
        description
          "Sign of the new time deviation value.";
      }
    }
  }
  augment "/ncs:devices/ncs:device/ncs:notifications/ncs:received-notifications/ncs:notification/ncs:data" {
    container ptp-ring-fiber-length-change {
      presence "";
      config false;
      description
        "The optical fiber length of the ring-network is changed.";
      leaf ifindex {
        type uint32;
        description
          "Index of the current port.";
      }
      leaf ifname {
        type string;
        description
          "Name of the current port.";
      }
      leaf change-value {
        type uint32;
        description
          "New time deviation value of the current port caused by the change of optical fiber length. (unit:ns)";
      }
      leaf value-flag {
        type clocksync-1588v2:ncs_rpc_notif_ptp-sign-flag;
        description
          "Sign of the new time deviation value.";
      }
    }
  }
  augment "/ncs:devices/ncs:device/ncs:notifications/ncs:received-notifications/ncs:notification/ncs:data" {
    container ptp-port-non-support-resume {
      presence "";
      config false;
      description
        "The alarm that the hardware do not support PTP time synchronization is resumed.";
      leaf chassis-id {
        type uint32;
        description
          "Indicates the chassis ID.";
      }
      leaf ifindex {
        type uint32;
        description
          "Indicates the port index.";
      }
      leaf ifname {
        type string;
        description
          "Indicates the port name.";
      }
    }
  }
  augment "/ncs:devices/ncs:device/ncs:notifications/ncs:received-notifications/ncs:notification/ncs:data" {
    container ptp-port-non-support {
      presence "";
      config false;
      description
        "In current link mode, the hardware, such as boards and optical modules, do not support PTP time synchronization.";
      leaf chassis-id {
        type uint32;
        description
          "Indicates the chassis ID.";
      }
      leaf ifindex {
        type uint32;
        description
          "Indicates the port index.";
      }
      leaf ifname {
        type string;
        description
          "Indicates the port name.";
      }
    }
  }
  augment "/ncs:devices/ncs:device/ncs:notifications/ncs:received-notifications/ncs:notification/ncs:data" {
    container ptp-pkt-los-resume {
      presence "";
      config false;
      description
        "The ptp packet of the trace port is normal.";
      leaf pkt-type {
        type ncs_rpc_notif_ptp-packet-type;
        description
          "The packet type.";
      }
    }
  }
  augment "/ncs:devices/ncs:device/ncs:notifications/ncs:received-notifications/ncs:notification/ncs:data" {
    container ptp-pkt-los {
      presence "";
      config false;
      description
        "The ptp packet of the trace source is lost.";
      leaf pkt-type {
        type ncs_rpc_notif_ptp-packet-type;
        description
          "The packet type.";
      }
    }
  }
  augment "/ncs:devices/ncs:device/ncs:notifications/ncs:received-notifications/ncs:notification/ncs:data" {
    container ptp-passive-measure-overflow-resume {
      presence "";
      config false;
      description
        "The time offset of the passive port is normal.";
      leaf ifindex {
        type uint32;
        description
          "Index of the current port.";
      }
      leaf ifname {
        type string;
        description
          "Name of the current port.";
      }
      leaf change-value {
        type uint32;
        description
          "New time deviation value of the current port caused by the change of optical fiber length. (unit:ns)";
      }
      leaf value-flag {
        type clocksync-1588v2:ncs_rpc_notif_ptp-sign-flag;
        description
          "Sign of the new time deviation value of the current port.";
      }
      leaf threshold {
        type uint32;
        description
          "The time offset threshold configured on the Passive port.";
      }
    }
  }
  augment "/ncs:devices/ncs:device/ncs:notifications/ncs:received-notifications/ncs:notification/ncs:data" {
    container ptp-passive-measure-overflow {
      presence "";
      config false;
      description
        "The time offset of the passive port is abnormal.";
      leaf ifindex {
        type uint32;
        description
          "Index of the current port.";
      }
      leaf ifname {
        type string;
        description
          "Name of the current port.";
      }
      leaf change-value {
        type uint32;
        description
          "New time deviation value of the current port caused by the change of optical fiber length. (unit:ns)";
      }
      leaf value-flag {
        type clocksync-1588v2:ncs_rpc_notif_ptp-sign-flag;
        description
          "Sign of the new time deviation value.";
      }
      leaf threshold {
        type uint32;
        description
          "The time offset threshold configured on the Passive port.";
      }
    }
  }
  augment "/ncs:devices/ncs:device/ncs:notifications/ncs:received-notifications/ncs:notification/ncs:data" {
    container ptp-frequency-lock-resume {
      presence "";
      config false;
      description
        "Current lock status of clock frequency synchronization resumed.";
      leaf lock-status {
        type ncs_rpc_notif_clock-lock-state;
        description
          "Lock status of clock frequency.";
      }
    }
  }
  augment "/ncs:devices/ncs:device/ncs:notifications/ncs:received-notifications/ncs:notification/ncs:data" {
    container ptp-frequency-lock-fail {
      presence "";
      config false;
      description
        "Current lock status of clock frequency synchronization failed.";
      leaf lock-status {
        type ncs_rpc_notif_clock-lock-state;
        description
          "Lock status of clock frequency.";
      }
    }
  }
  augment "/ncs:devices/ncs:device/ncs:notifications/ncs:received-notifications/ncs:notification/ncs:data" {
    container ptp-ext-time-port-lost-resume {
      presence "";
      config false;
      description
        "The external Time Port status resumed.";
      leaf port-status {
        type ncs_rpc_notif_time-port-state;
        description
          "Port status of the external Time.";
      }
      leaf port-type {
        type ncs_rpc_notif_ext-time-port-type;
        description
          "Port type of the external Time.";
      }
    }
  }
  augment "/ncs:devices/ncs:device/ncs:notifications/ncs:received-notifications/ncs:notification/ncs:data" {
    container ptp-ext-time-port-lost {
      presence "";
      config false;
      description
        "The external Time Port status changed.";
      leaf port-status {
        type ncs_rpc_notif_time-port-state;
        description
          "Port status of the external Time.";
      }
      leaf port-type {
        type ncs_rpc_notif_ext-time-port-type;
        description
          "Port type of the external Time.";
      }
    }
  }
  augment "/ncs:devices/ncs:device/ncs:notifications/ncs:received-notifications/ncs:notification/ncs:data" {
    container ptp-acr-sync-bad-resume {
      presence "";
      config false;
      description
        "1588 ACR synchronization state resume at present.";
      leaf state {
        type ncs_rpc_notif_sync-state;
        description
          "State of synchoronization.";
      }
    }
  }
  augment "/ncs:devices/ncs:device/ncs:notifications/ncs:received-notifications/ncs:notification/ncs:data" {
    container ptp-acr-sync-bad {
      presence "";
      config false;
      description
        "1588 ACR synchronization state is bad.";
      leaf state {
        type ncs_rpc_notif_sync-state;
        description
          "State of synchoronization.";
      }
    }
  }
  augment "/ncs:devices/ncs:device/ncs:notifications/ncs:received-notifications/ncs:notification/ncs:data" {
    container clock-sync-bad-resume {
      presence "";
      config false;
      description
        "Clock frequency synchronization bad resume.";
      leaf chassis-id {
        type int32;
        description
          "The chassis ID.";
      }
    }
  }
  augment "/ncs:devices/ncs:device/ncs:notifications/ncs:received-notifications/ncs:notification/ncs:data" {
    container clock-sync-bad {
      presence "";
      config false;
      description
        "Clock frequency synchronization bad.";
      leaf chassis-id {
        type int32;
        description
          "The chassis ID.";
      }
    }
  }
  augment "/ncs:devices/ncs:device/ncs:notifications/ncs:received-notifications/ncs:notification/ncs:data" {
    container clock-ssm-pkt-los-resume {
      presence "";
      config false;
      description
        "The ssm packet of clock source is normal.";
      leaf source-name {
        type string {
          length "1..63";
        }
        description
          "Name of the current clock source.";
      }
    }
  }
  augment "/ncs:devices/ncs:device/ncs:notifications/ncs:received-notifications/ncs:notification/ncs:data" {
    container clock-ssm-pkt-los {
      presence "";
      config false;
      description
        "The ssm packet of clock source is lost.";
      leaf source-name {
        type string {
          length "1..63";
        }
        description
          "Name of the current clock source.";
      }
    }
  }
  augment "/ncs:devices/ncs:device/ncs:notifications/ncs:received-notifications/ncs:notification/ncs:data" {
    container clock-source-output-below-threshold-resume {
      presence "";
      config false;
      description
        "The SSM of output above threshold notification.";
      leaf attr-chassis-index {
        type uint32;
        description
          "Indicates the index of the chassis where the non-PTP clock source is located. In the case of a single chassis, the index is 1. For a chassis where a PTP clock source is located, the index is invalid.";
      }
      leaf chassis-id {
        type uint32;
        description
          "Chassis id of the clock source.";
      }
      leaf pll-id {
        type ncs_rpc_notif_clock-pll-id;
        description
          "Id of the clock source type. values: System(1), system PLL. sync2M-1(2), 2M PLL-1. sync2M-2(3), 2M PLL-2.";
      }
      leaf threshold {
        type clocksync-phy:ncs_rpc_notif_ssm-level;
        must "(../threshold='prc' or ../threshold='ssua' or ../threshold='ssub' or ../threshold='sec' or ../threshold='dnu')" {
          tailf:xpath-root 6;
        }
        description
          "Threshold of the external Clock output.";
      }
      leaf value {
        type clocksync-phy:ncs_rpc_notif_ssm-level;
        must "(../value='prc' or ../value='ssua' or ../value='ssub' or ../value='sec' or ../value='dnu')" {
          tailf:xpath-root 6;
        }
        description
          "SSM of the external Clock output.";
      }
      leaf source-name {
        type string {
          length "1..63";
        }
        description
          "Name of the curent clock source.";
      }
    }
  }
  augment "/ncs:devices/ncs:device/ncs:notifications/ncs:received-notifications/ncs:notification/ncs:data" {
    container clock-source-output-below-threshold {
      presence "";
      config false;
      description
        "The SSM of output below threshold notification.";
      leaf attr-chassis-index {
        type uint32;
        description
          "Indicates the index of the chassis where the non-PTP clock source is located. In the case of a single chassis, the index is 1. For a chassis where a PTP clock source is located, the index is invalid.";
      }
      leaf chassis-id {
        type uint32;
        description
          "Chassis id of the clock source.";
      }
      leaf pll-id {
        type ncs_rpc_notif_clock-pll-id;
        description
          "Id of the clock source type. values: System(1), system PLL. sync2M-1(2), 2M PLL-1. sync2M-2(3), 2M PLL-2.";
      }
      leaf threshold {
        type clocksync-phy:ncs_rpc_notif_ssm-level;
        must "(../threshold='prc' or ../threshold='ssua' or ../threshold='ssub' or ../threshold='sec' or ../threshold='dnu')" {
          tailf:xpath-root 6;
        }
        description
          "Threshold of the external Clock output.";
      }
      leaf value {
        type clocksync-phy:ncs_rpc_notif_ssm-level;
        must "(../value='prc' or ../value='ssua' or ../value='ssub' or ../value='sec' or ../value='dnu')" {
          tailf:xpath-root 6;
        }
        description
          "SSM of the external Clock output.";
      }
      leaf source-name {
        type string {
          length "1..63";
        }
        description
          "Name of the curent clock source.";
      }
    }
  }
  augment "/ncs:devices/ncs:device/ncs:notifications/ncs:received-notifications/ncs:notification/ncs:data" {
    container clock-source-input-below-threshold-resume {
      presence "";
      config false;
      description
        "The SSM of input above or equal threshold notification.";
      leaf chassis-id {
        type uint32;
        description
          "Chassis index of the clock source.";
      }
      leaf pll-id {
        type ncs_rpc_notif_clock-pll-id;
        description
          "Id of the clock source type..";
      }
      leaf threshold {
        type clocksync-phy:ncs_rpc_notif_ssm-level;
        must "(../threshold='prc' or ../threshold='ssua' or ../threshold='ssub' or ../threshold='sec' or ../threshold='dnu')" {
          tailf:xpath-root 6;
        }
        description
          "Threshold of the external clock source input.";
      }
      leaf attr-chassis-index {
        type uint32;
        description
          "Indicates the index of the chassis where the non-PTP clock source is located. In the case of a single chassis, the index is 1. For a chassis where a PTP clock source is located, the index is invalid.";
      }
      leaf ssm {
        type clocksync-phy:ncs_rpc_notif_ssm-level;
        description
          "SSM of the clock source.";
      }
      leaf chassis-index {
        type uint32;
        description
          "Chassis index of the clock source.";
      }
      leaf source-type-index {
        type ncs_rpc_notif_clock-src-type;
        description
          "Index of the clock source type.";
      }
      leaf source-index {
        type uint32;
        description
          "Index of the clock source.";
      }
    }
  }
  augment "/ncs:devices/ncs:device/ncs:notifications/ncs:received-notifications/ncs:notification/ncs:data" {
    container clock-source-input-below-threshold {
      presence "";
      config false;
      description
        "The SSM of input below threshold notification.";
      leaf chassis-id {
        type uint32;
        description
          "Chassis index of the clock source.";
      }
      leaf pll-id {
        type ncs_rpc_notif_clock-pll-id;
        description
          "Id of the clock source type.";
      }
      leaf threshold {
        type clocksync-phy:ncs_rpc_notif_ssm-level;
        must "(../threshold='prc' or ../threshold='ssua' or ../threshold='ssub' or ../threshold='sec' or ../threshold='dnu')" {
          tailf:xpath-root 6;
        }
        description
          "Threshold of the external clock source input.";
      }
      leaf attr-chassis-index {
        type uint32;
        description
          "Indicates the index of the chassis where the non-PTP clock source is located. In the case of a single chassis, the index is 1. For a chassis where a PTP clock source is located, the index is invalid.";
      }
      leaf ssm {
        type clocksync-phy:ncs_rpc_notif_ssm-level;
        description
          "SSM of the clock source.";
      }
      leaf chassis-index {
        type uint32;
        description
          "Chassis index of the clock source.";
      }
      leaf source-type-index {
        type ncs_rpc_notif_clock-src-type;
        description
          "Index of the clock source type.";
      }
      leaf source-index {
        type uint32;
        description
          "Index of the clock source.";
      }
    }
  }
  augment "/ncs:devices/ncs:device/ncs:notifications/ncs:received-notifications/ncs:notification/ncs:data" {
    container clock-source-freq-check-resume {
      presence "";
      config false;
      description
        "The check of frequence normal notification.";
      leaf chassis-index {
        type uint32;
        description
          "Indicates the index of the chassis where the non-PTP clock source is located. In the case of a single chassis, the index is 1. For a chassis where a PTP clock source is located, the index is invalid.";
      }
      leaf source-type-index {
        type ncs_rpc_notif_clock-src-type;
        description
          "Index of the clock source type.";
      }
      leaf source-index {
        type uint32;
        description
          "Index of the clock source.";
      }
      leaf chassis-id {
        type uint32;
        description
          "Chassis id.";
      }
      leaf result {
        type ncs_rpc_notif_fre-check-result;
        description
          "Result of the check of frequency.";
      }
      leaf source-descr {
        type string {
          length "1..63";
        }
        description
          "The description of clock source.";
      }
    }
  }
  augment "/ncs:devices/ncs:device/ncs:notifications/ncs:received-notifications/ncs:notification/ncs:data" {
    container clock-source-freq-check {
      presence "";
      config false;
      description
        "The check of frequence abnormal notification.";
      leaf chassis-index {
        type uint32;
        description
          "Indicates the index of the chassis where the non-PTP clock source is located. In the case of a single chassis, the index is 1. For a chassis where a PTP clock source is located, the index is invalid.";
      }
      leaf source-type-index {
        type ncs_rpc_notif_clock-src-type;
        description
          "Index of the clock source type.";
      }
      leaf source-index {
        type uint32;
        description
          "Index of the clock source.";
      }
      leaf chassis-id {
        type uint32;
        description
          "Chassis id.";
      }
      leaf result {
        type ncs_rpc_notif_fre-check-result;
        description
          "Result of the check of frequency.";
      }
      leaf source-descr {
        type string {
          length "1..63";
        }
        description
          "The description of clock source.";
      }
    }
  }
  augment "/ncs:devices/ncs:device/ncs:notifications/ncs:received-notifications/ncs:notification/ncs:data" {
    container clock-source-valid {
      presence "";
      config false;
      description
        "The state of clock source is normal.";
      leaf chassis-index {
        type uint32;
        description
          "Indicates the index of the chassis where the non-PTP clock source is located. In the case of a single chassis, the index is 1. For a chassis where a PTP clock source is located, the index is invalid.";
      }
      leaf source-type-index {
        type ncs_rpc_notif_clock-src-type;
        description
          "Index of the clock source type.";
      }
      leaf source-index {
        type uint32;
        description
          "Index of the clock source.";
      }
      leaf chassis-id {
        type uint32;
        description
          "Chassis id.";
      }
      leaf source-name {
        type string {
          length "1..63";
        }
        description
          "Name of the current clock source.";
      }
      leaf source-state {
        type ncs_rpc_notif_clock-src-state;
        description
          "The state of the current clock source.";
      }
    }
  }
  augment "/ncs:devices/ncs:device/ncs:notifications/ncs:received-notifications/ncs:notification/ncs:data" {
    container clock-source-failed {
      presence "";
      config false;
      description
        "The state of clock source is abnormal.";
      leaf chassis-index {
        type uint32;
        description
          "Indicates the index of the chassis where the non-PTP clock source is located. In the case of a single chassis, the index is 1. For a chassis where a PTP clock source is located, the index is invalid.";
      }
      leaf source-type-index {
        type ncs_rpc_notif_clock-src-type;
        description
          "Index of the clock source type.";
      }
      leaf source-index {
        type uint32;
        description
          "Index of the clock source.";
      }
      leaf chassis-id {
        type uint32;
        description
          "Chassis id.";
      }
      leaf source-name {
        type string {
          length "1..63";
        }
        description
          "Name of the current clock source.";
      }
      leaf source-state {
        type ncs_rpc_notif_clock-src-state;
        description
          "The state of the current clock source.";
      }
    }
  }
  augment "/ncs:devices/ncs:device/ncs:notifications/ncs:received-notifications/ncs:notification/ncs:data" {
    container clock-port-non-support-resume {
      presence "";
      config false;
      description
        "The alarm that the hardware do not support physical-layer clock synchronization is resumed.";
      leaf chassis-id {
        type uint32;
        description
          "The chassis ID.";
      }
      leaf ifindex {
        type uint32;
        description
          "Port index.";
      }
      leaf source-name {
        type string {
          length "1..63";
        }
        description
          "The current clock source name.";
      }
    }
  }
  augment "/ncs:devices/ncs:device/ncs:notifications/ncs:received-notifications/ncs:notification/ncs:data" {
    container clock-port-non-support {
      presence "";
      config false;
      description
        "In current link mode, the hardware, such as boards and optical modules, do not support physical-layer clock synchronization.";
      leaf chassis-id {
        type uint32;
        description
          "The chassis ID.";
      }
      leaf ifindex {
        type uint32;
        description
          "Port index.";
      }
      leaf source-name {
        type string {
          length "1..63";
        }
        description
          "The current clock source name.";
      }
    }
  }
  augment "/ncs:devices/ncs:device/ncs:notifications/ncs:received-notifications/ncs:notification/ncs:data" {
    container clock-in-locked-mode {
      presence "";
      config false;
      description
        "The work mode of system clock source resume.";
      leaf chassis-index {
        type uint32;
        description
          "Indicates the index of the chassis where the non-PTP clock source is located. In the case of a single chassis, the index is 1. For a chassis where a PTP clock source is located, the index is invalid.";
      }
      leaf chassis-id {
        type uint32;
        description
          "Chassis id of the clock source.";
      }
      leaf lock-mode {
        type ncs_rpc_notif_clock-lock-mode;
        description
          "Lock mode of system clock.";
      }
    }
  }
  augment "/ncs:devices/ncs:device/ncs:notifications/ncs:received-notifications/ncs:notification/ncs:data" {
    container clock-not-in-locked-mode {
      presence "";
      config false;
      description
        "The work mode of system clock source out trace.";
      leaf chassis-index {
        type uint32;
        description
          "Indicates the index of the chassis where the non-PTP clock source is located. In the case of a single chassis, the index is 1. For a chassis where a PTP clock source is located, the index is invalid.";
      }
      leaf chassis-id {
        type uint32;
        description
          "Chassis id of the clock source.";
      }
      leaf lock-mode {
        type ncs_rpc_notif_clock-lock-mode;
        description
          "Lock mode of system clock.";
      }
    }
  }
  augment "/ncs:devices/ncs:device/ncs:notifications/ncs:received-notifications/ncs:notification/ncs:data" {
    container clock-fm-switch-resume {
      presence "";
      config false;
      description
        "Clock select mode is automative.";
      leaf chassis-id {
        type uint32;
        description
          "Chassis id of the clock source.";
      }
      leaf pll-id {
        type ncs_rpc_notif_clock-pll-id;
        description
          "The id of pll.";
      }
    }
  }
  augment "/ncs:devices/ncs:device/ncs:notifications/ncs:received-notifications/ncs:notification/ncs:data" {
    container clock-fm-switch {
      presence "";
      config false;
      description
        "Clock select mode is force or manual.";
      leaf chassis-id {
        type uint32;
        description
          "Chassis id of the clock source.";
      }
      leaf pll-id {
        type ncs_rpc_notif_clock-pll-id;
        description
          "The id of pll.";
      }
    }
  }
  augment "/ncs:devices/ncs:device/ncs:notifications/ncs:received-notifications/ncs:notification/ncs:data" {
    container clock-cluster-topo-fail-resume {
      presence "";
      config false;
      description
        "Clock cluster inter-chassis synchronization topo compute successfully.";
      leaf sync-type {
        type ncs_rpc_notif_cluster-sync-type;
        description
          "Inter-chassis synchronization type.";
      }
      leaf topo-type {
        type ncs_rpc_notif_cluster-topo-type;
        description
          "Inter-chassis synchronization topo type.";
      }
      leaf topo-link-type {
        type ncs_rpc_notif_cluster-link-type;
        description
          "Inter-chassis synchronization link type.";
      }
      leaf topo-status {
        type ncs_rpc_notif_cluster-sync-topo-state;
        description
          "Inter-chassis synchronization topo status.";
      }
    }
  }
  augment "/ncs:devices/ncs:device/ncs:notifications/ncs:received-notifications/ncs:notification/ncs:data" {
    container clock-cluster-topo-fail {
      presence "";
      config false;
      description
        "Clock cluster inter-chassis synchronization topo compute failed.";
      leaf sync-type {
        type ncs_rpc_notif_cluster-sync-type;
        description
          "Inter-chassis synchronization type.";
      }
      leaf topo-type {
        type ncs_rpc_notif_cluster-topo-type;
        description
          "Inter-chassis synchronization topo type.";
      }
      leaf topo-link-type {
        type ncs_rpc_notif_cluster-link-type;
        description
          "Inter-chassis synchronization link type.";
      }
      leaf topo-status {
        type ncs_rpc_notif_cluster-sync-topo-state;
        description
          "Inter-chassis synchronization topo status.";
      }
    }
  }
  augment "/ncs:devices/ncs:device/ncs:notifications/ncs:received-notifications/ncs:notification/ncs:data" {
    container clock-ces-acr-lock-fail-resume {
      presence "";
      config false;
      description
        "The clock source of CES ACR is in locked mode.";
      leaf slot {
        type uint32;
        description
          "Slot id of the clock source.";
      }
      leaf card {
        type uint32;
        description
          "Card id of the clock source.";
      }
      leaf domain {
        type uint32;
        description
          "Recovery domain of the clock source.";
      }
      leaf lock-state {
        type ncs_rpc_notif_clock-lock-state;
        description
          "Lock state of the clock source.";
      }
    }
  }
  augment "/ncs:devices/ncs:device/ncs:notifications/ncs:received-notifications/ncs:notification/ncs:data" {
    container clock-ces-acr-lock-fail {
      presence "";
      config false;
      description
        "The clock source of CES ACR is not in locked mode.";
      leaf slot {
        type uint32;
        description
          "Slot id of the clock source.";
      }
      leaf card {
        type uint32;
        description
          "Card id of the clock source.";
      }
      leaf domain {
        type uint32;
        description
          "Recovery domain of the clock source.";
      }
      leaf lock-state {
        type ncs_rpc_notif_clock-lock-state;
        description
          "Lock state of the clock source.";
      }
    }
  }
  augment "/ncs:devices/ncs:device/ncs:netconf-notifications/ncs:received-notifications/ncs:notification/ncs:data" {
    container ptp-pdv-limit-exceed {
      presence "";
      config false;
      description
        "The value of State can be: normal(0), indicating that 1588 ACR/ATR PDV data performance is normal. limitExceed(1), indicating that 1588 ACR/ATR PDV data performance exceeds the threshold.";
      leaf state {
        type uint32;
        description
          "1588 ACR/ATR PDV data threshold-crossing event occurred.";
      }
    }
  }
  augment "/ncs:devices/ncs:device/ncs:netconf-notifications/ncs:received-notifications/ncs:notification/ncs:data" {
    container ptp-adaptive-trace-source-change {
      presence "";
      config false;
      description
        "The clock source traced by the client changed.";
      leaf old-trace-source {
        type ncs_rpc_notif_ptpa-sync-server-src;
        description
          "Historical clock source that the client has traced.";
      }
      leaf trace-source {
        type ncs_rpc_notif_ptpa-sync-server-src;
        description
          "Current clock source that the client is synchroniazation.";
      }
    }
  }
  augment "/ncs:devices/ncs:device/ncs:netconf-notifications/ncs:received-notifications/ncs:notification/ncs:data" {
    container ptp-adaptive-nego-info-change {
      presence "";
      config false;
      description
        "The negotiation status of the client with server 1 and with server 2 changed.";
      leaf server-id {
        type ncs_rpc_notif_ptpa-server-id;
        description
          "Indicates the server ID.";
      }
      leaf nego-state {
        type ncs_rpc_notif_ptpa-nego-state;
        description
          "Indicates the negotiation status of the client with server.";
      }
      leaf error-reason {
        type ncs_rpc_notif_ptpa-nego-fail-reason;
        description
          "Indicates causes of the negotiation failure.";
      }
    }
  }
  augment "/ncs:devices/ncs:device/ncs:netconf-notifications/ncs:received-notifications/ncs:notification/ncs:data" {
    container ptp-adaptive-client-list-change {
      presence "";
      config false;
      description
        "The status of the client list was refreshed.";
      leaf client-ip-list {
        type inet:ipv4-address-no-zone;
        description
          "Indicates the IP address of the client.";
      }
      leaf client-ip-change-flag {
        type ncs_rpc_notif_ptpa-client-state;
        description
          "Indicate the client status.";
      }
      leaf client-index {
        type uint32;
        description
          "Indicates the Index of the client.";
      }
      leaf client-id {
        type uint32;
        description
          "Indicates the ID of the client.";
      }
    }
  }
  augment "/ncs:devices/ncs:device/ncs:netconf-notifications/ncs:received-notifications/ncs:notification/ncs:data" {
    container ptp-port-state-change {
      presence "";
      config false;
      description
        "The alarm was generated when the interface status changed.";
      leaf ifindex {
        type int32;
        description
          "Interface index.";
      }
      leaf ifname {
        type string;
        description
          "Name of the port whose state has changed.";
      }
      leaf port-state {
        type ncs_rpc_notif_ptp-port-status;
        description
          "Current status of the interface.";
      }
      leaf old-port-state {
        type ncs_rpc_notif_ptp-port-status;
        description
          "Old status of the interface.";
      }
    }
  }
  augment "/ncs:devices/ncs:device/ncs:netconf-notifications/ncs:received-notifications/ncs:notification/ncs:data" {
    container ptp-port-bmc-info-change {
      presence "";
      config false;
      description
        "The PTP port clock source information is changed. The clock source ID, clock source port number, or clock source's hop count received on a port was changed.";
      leaf ifindex {
        type int32;
        description
          "Port index.";
      }
      leaf ifname {
        type string;
        description
          "Port name.";
      }
      leaf clock-id {
        type string {
          length "16";
        }
        description
          "Clock source ID received on a port.";
      }
      leaf port-num {
        type int32;
        description
          "Clock source port number received on a port.";
      }
      leaf steps {
        type int32;
        description
          "Clock source's hop count received on a port.";
      }
      leaf master-clock-id {
        type string {
          length "16";
        }
        description
          "ID of the current master clock source.";
      }
    }
  }
  augment "/ncs:devices/ncs:device/ncs:netconf-notifications/ncs:received-notifications/ncs:notification/ncs:data" {
    container ptp-passive-fiber-length-change {
      presence "";
      config false;
      description
        "The optical fiber length on the Passive port was changed.";
      leaf ifindex {
        type int32;
        description
          "Index of the current port.";
      }
      leaf ifname {
        type string;
        description
          "Name of the current port.";
      }
      leaf change-value {
        type int32;
        description
          "New time offset caused by the fiber length change of the current port.";
      }
      leaf value-flag {
        type clocksync-1588v2:ncs_rpc_notif_ptp-sign-flag;
        description
          "Positive or negative sign of the new time offset.";
      }
    }
  }
  augment "/ncs:devices/ncs:device/ncs:netconf-notifications/ncs:received-notifications/ncs:notification/ncs:data" {
    container ptp-clock-source-change {
      presence "";
      config false;
      description
        "This trap was generated when the clock source changed.";
      leaf old-clock-id {
        type string {
          length "16";
        }
        description
          "Indicates the ID of the old master clock.";
      }
      leaf clock-id {
        type string {
          length "16";
        }
        description
          "Indicates the ID of the current master clock.";
      }
      leaf ifindex {
        type uint32;
        description
          "Indicates the port index of the current clock source.";
      }
      leaf old-port-num {
        type int32;
        description
          "Indicates the port number of the original clock source.";
      }
      leaf port-num {
        type int32;
        description
          "Indicates the port number of the current clock source.";
      }
      leaf old-ifname {
        type string;
        description
          "Indicates the port name of the original clock source.";
      }
      leaf ifname {
        type string;
        description
          "Indicates the port name of the current clock source.";
      }
    }
  }
  augment "/ncs:devices/ncs:device/ncs:netconf-notifications/ncs:received-notifications/ncs:notification/ncs:data" {
    container ptp-adaptive-ptsf-state-change {
      presence "";
      config false;
      description
        "The PTSF status of PTP adaptive clock synchronization is changed.";
      leaf server-index {
        type int32;
        description
          "Server index for the PTSF status change.";
      }
      leaf ptsf-type {
        type ncs_rpc_notif_ptpa-ptsf-type;
        description
          "PTSF type.";
      }
      leaf ptsf-state {
        type ncs_rpc_notif_ptpa-ptsf-state;
        description
          "New PTSF status.";
      }
    }
  }
  augment "/ncs:devices/ncs:device/ncs:netconf-notifications/ncs:received-notifications/ncs:notification/ncs:data" {
    container clock-source-switch {
      presence "";
      config false;
      description
        "The working mode of the system clock changed.";
      leaf chassis-id {
        type int32;
        description
          "Indicates the ID of the chassis where the clock source resides, The value is 1 in single chassis scenarios.";
      }
      leaf pll-id {
        type ncs_rpc_notif_clock-pll-id;
        description
          "Indicates the clock source type ID.";
      }
      leaf old-source-name {
        type string {
          length "1..63";
        }
        description
          "Indicates the last clock source name.";
      }
      leaf source-name {
        type string {
          length "1..63";
        }
        description
          "Indicates the current clock source name.";
      }
      leaf chassis-index {
        type int32;
        description
          "Indicates the index of the chassis where the clock source resides,.The value is 1 in single chassis scenarios.";
      }
      leaf src-type {
        type ncs_rpc_notif_clock-pll-id;
        description
          "Indicates the type of clock source selection.";
      }
      leaf src-mode {
        type clocksync-phy:ncs_rpc_notif_source-selection-mode;
        description
          "Indicates the mode of clock source selection.";
      }
    }
  }
  augment "/ncs:devices/ncs:device/ncs:netconf-notifications/ncs:received-notifications/ncs:notification/ncs:data" {
    container clock-source-ssm-change {
      presence "";
      config false;
      description
        "The SSM level of the clock source was changed.";
      leaf chassis-id {
        type uint32;
        description
          "Chassis ID. The value is 1 in single chassis scenarios.";
      }
      leaf source-name {
        type string {
          length "1..63";
        }
        description
          "Name of the current clock source.";
      }
      leaf old-ssm {
        type ncs_rpc_notif_clock-ssm-level;
        description
          "SSM level before the change.";
      }
      leaf ssm {
        type ncs_rpc_notif_clock-ssm-level;
        description
          "Current SSM level.";
      }
    }
  }
  augment "/ncs:devices/ncs:device/ncs:netconf-notifications/ncs:received-notifications/ncs:notification/ncs:data" {
    container clock-gnss-model-change {
      presence "";
      config false;
      description
        "Gnss model change notification.";
      leaf ifindex {
        type int32;
        description
          "Specifies the index of the port on which the working mode is changed.";
      }
      leaf ifname {
        type string;
        description
          "Specifies the name of the port on which the working mode is changed.";
      }
      leaf model {
        type ncs_rpc_notif_gnss-model-type;
        must "(../model='gps' or ../model='glonass' or ../model='beidou' or ../model='gps-glonass' or ../model='gps-beidou')" {
          tailf:xpath-root 6;
        }
        description
          "Specifies the new working mode.";
      }
      leaf old-model {
        type ncs_rpc_notif_gnss-model-type;
        must "(../old-model='gps' or ../old-model='glonass' or ../old-model='beidou' or ../old-model='gps-glonass' or ../old-model='gps-beidou')" {
          tailf:xpath-root 6;
        }
        description
          "Specifies the old working mode.";
      }
    }
  }
  augment "/ncs:devices/ncs:device/ncs:netconf-notifications/ncs:received-notifications/ncs:notification/ncs:data" {
    container clock-source-sys-clk-lock-mode-change {
      presence "";
      config false;
      description
        "The working mode of the system clock changed.";
      leaf chassis-id {
        type int32;
        description
          "Indicates the ID of the chassis where the clock source resides, The index is always 1 for a single chassis.";
      }
      leaf old-lock-mode {
        type uint32 {
          range "0..3";
        }
        description
          "Indicates the old lock mode of the clock source.";
      }
      leaf attr-chassis-index {
        type int32;
        description
          "Index of the chassis where the clock source is located. In the case of a single chassis, the index is 1.";
      }
      leaf lock-mode {
        type ncs_rpc_notif_clock-lock-mode;
        description
          "Indicates the lock mode of the system clock.";
      }
    }
  }
  augment "/ncs:devices/ncs:device/ncs:netconf-notifications/ncs:received-notifications/ncs:notification/ncs:data" {
    container clock-source-state-change {
      presence "";
      config false;
      description
        "The status of the clock source changed.";
      leaf chassis-id {
        type int32;
        description
          "Chassis ID. In the case of a single chassis, the value is 1.";
      }
      leaf source-name {
        type string {
          length "1..63";
        }
        description
          "Name of the current clock source.";
      }
      leaf old-source-state {
        type ncs_rpc_notif_clock-src-state;
        description
          "Clock source state before the change.";
      }
      leaf chassis-index {
        type int32;
        description
          "Index of the chassis where the clock source is located. In the case of a single chassis, the index is 1.";
      }
      leaf source-type-index {
        type ncs_rpc_notif_clock-src-type;
        description
          "Index of the interface type.";
      }
      leaf source-index {
        type uint32;
        description
          "Index of the clock source.";
      }
      leaf source-state {
        type ncs_rpc_notif_clock-src-state;
        description
          "Status of the current clock source.";
      }
    }
  }
  augment "/ncs:devices/ncs:device/ncs:netconf-notifications/ncs:received-notifications/ncs:notification/ncs:data" {
    container clock-ces-acr-master-pw-change {
      presence "";
      config false;
      description
        "The master PW in the CES ACR clock domain changed.";
      leaf slot {
        type uint32;
        description
          "Slot ID of the clock source.";
      }
      leaf card {
        type uint32;
        description
          "Card ID of the clock source.";
      }
      leaf domain {
        type uint32;
        description
          "Clock source recovery domain.";
      }
      leaf old-pw-name {
        type string {
          length "1..63";
        }
        description
          "Name of the old master PW of CES ACR clock source.";
      }
      leaf pw-name {
        type string {
          length "1..63";
        }
        description
          "Name of the new master PW of CES ACR clock source.";
      }
    }
  }
  augment "/ncs:devices/ncs:device/ncs:netconf-notifications/ncs:received-notifications/ncs:notification/ncs:data" {
    container ptp-time-sync-resume {
      presence "";
      config false;
      description
        "Time source traced status is normal.";
      leaf sync-status {
        type ncs_rpc_notif_clock-sync-state;
        description
          "Indicate that the status of the equipment is synchronization or unsynchoronization.";
      }
    }
  }
  augment "/ncs:devices/ncs:device/ncs:netconf-notifications/ncs:received-notifications/ncs:notification/ncs:data" {
    container ptp-time-sync-faulty {
      presence "";
      config false;
      description
        "Time source traced status is faulty.";
      leaf sync-status {
        type ncs_rpc_notif_clock-sync-state;
        description
          "Indicate that the status of the equipment is synchronization or unsynchoronization.";
      }
    }
  }
  augment "/ncs:devices/ncs:device/ncs:netconf-notifications/ncs:received-notifications/ncs:notification/ncs:data" {
    container ptp-time-offset-sum-over-resume {
      presence "";
      config false;
      description
        "The ptp time offset sum is normal.";
      leaf offset-sum {
        type uint32;
        description
          "Accumulated and peak time offset values.";
      }
      leaf threshold {
        type uint32;
        description
          "Threshold of the sum of time offset.";
      }
    }
  }
  augment "/ncs:devices/ncs:device/ncs:netconf-notifications/ncs:received-notifications/ncs:notification/ncs:data" {
    container ptp-time-offset-sum-over {
      presence "";
      config false;
      description
        "The ptp time offset sum is abnormal.";
      leaf offset-sum {
        type uint32;
        description
          "Accumulated and peak time offset values.";
      }
      leaf threshold {
        type uint32;
        description
          "Threshold of the sum of time offset.";
      }
    }
  }
  augment "/ncs:devices/ncs:device/ncs:netconf-notifications/ncs:received-notifications/ncs:notification/ncs:data" {
    container ptp-time-lock-fail-resume {
      presence "";
      config false;
      description
        "Time lock is resumed at present.";
      leaf lock-status {
        type ncs_rpc_notif_clock-lock-state;
        description
          "Time lock status.";
      }
    }
  }
  augment "/ncs:devices/ncs:device/ncs:netconf-notifications/ncs:received-notifications/ncs:notification/ncs:data" {
    container ptp-time-lock-fail {
      presence "";
      config false;
      description
        "The time lock status is failed.";
      leaf lock-status {
        type ncs_rpc_notif_clock-lock-state;
        description
          "Time lock status.";
      }
    }
  }
  augment "/ncs:devices/ncs:device/ncs:netconf-notifications/ncs:received-notifications/ncs:notification/ncs:data" {
    container ptp-standard-time-offset-over-resume {
      presence "";
      config false;
      description
        "The ptp standard time offset is normal.";
      leaf offset {
        type uint32;
        description
          "The standard time offset.";
      }
      leaf threshold {
        type uint32;
        description
          "Threshold of the standard time offset.";
      }
    }
  }
  augment "/ncs:devices/ncs:device/ncs:netconf-notifications/ncs:received-notifications/ncs:notification/ncs:data" {
    container ptp-standard-time-offset-over {
      presence "";
      config false;
      description
        "The ptp standard time offset is abnormal.";
      leaf offset {
        type uint32;
        description
          "The standard time offset.";
      }
      leaf threshold {
        type uint32;
        description
          "Threshold of the standard time offset.";
      }
    }
  }
  augment "/ncs:devices/ncs:device/ncs:netconf-notifications/ncs:received-notifications/ncs:notification/ncs:data" {
    container ptp-ring-fiber-length-change-resume {
      presence "";
      config false;
      description
        "The length change value of the ring-network optical fiber is determined.";
      leaf ifindex {
        type uint32;
        description
          "Index of the current port.";
      }
      leaf ifname {
        type string;
        description
          "Name of the current port.";
      }
      leaf change-value {
        type uint32;
        description
          "New time deviation value of the current port caused by the change of optical fiber length. (unit:ns)";
      }
      leaf value-flag {
        type clocksync-1588v2:ncs_rpc_notif_ptp-sign-flag;
        description
          "Sign of the new time deviation value.";
      }
    }
  }
  augment "/ncs:devices/ncs:device/ncs:netconf-notifications/ncs:received-notifications/ncs:notification/ncs:data" {
    container ptp-ring-fiber-length-change {
      presence "";
      config false;
      description
        "The optical fiber length of the ring-network is changed.";
      leaf ifindex {
        type uint32;
        description
          "Index of the current port.";
      }
      leaf ifname {
        type string;
        description
          "Name of the current port.";
      }
      leaf change-value {
        type uint32;
        description
          "New time deviation value of the current port caused by the change of optical fiber length. (unit:ns)";
      }
      leaf value-flag {
        type clocksync-1588v2:ncs_rpc_notif_ptp-sign-flag;
        description
          "Sign of the new time deviation value.";
      }
    }
  }
  augment "/ncs:devices/ncs:device/ncs:netconf-notifications/ncs:received-notifications/ncs:notification/ncs:data" {
    container ptp-port-non-support-resume {
      presence "";
      config false;
      description
        "The alarm that the hardware do not support PTP time synchronization is resumed.";
      leaf chassis-id {
        type uint32;
        description
          "Indicates the chassis ID.";
      }
      leaf ifindex {
        type uint32;
        description
          "Indicates the port index.";
      }
      leaf ifname {
        type string;
        description
          "Indicates the port name.";
      }
    }
  }
  augment "/ncs:devices/ncs:device/ncs:netconf-notifications/ncs:received-notifications/ncs:notification/ncs:data" {
    container ptp-port-non-support {
      presence "";
      config false;
      description
        "In current link mode, the hardware, such as boards and optical modules, do not support PTP time synchronization.";
      leaf chassis-id {
        type uint32;
        description
          "Indicates the chassis ID.";
      }
      leaf ifindex {
        type uint32;
        description
          "Indicates the port index.";
      }
      leaf ifname {
        type string;
        description
          "Indicates the port name.";
      }
    }
  }
  augment "/ncs:devices/ncs:device/ncs:netconf-notifications/ncs:received-notifications/ncs:notification/ncs:data" {
    container ptp-pkt-los-resume {
      presence "";
      config false;
      description
        "The ptp packet of the trace port is normal.";
      leaf pkt-type {
        type ncs_rpc_notif_ptp-packet-type;
        description
          "The packet type.";
      }
    }
  }
  augment "/ncs:devices/ncs:device/ncs:netconf-notifications/ncs:received-notifications/ncs:notification/ncs:data" {
    container ptp-pkt-los {
      presence "";
      config false;
      description
        "The ptp packet of the trace source is lost.";
      leaf pkt-type {
        type ncs_rpc_notif_ptp-packet-type;
        description
          "The packet type.";
      }
    }
  }
  augment "/ncs:devices/ncs:device/ncs:netconf-notifications/ncs:received-notifications/ncs:notification/ncs:data" {
    container ptp-passive-measure-overflow-resume {
      presence "";
      config false;
      description
        "The time offset of the passive port is normal.";
      leaf ifindex {
        type uint32;
        description
          "Index of the current port.";
      }
      leaf ifname {
        type string;
        description
          "Name of the current port.";
      }
      leaf change-value {
        type uint32;
        description
          "New time deviation value of the current port caused by the change of optical fiber length. (unit:ns)";
      }
      leaf value-flag {
        type clocksync-1588v2:ncs_rpc_notif_ptp-sign-flag;
        description
          "Sign of the new time deviation value of the current port.";
      }
      leaf threshold {
        type uint32;
        description
          "The time offset threshold configured on the Passive port.";
      }
    }
  }
  augment "/ncs:devices/ncs:device/ncs:netconf-notifications/ncs:received-notifications/ncs:notification/ncs:data" {
    container ptp-passive-measure-overflow {
      presence "";
      config false;
      description
        "The time offset of the passive port is abnormal.";
      leaf ifindex {
        type uint32;
        description
          "Index of the current port.";
      }
      leaf ifname {
        type string;
        description
          "Name of the current port.";
      }
      leaf change-value {
        type uint32;
        description
          "New time deviation value of the current port caused by the change of optical fiber length. (unit:ns)";
      }
      leaf value-flag {
        type clocksync-1588v2:ncs_rpc_notif_ptp-sign-flag;
        description
          "Sign of the new time deviation value.";
      }
      leaf threshold {
        type uint32;
        description
          "The time offset threshold configured on the Passive port.";
      }
    }
  }
  augment "/ncs:devices/ncs:device/ncs:netconf-notifications/ncs:received-notifications/ncs:notification/ncs:data" {
    container ptp-frequency-lock-resume {
      presence "";
      config false;
      description
        "Current lock status of clock frequency synchronization resumed.";
      leaf lock-status {
        type ncs_rpc_notif_clock-lock-state;
        description
          "Lock status of clock frequency.";
      }
    }
  }
  augment "/ncs:devices/ncs:device/ncs:netconf-notifications/ncs:received-notifications/ncs:notification/ncs:data" {
    container ptp-frequency-lock-fail {
      presence "";
      config false;
      description
        "Current lock status of clock frequency synchronization failed.";
      leaf lock-status {
        type ncs_rpc_notif_clock-lock-state;
        description
          "Lock status of clock frequency.";
      }
    }
  }
  augment "/ncs:devices/ncs:device/ncs:netconf-notifications/ncs:received-notifications/ncs:notification/ncs:data" {
    container ptp-ext-time-port-lost-resume {
      presence "";
      config false;
      description
        "The external Time Port status resumed.";
      leaf port-status {
        type ncs_rpc_notif_time-port-state;
        description
          "Port status of the external Time.";
      }
      leaf port-type {
        type ncs_rpc_notif_ext-time-port-type;
        description
          "Port type of the external Time.";
      }
    }
  }
  augment "/ncs:devices/ncs:device/ncs:netconf-notifications/ncs:received-notifications/ncs:notification/ncs:data" {
    container ptp-ext-time-port-lost {
      presence "";
      config false;
      description
        "The external Time Port status changed.";
      leaf port-status {
        type ncs_rpc_notif_time-port-state;
        description
          "Port status of the external Time.";
      }
      leaf port-type {
        type ncs_rpc_notif_ext-time-port-type;
        description
          "Port type of the external Time.";
      }
    }
  }
  augment "/ncs:devices/ncs:device/ncs:netconf-notifications/ncs:received-notifications/ncs:notification/ncs:data" {
    container ptp-acr-sync-bad-resume {
      presence "";
      config false;
      description
        "1588 ACR synchronization state resume at present.";
      leaf state {
        type ncs_rpc_notif_sync-state;
        description
          "State of synchoronization.";
      }
    }
  }
  augment "/ncs:devices/ncs:device/ncs:netconf-notifications/ncs:received-notifications/ncs:notification/ncs:data" {
    container ptp-acr-sync-bad {
      presence "";
      config false;
      description
        "1588 ACR synchronization state is bad.";
      leaf state {
        type ncs_rpc_notif_sync-state;
        description
          "State of synchoronization.";
      }
    }
  }
  augment "/ncs:devices/ncs:device/ncs:netconf-notifications/ncs:received-notifications/ncs:notification/ncs:data" {
    container clock-sync-bad-resume {
      presence "";
      config false;
      description
        "Clock frequency synchronization bad resume.";
      leaf chassis-id {
        type int32;
        description
          "The chassis ID.";
      }
    }
  }
  augment "/ncs:devices/ncs:device/ncs:netconf-notifications/ncs:received-notifications/ncs:notification/ncs:data" {
    container clock-sync-bad {
      presence "";
      config false;
      description
        "Clock frequency synchronization bad.";
      leaf chassis-id {
        type int32;
        description
          "The chassis ID.";
      }
    }
  }
  augment "/ncs:devices/ncs:device/ncs:netconf-notifications/ncs:received-notifications/ncs:notification/ncs:data" {
    container clock-ssm-pkt-los-resume {
      presence "";
      config false;
      description
        "The ssm packet of clock source is normal.";
      leaf source-name {
        type string {
          length "1..63";
        }
        description
          "Name of the current clock source.";
      }
    }
  }
  augment "/ncs:devices/ncs:device/ncs:netconf-notifications/ncs:received-notifications/ncs:notification/ncs:data" {
    container clock-ssm-pkt-los {
      presence "";
      config false;
      description
        "The ssm packet of clock source is lost.";
      leaf source-name {
        type string {
          length "1..63";
        }
        description
          "Name of the current clock source.";
      }
    }
  }
  augment "/ncs:devices/ncs:device/ncs:netconf-notifications/ncs:received-notifications/ncs:notification/ncs:data" {
    container clock-source-output-below-threshold-resume {
      presence "";
      config false;
      description
        "The SSM of output above threshold notification.";
      leaf attr-chassis-index {
        type uint32;
        description
          "Indicates the index of the chassis where the non-PTP clock source is located. In the case of a single chassis, the index is 1. For a chassis where a PTP clock source is located, the index is invalid.";
      }
      leaf chassis-id {
        type uint32;
        description
          "Chassis id of the clock source.";
      }
      leaf pll-id {
        type ncs_rpc_notif_clock-pll-id;
        description
          "Id of the clock source type. values: System(1), system PLL. sync2M-1(2), 2M PLL-1. sync2M-2(3), 2M PLL-2.";
      }
      leaf threshold {
        type clocksync-phy:ncs_rpc_notif_ssm-level;
        must "(../threshold='prc' or ../threshold='ssua' or ../threshold='ssub' or ../threshold='sec' or ../threshold='dnu')" {
          tailf:xpath-root 6;
        }
        description
          "Threshold of the external Clock output.";
      }
      leaf value {
        type clocksync-phy:ncs_rpc_notif_ssm-level;
        must "(../value='prc' or ../value='ssua' or ../value='ssub' or ../value='sec' or ../value='dnu')" {
          tailf:xpath-root 6;
        }
        description
          "SSM of the external Clock output.";
      }
      leaf source-name {
        type string {
          length "1..63";
        }
        description
          "Name of the curent clock source.";
      }
    }
  }
  augment "/ncs:devices/ncs:device/ncs:netconf-notifications/ncs:received-notifications/ncs:notification/ncs:data" {
    container clock-source-output-below-threshold {
      presence "";
      config false;
      description
        "The SSM of output below threshold notification.";
      leaf attr-chassis-index {
        type uint32;
        description
          "Indicates the index of the chassis where the non-PTP clock source is located. In the case of a single chassis, the index is 1. For a chassis where a PTP clock source is located, the index is invalid.";
      }
      leaf chassis-id {
        type uint32;
        description
          "Chassis id of the clock source.";
      }
      leaf pll-id {
        type ncs_rpc_notif_clock-pll-id;
        description
          "Id of the clock source type. values: System(1), system PLL. sync2M-1(2), 2M PLL-1. sync2M-2(3), 2M PLL-2.";
      }
      leaf threshold {
        type clocksync-phy:ncs_rpc_notif_ssm-level;
        must "(../threshold='prc' or ../threshold='ssua' or ../threshold='ssub' or ../threshold='sec' or ../threshold='dnu')" {
          tailf:xpath-root 6;
        }
        description
          "Threshold of the external Clock output.";
      }
      leaf value {
        type clocksync-phy:ncs_rpc_notif_ssm-level;
        must "(../value='prc' or ../value='ssua' or ../value='ssub' or ../value='sec' or ../value='dnu')" {
          tailf:xpath-root 6;
        }
        description
          "SSM of the external Clock output.";
      }
      leaf source-name {
        type string {
          length "1..63";
        }
        description
          "Name of the curent clock source.";
      }
    }
  }
  augment "/ncs:devices/ncs:device/ncs:netconf-notifications/ncs:received-notifications/ncs:notification/ncs:data" {
    container clock-source-input-below-threshold-resume {
      presence "";
      config false;
      description
        "The SSM of input above or equal threshold notification.";
      leaf chassis-id {
        type uint32;
        description
          "Chassis index of the clock source.";
      }
      leaf pll-id {
        type ncs_rpc_notif_clock-pll-id;
        description
          "Id of the clock source type..";
      }
      leaf threshold {
        type clocksync-phy:ncs_rpc_notif_ssm-level;
        must "(../threshold='prc' or ../threshold='ssua' or ../threshold='ssub' or ../threshold='sec' or ../threshold='dnu')" {
          tailf:xpath-root 6;
        }
        description
          "Threshold of the external clock source input.";
      }
      leaf attr-chassis-index {
        type uint32;
        description
          "Indicates the index of the chassis where the non-PTP clock source is located. In the case of a single chassis, the index is 1. For a chassis where a PTP clock source is located, the index is invalid.";
      }
      leaf ssm {
        type clocksync-phy:ncs_rpc_notif_ssm-level;
        description
          "SSM of the clock source.";
      }
      leaf chassis-index {
        type uint32;
        description
          "Chassis index of the clock source.";
      }
      leaf source-type-index {
        type ncs_rpc_notif_clock-src-type;
        description
          "Index of the clock source type.";
      }
      leaf source-index {
        type uint32;
        description
          "Index of the clock source.";
      }
    }
  }
  augment "/ncs:devices/ncs:device/ncs:netconf-notifications/ncs:received-notifications/ncs:notification/ncs:data" {
    container clock-source-input-below-threshold {
      presence "";
      config false;
      description
        "The SSM of input below threshold notification.";
      leaf chassis-id {
        type uint32;
        description
          "Chassis index of the clock source.";
      }
      leaf pll-id {
        type ncs_rpc_notif_clock-pll-id;
        description
          "Id of the clock source type.";
      }
      leaf threshold {
        type clocksync-phy:ncs_rpc_notif_ssm-level;
        must "(../threshold='prc' or ../threshold='ssua' or ../threshold='ssub' or ../threshold='sec' or ../threshold='dnu')" {
          tailf:xpath-root 6;
        }
        description
          "Threshold of the external clock source input.";
      }
      leaf attr-chassis-index {
        type uint32;
        description
          "Indicates the index of the chassis where the non-PTP clock source is located. In the case of a single chassis, the index is 1. For a chassis where a PTP clock source is located, the index is invalid.";
      }
      leaf ssm {
        type clocksync-phy:ncs_rpc_notif_ssm-level;
        description
          "SSM of the clock source.";
      }
      leaf chassis-index {
        type uint32;
        description
          "Chassis index of the clock source.";
      }
      leaf source-type-index {
        type ncs_rpc_notif_clock-src-type;
        description
          "Index of the clock source type.";
      }
      leaf source-index {
        type uint32;
        description
          "Index of the clock source.";
      }
    }
  }
  augment "/ncs:devices/ncs:device/ncs:netconf-notifications/ncs:received-notifications/ncs:notification/ncs:data" {
    container clock-source-freq-check-resume {
      presence "";
      config false;
      description
        "The check of frequence normal notification.";
      leaf chassis-index {
        type uint32;
        description
          "Indicates the index of the chassis where the non-PTP clock source is located. In the case of a single chassis, the index is 1. For a chassis where a PTP clock source is located, the index is invalid.";
      }
      leaf source-type-index {
        type ncs_rpc_notif_clock-src-type;
        description
          "Index of the clock source type.";
      }
      leaf source-index {
        type uint32;
        description
          "Index of the clock source.";
      }
      leaf chassis-id {
        type uint32;
        description
          "Chassis id.";
      }
      leaf result {
        type ncs_rpc_notif_fre-check-result;
        description
          "Result of the check of frequency.";
      }
      leaf source-descr {
        type string {
          length "1..63";
        }
        description
          "The description of clock source.";
      }
    }
  }
  augment "/ncs:devices/ncs:device/ncs:netconf-notifications/ncs:received-notifications/ncs:notification/ncs:data" {
    container clock-source-freq-check {
      presence "";
      config false;
      description
        "The check of frequence abnormal notification.";
      leaf chassis-index {
        type uint32;
        description
          "Indicates the index of the chassis where the non-PTP clock source is located. In the case of a single chassis, the index is 1. For a chassis where a PTP clock source is located, the index is invalid.";
      }
      leaf source-type-index {
        type ncs_rpc_notif_clock-src-type;
        description
          "Index of the clock source type.";
      }
      leaf source-index {
        type uint32;
        description
          "Index of the clock source.";
      }
      leaf chassis-id {
        type uint32;
        description
          "Chassis id.";
      }
      leaf result {
        type ncs_rpc_notif_fre-check-result;
        description
          "Result of the check of frequency.";
      }
      leaf source-descr {
        type string {
          length "1..63";
        }
        description
          "The description of clock source.";
      }
    }
  }
  augment "/ncs:devices/ncs:device/ncs:netconf-notifications/ncs:received-notifications/ncs:notification/ncs:data" {
    container clock-source-valid {
      presence "";
      config false;
      description
        "The state of clock source is normal.";
      leaf chassis-index {
        type uint32;
        description
          "Indicates the index of the chassis where the non-PTP clock source is located. In the case of a single chassis, the index is 1. For a chassis where a PTP clock source is located, the index is invalid.";
      }
      leaf source-type-index {
        type ncs_rpc_notif_clock-src-type;
        description
          "Index of the clock source type.";
      }
      leaf source-index {
        type uint32;
        description
          "Index of the clock source.";
      }
      leaf chassis-id {
        type uint32;
        description
          "Chassis id.";
      }
      leaf source-name {
        type string {
          length "1..63";
        }
        description
          "Name of the current clock source.";
      }
      leaf source-state {
        type ncs_rpc_notif_clock-src-state;
        description
          "The state of the current clock source.";
      }
    }
  }
  augment "/ncs:devices/ncs:device/ncs:netconf-notifications/ncs:received-notifications/ncs:notification/ncs:data" {
    container clock-source-failed {
      presence "";
      config false;
      description
        "The state of clock source is abnormal.";
      leaf chassis-index {
        type uint32;
        description
          "Indicates the index of the chassis where the non-PTP clock source is located. In the case of a single chassis, the index is 1. For a chassis where a PTP clock source is located, the index is invalid.";
      }
      leaf source-type-index {
        type ncs_rpc_notif_clock-src-type;
        description
          "Index of the clock source type.";
      }
      leaf source-index {
        type uint32;
        description
          "Index of the clock source.";
      }
      leaf chassis-id {
        type uint32;
        description
          "Chassis id.";
      }
      leaf source-name {
        type string {
          length "1..63";
        }
        description
          "Name of the current clock source.";
      }
      leaf source-state {
        type ncs_rpc_notif_clock-src-state;
        description
          "The state of the current clock source.";
      }
    }
  }
  augment "/ncs:devices/ncs:device/ncs:netconf-notifications/ncs:received-notifications/ncs:notification/ncs:data" {
    container clock-port-non-support-resume {
      presence "";
      config false;
      description
        "The alarm that the hardware do not support physical-layer clock synchronization is resumed.";
      leaf chassis-id {
        type uint32;
        description
          "The chassis ID.";
      }
      leaf ifindex {
        type uint32;
        description
          "Port index.";
      }
      leaf source-name {
        type string {
          length "1..63";
        }
        description
          "The current clock source name.";
      }
    }
  }
  augment "/ncs:devices/ncs:device/ncs:netconf-notifications/ncs:received-notifications/ncs:notification/ncs:data" {
    container clock-port-non-support {
      presence "";
      config false;
      description
        "In current link mode, the hardware, such as boards and optical modules, do not support physical-layer clock synchronization.";
      leaf chassis-id {
        type uint32;
        description
          "The chassis ID.";
      }
      leaf ifindex {
        type uint32;
        description
          "Port index.";
      }
      leaf source-name {
        type string {
          length "1..63";
        }
        description
          "The current clock source name.";
      }
    }
  }
  augment "/ncs:devices/ncs:device/ncs:netconf-notifications/ncs:received-notifications/ncs:notification/ncs:data" {
    container clock-in-locked-mode {
      presence "";
      config false;
      description
        "The work mode of system clock source resume.";
      leaf chassis-index {
        type uint32;
        description
          "Indicates the index of the chassis where the non-PTP clock source is located. In the case of a single chassis, the index is 1. For a chassis where a PTP clock source is located, the index is invalid.";
      }
      leaf chassis-id {
        type uint32;
        description
          "Chassis id of the clock source.";
      }
      leaf lock-mode {
        type ncs_rpc_notif_clock-lock-mode;
        description
          "Lock mode of system clock.";
      }
    }
  }
  augment "/ncs:devices/ncs:device/ncs:netconf-notifications/ncs:received-notifications/ncs:notification/ncs:data" {
    container clock-not-in-locked-mode {
      presence "";
      config false;
      description
        "The work mode of system clock source out trace.";
      leaf chassis-index {
        type uint32;
        description
          "Indicates the index of the chassis where the non-PTP clock source is located. In the case of a single chassis, the index is 1. For a chassis where a PTP clock source is located, the index is invalid.";
      }
      leaf chassis-id {
        type uint32;
        description
          "Chassis id of the clock source.";
      }
      leaf lock-mode {
        type ncs_rpc_notif_clock-lock-mode;
        description
          "Lock mode of system clock.";
      }
    }
  }
  augment "/ncs:devices/ncs:device/ncs:netconf-notifications/ncs:received-notifications/ncs:notification/ncs:data" {
    container clock-fm-switch-resume {
      presence "";
      config false;
      description
        "Clock select mode is automative.";
      leaf chassis-id {
        type uint32;
        description
          "Chassis id of the clock source.";
      }
      leaf pll-id {
        type ncs_rpc_notif_clock-pll-id;
        description
          "The id of pll.";
      }
    }
  }
  augment "/ncs:devices/ncs:device/ncs:netconf-notifications/ncs:received-notifications/ncs:notification/ncs:data" {
    container clock-fm-switch {
      presence "";
      config false;
      description
        "Clock select mode is force or manual.";
      leaf chassis-id {
        type uint32;
        description
          "Chassis id of the clock source.";
      }
      leaf pll-id {
        type ncs_rpc_notif_clock-pll-id;
        description
          "The id of pll.";
      }
    }
  }
  augment "/ncs:devices/ncs:device/ncs:netconf-notifications/ncs:received-notifications/ncs:notification/ncs:data" {
    container clock-cluster-topo-fail-resume {
      presence "";
      config false;
      description
        "Clock cluster inter-chassis synchronization topo compute successfully.";
      leaf sync-type {
        type ncs_rpc_notif_cluster-sync-type;
        description
          "Inter-chassis synchronization type.";
      }
      leaf topo-type {
        type ncs_rpc_notif_cluster-topo-type;
        description
          "Inter-chassis synchronization topo type.";
      }
      leaf topo-link-type {
        type ncs_rpc_notif_cluster-link-type;
        description
          "Inter-chassis synchronization link type.";
      }
      leaf topo-status {
        type ncs_rpc_notif_cluster-sync-topo-state;
        description
          "Inter-chassis synchronization topo status.";
      }
    }
  }
  augment "/ncs:devices/ncs:device/ncs:netconf-notifications/ncs:received-notifications/ncs:notification/ncs:data" {
    container clock-cluster-topo-fail {
      presence "";
      config false;
      description
        "Clock cluster inter-chassis synchronization topo compute failed.";
      leaf sync-type {
        type ncs_rpc_notif_cluster-sync-type;
        description
          "Inter-chassis synchronization type.";
      }
      leaf topo-type {
        type ncs_rpc_notif_cluster-topo-type;
        description
          "Inter-chassis synchronization topo type.";
      }
      leaf topo-link-type {
        type ncs_rpc_notif_cluster-link-type;
        description
          "Inter-chassis synchronization link type.";
      }
      leaf topo-status {
        type ncs_rpc_notif_cluster-sync-topo-state;
        description
          "Inter-chassis synchronization topo status.";
      }
    }
  }
  augment "/ncs:devices/ncs:device/ncs:netconf-notifications/ncs:received-notifications/ncs:notification/ncs:data" {
    container clock-ces-acr-lock-fail-resume {
      presence "";
      config false;
      description
        "The clock source of CES ACR is in locked mode.";
      leaf slot {
        type uint32;
        description
          "Slot id of the clock source.";
      }
      leaf card {
        type uint32;
        description
          "Card id of the clock source.";
      }
      leaf domain {
        type uint32;
        description
          "Recovery domain of the clock source.";
      }
      leaf lock-state {
        type ncs_rpc_notif_clock-lock-state;
        description
          "Lock state of the clock source.";
      }
    }
  }
  augment "/ncs:devices/ncs:device/ncs:netconf-notifications/ncs:received-notifications/ncs:notification/ncs:data" {
    container clock-ces-acr-lock-fail {
      presence "";
      config false;
      description
        "The clock source of CES ACR is not in locked mode.";
      leaf slot {
        type uint32;
        description
          "Slot id of the clock source.";
      }
      leaf card {
        type uint32;
        description
          "Card id of the clock source.";
      }
      leaf domain {
        type uint32;
        description
          "Recovery domain of the clock source.";
      }
      leaf lock-state {
        type ncs_rpc_notif_clock-lock-state;
        description
          "Lock state of the clock source.";
      }
    }
  }
}
