module huawei-bras-rui {
  // Generated by yanger -t ncs
  tailf:mount-id "huawei-nc-1.0:huawei-nc-1.0";
  tailf:ncs-device-type "netconf";

  namespace "urn:huawei:yang:huawei-bras-rui";
  prefix bras-rui;

  import huawei-aaa {
    prefix aaa;
  }
  import huawei-pub-type {
    prefix pub-type;
  }
  import ietf-inet-types {
    prefix inet;
  }
  import huawei-bras-ipv4-address-manage {
    prefix bras-ipv4-address-manage;
  }
  import huawei-bras-ipv6-address-manage {
    prefix bras-ipv6-address-manage;
  }
  import huawei-network-instance {
    prefix ni;
  }
  import huawei-tunnel-management {
    prefix tnlm;
  }
  import huawei-l3vpn {
    prefix l3vpn;
  }
  import huawei-rbs {
    prefix rbs;
  }
  import huawei-ifm {
    prefix ifm;
  }
  import huawei-extension {
    prefix ext;
  }
  import huawei-bfd {
    prefix bfd;
  }
  import huawei-route-monitor-group {
    prefix rmg;
  }
  import huawei-bras-user-manage {
    prefix bras-user-manage;
  }
  import huawei-monitor-group {
    prefix mg;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Bras RUI.";

  revision 2019-10-31 {
    description
      "Modify container ip-vpns, backup-user-infos.";
    reference "Huawei private.";
  }
  revision 2019-10-17 {
    description
      "Add container rbp-lpu-infos, rbp-slave-mpu-infos, access-remark-macs, load-balance-hash-algorithm, accounting.";
    reference "Huawei private.";
  }
  revision 2019-04-07 {
    description
      "Initial revision.";
    reference "Huawei private.";
  }
  ext:task-name "rui";

  typedef ncs_template_common-state-type {
    type string;
    description
      "Defines the type of state.";
  }

  typedef ncs_rpc_notif_common-state-type {
    type enumeration {
      enum "down" {
        value 1;
        description
          "Down state.";
      }
      enum "up" {
        value 2;
        description
          "Up state.";
      }
    }
    description
      "Defines the type of state.";
  }

  typedef live_ncs_common-state-type {
    type enumeration {
      enum "down" {
        value 1;
        description
          "Down state.";
      }
      enum "up" {
        value 2;
        description
          "Up state.";
      }
    }
    description
      "Defines the type of state.";
  }

  typedef common-state-type {
    type enumeration {
      enum "down" {
        value 1;
        description
          "Down state.";
      }
      enum "up" {
        value 2;
        description
          "Up state.";
      }
    }
    description
      "Defines the type of state.";
  }

  augment "/ncs:devices/ncs:device/ncs:config" {
    container bras-rui {
      tailf:ncs-device-type "netconf";
      tailf:display-when "not(../../ncs:module) or ../../ncs:module[ncs:name='huawei-bras-rui']";
      description
        "Bras RUI.";
      container global {
        description
          "Configure global config of bras RUI.";
        container rui-option {
          description
            "Configure global rui option code for DHCP and DHCPv6.";
          leaf dhcpv4 {
            type uint8 {
              range "151..174";
            }
            default "151";
            description
              "DHCP option code.";
          }
          leaf dhcpv6 {
            type uint8 {
              range "151..174";
            }
            default "151";
            description
              "DHCPv6 option code.";
          }
        }
        container peer-backup-batch-access {
          description
            "Configure enables users to go online during batch backup.";
          leaf status {
            type boolean;
            default "false";
            description
              "Enable/disable peer backup batch access status.";
          }
        }
        container peer-backup {
          description
            "Configure global peer backup.";
          leaf download-vrrp-delay-time {
            type uint8 {
              range "0..60";
            }
            units "s";
            default "0";
            description
              "Download vrrp table delay time.";
          }
          leaf trigger-speed {
            type uint16 {
              range "0..400";
            }
            description
              "Peer-backup rui-trigger-speed.";
          }
          leaf ttl {
            type uint8 {
              range "0..15";
            }
            default "0";
            description
              "IP ttl.";
          }
        }
        container route-cost-auto-advertise {
          description
            "Configure route cost.";
          leaf enable {
            type boolean;
            default "false";
            description
              "Enable/disable route cost.";
          }
          leaf exclude-loopback {
            when "../enable = 'true'" {
              tailf:xpath-root 3;
            }
            type boolean;
            default "false";
            description
              "Enable/disable the function of automatically advertising the cost value of the loopback interface route.";
          }
        }
      }
      // NCS drop config false container 'backup-user-infos'
    }
  }
  augment "/ncs:devices/ncs:device/ncs:live-status" {
    container bras-rui {
      tailf:ncs-device-type "netconf";
      tailf:display-when "not(../../ncs:module) or ../../ncs:module[ncs:name='huawei-bras-rui'] or (../../ncs:live-status-protocol[not(ncs:capability)]) or (../../ncs:live-status-protocol/ncs:capability/ncs:module[.='huawei-bras-rui'])";
      description
        "Bras RUI.";
      container global {
        description
          "Configure global config of bras RUI.";
        container rui-option {
          description
            "Configure global rui option code for DHCP and DHCPv6.";
          leaf dhcpv4 {
            type uint8 {
              range "151..174";
            }
            // NCS drop default statement
            description
              "DHCP option code.";
          }
          leaf dhcpv6 {
            type uint8 {
              range "151..174";
            }
            // NCS drop default statement
            description
              "DHCPv6 option code.";
          }
        }
        container peer-backup-batch-access {
          description
            "Configure enables users to go online during batch backup.";
          leaf status {
            type boolean;
            // NCS drop default statement
            description
              "Enable/disable peer backup batch access status.";
          }
        }
        container peer-backup {
          description
            "Configure global peer backup.";
          leaf download-vrrp-delay-time {
            type uint8 {
              range "0..60";
            }
            units "s";
            // NCS drop default statement
            description
              "Download vrrp table delay time.";
          }
          leaf trigger-speed {
            type uint16 {
              range "0..400";
            }
            description
              "Peer-backup rui-trigger-speed.";
          }
          leaf ttl {
            type uint8 {
              range "0..15";
            }
            // NCS drop default statement
            description
              "IP ttl.";
          }
        }
        container route-cost-auto-advertise {
          description
            "Configure route cost.";
          leaf enable {
            type boolean;
            // NCS drop default statement
            description
              "Enable/disable route cost.";
          }
          leaf exclude-loopback {
            // NCS drop when statement
            type boolean;
            // NCS drop default statement
            description
              "Enable/disable the function of automatically advertising the cost value of the loopback interface route.";
          }
        }
      }
      container backup-user-infos {
        description
          "List of Statistics of Query Rui Backup User Info.";
        list backup-user {
          key "user-id user-name";
          description
            "Statistics of Query Rui Backup User Info.";
          leaf user-id {
            type uint32 {
              range "0..3145727";
            }
            description
              "ID of a rui user.";
          }
          leaf user-name {
            type string {
              length "1..253";
            }
            description
              "Name of a user.";
          }
          leaf cid {
            type uint32 {
              range "0..4294967295";
            }
            description
              "User cid.";
          }
          leaf session-id {
            type uint32 {
              range "0..4294967295";
            }
            description
              "SessionId of user.";
          }
          leaf mac {
            type pub-type:live_ncs_mac-address;
            description
              "Mac address.";
          }
          leaf pe-vlan {
            type uint16 {
              range "0..65535";
            }
            description
              "PeVLAN of user.";
          }
          leaf ce-vlan {
            type uint16 {
              range "0..65535";
            }
            description
              "CeVLAN of user.";
          }
          leaf vrrp-id {
            type uint8 {
              range "0..255";
            }
            description
              "VRRP Protocol Id.";
          }
          leaf ip {
            type string {
              length "1..31";
            }
            description
              "Ip address.";
          }
          leaf backup-id {
            type uint16 {
              range "0..65535";
            }
            description
              "Remote backup ID.";
          }
          leaf rbp-name {
            type string {
              length "1..128";
            }
            description
              "Name of an RBP.";
          }
          leaf process-id {
            type uint16 {
              range "0..65535";
            }
            description
              "RBS Index.";
          }
          leaf rbs-name {
            type string {
              length "1..32";
            }
            description
              "Name of the RBS bound to an RBP.";
          }
          leaf interface {
            type leafref {
              path "/ncs:devices/ncs:device/ncs:live-status/ifm:ifm/ifm:interfaces/ifm:interface/ifm:name" {
                tailf:xpath-root 3;
              }
            }
            description
              "Interface name.";
          }
          leaf ipv4-vpn {
            type string {
              length "1..31";
            }
            description
              "IPv4 vpn name.";
          }
          leaf ipv6-vpn {
            type string {
              length "1..31";
            }
            description
              "IPv6 vpn name.";
          }
          leaf online-pos {
            type string {
              length "1..15";
            }
            description
              "User Online Position (From local server or remote server).";
          }
          leaf link-local-address {
            type string {
              length "1..49";
            }
            description
              "User Lan Address.";
          }
          leaf wan-address {
            type string {
              length "1..49";
            }
            description
              "User Wan Address.";
          }
          leaf wan-prefix-len {
            type string {
              length "1..3";
            }
            description
              "User Wan Address Prefix Length.";
          }
          leaf user-mode {
            type string {
              length "1..15";
            }
            description
              "Rui User Backup Mode.";
          }
        }
      }
    }
  }
  augment "/ncs:devices/ncs:template/ncs:ned-id/ncs:config" {
    container bras-rui {
      description
        "Bras RUI.";
      container global {
        description
          "Configure global config of bras RUI.";
        container rui-option {
          description
            "Configure global rui option code for DHCP and DHCPv6.";
          leaf dhcpv4 {
            type string;
            // NCS drop default statement
            description
              "DHCP option code.";
          }
          leaf dhcpv6 {
            type string;
            // NCS drop default statement
            description
              "DHCPv6 option code.";
          }
        }
        container peer-backup-batch-access {
          description
            "Configure enables users to go online during batch backup.";
          leaf status {
            type string;
            // NCS drop default statement
            description
              "Enable/disable peer backup batch access status.";
          }
        }
        container peer-backup {
          description
            "Configure global peer backup.";
          leaf download-vrrp-delay-time {
            type string;
            units "s";
            // NCS drop default statement
            description
              "Download vrrp table delay time.";
          }
          leaf trigger-speed {
            type string;
            description
              "Peer-backup rui-trigger-speed.";
          }
          leaf ttl {
            type string;
            // NCS drop default statement
            description
              "IP ttl.";
          }
        }
        container route-cost-auto-advertise {
          description
            "Configure route cost.";
          leaf enable {
            type string;
            // NCS drop default statement
            description
              "Enable/disable route cost.";
          }
          leaf exclude-loopback {
            // NCS drop when statement
            type string;
            // NCS drop default statement
            description
              "Enable/disable the function of automatically advertising the cost value of the loopback interface route.";
          }
        }
      }
      // NCS drop config false container 'backup-user-infos'
    }
  }
  augment "/ncs:devices/ncs:template/ncs:ned-id/ncs:config/aaa:aaa/aaa:domains/aaa:domain" {
    description
      "Domain View.";
    container bras-rui {
      description
        "Configure Bras RUI.";
      leaf peer-backup-enable {
        type string;
        // NCS drop default statement
        description
          "Enable/disable RUI backup for users who get online through an AAA domain.";
      }
    }
  }
  augment "/ncs:devices/ncs:device/ncs:live-status/aaa:aaa/aaa:domains/aaa:domain" {
    description
      "Domain View.";
    container bras-rui {
      tailf:ncs-device-type "netconf";
      tailf:display-when "not(../../../../../ncs:module) or ../../../../../ncs:module[ncs:name='huawei-bras-rui'] or (../../../../../ncs:live-status-protocol[not(ncs:capability)]) or (../../../../../ncs:live-status-protocol/ncs:capability/ncs:module[.='huawei-bras-rui'])";
      description
        "Configure Bras RUI.";
      leaf peer-backup-enable {
        type boolean;
        // NCS drop default statement
        description
          "Enable/disable RUI backup for users who get online through an AAA domain.";
      }
    }
  }
  augment "/ncs:devices/ncs:device/ncs:config/aaa:aaa/aaa:domains/aaa:domain" {
    description
      "Domain View.";
    container bras-rui {
      tailf:ncs-device-type "netconf";
      tailf:display-when "not(../../../../../ncs:module) or ../../../../../ncs:module[ncs:name='huawei-bras-rui']";
      description
        "Configure Bras RUI.";
      leaf peer-backup-enable {
        type boolean;
        default "true";
        description
          "Enable/disable RUI backup for users who get online through an AAA domain.";
      }
    }
  }
  augment "/ncs:devices/ncs:template/ncs:ned-id/ncs:config/rbs:rbs/rbs:services/rbs:service" {
    description
      "Bras config below remote-backup-service View.";
    container bras-rui-config {
      description
        "Configure bras config below remote-backup-service View.";
      container domain-map-list {
        description
          "Configure bind the domain mapping list to an RBS.";
        leaf name {
          type string;
          description
            "Domain-map-list name.";
        }
      }
      container ipv4-pools {
        description
          "List of configure in the remote backup server View, bind the address pool.";
        list ipv4-pool {
          // NCS patched for predictable order
          ordered-by user;
          key "name";
          description
            "Configure in the remote backup server View, bind the address pool.";
          leaf name {
            type string;
            description
              "IP pool name.";
          }
          leaf priority {
            type string;
            description
              "Cost of ip pool network route.";
          }
        }
      }
      container ipv6-pools {
        description
          "List of configure in the remote backup server View, bind the IPv6 address pool.";
        list ipv6-pool {
          // NCS patched for predictable order
          ordered-by user;
          key "name";
          description
            "Configure in the remote backup server View, bind the IPv6 address pool.";
          leaf name {
            type string;
            description
              "IPv6 pool name.";
          }
          leaf priority {
            type string;
            description
              "Cost of IPv6 pool network route.";
          }
        }
      }
      container ipv6-inter-chassis-borrow {
        // NCS drop must statement
        presence "Create the source and destination IPv6 addresses for the device functioning as the DHCPv6 server when addresses are assigned from local IPv6 address pools to implement inter-chassis address borrowing.";
        description
          "Enable/disable the source and destination IPv6 addresses for the device functioning as the DHCPv6 server when addresses are assigned from local IPv6 address pools to implement inter-chassis address borrowing.";
        leaf dest-address {
          type string;
          // NCS drop mandatory statement
          description
            "DHCPv6 server destination address.";
        }
        leaf source-address {
          type string;
          // NCS drop mandatory statement
          description
            "DHCPv6 server source address.";
        }
        leaf vpn {
          type string;
          // NCS drop must statement
          description
            "VPN instance.";
        }
      }
      container l2tp-protect-tunnel-enable {
        description
          "Configure l2tp protect-tunnel.";
        leaf status {
          type string;
          // NCS drop default statement
          description
            "Enable/disable the status of l2tp protect-tunnel.";
        }
      }
      container l2tp-tunnel-sources {
        description
          "List of configures a source L2TP tunnel interface in the RBS View so that the source interface route bound to the RBS is updated based on the link status on the network side.";
        list l2tp-tunnel-source {
          // NCS patched for predictable order
          ordered-by user;
          key "interface";
          description
            "Configure the remote backup service to bind source interface.";
          leaf interface {
            type string;
            // NCS drop must statement
            description
              "Specify interface.";
          }
        }
      }
      container protect-tunnels {
        // NCS drop must statement
        description
          "Configure protection tunnel template in hot backup scenarios.";
        container all-instance-lsp {
          description
            "Configure an all instance protection tunnel template in hot backup scenarios.";
          leaf peer-ip {
            type string;
            description
              "IP next hop.";
          }
        }
        container policy {
          presence "Create a protection path for public users with the tunnel policy.";
          description
            "Enable/disable a protection path for public users with the tunnel policy.";
          leaf interface {
            type string;
            // NCS drop must statement
            description
              "Out interface.";
          }
          leaf peer-ip {
            type string;
            // NCS drop mandatory statement
            description
              "Tunnel peer IP.";
          }
          leaf tunnel-policy {
            type string;
            // NCS drop mandatory statement
            description
              "Tunnel name.";
          }
        }
        container redirect {
          presence "Create a protection path of the IP redirection type.";
          description
            "Enable/disable a protection path of the IP redirection type.";
          leaf interface {
            type string;
            // NCS drop must statement
            // NCS drop mandatory statement
            description
              "Out interface.";
          }
          leaf peer-ip {
            type string;
            // NCS drop mandatory statement
            description
              "IP next hop.";
          }
        }
        container ip-vpns {
          description
            "List of configure a protection path between the active and standby devices when there is return traffic on the network side.";
          list protect-tunnel-vpn {
            // NCS patched for predictable order
            ordered-by user;
            key "vpn";
            description
              "Configure a protection path between the active and standby devices when there is return traffic on the network side.";
            leaf vpn {
              type string;
              // NCS drop must statement
              description
                "IP VPN instance.";
            }
            leaf peer-ip {
              type string;
              // NCS drop mandatory statement
              description
                "Tunnel peer ip.";
            }
            leaf interface {
              type string;
              // NCS drop must statement
              description
                "Out interface.";
            }
          }
        }
      }
      container radius-author-server {
        description
          "Configure the radius author server for remote backup service.";
        container ip-vpn-servers {
          description
            "List of configure the Radius Authorization Server Source IP under Remote Backup Server.";
          list ip-vpn-server {
            // NCS patched for predictable order
            ordered-by user;
            key "vpn";
            description
              "Configure the Radius Authorization Server Source IP under Remote Backup Server.";
            leaf vpn {
              type string;
              // NCS drop must statement
              description
                "Vpn instance name.";
            }
            leaf ip {
              type string;
              // NCS drop mandatory statement
              description
                "IP Address.";
            }
          }
        }
        container nas-server {
          description
            "Configure the source IP address of the packets that the router sends back to the RADIUS server to be the same as the NAS IP address.";
          leaf same-as-logic-ip {
            type string;
            // NCS drop default statement
            description
              "Enable/disable specify the source IP same as NAS logic ip.";
          }
        }
      }
      container static-routes {
        description
          "List of configure IP static routes.";
        list static-route {
          // NCS patched for predictable order
          ordered-by user;
          key "tag";
          // NCS drop max-elements statement
          description
            "Configure IP static routes.";
          leaf tag {
            type string;
            description
              "Binding IP static routes of specified tag value.";
          }
          leaf cost {
            type string;
            ext:dynamic-default {
              ext:default-value "10" {
                // NCS drop when statement
                description
                  "The default value is 10 when slave-flag is false.";
              }
              ext:default-value "20" {
                // NCS drop when statement
                description
                  "The default value is 20 when slave-flag is true.";
              }
            }
            description
              "Specified by rbs static routes bound to the final release cost value.";
          }
          leaf null-interface-index {
            type string;
            // NCS drop default statement
            description
              "Null interface index, current value only supports NULL0.";
          }
          leaf slave-flag {
            type string;
            // NCS drop default statement
            description
              "Enable/disable specify the route as a backup state for RUI.";
          }
        }
      }
      container switch-over-uplink {
        // NCS drop when statement
        description
          "Configure the uplink fault rate threshold for a master/backup switchover and the duration of the uplink fault before the switchover.";
        leaf duration {
          type string;
          units "min";
          // NCS drop default statement
          description
            "Duration value.";
        }
        leaf failure-ratio {
          type string;
          units "%";
          // NCS drop default statement
          description
            "Failure-ratio value.";
        }
      }
      container track {
        description
          "Configure the remote backup service to track.";
        container bfd-session {
          description
            "Configure the remote backup service to track the bidirectional forwarding detection (BFD) session status.";
          leaf session-id {
            type string;
            description
              "Specify BFD session ID.";
          }
        }
        container interfaces {
          // NCS drop when statement
          description
            "List of configure the remote backup service to track the status of the network-side interface.";
          list interface {
            // NCS patched for predictable order
            ordered-by user;
            key "name";
            description
              "Configure the remote backup service to track the status of the network-side interface.";
            leaf name {
              type string;
              // NCS drop must statement
              description
                "Specify interface.";
            }
            leaf weight {
              type string;
              // NCS drop default statement
              description
                "Interface weight value.";
            }
          }
        }
        container monitor-groups {
          description
            "List of configure the status of the remote backup service tracing interface group.";
          list monitor-group {
            // NCS patched for predictable order
            ordered-by user;
            key "name";
            // NCS drop max-elements statement
            description
              "Configure the status of the remote backup service tracing interface group.";
            leaf name {
              type string;
              description
                "Interface monitor group name.";
            }
            leaf failure-ratio {
              type string;
              units "%";
              // NCS drop mandatory statement
              description
                "Failure-ratio value by a percent.";
            }
          }
        }
        container route-monitor-groups {
          description
            "List of configure the route monitoring group monitored by the network to meet the percentage of link failure thresholds.";
          list route-monitor-group {
            // NCS patched for predictable order
            ordered-by user;
            key "name";
            // NCS drop max-elements statement
            description
              "Configure the route monitoring group monitored by the network to meet the percentage of link failure thresholds.";
            leaf name {
              type string;
              description
                "Route group name.";
            }
            leaf failure-ratio {
              type string;
              units "%";
              // NCS drop mandatory statement
              description
                "Failure-ratio value by a percent.";
            }
          }
        }
      }
      // NCS drop config false container 'dynamic-statistics'
    }
  }
  augment "/ncs:devices/ncs:device/ncs:live-status/rbs:rbs/rbs:services/rbs:service" {
    description
      "Bras config below remote-backup-service View.";
    container bras-rui-config {
      tailf:ncs-device-type "netconf";
      tailf:display-when "not(../../../../../ncs:module) or ../../../../../ncs:module[ncs:name='huawei-bras-rui'] or (../../../../../ncs:live-status-protocol[not(ncs:capability)]) or (../../../../../ncs:live-status-protocol/ncs:capability/ncs:module[.='huawei-bras-rui'])";
      description
        "Configure bras config below remote-backup-service View.";
      container domain-map-list {
        description
          "Configure bind the domain mapping list to an RBS.";
        leaf name {
          type leafref {
            path "/ncs:devices/ncs:device/ncs:live-status/bras-user-manage:bras-user-manage/bras-user-manage:domain-map-lists/bras-user-manage:domain-map-list/bras-user-manage:name" {
              tailf:xpath-root 3;
            }
          }
          description
            "Domain-map-list name.";
        }
      }
      container ipv4-pools {
        description
          "List of configure in the remote backup server View, bind the address pool.";
        list ipv4-pool {
          key "name";
          description
            "Configure in the remote backup server View, bind the address pool.";
          leaf name {
            type leafref {
              path "/ncs:devices/ncs:device/ncs:live-status/bras-ipv4-address-manage:bras-ipv4-address-manage/bras-ipv4-address-manage:ipv4-pools/bras-ipv4-address-manage:ipv4-pool/bras-ipv4-address-manage:name" {
                tailf:xpath-root 3;
              }
            }
            description
              "IP pool name.";
          }
          leaf priority {
            type uint32 {
              range "1..65535";
            }
            description
              "Cost of ip pool network route.";
          }
        }
      }
      container ipv6-pools {
        description
          "List of configure in the remote backup server View, bind the IPv6 address pool.";
        list ipv6-pool {
          key "name";
          description
            "Configure in the remote backup server View, bind the IPv6 address pool.";
          leaf name {
            type leafref {
              path "/ncs:devices/ncs:device/ncs:live-status/bras-ipv6-address-manage:bras-ipv6-address-manage/bras-ipv6-address-manage:ipv6-pools/bras-ipv6-address-manage:ipv6-pool/bras-ipv6-address-manage:name" {
                tailf:xpath-root 3;
              }
            }
            description
              "IPv6 pool name.";
          }
          leaf priority {
            type uint32 {
              range "1..65535";
            }
            description
              "Cost of IPv6 pool network route.";
          }
        }
      }
      container ipv6-inter-chassis-borrow {
        // NCS drop must statement
        presence "Create the source and destination IPv6 addresses for the device functioning as the DHCPv6 server when addresses are assigned from local IPv6 address pools to implement inter-chassis address borrowing.";
        description
          "Enable/disable the source and destination IPv6 addresses for the device functioning as the DHCPv6 server when addresses are assigned from local IPv6 address pools to implement inter-chassis address borrowing.";
        leaf dest-address {
          type inet:ipv6-address-no-zone;
          // NCS drop mandatory statement
          description
            "DHCPv6 server destination address.";
        }
        leaf source-address {
          type inet:ipv6-address-no-zone;
          // NCS drop mandatory statement
          description
            "DHCPv6 server source address.";
        }
        leaf vpn {
          type leafref {
            path "/ncs:devices/ncs:device/ncs:live-status/ni:network-instance/ni:instances/ni:instance/ni:name" {
              tailf:xpath-root 3;
            }
          }
          // NCS drop must statement
          description
            "VPN instance.";
        }
      }
      container l2tp-protect-tunnel-enable {
        description
          "Configure l2tp protect-tunnel.";
        leaf status {
          type boolean;
          // NCS drop default statement
          description
            "Enable/disable the status of l2tp protect-tunnel.";
        }
      }
      container l2tp-tunnel-sources {
        description
          "List of configures a source L2TP tunnel interface in the RBS View so that the source interface route bound to the RBS is updated based on the link status on the network side.";
        list l2tp-tunnel-source {
          key "interface";
          description
            "Configure the remote backup service to bind source interface.";
          leaf interface {
            type leafref {
              path "/ncs:devices/ncs:device/ncs:live-status/ifm:ifm/ifm:interfaces/ifm:interface/ifm:name" {
                tailf:xpath-root 3;
              }
            }
            // NCS drop must statement
            description
              "Specify interface.";
          }
        }
      }
      container protect-tunnels {
        // NCS drop must statement
        description
          "Configure protection tunnel template in hot backup scenarios.";
        container all-instance-lsp {
          description
            "Configure an all instance protection tunnel template in hot backup scenarios.";
          leaf peer-ip {
            type inet:ipv4-address-no-zone;
            description
              "IP next hop.";
          }
        }
        container policy {
          presence "Create a protection path for public users with the tunnel policy.";
          description
            "Enable/disable a protection path for public users with the tunnel policy.";
          leaf interface {
            type leafref {
              path "/ncs:devices/ncs:device/ncs:live-status/ifm:ifm/ifm:interfaces/ifm:interface/ifm:name" {
                tailf:xpath-root 3;
              }
            }
            // NCS drop must statement
            description
              "Out interface.";
          }
          leaf peer-ip {
            type inet:ipv4-address-no-zone;
            // NCS drop mandatory statement
            description
              "Tunnel peer IP.";
          }
          leaf tunnel-policy {
            type leafref {
              path "/ncs:devices/ncs:device/ncs:live-status/tnlm:tunnel-management/tnlm:tunnel-policys/tnlm:tunnel-policy/tnlm:name" {
                tailf:xpath-root 3;
              }
            }
            // NCS drop mandatory statement
            description
              "Tunnel name.";
          }
        }
        container redirect {
          presence "Create a protection path of the IP redirection type.";
          description
            "Enable/disable a protection path of the IP redirection type.";
          leaf interface {
            type leafref {
              path "/ncs:devices/ncs:device/ncs:live-status/ifm:ifm/ifm:interfaces/ifm:interface/ifm:name" {
                tailf:xpath-root 3;
              }
            }
            // NCS drop must statement
            // NCS drop mandatory statement
            description
              "Out interface.";
          }
          leaf peer-ip {
            type inet:ipv4-address-no-zone;
            // NCS drop mandatory statement
            description
              "IP next hop.";
          }
        }
        container ip-vpns {
          description
            "List of configure a protection path between the active and standby devices when there is return traffic on the network side.";
          list protect-tunnel-vpn {
            key "vpn";
            description
              "Configure a protection path between the active and standby devices when there is return traffic on the network side.";
            leaf vpn {
              type leafref {
                path "/ncs:devices/ncs:device/ncs:live-status/ni:network-instance/ni:instances/ni:instance/ni:name" {
                  tailf:xpath-root 3;
                }
              }
              // NCS drop must statement
              description
                "IP VPN instance.";
            }
            leaf peer-ip {
              type inet:ipv4-address-no-zone;
              // NCS drop mandatory statement
              description
                "Tunnel peer ip.";
            }
            leaf interface {
              type leafref {
                path "/ncs:devices/ncs:device/ncs:live-status/ifm:ifm/ifm:interfaces/ifm:interface/ifm:name" {
                  tailf:xpath-root 3;
                }
              }
              // NCS drop must statement
              description
                "Out interface.";
            }
          }
        }
      }
      container radius-author-server {
        description
          "Configure the radius author server for remote backup service.";
        container ip-vpn-servers {
          description
            "List of configure the Radius Authorization Server Source IP under Remote Backup Server.";
          list ip-vpn-server {
            key "vpn";
            description
              "Configure the Radius Authorization Server Source IP under Remote Backup Server.";
            leaf vpn {
              type leafref {
                path "/ncs:devices/ncs:device/ncs:live-status/ni:network-instance/ni:instances/ni:instance/ni:name" {
                  tailf:xpath-root 3;
                }
              }
              // NCS drop must statement
              description
                "Vpn instance name.";
            }
            leaf ip {
              type inet:ipv4-address-no-zone;
              // NCS drop mandatory statement
              description
                "IP Address.";
            }
          }
        }
        container nas-server {
          description
            "Configure the source IP address of the packets that the router sends back to the RADIUS server to be the same as the NAS IP address.";
          leaf same-as-logic-ip {
            type boolean;
            // NCS drop default statement
            description
              "Enable/disable specify the source IP same as NAS logic ip.";
          }
        }
      }
      container static-routes {
        description
          "List of configure IP static routes.";
        list static-route {
          key "tag";
          // NCS drop max-elements statement
          description
            "Configure IP static routes.";
          leaf tag {
            type uint32 {
              range "1..4294967295";
            }
            description
              "Binding IP static routes of specified tag value.";
          }
          leaf cost {
            type uint32 {
              range "1..65535";
            }
            ext:dynamic-default {
              ext:default-value "10" {
                // NCS drop when statement
                description
                  "The default value is 10 when slave-flag is false.";
              }
              ext:default-value "20" {
                // NCS drop when statement
                description
                  "The default value is 20 when slave-flag is true.";
              }
            }
            description
              "Specified by rbs static routes bound to the final release cost value.";
          }
          leaf null-interface-index {
            type uint32 {
              range "0";
            }
            // NCS drop default statement
            description
              "Null interface index, current value only supports NULL0.";
          }
          leaf slave-flag {
            type boolean;
            // NCS drop default statement
            description
              "Enable/disable specify the route as a backup state for RUI.";
          }
        }
      }
      container switch-over-uplink {
        // NCS drop when statement
        description
          "Configure the uplink fault rate threshold for a master/backup switchover and the duration of the uplink fault before the switchover.";
        leaf duration {
          type uint32 {
            range "0..30";
          }
          units "min";
          // NCS drop default statement
          description
            "Duration value.";
        }
        leaf failure-ratio {
          type uint32 {
            range "1..100";
          }
          units "%";
          // NCS drop default statement
          description
            "Failure-ratio value.";
        }
      }
      container track {
        description
          "Configure the remote backup service to track.";
        container bfd-session {
          description
            "Configure the remote backup service to track the bidirectional forwarding detection (BFD) session status.";
          leaf session-id {
            type leafref {
              path "/ncs:devices/ncs:device/ncs:live-status/bfd:bfd/bfd:sessions/bfd:session/bfd:local-discriminator" {
                tailf:xpath-root 3;
              }
            }
            description
              "Specify BFD session ID.";
          }
        }
        container interfaces {
          // NCS drop when statement
          description
            "List of configure the remote backup service to track the status of the network-side interface.";
          list interface {
            key "name";
            description
              "Configure the remote backup service to track the status of the network-side interface.";
            leaf name {
              type leafref {
                path "/ncs:devices/ncs:device/ncs:live-status/ifm:ifm/ifm:interfaces/ifm:interface/ifm:name" {
                  tailf:xpath-root 3;
                }
              }
              // NCS drop must statement
              description
                "Specify interface.";
            }
            leaf weight {
              type uint8 {
                range "1..100";
              }
              // NCS drop default statement
              description
                "Interface weight value.";
            }
          }
        }
        container monitor-groups {
          description
            "List of configure the status of the remote backup service tracing interface group.";
          list monitor-group {
            key "name";
            // NCS drop max-elements statement
            description
              "Configure the status of the remote backup service tracing interface group.";
            leaf name {
              type leafref {
                path "/ncs:devices/ncs:device/ncs:live-status/mg:monitor-group/mg:groups/mg:group/mg:name" {
                  tailf:xpath-root 3;
                }
              }
              description
                "Interface monitor group name.";
            }
            leaf failure-ratio {
              type uint8 {
                range "1..100";
              }
              units "%";
              // NCS drop mandatory statement
              description
                "Failure-ratio value by a percent.";
            }
          }
        }
        container route-monitor-groups {
          description
            "List of configure the route monitoring group monitored by the network to meet the percentage of link failure thresholds.";
          list route-monitor-group {
            key "name";
            // NCS drop max-elements statement
            description
              "Configure the route monitoring group monitored by the network to meet the percentage of link failure thresholds.";
            leaf name {
              type leafref {
                path "/ncs:devices/ncs:device/ncs:live-status/rmg:route-monitor-group/rmg:monitor-groups/rmg:monitor-group/rmg:group-name" {
                  tailf:xpath-root 3;
                }
              }
              description
                "Route group name.";
            }
            leaf failure-ratio {
              type uint8 {
                range "1..100";
              }
              units "%";
              // NCS drop mandatory statement
              description
                "Failure-ratio value by a percent.";
            }
          }
        }
      }
      container dynamic-statistics {
        description
          "Statistics of dynamic rbs about bras.";
        leaf uplink-state {
          type live_ncs_common-state-type;
          description
            "The uplink state of rbs.";
        }
        container protect-tunnels {
          description
            "List of Statistics of Vpn-based information.";
          list protect-tunnel {
            key "vpn-id";
            description
              "Statistics of Vpn-based information.";
            leaf vpn-id {
              type uint32;
              description
                "Specify the VPN instance index.";
            }
            leaf vpn-name {
              type string {
                length "1..32";
              }
              description
                "Specify the VPN instance name.";
              ext:support-filter "true";
            }
            leaf protect-type {
              type string {
                length "1..64";
              }
              description
                "The type of protect tunnel.";
            }
            leaf peer-ip {
              type string {
                length "1..16";
              }
              description
                "The peer ip address of protect tunnel.";
            }
            leaf tunnel-state {
              type string {
                length "1..8";
              }
              description
                "The tunnel state of protect tunnel.";
            }
          }
        }
      }
    }
  }
  augment "/ncs:devices/ncs:device/ncs:config/rbs:rbs/rbs:services/rbs:service" {
    description
      "Bras config below remote-backup-service View.";
    container bras-rui-config {
      tailf:ncs-device-type "netconf";
      tailf:display-when "not(../../../../../ncs:module) or ../../../../../ncs:module[ncs:name='huawei-bras-rui']";
      description
        "Configure bras config below remote-backup-service View.";
      container domain-map-list {
        description
          "Configure bind the domain mapping list to an RBS.";
        leaf name {
          type leafref {
            path "/ncs:devices/ncs:device/ncs:config/bras-user-manage:bras-user-manage/bras-user-manage:domain-map-lists/bras-user-manage:domain-map-list/bras-user-manage:name" {
              tailf:xpath-root 3;
            }
          }
          description
            "Domain-map-list name.";
        }
      }
      container ipv4-pools {
        description
          "List of configure in the remote backup server View, bind the address pool.";
        list ipv4-pool {
          key "name";
          description
            "Configure in the remote backup server View, bind the address pool.";
          leaf name {
            type leafref {
              path "/ncs:devices/ncs:device/ncs:config/bras-ipv4-address-manage:bras-ipv4-address-manage/bras-ipv4-address-manage:ipv4-pools/bras-ipv4-address-manage:ipv4-pool/bras-ipv4-address-manage:name" {
                tailf:xpath-root 3;
              }
            }
            description
              "IP pool name.";
          }
          leaf priority {
            type uint32 {
              range "1..65535";
            }
            description
              "Cost of ip pool network route.";
          }
        }
      }
      container ipv6-pools {
        description
          "List of configure in the remote backup server View, bind the IPv6 address pool.";
        list ipv6-pool {
          key "name";
          description
            "Configure in the remote backup server View, bind the IPv6 address pool.";
          leaf name {
            type leafref {
              path "/ncs:devices/ncs:device/ncs:config/bras-ipv6-address-manage:bras-ipv6-address-manage/bras-ipv6-address-manage:ipv6-pools/bras-ipv6-address-manage:ipv6-pool/bras-ipv6-address-manage:name" {
                tailf:xpath-root 3;
              }
            }
            description
              "IPv6 pool name.";
          }
          leaf priority {
            type uint32 {
              range "1..65535";
            }
            description
              "Cost of IPv6 pool network route.";
          }
        }
      }
      container ipv6-inter-chassis-borrow {
        must 'not(./source-address = ./dest-address)' {
          tailf:xpath-root 3;
        }
        presence "Create the source and destination IPv6 addresses for the device functioning as the DHCPv6 server when addresses are assigned from local IPv6 address pools to implement inter-chassis address borrowing.";
        description
          "Enable/disable the source and destination IPv6 addresses for the device functioning as the DHCPv6 server when addresses are assigned from local IPv6 address pools to implement inter-chassis address borrowing.";
        leaf dest-address {
          type inet:ipv6-address-no-zone;
          mandatory true;
          description
            "DHCPv6 server destination address.";
        }
        leaf source-address {
          type inet:ipv6-address-no-zone;
          mandatory true;
          description
            "DHCPv6 server source address.";
        }
        leaf vpn {
          type leafref {
            path "/ncs:devices/ncs:device/ncs:config/ni:network-instance/ni:instances/ni:instance/ni:name" {
              tailf:xpath-root 3;
            }
          }
          must "/ni:network-instance/ni:instances/ni:instance[ni:name=current()]/l3vpn:afs/l3vpn:af[l3vpn:type='ipv6-unicast']" {
            tailf:xpath-root 3;
          }
          description
            "VPN instance.";
        }
      }
      container l2tp-protect-tunnel-enable {
        description
          "Configure l2tp protect-tunnel.";
        leaf status {
          type boolean;
          default "false";
          description
            "Enable/disable the status of l2tp protect-tunnel.";
        }
      }
      container l2tp-tunnel-sources {
        description
          "List of configures a source L2TP tunnel interface in the RBS View so that the source interface route bound to the RBS is updated based on the link status on the network side.";
        list l2tp-tunnel-source {
          key "interface";
          description
            "Configure the remote backup service to bind source interface.";
          leaf interface {
            type leafref {
              path "/ncs:devices/ncs:device/ncs:config/ifm:ifm/ifm:interfaces/ifm:interface/ifm:name" {
                tailf:xpath-root 3;
              }
            }
            must "/ifm:ifm/ifm:interfaces/ifm:interface[ifm:name=current()]/ifm:type='LoopBack'" {
              tailf:xpath-root 3;
            }
            description
              "Specify interface.";
          }
        }
      }
      container protect-tunnels {
        must 'not(./policy and ./redirect)' {
          tailf:xpath-root 3;
        }
        description
          "Configure protection tunnel template in hot backup scenarios.";
        container all-instance-lsp {
          description
            "Configure an all instance protection tunnel template in hot backup scenarios.";
          leaf peer-ip {
            type inet:ipv4-address-no-zone;
            description
              "IP next hop.";
          }
        }
        container policy {
          presence "Create a protection path for public users with the tunnel policy.";
          description
            "Enable/disable a protection path for public users with the tunnel policy.";
          leaf interface {
            type leafref {
              path "/ncs:devices/ncs:device/ncs:config/ifm:ifm/ifm:interfaces/ifm:interface/ifm:name" {
                tailf:xpath-root 3;
              }
            }
            must "/ifm:ifm/ifm:interfaces/ifm:interface[ifm:name=current()]/ifm:type='Ethernet' or
/ifm:ifm/ifm:interfaces/ifm:interface[ifm:name=current()]/ifm:type='GigabitEthernet' or
/ifm:ifm/ifm:interfaces/ifm:interface[ifm:name=current()]/ifm:type='Eth-Trunk' or
/ifm:ifm/ifm:interfaces/ifm:interface[ifm:name=current()]/ifm:type='10GE' or
/ifm:ifm/ifm:interfaces/ifm:interface[ifm:name=current()]/ifm:type='Virtual-Ethernet' or
/ifm:ifm/ifm:interfaces/ifm:interface[ifm:name=current()]/ifm:type='PW-VE' or
/ifm:ifm/ifm:interfaces/ifm:interface[ifm:name=current()]/ifm:type='XGigabitEthernet' or
/ifm:ifm/ifm:interfaces/ifm:interface[ifm:name=current()]/ifm:type='100GE' or
/ifm:ifm/ifm:interfaces/ifm:interface[ifm:name=current()]/ifm:type='50GE' or
/ifm:ifm/ifm:interfaces/ifm:interface[ifm:name=current()]/ifm:type='50|100GE' or
/ifm:ifm/ifm:interfaces/ifm:interface[ifm:name=current()]/ifm:type='FlexE' or
/ifm:ifm/ifm:interfaces/ifm:interface[ifm:name=current()]/ifm:type='25GE' or
/ifm:ifm/ifm:interfaces/ifm:interface[ifm:name=current()]/ifm:type='LoopBack' or
/ifm:ifm/ifm:interfaces/ifm:interface[ifm:name=current()]/ifm:type='40GE' or
/ifm:ifm/ifm:interfaces/ifm:interface[ifm:name=current()]/ifm:type='400GE'" {
              tailf:xpath-root 3;
            }
            description
              "Out interface.";
          }
          leaf peer-ip {
            type inet:ipv4-address-no-zone;
            mandatory true;
            description
              "Tunnel peer IP.";
          }
          leaf tunnel-policy {
            type leafref {
              path "/ncs:devices/ncs:device/ncs:config/tnlm:tunnel-management/tnlm:tunnel-policys/tnlm:tunnel-policy/tnlm:name" {
                tailf:xpath-root 3;
              }
            }
            mandatory true;
            description
              "Tunnel name.";
          }
        }
        container redirect {
          presence "Create a protection path of the IP redirection type.";
          description
            "Enable/disable a protection path of the IP redirection type.";
          leaf interface {
            type leafref {
              path "/ncs:devices/ncs:device/ncs:config/ifm:ifm/ifm:interfaces/ifm:interface/ifm:name" {
                tailf:xpath-root 3;
              }
            }
            must "/ifm:ifm/ifm:interfaces/ifm:interface[ifm:name=current()]/ifm:type='Ethernet' or
/ifm:ifm/ifm:interfaces/ifm:interface[ifm:name=current()]/ifm:type='GigabitEthernet' or
/ifm:ifm/ifm:interfaces/ifm:interface[ifm:name=current()]/ifm:type='Eth-Trunk' or
/ifm:ifm/ifm:interfaces/ifm:interface[ifm:name=current()]/ifm:type='10GE' or
/ifm:ifm/ifm:interfaces/ifm:interface[ifm:name=current()]/ifm:type='Virtual-Ethernet' or
/ifm:ifm/ifm:interfaces/ifm:interface[ifm:name=current()]/ifm:type='PW-VE' or
/ifm:ifm/ifm:interfaces/ifm:interface[ifm:name=current()]/ifm:type='XGigabitEthernet' or
/ifm:ifm/ifm:interfaces/ifm:interface[ifm:name=current()]/ifm:type='100GE' or
/ifm:ifm/ifm:interfaces/ifm:interface[ifm:name=current()]/ifm:type='50GE' or
/ifm:ifm/ifm:interfaces/ifm:interface[ifm:name=current()]/ifm:type='50|100GE' or
/ifm:ifm/ifm:interfaces/ifm:interface[ifm:name=current()]/ifm:type='FlexE' or
/ifm:ifm/ifm:interfaces/ifm:interface[ifm:name=current()]/ifm:type='25GE' or
/ifm:ifm/ifm:interfaces/ifm:interface[ifm:name=current()]/ifm:type='LoopBack' or
/ifm:ifm/ifm:interfaces/ifm:interface[ifm:name=current()]/ifm:type='40GE' or
/ifm:ifm/ifm:interfaces/ifm:interface[ifm:name=current()]/ifm:type='400GE'" {
              tailf:xpath-root 3;
            }
            mandatory true;
            description
              "Out interface.";
          }
          leaf peer-ip {
            type inet:ipv4-address-no-zone;
            mandatory true;
            description
              "IP next hop.";
          }
        }
        container ip-vpns {
          description
            "List of configure a protection path between the active and standby devices when there is return traffic on the network side.";
          list protect-tunnel-vpn {
            key "vpn";
            description
              "Configure a protection path between the active and standby devices when there is return traffic on the network side.";
            leaf vpn {
              type leafref {
                path "/ncs:devices/ncs:device/ncs:config/ni:network-instance/ni:instances/ni:instance/ni:name" {
                  tailf:xpath-root 3;
                }
              }
              must "/ni:network-instance/ni:instances/ni:instance[ni:name=current()]/l3vpn:afs/l3vpn:af[l3vpn:type='ipv4-unicast']" {
                tailf:xpath-root 3;
              }
              description
                "IP VPN instance.";
            }
            leaf peer-ip {
              type inet:ipv4-address-no-zone;
              mandatory true;
              description
                "Tunnel peer ip.";
            }
            leaf interface {
              type leafref {
                path "/ncs:devices/ncs:device/ncs:config/ifm:ifm/ifm:interfaces/ifm:interface/ifm:name" {
                  tailf:xpath-root 3;
                }
              }
              must "/ifm:ifm/ifm:interfaces/ifm:interface[ifm:name=current()]/ifm:type='Ethernet' or
/ifm:ifm/ifm:interfaces/ifm:interface[ifm:name=current()]/ifm:type='GigabitEthernet' or
/ifm:ifm/ifm:interfaces/ifm:interface[ifm:name=current()]/ifm:type='Eth-Trunk' or
/ifm:ifm/ifm:interfaces/ifm:interface[ifm:name=current()]/ifm:type='10GE' or
/ifm:ifm/ifm:interfaces/ifm:interface[ifm:name=current()]/ifm:type='Virtual-Ethernet' or
/ifm:ifm/ifm:interfaces/ifm:interface[ifm:name=current()]/ifm:type='PW-VE' or
/ifm:ifm/ifm:interfaces/ifm:interface[ifm:name=current()]/ifm:type='XGigabitEthernet' or
/ifm:ifm/ifm:interfaces/ifm:interface[ifm:name=current()]/ifm:type='100GE' or
/ifm:ifm/ifm:interfaces/ifm:interface[ifm:name=current()]/ifm:type='50GE' or
/ifm:ifm/ifm:interfaces/ifm:interface[ifm:name=current()]/ifm:type='50|100GE' or
/ifm:ifm/ifm:interfaces/ifm:interface[ifm:name=current()]/ifm:type='FlexE' or
/ifm:ifm/ifm:interfaces/ifm:interface[ifm:name=current()]/ifm:type='25GE' or
/ifm:ifm/ifm:interfaces/ifm:interface[ifm:name=current()]/ifm:type='LoopBack' or
/ifm:ifm/ifm:interfaces/ifm:interface[ifm:name=current()]/ifm:type='40GE' or
/ifm:ifm/ifm:interfaces/ifm:interface[ifm:name=current()]/ifm:type='400GE'" {
                tailf:xpath-root 3;
              }
              description
                "Out interface.";
            }
          }
        }
      }
      container radius-author-server {
        description
          "Configure the radius author server for remote backup service.";
        container ip-vpn-servers {
          description
            "List of configure the Radius Authorization Server Source IP under Remote Backup Server.";
          list ip-vpn-server {
            key "vpn";
            description
              "Configure the Radius Authorization Server Source IP under Remote Backup Server.";
            leaf vpn {
              type leafref {
                path "/ncs:devices/ncs:device/ncs:config/ni:network-instance/ni:instances/ni:instance/ni:name" {
                  tailf:xpath-root 3;
                }
              }
              must "/ni:network-instance/ni:instances/ni:instance[ni:name=current()]/l3vpn:afs/l3vpn:af[l3vpn:type='ipv4-unicast']" {
                tailf:xpath-root 3;
              }
              description
                "Vpn instance name.";
            }
            leaf ip {
              type inet:ipv4-address-no-zone;
              mandatory true;
              description
                "IP Address.";
            }
          }
        }
        container nas-server {
          description
            "Configure the source IP address of the packets that the router sends back to the RADIUS server to be the same as the NAS IP address.";
          leaf same-as-logic-ip {
            type boolean;
            default "false";
            description
              "Enable/disable specify the source IP same as NAS logic ip.";
          }
        }
      }
      container static-routes {
        description
          "List of configure IP static routes.";
        list static-route {
          key "tag";
          max-elements 10;
          description
            "Configure IP static routes.";
          leaf tag {
            type uint32 {
              range "1..4294967295";
            }
            description
              "Binding IP static routes of specified tag value.";
          }
          leaf cost {
            type uint32 {
              range "1..65535";
            }
            ext:dynamic-default {
              ext:default-value "10" {
                when "../slave-flag = 'false'" {
                  tailf:xpath-root 3;
                }
                description
                  "The default value is 10 when slave-flag is false.";
              }
              ext:default-value "20" {
                when "../slave-flag = 'true'" {
                  tailf:xpath-root 3;
                }
                description
                  "The default value is 20 when slave-flag is true.";
              }
            }
            description
              "Specified by rbs static routes bound to the final release cost value.";
          }
          leaf null-interface-index {
            type uint32 {
              range "0";
            }
            default "0";
            description
              "Null interface index, current value only supports NULL0.";
          }
          leaf slave-flag {
            type boolean;
            default "false";
            description
              "Enable/disable specify the route as a backup state for RUI.";
          }
        }
      }
      container switch-over-uplink {
        when 'not(../track/monitor-groups/monitor-group or ../track/route-monitor-groups/route-monitor-group)' {
          tailf:xpath-root 3;
        }
        description
          "Configure the uplink fault rate threshold for a master/backup switchover and the duration of the uplink fault before the switchover.";
        leaf duration {
          type uint32 {
            range "0..30";
          }
          units "min";
          default "0";
          description
            "Duration value.";
        }
        leaf failure-ratio {
          type uint32 {
            range "1..100";
          }
          units "%";
          default "100";
          description
            "Failure-ratio value.";
        }
      }
      container track {
        description
          "Configure the remote backup service to track.";
        container bfd-session {
          description
            "Configure the remote backup service to track the bidirectional forwarding detection (BFD) session status.";
          leaf session-id {
            type leafref {
              path "/ncs:devices/ncs:device/ncs:config/bfd:bfd/bfd:sessions/bfd:session/bfd:local-discriminator" {
                tailf:xpath-root 3;
              }
            }
            description
              "Specify BFD session ID.";
          }
        }
        container interfaces {
          when 'not(../monitor-groups or ../route-monitor-groups)' {
            tailf:xpath-root 3;
          }
          description
            "List of configure the remote backup service to track the status of the network-side interface.";
          list interface {
            key "name";
            description
              "Configure the remote backup service to track the status of the network-side interface.";
            leaf name {
              type leafref {
                path "/ncs:devices/ncs:device/ncs:config/ifm:ifm/ifm:interfaces/ifm:interface/ifm:name" {
                  tailf:xpath-root 3;
                }
              }
              must "/ifm:ifm/ifm:interfaces/ifm:interface[ifm:name=current()]/ifm:type='MEth' or
/ifm:ifm/ifm:interfaces/ifm:interface[ifm:name=current()]/ifm:type='Ethernet' or
/ifm:ifm/ifm:interfaces/ifm:interface[ifm:name=current()]/ifm:type='GigabitEthernet' or
/ifm:ifm/ifm:interfaces/ifm:interface[ifm:name=current()]/ifm:type='ATM' or
/ifm:ifm/ifm:interfaces/ifm:interface[ifm:name=current()]/ifm:type='Eth-Trunk' or
/ifm:ifm/ifm:interfaces/ifm:interface[ifm:name=current()]/ifm:type='Pos' or
/ifm:ifm/ifm:interfaces/ifm:interface[ifm:name=current()]/ifm:type='XGigabitEthernet' or
/ifm:ifm/ifm:interfaces/ifm:interface[ifm:name=current()]/ifm:type='100GE' or
/ifm:ifm/ifm:interfaces/ifm:interface[ifm:name=current()]/ifm:type='25GE' or
/ifm:ifm/ifm:interfaces/ifm:interface[ifm:name=current()]/ifm:type='10GE' or
/ifm:ifm/ifm:interfaces/ifm:interface[ifm:name=current()]/ifm:type='50GE' or
/ifm:ifm/ifm:interfaces/ifm:interface[ifm:name=current()]/ifm:type='50|100GE' or
/ifm:ifm/ifm:interfaces/ifm:interface[ifm:name=current()]/ifm:type='FlexE' or
/ifm:ifm/ifm:interfaces/ifm:interface[ifm:name=current()]/ifm:type='40GE' or
/ifm:ifm/ifm:interfaces/ifm:interface[ifm:name=current()]/ifm:type='400GE'" {
                tailf:xpath-root 3;
              }
              description
                "Specify interface.";
            }
            leaf weight {
              type uint8 {
                range "1..100";
              }
              default "10";
              description
                "Interface weight value.";
            }
          }
        }
        container monitor-groups {
          description
            "List of configure the status of the remote backup service tracing interface group.";
          list monitor-group {
            key "name";
            max-elements 2;
            description
              "Configure the status of the remote backup service tracing interface group.";
            leaf name {
              type leafref {
                path "/ncs:devices/ncs:device/ncs:config/mg:monitor-group/mg:groups/mg:group/mg:name" {
                  tailf:xpath-root 3;
                }
              }
              description
                "Interface monitor group name.";
            }
            leaf failure-ratio {
              type uint8 {
                range "1..100";
              }
              units "%";
              mandatory true;
              description
                "Failure-ratio value by a percent.";
            }
          }
        }
        container route-monitor-groups {
          description
            "List of configure the route monitoring group monitored by the network to meet the percentage of link failure thresholds.";
          list route-monitor-group {
            key "name";
            max-elements 2;
            description
              "Configure the route monitoring group monitored by the network to meet the percentage of link failure thresholds.";
            leaf name {
              type leafref {
                path "/ncs:devices/ncs:device/ncs:config/rmg:route-monitor-group/rmg:monitor-groups/rmg:monitor-group/rmg:group-name" {
                  tailf:xpath-root 3;
                }
              }
              description
                "Route group name.";
            }
            leaf failure-ratio {
              type uint8 {
                range "1..100";
              }
              units "%";
              mandatory true;
              description
                "Failure-ratio value by a percent.";
            }
          }
        }
      }
      // NCS drop config false container 'dynamic-statistics'
    }
  }
  augment "/ncs:devices/ncs:template/ncs:ned-id/ncs:config/rbs:rbs/rbs:profiles/rbs:profile" {
    description
      "Bras config below remote-backup-profile View.";
    container bras-rui {
      description
        "Configure bras config below remote-backup-profile View.";
      container frame-route {
        // NCS drop when statement
        description
          "Configure a cost value for user routes in a remote backup profile (RBP) on the master device.";
        leaf cost {
          type string;
          description
            "Cost of frame route network route.";
        }
      }
      container ipv4-pools {
        // NCS drop when statement
        description
          "List of configure the address pool under the remote backup template.";
        list ipv4-pool {
          // NCS patched for predictable order
          ordered-by user;
          key "name";
          description
            "Configure the address pool under the remote backup template.";
          leaf name {
            type string;
            description
              "IP pool name.";
          }
        }
      }
      container ipv4-pool-map {
        // NCS drop when statement
        description
          "Configure the name of a source IP address pool (or pool group) and the destination IP address pool (or pool group).";
        container group-groups {
          description
            "List of configure the name of a source IP address pool group and the destination IP address pool group.";
          list group-group {
            // NCS patched for predictable order
            ordered-by user;
            key "source target";
            description
              "Configure the name of a source IP address pool group and the destination IP address pool group.";
            leaf source {
              type string;
              description
                "The source pool group name.";
            }
            leaf target {
              type string;
              description
                "The target pool group name.";
            }
            leaf order {
              type string;
              ext:dynamic-default;
              description
                "The order to choose target pool group. If node-id is not specified, the system automatically assigns node-id according to the configuration sequence. The number is a multiple of 5. That is, the first node-id is 5, the second node-id is 10.";
            }
          }
        }
        container group-pools {
          description
            "List of configure the name of a source IP address pool group and the destination IP address pool.";
          list group-pool {
            // NCS patched for predictable order
            ordered-by user;
            key "source target";
            description
              "Configure the name of a source IP address pool group and the destination IP address pool.";
            leaf source {
              type string;
              description
                "The source pool group name.";
            }
            leaf target {
              type string;
              description
                "The target pool name.";
            }
            leaf order {
              type string;
              ext:dynamic-default;
              description
                "The order to choose target pool group. If node-id is not specified, the system automatically assigns node-id according to the configuration sequence. The number is a multiple of 5. That is, the first node-id is 5, the second node-id is 10.";
            }
          }
        }
        container pool-groups {
          description
            "List of configure the name of a source IP address pool and the destination IP address pool group.";
          list pool-group {
            // NCS patched for predictable order
            ordered-by user;
            key "source target";
            description
              "Configure the name of a source IP address pool and the destination IP address pool group.";
            leaf source {
              type string;
              description
                "IP pool name.";
            }
            leaf target {
              type string;
              description
                "The target pool group name.";
            }
            leaf order {
              type string;
              ext:dynamic-default;
              description
                "The order to choose target pool group. If node-id is not specified, the system automatically assigns node-id according to the configuration sequence. The number is a multiple of 5. That is, the first node-id is 5, the second node-id is 10.";
            }
          }
        }
        container pool-pools {
          description
            "List of configure the name of a source IP address pool and the destination IP address pool.";
          list pool-pool {
            // NCS patched for predictable order
            ordered-by user;
            key "source target";
            description
              "Configure the name of a source IP address pool and the destination IP address pool.";
            leaf source {
              type string;
              description
                "IP pool name.";
            }
            leaf target {
              type string;
              description
                "The target pool name.";
            }
            leaf order {
              type string;
              ext:dynamic-default;
              description
                "The order to choose target pool group. If node-id is not specified, the system automatically assigns node-id according to the configuration sequence. The number is a multiple of 5. That is, the first node-id is 5, the second node-id is 10.";
            }
          }
        }
      }
      container ipv6-pools {
        // NCS drop when statement
        description
          "List of configure the IPv6 address pool under the remote backup template.";
        list ipv6-pool {
          // NCS patched for predictable order
          ordered-by user;
          key "name";
          description
            "Configure the IPv6 address pool under the remote backup template.";
          leaf name {
            type string;
            description
              "IPv6 pool name.";
          }
        }
      }
      container ipv6-pool-maps {
        // NCS drop when statement
        description
          "List of configure the name of a source IPv6 address pool and the destination IPv6 address pool.";
        list ipv6-pool-map {
          // NCS patched for predictable order
          ordered-by user;
          key "source target";
          description
            "Configure the name of a source IPv6 address pool and the destination IPv6 address pool.";
          leaf source {
            type string;
            description
              "IPv6 pool name.";
          }
          leaf target {
            type string;
            description
              "The target IPv6 pool name.";
          }
          leaf order {
            type string;
            ext:dynamic-default;
            description
              "The order to choose target pool group. If node-id is not specified, the system automatically assigns node-id according to the configuration sequence. The number is a multiple of 5. That is, the first node-id is 5, the second node-id is 10.";
          }
        }
      }
      container nas-logic {
        // NCS drop when statement
        description
          "Configure nas logic.";
        container ip-address {
          description
            "Configure logical IP addresses in the remote backup profile.";
          leaf ip {
            type string;
            description
              "Specify logic ip.";
          }
        }
        container port {
          description
            "Configure logical interfaces in the remote backup profile.";
          leaf interface-name {
            type pub-type:ncs_template_if-name;
            description
              "Specify logic port of NAS, the format of the logical interface location information is type+slot ID/subcard ID/interface number, such as Eth-Trunk0/0/10 or Ethernet0/0/10 or Gigabitethernet0/0/10.";
          }
        }
        container system-name {
          description
            "Configure logical host names in the remote backup profile.";
          leaf name {
            type string;
            description
              "Logic host name (1 to 30 characters).";
          }
        }
      }
      container slave-without-forwarding {
        description
          "Configure the slave device in a backup group from forwarding backup packets.";
        leaf enable {
          type string;
          // NCS drop default statement
          description
            "Enable/disable Without-Forwarding.";
        }
      }
      container traffic-backup {
        // NCS drop when statement
        description
          "Configure the interval for backing up access user traffic or the traffic threshold.";
        leaf interval {
          type string;
          // NCS drop default statement
          description
            "Interval of backup (minutes).";
        }
        leaf threshold {
          type string;
          // NCS drop default statement
          description
            "Threshold (MByte).";
        }
      }
    }
  }
  augment "/ncs:devices/ncs:device/ncs:live-status/rbs:rbs/rbs:profiles/rbs:profile" {
    description
      "Bras config below remote-backup-profile View.";
    container bras-rui {
      tailf:ncs-device-type "netconf";
      tailf:display-when "not(../../../../../ncs:module) or ../../../../../ncs:module[ncs:name='huawei-bras-rui'] or (../../../../../ncs:live-status-protocol[not(ncs:capability)]) or (../../../../../ncs:live-status-protocol/ncs:capability/ncs:module[.='huawei-bras-rui'])";
      description
        "Configure bras config below remote-backup-profile View.";
      container frame-route {
        // NCS drop when statement
        description
          "Configure a cost value for user routes in a remote backup profile (RBP) on the master device.";
        leaf cost {
          type uint32 {
            range "1..65535";
          }
          description
            "Cost of frame route network route.";
        }
      }
      container ipv4-pools {
        // NCS drop when statement
        description
          "List of configure the address pool under the remote backup template.";
        list ipv4-pool {
          key "name";
          description
            "Configure the address pool under the remote backup template.";
          leaf name {
            type leafref {
              path "/ncs:devices/ncs:device/ncs:live-status/bras-ipv4-address-manage:bras-ipv4-address-manage/bras-ipv4-address-manage:ipv4-pools/bras-ipv4-address-manage:ipv4-pool/bras-ipv4-address-manage:name" {
                tailf:xpath-root 3;
              }
            }
            description
              "IP pool name.";
          }
        }
      }
      container ipv4-pool-map {
        // NCS drop when statement
        description
          "Configure the name of a source IP address pool (or pool group) and the destination IP address pool (or pool group).";
        container group-groups {
          description
            "List of configure the name of a source IP address pool group and the destination IP address pool group.";
          list group-group {
            key "source target";
            description
              "Configure the name of a source IP address pool group and the destination IP address pool group.";
            leaf source {
              type string {
                length "1..128";
              }
              description
                "The source pool group name.";
            }
            leaf target {
              type leafref {
                path "/ncs:devices/ncs:device/ncs:live-status/bras-ipv4-address-manage:bras-ipv4-address-manage/bras-ipv4-address-manage:pool-groups/bras-ipv4-address-manage:pool-group/bras-ipv4-address-manage:name" {
                  tailf:xpath-root 3;
                }
              }
              description
                "The target pool group name.";
            }
            leaf order {
              type uint32 {
                range "1..65534";
              }
              ext:dynamic-default;
              description
                "The order to choose target pool group. If node-id is not specified, the system automatically assigns node-id according to the configuration sequence. The number is a multiple of 5. That is, the first node-id is 5, the second node-id is 10.";
            }
          }
        }
        container group-pools {
          description
            "List of configure the name of a source IP address pool group and the destination IP address pool.";
          list group-pool {
            key "source target";
            description
              "Configure the name of a source IP address pool group and the destination IP address pool.";
            leaf source {
              type string {
                length "1..128";
              }
              description
                "The source pool group name.";
            }
            leaf target {
              type leafref {
                path "/ncs:devices/ncs:device/ncs:live-status/bras-ipv4-address-manage:bras-ipv4-address-manage/bras-ipv4-address-manage:ipv4-pools/bras-ipv4-address-manage:ipv4-pool/bras-ipv4-address-manage:name" {
                  tailf:xpath-root 3;
                }
              }
              description
                "The target pool name.";
            }
            leaf order {
              type uint32 {
                range "1..65534";
              }
              ext:dynamic-default;
              description
                "The order to choose target pool group. If node-id is not specified, the system automatically assigns node-id according to the configuration sequence. The number is a multiple of 5. That is, the first node-id is 5, the second node-id is 10.";
            }
          }
        }
        container pool-groups {
          description
            "List of configure the name of a source IP address pool and the destination IP address pool group.";
          list pool-group {
            key "source target";
            description
              "Configure the name of a source IP address pool and the destination IP address pool group.";
            leaf source {
              type string {
                length "1..128";
              }
              description
                "IP pool name.";
            }
            leaf target {
              type leafref {
                path "/ncs:devices/ncs:device/ncs:live-status/bras-ipv4-address-manage:bras-ipv4-address-manage/bras-ipv4-address-manage:pool-groups/bras-ipv4-address-manage:pool-group/bras-ipv4-address-manage:name" {
                  tailf:xpath-root 3;
                }
              }
              description
                "The target pool group name.";
            }
            leaf order {
              type uint32 {
                range "1..65534";
              }
              ext:dynamic-default;
              description
                "The order to choose target pool group. If node-id is not specified, the system automatically assigns node-id according to the configuration sequence. The number is a multiple of 5. That is, the first node-id is 5, the second node-id is 10.";
            }
          }
        }
        container pool-pools {
          description
            "List of configure the name of a source IP address pool and the destination IP address pool.";
          list pool-pool {
            key "source target";
            description
              "Configure the name of a source IP address pool and the destination IP address pool.";
            leaf source {
              type string {
                length "1..128";
              }
              description
                "IP pool name.";
            }
            leaf target {
              type leafref {
                path "/ncs:devices/ncs:device/ncs:live-status/bras-ipv4-address-manage:bras-ipv4-address-manage/bras-ipv4-address-manage:ipv4-pools/bras-ipv4-address-manage:ipv4-pool/bras-ipv4-address-manage:name" {
                  tailf:xpath-root 3;
                }
              }
              description
                "The target pool name.";
            }
            leaf order {
              type uint32 {
                range "1..65534";
              }
              ext:dynamic-default;
              description
                "The order to choose target pool group. If node-id is not specified, the system automatically assigns node-id according to the configuration sequence. The number is a multiple of 5. That is, the first node-id is 5, the second node-id is 10.";
            }
          }
        }
      }
      container ipv6-pools {
        // NCS drop when statement
        description
          "List of configure the IPv6 address pool under the remote backup template.";
        list ipv6-pool {
          key "name";
          description
            "Configure the IPv6 address pool under the remote backup template.";
          leaf name {
            type leafref {
              path "/ncs:devices/ncs:device/ncs:live-status/bras-ipv6-address-manage:bras-ipv6-address-manage/bras-ipv6-address-manage:ipv6-pools/bras-ipv6-address-manage:ipv6-pool/bras-ipv6-address-manage:name" {
                tailf:xpath-root 3;
              }
            }
            description
              "IPv6 pool name.";
          }
        }
      }
      container ipv6-pool-maps {
        // NCS drop when statement
        description
          "List of configure the name of a source IPv6 address pool and the destination IPv6 address pool.";
        list ipv6-pool-map {
          key "source target";
          description
            "Configure the name of a source IPv6 address pool and the destination IPv6 address pool.";
          leaf source {
            type string {
              length "1..32";
            }
            description
              "IPv6 pool name.";
          }
          leaf target {
            type leafref {
              path "/ncs:devices/ncs:device/ncs:live-status/bras-ipv6-address-manage:bras-ipv6-address-manage/bras-ipv6-address-manage:ipv6-pools/bras-ipv6-address-manage:ipv6-pool/bras-ipv6-address-manage:name" {
                tailf:xpath-root 3;
              }
            }
            description
              "The target IPv6 pool name.";
          }
          leaf order {
            type uint32 {
              range "1..65534";
            }
            ext:dynamic-default;
            description
              "The order to choose target pool group. If node-id is not specified, the system automatically assigns node-id according to the configuration sequence. The number is a multiple of 5. That is, the first node-id is 5, the second node-id is 10.";
          }
        }
      }
      container nas-logic {
        // NCS drop when statement
        description
          "Configure nas logic.";
        container ip-address {
          description
            "Configure logical IP addresses in the remote backup profile.";
          leaf ip {
            type inet:ipv4-address-no-zone;
            description
              "Specify logic ip.";
          }
        }
        container port {
          description
            "Configure logical interfaces in the remote backup profile.";
          leaf interface-name {
            type pub-type:live_ncs_if-name;
            description
              "Specify logic port of NAS, the format of the logical interface location information is type+slot ID/subcard ID/interface number, such as Eth-Trunk0/0/10 or Ethernet0/0/10 or Gigabitethernet0/0/10.";
          }
        }
        container system-name {
          description
            "Configure logical host names in the remote backup profile.";
          leaf name {
            type string {
              length "1..30";
            }
            description
              "Logic host name (1 to 30 characters).";
          }
        }
      }
      container slave-without-forwarding {
        description
          "Configure the slave device in a backup group from forwarding backup packets.";
        leaf enable {
          type boolean;
          // NCS drop default statement
          description
            "Enable/disable Without-Forwarding.";
        }
      }
      container traffic-backup {
        // NCS drop when statement
        description
          "Configure the interval for backing up access user traffic or the traffic threshold.";
        leaf interval {
          type uint32 {
            range "0..1440";
          }
          // NCS drop default statement
          description
            "Interval of backup (minutes).";
        }
        leaf threshold {
          type uint32 {
            range "0..100000";
          }
          // NCS drop default statement
          description
            "Threshold (MByte).";
        }
      }
    }
  }
  augment "/ncs:devices/ncs:device/ncs:config/rbs:rbs/rbs:profiles/rbs:profile" {
    description
      "Bras config below remote-backup-profile View.";
    container bras-rui {
      tailf:ncs-device-type "netconf";
      tailf:display-when "not(../../../../../ncs:module) or ../../../../../ncs:module[ncs:name='huawei-bras-rui']";
      description
        "Configure bras config below remote-backup-profile View.";
      container frame-route {
        when "../../rbs:service-types/rbs:service-type[rbs:type = 'bras']" {
          tailf:xpath-root 3;
        }
        description
          "Configure a cost value for user routes in a remote backup profile (RBP) on the master device.";
        leaf cost {
          type uint32 {
            range "1..65535";
          }
          description
            "Cost of frame route network route.";
        }
      }
      container ipv4-pools {
        when "../../rbs:service-types/rbs:service-type[rbs:type = 'bras']" {
          tailf:xpath-root 3;
        }
        description
          "List of configure the address pool under the remote backup template.";
        list ipv4-pool {
          key "name";
          description
            "Configure the address pool under the remote backup template.";
          leaf name {
            type leafref {
              path "/ncs:devices/ncs:device/ncs:config/bras-ipv4-address-manage:bras-ipv4-address-manage/bras-ipv4-address-manage:ipv4-pools/bras-ipv4-address-manage:ipv4-pool/bras-ipv4-address-manage:name" {
                tailf:xpath-root 3;
              }
            }
            description
              "IP pool name.";
          }
        }
      }
      container ipv4-pool-map {
        when "../../rbs:service-types/rbs:service-type[rbs:type = 'bras']" {
          tailf:xpath-root 3;
        }
        description
          "Configure the name of a source IP address pool (or pool group) and the destination IP address pool (or pool group).";
        container group-groups {
          description
            "List of configure the name of a source IP address pool group and the destination IP address pool group.";
          list group-group {
            key "source target";
            description
              "Configure the name of a source IP address pool group and the destination IP address pool group.";
            leaf source {
              type string {
                length "1..128";
              }
              description
                "The source pool group name.";
            }
            leaf target {
              type leafref {
                path "/ncs:devices/ncs:device/ncs:config/bras-ipv4-address-manage:bras-ipv4-address-manage/bras-ipv4-address-manage:pool-groups/bras-ipv4-address-manage:pool-group/bras-ipv4-address-manage:name" {
                  tailf:xpath-root 3;
                }
              }
              description
                "The target pool group name.";
            }
            leaf order {
              type uint32 {
                range "1..65534";
              }
              ext:dynamic-default;
              description
                "The order to choose target pool group. If node-id is not specified, the system automatically assigns node-id according to the configuration sequence. The number is a multiple of 5. That is, the first node-id is 5, the second node-id is 10.";
            }
          }
        }
        container group-pools {
          description
            "List of configure the name of a source IP address pool group and the destination IP address pool.";
          list group-pool {
            key "source target";
            description
              "Configure the name of a source IP address pool group and the destination IP address pool.";
            leaf source {
              type string {
                length "1..128";
              }
              description
                "The source pool group name.";
            }
            leaf target {
              type leafref {
                path "/ncs:devices/ncs:device/ncs:config/bras-ipv4-address-manage:bras-ipv4-address-manage/bras-ipv4-address-manage:ipv4-pools/bras-ipv4-address-manage:ipv4-pool/bras-ipv4-address-manage:name" {
                  tailf:xpath-root 3;
                }
              }
              description
                "The target pool name.";
            }
            leaf order {
              type uint32 {
                range "1..65534";
              }
              ext:dynamic-default;
              description
                "The order to choose target pool group. If node-id is not specified, the system automatically assigns node-id according to the configuration sequence. The number is a multiple of 5. That is, the first node-id is 5, the second node-id is 10.";
            }
          }
        }
        container pool-groups {
          description
            "List of configure the name of a source IP address pool and the destination IP address pool group.";
          list pool-group {
            key "source target";
            description
              "Configure the name of a source IP address pool and the destination IP address pool group.";
            leaf source {
              type string {
                length "1..128";
              }
              description
                "IP pool name.";
            }
            leaf target {
              type leafref {
                path "/ncs:devices/ncs:device/ncs:config/bras-ipv4-address-manage:bras-ipv4-address-manage/bras-ipv4-address-manage:pool-groups/bras-ipv4-address-manage:pool-group/bras-ipv4-address-manage:name" {
                  tailf:xpath-root 3;
                }
              }
              description
                "The target pool group name.";
            }
            leaf order {
              type uint32 {
                range "1..65534";
              }
              ext:dynamic-default;
              description
                "The order to choose target pool group. If node-id is not specified, the system automatically assigns node-id according to the configuration sequence. The number is a multiple of 5. That is, the first node-id is 5, the second node-id is 10.";
            }
          }
        }
        container pool-pools {
          description
            "List of configure the name of a source IP address pool and the destination IP address pool.";
          list pool-pool {
            key "source target";
            description
              "Configure the name of a source IP address pool and the destination IP address pool.";
            leaf source {
              type string {
                length "1..128";
              }
              description
                "IP pool name.";
            }
            leaf target {
              type leafref {
                path "/ncs:devices/ncs:device/ncs:config/bras-ipv4-address-manage:bras-ipv4-address-manage/bras-ipv4-address-manage:ipv4-pools/bras-ipv4-address-manage:ipv4-pool/bras-ipv4-address-manage:name" {
                  tailf:xpath-root 3;
                }
              }
              description
                "The target pool name.";
            }
            leaf order {
              type uint32 {
                range "1..65534";
              }
              ext:dynamic-default;
              description
                "The order to choose target pool group. If node-id is not specified, the system automatically assigns node-id according to the configuration sequence. The number is a multiple of 5. That is, the first node-id is 5, the second node-id is 10.";
            }
          }
        }
      }
      container ipv6-pools {
        when "../../rbs:service-types/rbs:service-type[rbs:type = 'bras']" {
          tailf:xpath-root 3;
        }
        description
          "List of configure the IPv6 address pool under the remote backup template.";
        list ipv6-pool {
          key "name";
          description
            "Configure the IPv6 address pool under the remote backup template.";
          leaf name {
            type leafref {
              path "/ncs:devices/ncs:device/ncs:config/bras-ipv6-address-manage:bras-ipv6-address-manage/bras-ipv6-address-manage:ipv6-pools/bras-ipv6-address-manage:ipv6-pool/bras-ipv6-address-manage:name" {
                tailf:xpath-root 3;
              }
            }
            description
              "IPv6 pool name.";
          }
        }
      }
      container ipv6-pool-maps {
        when "../../rbs:service-types/rbs:service-type[rbs:type = 'bras']" {
          tailf:xpath-root 3;
        }
        description
          "List of configure the name of a source IPv6 address pool and the destination IPv6 address pool.";
        list ipv6-pool-map {
          key "source target";
          description
            "Configure the name of a source IPv6 address pool and the destination IPv6 address pool.";
          leaf source {
            type string {
              length "1..32";
            }
            description
              "IPv6 pool name.";
          }
          leaf target {
            type leafref {
              path "/ncs:devices/ncs:device/ncs:config/bras-ipv6-address-manage:bras-ipv6-address-manage/bras-ipv6-address-manage:ipv6-pools/bras-ipv6-address-manage:ipv6-pool/bras-ipv6-address-manage:name" {
                tailf:xpath-root 3;
              }
            }
            description
              "The target IPv6 pool name.";
          }
          leaf order {
            type uint32 {
              range "1..65534";
            }
            ext:dynamic-default;
            description
              "The order to choose target pool group. If node-id is not specified, the system automatically assigns node-id according to the configuration sequence. The number is a multiple of 5. That is, the first node-id is 5, the second node-id is 10.";
          }
        }
      }
      container nas-logic {
        when "../../rbs:service-types/rbs:service-type[rbs:type = 'bras']" {
          tailf:xpath-root 3;
        }
        description
          "Configure nas logic.";
        container ip-address {
          description
            "Configure logical IP addresses in the remote backup profile.";
          leaf ip {
            type inet:ipv4-address-no-zone;
            description
              "Specify logic ip.";
          }
        }
        container port {
          description
            "Configure logical interfaces in the remote backup profile.";
          leaf interface-name {
            type pub-type:if-name;
            description
              "Specify logic port of NAS, the format of the logical interface location information is type+slot ID/subcard ID/interface number, such as Eth-Trunk0/0/10 or Ethernet0/0/10 or Gigabitethernet0/0/10.";
          }
        }
        container system-name {
          description
            "Configure logical host names in the remote backup profile.";
          leaf name {
            type string {
              length "1..30";
            }
            description
              "Logic host name (1 to 30 characters).";
          }
        }
      }
      container slave-without-forwarding {
        description
          "Configure the slave device in a backup group from forwarding backup packets.";
        leaf enable {
          type boolean;
          default "false";
          description
            "Enable/disable Without-Forwarding.";
        }
      }
      container traffic-backup {
        when "../../rbs:service-types/rbs:service-type[rbs:type = 'bras']" {
          tailf:xpath-root 3;
        }
        description
          "Configure the interval for backing up access user traffic or the traffic threshold.";
        leaf interval {
          type uint32 {
            range "0..1440";
          }
          default "20";
          description
            "Interval of backup (minutes).";
        }
        leaf threshold {
          type uint32 {
            range "0..100000";
          }
          default "100";
          description
            "Threshold (MByte).";
        }
      }
    }
  }
}
