module huawei-gre {
  // Generated by yanger -t ncs
  tailf:mount-id "huawei-nc-1.0:huawei-nc-1.0";
  tailf:ncs-device-type "netconf";

  namespace "urn:huawei:yang:huawei-gre";
  prefix gre;

  import ietf-inet-types {
    prefix inet;
  }
  import huawei-pub-type {
    prefix pub-type;
  }
  import huawei-extension {
    prefix ext;
  }
  import huawei-ifm {
    prefix ifm;
  }
  import huawei-tunnel-management {
    prefix tnlm;
  }
  import huawei-network-instance {
    prefix ni;
  }
  import huawei-l3vpn {
    prefix l3vpn;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Generic Routing Encapsulation (GRE) is a tunneling protocol that can encapsulate a
     wide variety of network layer protocols inside virtual point-to-point links or point-to-multipoint
     links over an Internet Protocol network.";

  revision 2020-05-18 {
    description
      "Add when/must condition.";
    reference "Huawei private.";
  }
  revision 2020-05-06 {
    description
      "Remove GRE group.";
    reference "Huawei private.";
  }
  revision 2020-03-26 {
    description
      "White-box errors are resolved.";
    reference "Huawei private.";
  }
  revision 2020-01-13 {
    description
      "Add a leaf node mtu-check-enable.";
    reference "Huawei private.";
  }
  revision 2019-10-10 {
    description
      "Initial revision.";
    reference "Huawei private.";
  }
  ext:task-name "gre";

  augment "/ncs:devices/ncs:device/ncs:rpc" {
    container rpc-reset-keep-alive {
      tailf:ncs-device-type "netconf";
      tailf:display-when "not(../../ncs:module) or ../../ncs:module[ncs:name='huawei-gre']";
      tailf:action reset-keep-alive {
        tailf:actionpoint ncsproxy {
          tailf:internal;
        }
        description
          "Clear Keepalive packet statistics.";
        input {
          leaf tnl-name {
            type string;
            mandatory true;
            description
              "Tunnel name.";
          }
        }
      }
    }
  }
  augment "/ncs:devices/ncs:device-group/ncs:ned-id/ncs:rpc" {
    container rpc-reset-keep-alive {
      tailf:ncs-device-type "netconf";
      tailf:display-when "/ncs:devices/ncs:device[ncs:name=current()/../../../ncs:member]/ncs:module[ncs:name='huawei-gre']";
      tailf:action reset-keep-alive {
        tailf:actionpoint ncsproxy {
          tailf:internal;
        }
        description
          "Clear Keepalive packet statistics.";
        input {
          leaf tnl-name {
            type string;
            mandatory true;
            description
              "Tunnel name.";
          }
        }
      }
    }
  }
  augment "/ncs:devices/ncs:template/ncs:ned-id/ncs:config/ni:network-instance/ni:instances/ni:instance" {
    description
      "GRE configuration on network instance.";
    container gre {
      description
        "Configure Generic Routing Encapsulation.";
      leaf-list bind-src-interface-names {
        // NCS patched for predictable order
        ordered-by user;
        type string;
        // NCS drop must statement
        // NCS drop max-elements statement
        description
          "Specify the interface bound to a GRE tunnel.";
      }
    }
  }
  augment "/ncs:devices/ncs:device/ncs:live-status/ni:network-instance/ni:instances/ni:instance" {
    description
      "GRE configuration on network instance.";
    container gre {
      tailf:ncs-device-type "netconf";
      tailf:display-when "not(../../../../../ncs:module) or ../../../../../ncs:module[ncs:name='huawei-gre'] or (../../../../../ncs:live-status-protocol[not(ncs:capability)]) or (../../../../../ncs:live-status-protocol/ncs:capability/ncs:module[.='huawei-gre'])";
      description
        "Configure Generic Routing Encapsulation.";
      leaf-list bind-src-interface-names {
        type leafref {
          path "/ncs:devices/ncs:device/ncs:live-status/ifm:ifm/ifm:interfaces/ifm:interface/ifm:name" {
            tailf:xpath-root 3;
          }
        }
        // NCS drop must statement
        // NCS drop max-elements statement
        description
          "Specify the interface bound to a GRE tunnel.";
      }
    }
  }
  augment "/ncs:devices/ncs:device/ncs:config/ni:network-instance/ni:instances/ni:instance" {
    description
      "GRE configuration on network instance.";
    container gre {
      tailf:ncs-device-type "netconf";
      tailf:display-when "not(../../../../../ncs:module) or ../../../../../ncs:module[ncs:name='huawei-gre']";
      description
        "Configure Generic Routing Encapsulation.";
      leaf-list bind-src-interface-names {
        type leafref {
          path "/ncs:devices/ncs:device/ncs:config/ifm:ifm/ifm:interfaces/ifm:interface/ifm:name" {
            tailf:xpath-root 3;
          }
        }
        must '../../ni:name=/ifm:ifm/ifm:interfaces/ifm:interface[ifm:name=current()]/ifm:vrf-name' {
          tailf:xpath-root 3;
        }
        max-elements 1024;
        description
          "Specify the interface bound to a GRE tunnel.";
      }
    }
  }
  augment "/ncs:devices/ncs:template/ncs:ned-id/ncs:config/ifm:ifm/ifm:interfaces/ifm:interface/tnlm:tunnel-protocol/tnlm:type" {
    description
      "GRE configuration on interface.";
    case gre {
      description
        "Generic Routing Encapsulation.";
      container gre-tunnel {
        // NCS drop when statement
        presence "Specifies tunnel-protocol GRE.";
        description
          "Configure GRE tunnel.";
        choice source {
          description
            "Source configuration.";
          case ip-info {
            description
              "Source IPv4 address configuration.";
            leaf address {
              type string;
              description
                "Source IPv4 address.";
            }
          }
          case if-info {
            description
              "Source interface name configuration.";
            leaf if-name {
              type string;
              // NCS drop must statement
              // NCS drop must statement
              description
                "Source interface name.";
            }
          }
        }
        container destination {
          description
            "Configure destination.";
          leaf vpn-name {
            // NCS drop when statement
            type string;
            // NCS drop must statement
            description
              "Destination VPN name.";
          }
          leaf address {
            type string;
            description
              "Destination IPv4 address.";
          }
        }
        leaf key {
          type pub-type:ncs_template_password-extend;
          description
            "GRE tunnel key, an integer ranging from 0 to 4294967295.";
        }
        container keep-alive-enable {
          presence "Enable keep alive.";
          description
            "Enable/disable GRE keep alive.";
          leaf period {
            type string;
            units "s";
            // NCS drop default statement
            description
              "Interval at which Keepalive packets are sent.";
          }
          leaf retry-cnt {
            type string;
            // NCS drop default statement
            description
              "Number of retry times for Keepalive packets.";
          }
        }
        leaf path-mtu-enable {
          type string;
          // NCS drop default statement
          description
            "Enable/disable tunnel PMTU learning.";
        }
        leaf statistic-enable {
          type string;
          // NCS drop default statement
          description
            "Enable/disable the GRE tunnel statistic.";
        }
        leaf checksum-enable {
          type string;
          // NCS drop default statement
          description
            "Enable/disable the GRE tunnel checksum.";
        }
        leaf mtu-check-enable {
          type string;
          // NCS drop default statement
          description
            "Enable/disable the GRE tunnel mtu check.";
        }
        // NCS drop config false container 'keep-alive'
      }
    }
    case gre6 {
      description
        "Generic Routing Encapsulation on IPv6.";
      container gre6-tunnel {
        // NCS drop when statement
        presence "Specifies tunnel-protocol GRE IPv6.";
        description
          "Configure GRE IPv6 tunnel.";
        choice source {
          description
            "Source configuration.";
          case ip-info {
            description
              "Source IPv6 address configuration.";
            leaf address {
              type string;
              description
                "Source IPv6 address.";
            }
          }
          case if-info {
            description
              "Source interface name configuration.";
            leaf if-name {
              type string;
              // NCS drop must statement
              // NCS drop must statement
              description
                "Source interface name.";
            }
          }
        }
        container destination {
          description
            "Configure destination.";
          leaf vpn-name {
            // NCS drop when statement
            type string;
            // NCS drop must statement
            description
              "Destination vpn name.";
          }
          leaf address {
            type string;
            description
              "Destination IPv6 address.";
          }
        }
      }
    }
    case p2mp-gre {
      description
        "Multicast Generic Routing Encapsulation.";
      container mgre-tunnel {
        // NCS drop when statement
        presence "Specifies tunnel-protocol GRE p2mp.";
        description
          "Configure mGRE tunnel.";
        choice source {
          description
            "Source configuration.";
          case ip-info {
            description
              "Source IPv4 address configuration.";
            leaf address {
              type string;
              description
                "Source IPv4 address.";
            }
          }
          case if-info {
            description
              "Source interface name configuration.";
            leaf if-name {
              type string;
              // NCS drop must statement
              // NCS drop must statement
              description
                "Source interface name.";
            }
          }
        }
        leaf key {
          type pub-type:ncs_template_password-extend;
          description
            "GRE tunnel key, an integer ranging from 0 to 4294967295.";
        }
      }
    }
  }
  augment "/ncs:devices/ncs:device/ncs:live-status/ifm:ifm/ifm:interfaces/ifm:interface/tnlm:tunnel-protocol/tnlm:type" {
    description
      "GRE configuration on interface.";
    case gre {
      description
        "Generic Routing Encapsulation.";
      container gre-tunnel {
        // NCS drop when statement
        presence "Specifies tunnel-protocol GRE.";
        description
          "Configure GRE tunnel.";
        choice source {
          description
            "Source configuration.";
          case ip-info {
            description
              "Source IPv4 address configuration.";
            leaf address {
              type inet:ipv4-address-no-zone;
              description
                "Source IPv4 address.";
            }
          }
          case if-info {
            description
              "Source interface name configuration.";
            leaf if-name {
              type leafref {
                path "/ncs:devices/ncs:device/ncs:live-status/ifm:ifm/ifm:interfaces/ifm:interface/ifm:name" {
                  tailf:xpath-root 3;
                }
              }
              // NCS drop must statement
              // NCS drop must statement
              description
                "Source interface name.";
            }
          }
        }
        container destination {
          description
            "Configure destination.";
          leaf vpn-name {
            // NCS drop when statement
            type leafref {
              path "/ncs:devices/ncs:device/ncs:live-status/ni:network-instance/ni:instances/ni:instance/ni:name" {
                tailf:xpath-root 3;
              }
            }
            // NCS drop must statement
            description
              "Destination VPN name.";
          }
          leaf address {
            type inet:ipv4-address-no-zone;
            description
              "Destination IPv4 address.";
          }
        }
        leaf key {
          type pub-type:live_ncs_password-extend;
          description
            "GRE tunnel key, an integer ranging from 0 to 4294967295.";
        }
        container keep-alive-enable {
          presence "Enable keep alive.";
          description
            "Enable/disable GRE keep alive.";
          leaf period {
            type uint32 {
              range "1..32767";
            }
            units "s";
            // NCS drop default statement
            description
              "Interval at which Keepalive packets are sent.";
          }
          leaf retry-cnt {
            type uint32 {
              range "1..255";
            }
            // NCS drop default statement
            description
              "Number of retry times for Keepalive packets.";
          }
        }
        leaf path-mtu-enable {
          type boolean;
          // NCS drop default statement
          description
            "Enable/disable tunnel PMTU learning.";
        }
        leaf statistic-enable {
          type boolean;
          // NCS drop default statement
          description
            "Enable/disable the GRE tunnel statistic.";
        }
        leaf checksum-enable {
          type boolean;
          // NCS drop default statement
          description
            "Enable/disable the GRE tunnel checksum.";
        }
        leaf mtu-check-enable {
          type boolean;
          // NCS drop default statement
          description
            "Enable/disable the GRE tunnel mtu check.";
        }
        container keep-alive {
          description
            "Statistics of Keepalive packets.";
          leaf send-req-cnt {
            type uint32 {
              range "0..4294967295";
            }
            description
              "Number of sent Keepalive packets.";
          }
          leaf recv-rsp-cnt {
            type uint32 {
              range "0..4294967295";
            }
            description
              "Number of received Keepalive response packets.";
          }
          leaf recv-req-cnt {
            type uint32 {
              range "0..4294967295";
            }
            description
              "Number of received Keepalive packets.";
          }
          leaf send-rsp-cnt {
            type uint32 {
              range "0..4294967295";
            }
            description
              "Number of sent Keepalive response packets.";
          }
        }
      }
    }
    case gre6 {
      description
        "Generic Routing Encapsulation on IPv6.";
      container gre6-tunnel {
        // NCS drop when statement
        presence "Specifies tunnel-protocol GRE IPv6.";
        description
          "Configure GRE IPv6 tunnel.";
        choice source {
          description
            "Source configuration.";
          case ip-info {
            description
              "Source IPv6 address configuration.";
            leaf address {
              type inet:ipv6-address-no-zone;
              description
                "Source IPv6 address.";
            }
          }
          case if-info {
            description
              "Source interface name configuration.";
            leaf if-name {
              type leafref {
                path "/ncs:devices/ncs:device/ncs:live-status/ifm:ifm/ifm:interfaces/ifm:interface/ifm:name" {
                  tailf:xpath-root 3;
                }
              }
              // NCS drop must statement
              // NCS drop must statement
              description
                "Source interface name.";
            }
          }
        }
        container destination {
          description
            "Configure destination.";
          leaf vpn-name {
            // NCS drop when statement
            type leafref {
              path "/ncs:devices/ncs:device/ncs:live-status/ni:network-instance/ni:instances/ni:instance/ni:name" {
                tailf:xpath-root 3;
              }
            }
            // NCS drop must statement
            description
              "Destination vpn name.";
          }
          leaf address {
            type inet:ipv6-address-no-zone;
            description
              "Destination IPv6 address.";
          }
        }
      }
    }
    case p2mp-gre {
      description
        "Multicast Generic Routing Encapsulation.";
      container mgre-tunnel {
        // NCS drop when statement
        presence "Specifies tunnel-protocol GRE p2mp.";
        description
          "Configure mGRE tunnel.";
        choice source {
          description
            "Source configuration.";
          case ip-info {
            description
              "Source IPv4 address configuration.";
            leaf address {
              type inet:ipv4-address-no-zone;
              description
                "Source IPv4 address.";
            }
          }
          case if-info {
            description
              "Source interface name configuration.";
            leaf if-name {
              type leafref {
                path "/ncs:devices/ncs:device/ncs:live-status/ifm:ifm/ifm:interfaces/ifm:interface/ifm:name" {
                  tailf:xpath-root 3;
                }
              }
              // NCS drop must statement
              // NCS drop must statement
              description
                "Source interface name.";
            }
          }
        }
        leaf key {
          type pub-type:live_ncs_password-extend;
          description
            "GRE tunnel key, an integer ranging from 0 to 4294967295.";
        }
      }
    }
  }
  augment "/ncs:devices/ncs:device/ncs:config/ifm:ifm/ifm:interfaces/ifm:interface/tnlm:tunnel-protocol/tnlm:type" {
    description
      "GRE configuration on interface.";
    case gre {
      description
        "Generic Routing Encapsulation.";
      container gre-tunnel {
        when "../../ifm:type='Tunnel'" {
          tailf:xpath-root 3;
        }
        presence "Specifies tunnel-protocol GRE.";
        description
          "Configure GRE tunnel.";
        choice source {
          description
            "Source configuration.";
          case ip-info {
            description
              "Source IPv4 address configuration.";
            leaf address {
              type inet:ipv4-address-no-zone;
              description
                "Source IPv4 address.";
            }
          }
          case if-info {
            description
              "Source interface name configuration.";
            leaf if-name {
              type leafref {
                path "/ncs:devices/ncs:device/ncs:config/ifm:ifm/ifm:interfaces/ifm:interface/ifm:name" {
                  tailf:xpath-root 3;
                }
              }
              must 'current()!=../../../ifm:name' {
                tailf:xpath-root 3;
              }
              must "not(/ifm:ifm/ifm:interfaces/ifm:interface[ifm:name=current()]/ifm:l2-mode-enable='true')" {
                tailf:xpath-root 3;
              }
              description
                "Source interface name.";
            }
          }
        }
        container destination {
          description
            "Configure destination.";
          leaf vpn-name {
            when '../address' {
              tailf:xpath-root 3;
            }
            type leafref {
              path "/ncs:devices/ncs:device/ncs:config/ni:network-instance/ni:instances/ni:instance/ni:name" {
                tailf:xpath-root 3;
              }
            }
            must "/ni:network-instance/ni:instances/ni:instance[ni:name=current()]/l3vpn:afs/l3vpn:af[l3vpn:type='ipv4-unicast']" {
              tailf:xpath-root 3;
            }
            description
              "Destination VPN name.";
          }
          leaf address {
            type inet:ipv4-address-no-zone;
            description
              "Destination IPv4 address.";
          }
        }
        leaf key {
          type pub-type:password-extend {
            length "1..128";
          }
          description
            "GRE tunnel key, an integer ranging from 0 to 4294967295.";
        }
        container keep-alive-enable {
          presence "Enable keep alive.";
          description
            "Enable/disable GRE keep alive.";
          leaf period {
            type uint32 {
              range "1..32767";
            }
            units "s";
            default "5";
            description
              "Interval at which Keepalive packets are sent.";
          }
          leaf retry-cnt {
            type uint32 {
              range "1..255";
            }
            default "3";
            description
              "Number of retry times for Keepalive packets.";
          }
        }
        leaf path-mtu-enable {
          type boolean;
          default "false";
          description
            "Enable/disable tunnel PMTU learning.";
        }
        leaf statistic-enable {
          type boolean;
          default "false";
          description
            "Enable/disable the GRE tunnel statistic.";
        }
        leaf checksum-enable {
          type boolean;
          default "false";
          description
            "Enable/disable the GRE tunnel checksum.";
        }
        leaf mtu-check-enable {
          type boolean;
          default "false";
          description
            "Enable/disable the GRE tunnel mtu check.";
        }
        // NCS drop config false container 'keep-alive'
      }
    }
    case gre6 {
      description
        "Generic Routing Encapsulation on IPv6.";
      container gre6-tunnel {
        when "../../ifm:type='Tunnel'" {
          tailf:xpath-root 3;
        }
        presence "Specifies tunnel-protocol GRE IPv6.";
        description
          "Configure GRE IPv6 tunnel.";
        choice source {
          description
            "Source configuration.";
          case ip-info {
            description
              "Source IPv6 address configuration.";
            leaf address {
              type inet:ipv6-address-no-zone;
              description
                "Source IPv6 address.";
            }
          }
          case if-info {
            description
              "Source interface name configuration.";
            leaf if-name {
              type leafref {
                path "/ncs:devices/ncs:device/ncs:config/ifm:ifm/ifm:interfaces/ifm:interface/ifm:name" {
                  tailf:xpath-root 3;
                }
              }
              must 'current()!=../../../ifm:name' {
                tailf:xpath-root 3;
              }
              must "not(/ifm:ifm/ifm:interfaces/ifm:interface[ifm:name=current()]/ifm:l2-mode-enable='true')" {
                tailf:xpath-root 3;
              }
              description
                "Source interface name.";
            }
          }
        }
        container destination {
          description
            "Configure destination.";
          leaf vpn-name {
            when '../address' {
              tailf:xpath-root 3;
            }
            type leafref {
              path "/ncs:devices/ncs:device/ncs:config/ni:network-instance/ni:instances/ni:instance/ni:name" {
                tailf:xpath-root 3;
              }
            }
            must "/ni:network-instance/ni:instances/ni:instance[ni:name=current()]/l3vpn:afs/l3vpn:af[l3vpn:type='ipv6-unicast']" {
              tailf:xpath-root 3;
            }
            description
              "Destination vpn name.";
          }
          leaf address {
            type inet:ipv6-address-no-zone;
            description
              "Destination IPv6 address.";
          }
        }
      }
    }
    case p2mp-gre {
      description
        "Multicast Generic Routing Encapsulation.";
      container mgre-tunnel {
        when "../../ifm:type='Tunnel'" {
          tailf:xpath-root 3;
        }
        presence "Specifies tunnel-protocol GRE p2mp.";
        description
          "Configure mGRE tunnel.";
        choice source {
          description
            "Source configuration.";
          case ip-info {
            description
              "Source IPv4 address configuration.";
            leaf address {
              type inet:ipv4-address-no-zone;
              description
                "Source IPv4 address.";
            }
          }
          case if-info {
            description
              "Source interface name configuration.";
            leaf if-name {
              type leafref {
                path "/ncs:devices/ncs:device/ncs:config/ifm:ifm/ifm:interfaces/ifm:interface/ifm:name" {
                  tailf:xpath-root 3;
                }
              }
              must 'current()!=../../../ifm:name' {
                tailf:xpath-root 3;
              }
              must "not(/ifm:ifm/ifm:interfaces/ifm:interface[ifm:name=current()]/ifm:l2-mode-enable='true')" {
                tailf:xpath-root 3;
              }
              description
                "Source interface name.";
            }
          }
        }
        leaf key {
          type pub-type:password-extend {
            length "1..128";
          }
          description
            "GRE tunnel key, an integer ranging from 0 to 4294967295.";
        }
      }
    }
  }
}
