module huawei-macacc {
  // Generated by yanger -t ncs
  tailf:mount-id "huawei-nc-1.0:huawei-nc-1.0";
  tailf:ncs-device-type "netconf";

  namespace "urn:huawei:yang:huawei-macacc";
  prefix macacc;

  import huawei-extension {
    prefix ext;
  }
  import huawei-l2vpn {
    prefix l2vpn;
  }
  import huawei-bd {
    prefix bd;
  }
  import huawei-ifm {
    prefix ifm;
  }
  import huawei-ethernet {
    prefix ethernet;
  }
  import huawei-pub-type {
    prefix pub-type;
  }
  ext:task-name "mac";

  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "MAC accounting.";

  revision 2021-03-01 {
    description
      "Add MAC accounting containers.";
    reference "Huawei private.";
  }
  revision 2020-06-11 {
    description
      "Add new containers.";
    reference "Huawei private.";
  }
  revision 2020-03-06 {
    description
      "Change description.";
    reference "Huawei private.";
  }
  revision 2019-04-15 {
    description
      "Init revision.";
    reference "Huawei private.";
  }

  augment "/ncs:devices/ncs:device/ncs:rpc" {
    container rpc-reset-mac-accounting-interface {
      tailf:ncs-device-type "netconf";
      tailf:display-when "not(../../ncs:module) or ../../ncs:module[ncs:name='huawei-macacc']";
      tailf:action reset-mac-accounting-interface {
        tailf:actionpoint ncsproxy {
          tailf:internal;
        }
        description
          "Reset MAC accounting counters.";
        ext:node-ref "/ifm:ifm/ifm:interfaces/ifm:interface";
        input {
          leaf interface-name {
            type string;
            mandatory true;
            description
              "Interface name.";
          }
          leaf mac-address {
            type pub-type:ncs_rpc_notif_mac-address;
            description
              "MAC address.";
          }
        }
      }
    }
  }
  augment "/ncs:devices/ncs:device-group/ncs:ned-id/ncs:rpc" {
    container rpc-reset-mac-accounting-interface {
      tailf:ncs-device-type "netconf";
      tailf:display-when "/ncs:devices/ncs:device[ncs:name=current()/../../../ncs:member]/ncs:module[ncs:name='huawei-macacc']";
      tailf:action reset-mac-accounting-interface {
        tailf:actionpoint ncsproxy {
          tailf:internal;
        }
        description
          "Reset MAC accounting counters.";
        ext:node-ref "/ifm:ifm/ifm:interfaces/ifm:interface";
        input {
          leaf interface-name {
            type string;
            mandatory true;
            description
              "Interface name.";
          }
          leaf mac-address {
            type pub-type:ncs_rpc_notif_mac-address;
            description
              "MAC address.";
          }
        }
      }
    }
  }
  augment "/ncs:devices/ncs:template/ncs:ned-id/ncs:config/l2vpn:l2vpn/l2vpn:instances/l2vpn:instance/l2vpn:vpls" {
    description
      "VSI MAC accounting.";
    container mac-accounting {
      // NCS drop when statement
      description
        "Configure VSI MAC accounting.";
      leaf enable {
        type string;
        // NCS drop default statement
        description
          "Enable/disable the flag of VSI MAC accounting.";
      }
    }
  }
  augment "/ncs:devices/ncs:device/ncs:live-status/l2vpn:l2vpn/l2vpn:instances/l2vpn:instance/l2vpn:vpls" {
    description
      "VSI MAC accounting.";
    container mac-accounting {
      tailf:ncs-device-type "netconf";
      tailf:display-when "not(../../../../../../ncs:module) or ../../../../../../ncs:module[ncs:name='huawei-macacc'] or (../../../../../../ncs:live-status-protocol[not(ncs:capability)]) or (../../../../../../ncs:live-status-protocol/ncs:capability/ncs:module[.='huawei-macacc'])";
      // NCS drop when statement
      description
        "Configure VSI MAC accounting.";
      leaf enable {
        type boolean;
        // NCS drop default statement
        description
          "Enable/disable the flag of VSI MAC accounting.";
      }
    }
  }
  augment "/ncs:devices/ncs:device/ncs:config/l2vpn:l2vpn/l2vpn:instances/l2vpn:instance/l2vpn:vpls" {
    description
      "VSI MAC accounting.";
    container mac-accounting {
      tailf:ncs-device-type "netconf";
      tailf:display-when "not(../../../../../../ncs:module) or ../../../../../../ncs:module[ncs:name='huawei-macacc']";
      when "../l2vpn:work-mode='normal'" {
        tailf:xpath-root 3;
      }
      description
        "Configure VSI MAC accounting.";
      leaf enable {
        type boolean;
        default "false";
        description
          "Enable/disable the flag of VSI MAC accounting.";
      }
    }
  }
  augment "/ncs:devices/ncs:template/ncs:ned-id/ncs:config/bd:bd/bd:instances/bd:instance" {
    description
      "BD MAC accounting.";
    container mac-accounting {
      description
        "Configure BD MAC accounting.";
      leaf enable {
        type string;
        // NCS drop default statement
        description
          "Enable/disable the flag of BD MAC accounting.";
      }
    }
  }
  augment "/ncs:devices/ncs:device/ncs:live-status/bd:bd/bd:instances/bd:instance" {
    description
      "BD MAC accounting.";
    container mac-accounting {
      tailf:ncs-device-type "netconf";
      tailf:display-when "not(../../../../../ncs:module) or ../../../../../ncs:module[ncs:name='huawei-macacc'] or (../../../../../ncs:live-status-protocol[not(ncs:capability)]) or (../../../../../ncs:live-status-protocol/ncs:capability/ncs:module[.='huawei-macacc'])";
      description
        "Configure BD MAC accounting.";
      leaf enable {
        type boolean;
        // NCS drop default statement
        description
          "Enable/disable the flag of BD MAC accounting.";
      }
    }
  }
  augment "/ncs:devices/ncs:device/ncs:config/bd:bd/bd:instances/bd:instance" {
    description
      "BD MAC accounting.";
    container mac-accounting {
      tailf:ncs-device-type "netconf";
      tailf:display-when "not(../../../../../ncs:module) or ../../../../../ncs:module[ncs:name='huawei-macacc']";
      description
        "Configure BD MAC accounting.";
      leaf enable {
        type boolean;
        default "false";
        description
          "Enable/disable the flag of BD MAC accounting.";
      }
    }
  }
  augment "/ncs:devices/ncs:template/ncs:ned-id/ncs:config/ifm:ifm/ifm:interfaces/ifm:interface/ethernet:ethernet/ethernet:main-interface" {
    description
      "MAC accounting.";
    container mac-accounting {
      // NCS drop must statement
      description
        "Configure MAC accounting.";
      leaf enable {
        type empty;
        description
          "Enable/disable the flag of MAC accounting.";
      }
    }
  }
  augment "/ncs:devices/ncs:device/ncs:live-status/ifm:ifm/ifm:interfaces/ifm:interface/ethernet:ethernet/ethernet:main-interface" {
    description
      "MAC accounting.";
    container mac-accounting {
      tailf:ncs-device-type "netconf";
      tailf:display-when "not(../../../../../../../ncs:module) or ../../../../../../../ncs:module[ncs:name='huawei-macacc'] or (../../../../../../../ncs:live-status-protocol[not(ncs:capability)]) or (../../../../../../../ncs:live-status-protocol/ncs:capability/ncs:module[.='huawei-macacc'])";
      // NCS drop must statement
      description
        "Configure MAC accounting.";
      leaf enable {
        type empty;
        description
          "Enable/disable the flag of MAC accounting.";
      }
    }
  }
  augment "/ncs:devices/ncs:device/ncs:config/ifm:ifm/ifm:interfaces/ifm:interface/ethernet:ethernet/ethernet:main-interface" {
    description
      "MAC accounting.";
    container mac-accounting {
      tailf:ncs-device-type "netconf";
      tailf:display-when "not(../../../../../../../ncs:module) or ../../../../../../../ncs:module[ncs:name='huawei-macacc']";
      must "(../../../ifm:type='Ethernet' or ../../../ifm:type='GigabitEthernet' or ../../../ifm:type='Eth-Trunk' or ../../../ifm:type='100GE' or ../../../ifm:type='XGigabitEthernet' or ../../../ifm:type='40GE' or ../../../ifm:type='10GE' or ../../../ifm:type='400GE' or ../../../ifm:type='25GE' or ../../../ifm:type='FlexE' or ../../../ifm:type='50GE' or ../../../ifm:type='50|100GE')" {
        tailf:xpath-root 3;
      }
      description
        "Configure MAC accounting.";
      leaf enable {
        type empty;
        description
          "Enable/disable the flag of MAC accounting.";
      }
    }
  }
  augment "/ncs:devices/ncs:template/ncs:ned-id/ncs:config/ifm:ifm/ifm:interfaces/ifm:interface" {
    description
      "Interface MAC accounting.";
    container mac-accounting {
      description
        "Configure MAC accounting.";
      // NCS drop config false container 'mac-accounting-counters'
    }
  }
  augment "/ncs:devices/ncs:device/ncs:live-status/ifm:ifm/ifm:interfaces/ifm:interface" {
    description
      "Interface MAC accounting.";
    container mac-accounting {
      tailf:ncs-device-type "netconf";
      tailf:display-when "not(../../../../../ncs:module) or ../../../../../ncs:module[ncs:name='huawei-macacc'] or (../../../../../ncs:live-status-protocol[not(ncs:capability)]) or (../../../../../ncs:live-status-protocol/ncs:capability/ncs:module[.='huawei-macacc'])";
      description
        "Configure MAC accounting.";
      container mac-accounting-counters {
        description
          "List of the statistics of interface MAC accounting.";
        list mac-accounting-counter {
          key "mac-address";
          description
            "Statistics of the MAC accounting.";
          leaf mac-address {
            type pub-type:live_ncs_mac-address;
            description
              "MAC address.";
          }
          leaf input-frames {
            type uint64;
            units "packet";
            description
              "Number of upstream packets.";
          }
          leaf input-bytes {
            type uint64;
            units "Byte";
            description
              "Number of upstream bytes.";
          }
          leaf output-frames {
            type uint64;
            units "packet";
            description
              "Number of downstream packets.";
          }
          leaf output-bytes {
            type uint64;
            units "Byte";
            description
              "Number of downstream bytes.";
          }
        }
      }
    }
  }
  augment "/ncs:devices/ncs:device/ncs:config/ifm:ifm/ifm:interfaces/ifm:interface" {
    description
      "Interface MAC accounting.";
    container mac-accounting {
      tailf:ncs-device-type "netconf";
      tailf:display-when "not(../../../../../ncs:module) or ../../../../../ncs:module[ncs:name='huawei-macacc']";
      description
        "Configure MAC accounting.";
      // NCS drop config false container 'mac-accounting-counters'
    }
  }
}
