module huawei-bras-auto-save-deviations-NE8000 {
  // Generated by yanger -t ncs
  tailf:mount-id "huawei-nc-1.0:huawei-nc-1.0";
  tailf:ncs-device-type "netconf";

  namespace "urn:huawei:yang:huawei-bras-auto-save-deviations-NE8000";
  prefix bras-auto-save-devs-NE8000;

  import huawei-bras-auto-save {
    prefix bras-auto-save;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "This module defines deviation statements for huawei-bras-auto-save module.";

  revision 2019-11-06 {
    description
      "Initial revision.";
    reference "Huawei private.";
  }

  deviation "/ncs:devices/ncs:template/ncs:ned-id/ncs:config/bras-auto-save:bras-auto-save/bras-auto-save:auto-save-max-user/bras-auto-save:number" {
    deviate replace {
      type string;
    }
  }
  deviation "/ncs:devices/ncs:device/ncs:live-status/bras-auto-save:bras-auto-save/bras-auto-save:auto-save-max-user/bras-auto-save:number" {
    deviate replace {
      type uint32 {
        range "8000..1024000";
      }
    }
  }
  deviation "/ncs:devices/ncs:device/ncs:config/bras-auto-save:bras-auto-save/bras-auto-save:auto-save-max-user/bras-auto-save:number" {
    deviate replace {
      type uint32 {
        range "8000..1024000";
      }
    }
  }
}
