module huawei-qppb-notification {
  // Generated by yanger -t ncs
  tailf:mount-id "huawei-nc-1.0:huawei-nc-1.0";
  tailf:ncs-device-type "netconf";

  yang-version 1;
  namespace "urn:huawei:yang:huawei-qppb-notification";
  prefix qppb-notification;

  import huawei-extension {
    prefix ext;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Notification of qppb.";

  revision 2019-11-06 {
    description
      "Initial revision.";
    reference "Huawei private.";
  }
  ext:task-name "qos";

  typedef ncs_template_qppb-direction-type {
    type string;
    description
      "Direction type.";
  }

  typedef ncs_rpc_notif_qppb-direction-type {
    type enumeration {
      enum "inbound" {
        value 1;
        description
          "Inbound.";
      }
      enum "outbound" {
        value 2;
        description
          "Outbound.";
      }
    }
    description
      "Direction type.";
  }

  typedef live_ncs_qppb-direction-type {
    type enumeration {
      enum "inbound" {
        value 1;
        description
          "Inbound.";
      }
      enum "outbound" {
        value 2;
        description
          "Outbound.";
      }
    }
    description
      "Direction type.";
  }

  typedef qppb-direction-type {
    type enumeration {
      enum "inbound" {
        value 1;
        description
          "Inbound.";
      }
      enum "outbound" {
        value 2;
        description
          "Outbound.";
      }
    }
    description
      "Direction type.";
  }

  augment "/ncs:devices/ncs:device/ncs:notifications/ncs:received-notifications/ncs:notification/ncs:data" {
    container xqos-interface-qppb-delete-alarm {
      presence "";
      config false;
      description
        "The QPPB policy on the interface is deleted or does not take effect.";
      leaf interface-name {
        type string {
          length "1..511";
        }
        description
          "Interface name.";
      }
      leaf policy-name {
        type string {
          length "1..31";
        }
        description
          "Policy name.";
      }
      leaf direction {
        type ncs_rpc_notif_qppb-direction-type;
        description
          "Direction. - 1: inbound - 2: outbound.";
      }
      leaf description {
        type string {
          length "1..128";
        }
        description
          "Precautions information.";
      }
    }
  }
  augment "/ncs:devices/ncs:device/ncs:netconf-notifications/ncs:received-notifications/ncs:notification/ncs:data" {
    container xqos-interface-qppb-delete-alarm {
      presence "";
      config false;
      description
        "The QPPB policy on the interface is deleted or does not take effect.";
      leaf interface-name {
        type string {
          length "1..511";
        }
        description
          "Interface name.";
      }
      leaf policy-name {
        type string {
          length "1..31";
        }
        description
          "Policy name.";
      }
      leaf direction {
        type ncs_rpc_notif_qppb-direction-type;
        description
          "Direction. - 1: inbound - 2: outbound.";
      }
      leaf description {
        type string {
          length "1..128";
        }
        description
          "Precautions information.";
      }
    }
  }
}
