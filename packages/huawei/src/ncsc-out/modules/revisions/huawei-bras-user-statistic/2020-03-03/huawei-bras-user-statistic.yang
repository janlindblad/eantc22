module huawei-bras-user-statistic {
  // Generated by yanger -t ncs
  tailf:mount-id "huawei-nc-1.0:huawei-nc-1.0";
  tailf:ncs-device-type "netconf";

  yang-version 1;
  namespace "urn:huawei:yang:huawei-bras-user-statistic";
  prefix bras-user-statistic;

  import huawei-ifm {
    prefix ifm;
  }
  import huawei-extension {
    prefix ext;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "BRAS user statistics.";
  reference "Huawei private.";

  revision 2020-03-03 {
    description
      "Modify description.";
    reference "Huawei private.";
  }
  revision 2019-04-03 {
    description
      "Init revision.";
    reference "Huawei private.";
  }
  ext:task-name "aaa-access";

  augment "/ncs:devices/ncs:device/ncs:rpc" {
    container rpc-filter-access-user-summary-info {
      tailf:ncs-device-type "netconf";
      tailf:display-when "not(../../ncs:module) or ../../ncs:module[ncs:name='huawei-bras-user-statistic']";
      tailf:action filter-access-user-summary-info {
        tailf:actionpoint ncsproxy {
          tailf:internal;
        }
        description
          "Display summary statistics about access users.";
        input {
          leaf interface-name {
            type string;
            description
              "Interface name.";
          }
          leaf include-sub-interface {
            when '../interface-name' {
              tailf:xpath-root 3;
            }
            type boolean;
            description
              "Whether user access sources include sub-interfaces.";
          }
          leaf pe-vlan-start-id {
            type uint16 {
              range "0..4094";
            }
            description
              "Start outer VLAN ID for user access.";
          }
        }
        output {
          leaf normal-users-number {
            type uint32;
            description
              "Number of common users.";
          }
          leaf rui-local-users-number {
            type uint32;
            description
              "Number of local RUI users.";
          }
          leaf rui-remote-users-number {
            type uint32;
            description
              "Number of remote RUI users.";
          }
          leaf radius-auth-number {
            type uint32;
            description
              "Number of users authenticated through a RADIUS server.";
          }
          leaf radius-proxy-auth-number {
            type uint32;
            description
              "Number of users authenticated through a RADIUS proxy server.";
          }
          leaf no-auth-number {
            type uint32;
            description
              "Number of users granted access without authentication.";
          }
          leaf local-auth-number {
            type uint32;
            description
              "Number of users authenticated locally.";
          }
          leaf tacacs-auth-number {
            type uint32;
            description
              "Number of users authenticated through a TACACS server.";
          }
          leaf total-users-number {
            type uint32;
            description
              "Total number of users.";
          }
        }
      }
    }
  }
  augment "/ncs:devices/ncs:device-group/ncs:ned-id/ncs:rpc" {
    container rpc-filter-access-user-summary-info {
      tailf:ncs-device-type "netconf";
      tailf:display-when "/ncs:devices/ncs:device[ncs:name=current()/../../../ncs:member]/ncs:module[ncs:name='huawei-bras-user-statistic']";
      tailf:action filter-access-user-summary-info {
        tailf:actionpoint ncsproxy {
          tailf:internal;
        }
        description
          "Display summary statistics about access users.";
        input {
          leaf interface-name {
            type string;
            description
              "Interface name.";
          }
          leaf include-sub-interface {
            when '../interface-name' {
              tailf:xpath-root 4;
            }
            type boolean;
            description
              "Whether user access sources include sub-interfaces.";
          }
          leaf pe-vlan-start-id {
            type uint16 {
              range "0..4094";
            }
            description
              "Start outer VLAN ID for user access.";
          }
        }
        output {
          container "device" {
            leaf "name" {
              type string;
            }
            leaf "info" {
              type string;
            }
            container "result" {
              leaf normal-users-number {
                type uint32;
                description
                  "Number of common users.";
              }
              leaf rui-local-users-number {
                type uint32;
                description
                  "Number of local RUI users.";
              }
              leaf rui-remote-users-number {
                type uint32;
                description
                  "Number of remote RUI users.";
              }
              leaf radius-auth-number {
                type uint32;
                description
                  "Number of users authenticated through a RADIUS server.";
              }
              leaf radius-proxy-auth-number {
                type uint32;
                description
                  "Number of users authenticated through a RADIUS proxy server.";
              }
              leaf no-auth-number {
                type uint32;
                description
                  "Number of users granted access without authentication.";
              }
              leaf local-auth-number {
                type uint32;
                description
                  "Number of users authenticated locally.";
              }
              leaf tacacs-auth-number {
                type uint32;
                description
                  "Number of users authenticated through a TACACS server.";
              }
              leaf total-users-number {
                type uint32;
                description
                  "Total number of users.";
              }
            }
          }
        }
      }
    }
  }
}
