module huawei-lldp-deviations-NE8000 {
  // Generated by yanger -t ncs
  tailf:mount-id "huawei-nc-1.0:huawei-nc-1.0";
  tailf:ncs-device-type "netconf";

  namespace "urn:huawei:yang:huawei-lldp-deviations-NE8000";
  prefix lldp-devs-NE8000;

  import huawei-ifm {
    prefix ifm;
  }
  import huawei-lldp {
    prefix lldp;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Link layer discovery protocol.";

  revision 2019-04-23 {
    description
      "Initial revision.";
    reference "Huawei private.";
  }

  deviation "/ncs:devices/ncs:template/ncs:ned-id/ncs:config/ifm:ifm/ifm:interfaces/ifm:interface/lldp:lldp/lldp:session/lldp:tlv-enable/lldp:ddp" {
    deviate not-supported;
  }
  deviation "/ncs:devices/ncs:device/ncs:live-status/ifm:ifm/ifm:interfaces/ifm:interface/lldp:lldp/lldp:session/lldp:tlv-enable/lldp:ddp" {
    deviate not-supported;
  }
  deviation "/ncs:devices/ncs:device/ncs:config/ifm:ifm/ifm:interfaces/ifm:interface/lldp:lldp/lldp:session/lldp:tlv-enable/lldp:ddp" {
    deviate not-supported;
  }
  deviation "/ncs:devices/ncs:template/ncs:ned-id/ncs:config/ifm:ifm/ifm:interfaces/ifm:interface/lldp:lldp/lldp:session/lldp:tlv-enable/lldp:identity" {
    deviate not-supported;
  }
  deviation "/ncs:devices/ncs:device/ncs:live-status/ifm:ifm/ifm:interfaces/ifm:interface/lldp:lldp/lldp:session/lldp:tlv-enable/lldp:identity" {
    deviate not-supported;
  }
  deviation "/ncs:devices/ncs:device/ncs:config/ifm:ifm/ifm:interfaces/ifm:interface/lldp:lldp/lldp:session/lldp:tlv-enable/lldp:identity" {
    deviate not-supported;
  }
  deviation "/ncs:devices/ncs:device/ncs:live-status/ifm:ifm/ifm:interfaces/ifm:interface/lldp:lldp/lldp:session/lldp:neighbors/lldp:neighbor/lldp:identity-tlv" {
    deviate not-supported;
  }
  deviation "/ncs:devices/ncs:template/ncs:ned-id/ncs:config/lldp:lldp/lldp:global-attribute/lldp:mdn-status" {
    deviate not-supported;
  }
  deviation "/ncs:devices/ncs:device/ncs:live-status/lldp:lldp/lldp:global-attribute/lldp:mdn-status" {
    deviate not-supported;
  }
  deviation "/ncs:devices/ncs:device/ncs:config/lldp:lldp/lldp:global-attribute/lldp:mdn-status" {
    deviate not-supported;
  }
  deviation "/ncs:devices/ncs:device/ncs:live-status/ifm:ifm/ifm:interfaces/ifm:interface/lldp:lldp/lldp:session/lldp:neighbors/lldp:neighbor/lldp:ddp-tlv" {
    deviate not-supported;
  }
  deviation "/ncs:devices/ncs:template/ncs:ned-id/ncs:config/lldp:lldp/lldp:global-attribute/lldp:management-address-mode/lldp:global-mode/lldp:management-address-ipv4-bind-if" {
    deviate not-supported;
  }
  deviation "/ncs:devices/ncs:device/ncs:live-status/lldp:lldp/lldp:global-attribute/lldp:management-address-mode/lldp:global-mode/lldp:management-address-ipv4-bind-if" {
    deviate not-supported;
  }
  deviation "/ncs:devices/ncs:device/ncs:config/lldp:lldp/lldp:global-attribute/lldp:management-address-mode/lldp:global-mode/lldp:management-address-ipv4-bind-if" {
    deviate not-supported;
  }
  deviation "/ncs:devices/ncs:template/ncs:ned-id/ncs:config/lldp:lldp/lldp:global-attribute/lldp:management-address-mode/lldp:interface-mode" {
    deviate not-supported;
  }
  deviation "/ncs:devices/ncs:device/ncs:live-status/lldp:lldp/lldp:global-attribute/lldp:management-address-mode/lldp:interface-mode" {
    deviate not-supported;
  }
  deviation "/ncs:devices/ncs:device/ncs:config/lldp:lldp/lldp:global-attribute/lldp:management-address-mode/lldp:interface-mode" {
    deviate not-supported;
  }
  deviation "/ncs:devices/ncs:device/ncs:live-status/ifm:ifm/ifm:interfaces/ifm:interface/lldp:lldp/lldp:session/lldp:local-info/lldp:identity-tlv" {
    deviate not-supported;
  }
  deviation "/ncs:devices/ncs:device/ncs:live-status/ifm:ifm/ifm:interfaces/ifm:interface/lldp:sub-interface-lldp/lldp:session/lldp:local-info/lldp:management-addresss" {
    deviate not-supported;
  }
  deviation "/ncs:devices/ncs:device/ncs:live-status/ifm:ifm/ifm:interfaces/ifm:interface/lldp:lldp/lldp:session/lldp:local-info/lldp:management-addresss" {
    deviate not-supported;
  }
}
