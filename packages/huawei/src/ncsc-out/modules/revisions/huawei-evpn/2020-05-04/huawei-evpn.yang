module huawei-evpn {
  // Generated by yanger -t ncs
  tailf:mount-id "huawei-nc-1.0:huawei-nc-1.0";
  tailf:ncs-device-type "netconf";

  namespace "urn:huawei:yang:huawei-evpn";
  prefix evpn;

  import huawei-acl {
    prefix acl;
  }
  import huawei-network-instance {
    prefix ni;
  }
  import huawei-l3vpn {
    prefix l3vpn;
  }
  import huawei-bd {
    prefix bd;
  }
  import huawei-ifm {
    prefix ifm;
  }
  import huawei-pub-type {
    prefix pub-type;
  }
  import huawei-routing-policy {
    prefix rtp;
  }
  import ietf-inet-types {
    prefix inet;
  }
  import huawei-extension {
    prefix ext;
  }
  import huawei-evpl {
    prefix evpl;
  }
  import huawei-bfd {
    prefix bfd;
  }
  import huawei-bgp {
    prefix bgp;
  }
  import huawei-tunnel-management {
    prefix tnlm;
  }
  import huawei-l2vpn {
    prefix l2vpn;
  }
  import huawei-nvo3 {
    prefix nvo3;
  }
  import ietf-yang-types {
    prefix yang;
  }
  include huawei-evpn-type;
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "EVPN configuration.";

  revision 2020-05-04 {
    description
      "Add container evpl-peer-info, add leaf local-ctrl-word in container evpl-info.";
    reference "Huawei private.";
  }
  revision 2020-04-20 {
    description
      "Add node tunnel-policy-name, modify descriptions of YANG module.";
    reference "Huawei private.";
  }
  revision 2019-03-22 {
    description
      "Initial revision.";
    reference "Huawei private.";
  }
  ext:task-name "evpnbgp";

  grouping ncs_template_mac-duplication-infos-type {
    description
      "Information aggregation about MAC addresses that are duplicate in an EVPN instance.";
    list mac-duplication-info {
      // NCS patched for predictable order
      ordered-by user;
      key "mac-address bd-id";
      description
        "Operational state of information about MAC addresses that are duplicate in an EVPN instance.";
      leaf mac-address {
        type pub-type:ncs_template_mac-address;
        description
          "MAC address.";
      }
      leaf bd-id {
        type string;
        description
          "Bridge domain ID.";
      }
      leaf bd-tag {
        type string;
        description
          "Bridge domain label.";
      }
      leaf dampened-times {
        type string;
        description
          "Number of times that MAC duplication occurs.";
      }
      leaf suppress-flag {
        type string;
        description
          "Flag indicating whether MAC duplication is suppressed.";
      }
      leaf last-source {
        type string;
        description
          "Source port.";
      }
      leaf peer-ip {
        type string;
        description
          "Peer IP address of a PW.";
      }
      leaf vc-id {
        type string;
        description
          "PW ID used to uniquely identify a VC.";
      }
      leaf vc-type {
        type evpn:ncs_template_l2vpn-encapsulate-type;
        description
          "Encapsulation type of a PW.";
      }
      leaf suppress-time {
        type string;
        description
          "Date and time when MAC duplication was suppressed.";
      }
    }
  }

  grouping ncs_template_label-stacks-type {
    description
      "Label stack.";
    list label-stack {
      // NCS patched for predictable order
      ordered-by user;
      key "label-stack level";
      description
        "Operational data of the EVPN label stack.";
      leaf label-stack {
        type string;
        description
          "Label stack index.";
      }
      leaf level {
        type string;
        description
          "Label level.";
      }
      leaf type {
        type string;
        description
          "Label type.";
      }
      leaf label {
        type string;
        description
          "Label value.";
      }
      leaf out-interface {
        type string;
        description
          "Outbound interface name.";
      }
    }
  }

  grouping ncs_template_routing-table-type {
    description
      "Routing table infomation.";
    leaf nexthop {
      type string;
      description
        "Next-hop address to which packets are sent.";
    }
    leaf local-preference {
      type string;
      description
        "Local priority. The attribute is only fit for the routes from IBGP peer, not suit for which of EBGP peer.";
    }
    leaf protocol-preferred-value {
      type string;
      description
        "Preferred value of a protocol.";
    }
    leaf route-preference {
      type string;
      description
        "Preference of a route.";
    }
    leaf route-worse-reason {
      type string;
      description
        "Reason why a route is not selected.";
    }
    leaf as-path {
      type string;
      description
        "List of the ASs that packets pass through.";
    }
    leaf origin {
      type evpn:ncs_template_bgp-origin-type;
      description
        "Origin of a route.";
    }
    leaf med {
      type string;
      description
        "Route MED in the attribute node. The attribute is only fit for the routes from EBGP peer, not suit for which of IBGP peer.";
    }
    leaf route-flag {
      type string;
      description
        "Route flag that contains a string of characters.";
    }
    leaf advertised-peers {
      type string;
      description
        "List of sending peers.";
    }
    leaf route-duration-time {
      type string;
      description
        "Time stamp of a route.";
    }
    leaf pmsi {
      type string;
      description
        "PMSI attribute.";
    }
    leaf other-attribute {
      type string;
      description
        "Other attribute.";
    }
    leaf private-route {
      type string;
      description
        "Private route attribute.";
    }
    leaf outbound-interface {
      type string;
      description
        "Name of the outbound interface of a route.";
    }
    leaf remote-route-id {
      type string;
      description
        "Router ID of a peer.";
    }
    leaf community {
      type string;
      description
        "Community attribute.";
    }
    leaf ext-community {
      type string;
      description
        "Extended community attribute.";
    }
    leaf ipv6-ext-community {
      type string;
      description
        "IPv6 extended community attribute.";
    }
    leaf large-community {
      type string;
      description
        "Large-community attribute information.";
    }
    leaf cluster-list {
      type string;
      description
        "List of Cluster IDs.";
    }
    leaf relay-nexthop {
      type string;
      description
        "Iterated next hop.";
    }
    leaf relay-tunnel-name {
      type string;
      description
        "Name of an iteration tunnel.";
    }
    leaf in-label {
      type string;
      description
        "In-label.";
    }
    leaf out-label {
      type string;
      description
        "Out-label.";
    }
    leaf originator {
      type string;
      description
        "Router ID of the route initiator.";
    }
  }

  grouping ncs_rpc_notif_mac-duplication-infos-type {
    description
      "Information aggregation about MAC addresses that are duplicate in an EVPN instance.";
    list mac-duplication-info {
      key "mac-address bd-id";
      description
        "Operational state of information about MAC addresses that are duplicate in an EVPN instance.";
      leaf mac-address {
        type pub-type:ncs_rpc_notif_mac-address;
        description
          "MAC address.";
      }
      leaf bd-id {
        type uint32 {
          range "1..16777215";
        }
        description
          "Bridge domain ID.";
      }
      leaf bd-tag {
        type uint32 {
          range "1..4094";
        }
        description
          "Bridge domain label.";
      }
      leaf dampened-times {
        type uint8;
        description
          "Number of times that MAC duplication occurs.";
      }
      leaf suppress-flag {
        type boolean;
        description
          "Flag indicating whether MAC duplication is suppressed.";
      }
      leaf last-source {
        type string {
          length "1..100";
        }
        description
          "Source port.";
      }
      leaf peer-ip {
        type inet:ipv4-address-no-zone;
        description
          "Peer IP address of a PW.";
      }
      leaf vc-id {
        type uint32 {
          range "1..4294967295";
        }
        description
          "PW ID used to uniquely identify a VC.";
      }
      leaf vc-type {
        type evpn:ncs_rpc_notif_l2vpn-encapsulate-type;
        description
          "Encapsulation type of a PW.";
      }
      leaf suppress-time {
        type yang:date-and-time;
        description
          "Date and time when MAC duplication was suppressed.";
      }
    }
  }

  grouping ncs_rpc_notif_label-stacks-type {
    description
      "Label stack.";
    list label-stack {
      key "label-stack level";
      description
        "Operational data of the EVPN label stack.";
      leaf label-stack {
        type uint32 {
          range "1..4294967295";
        }
        description
          "Label stack index.";
      }
      leaf level {
        type uint32 {
          range "1..4294967295";
        }
        description
          "Label level.";
      }
      leaf type {
        type string {
          length "1..20";
        }
        description
          "Label type.";
      }
      leaf label {
        type string {
          length "1..20";
        }
        description
          "Label value.";
      }
      leaf out-interface {
        type string;
        description
          "Outbound interface name.";
      }
    }
  }

  grouping ncs_rpc_notif_routing-table-type {
    description
      "Routing table infomation.";
    leaf nexthop {
      type inet:ip-address-no-zone;
      description
        "Next-hop address to which packets are sent.";
    }
    leaf local-preference {
      type uint32;
      description
        "Local priority. The attribute is only fit for the routes from IBGP peer, not suit for which of EBGP peer.";
    }
    leaf protocol-preferred-value {
      type uint32 {
        range "0..4294967295";
      }
      description
        "Preferred value of a protocol.";
    }
    leaf route-preference {
      type uint8 {
        range "0..255";
      }
      description
        "Preference of a route.";
    }
    leaf route-worse-reason {
      type string {
        length "1..50";
      }
      description
        "Reason why a route is not selected.";
    }
    leaf as-path {
      type string {
        length "1..300";
      }
      description
        "List of the ASs that packets pass through.";
    }
    leaf origin {
      type evpn:ncs_rpc_notif_bgp-origin-type;
      description
        "Origin of a route.";
    }
    leaf med {
      type uint32 {
        range "0..4294967295";
      }
      description
        "Route MED in the attribute node. The attribute is only fit for the routes from EBGP peer, not suit for which of IBGP peer.";
    }
    leaf route-flag {
      type string {
        length "1..100";
      }
      description
        "Route flag that contains a string of characters.";
    }
    leaf advertised-peers {
      type string {
        length "1..300";
      }
      description
        "List of sending peers.";
    }
    leaf route-duration-time {
      type uint32;
      description
        "Time stamp of a route.";
    }
    leaf pmsi {
      type string {
        length "1..300";
      }
      description
        "PMSI attribute.";
    }
    leaf other-attribute {
      type string {
        length "1..300";
      }
      description
        "Other attribute.";
    }
    leaf private-route {
      type string {
        length "1..300";
      }
      description
        "Private route attribute.";
    }
    leaf outbound-interface {
      type string {
        length "1..63";
      }
      description
        "Name of the outbound interface of a route.";
    }
    leaf remote-route-id {
      type inet:ipv4-address-no-zone;
      description
        "Router ID of a peer.";
    }
    leaf community {
      type string {
        length "1..300";
      }
      description
        "Community attribute.";
    }
    leaf ext-community {
      type string {
        length "1..300";
      }
      description
        "Extended community attribute.";
    }
    leaf ipv6-ext-community {
      type string {
        length "1..300";
      }
      description
        "IPv6 extended community attribute.";
    }
    leaf large-community {
      type string {
        length "1..200";
      }
      description
        "Large-community attribute information.";
    }
    leaf cluster-list {
      type string {
        length "1..300";
      }
      description
        "List of Cluster IDs.";
    }
    leaf relay-nexthop {
      type inet:ip-address-no-zone;
      description
        "Iterated next hop.";
    }
    leaf relay-tunnel-name {
      type string {
        length "1..44";
      }
      description
        "Name of an iteration tunnel.";
    }
    leaf in-label {
      type uint32 {
        range "0..4294967295";
      }
      description
        "In-label.";
    }
    leaf out-label {
      type uint32 {
        range "0..4294967295";
      }
      description
        "Out-label.";
    }
    leaf originator {
      type inet:ipv4-address-no-zone;
      description
        "Router ID of the route initiator.";
    }
  }

  grouping live_ncs_mac-duplication-infos-type {
    description
      "Information aggregation about MAC addresses that are duplicate in an EVPN instance.";
    list mac-duplication-info {
      key "mac-address bd-id";
      description
        "Operational state of information about MAC addresses that are duplicate in an EVPN instance.";
      leaf mac-address {
        type pub-type:live_ncs_mac-address;
        description
          "MAC address.";
      }
      leaf bd-id {
        type uint32 {
          range "1..16777215";
        }
        description
          "Bridge domain ID.";
      }
      leaf bd-tag {
        type uint32 {
          range "1..4094";
        }
        description
          "Bridge domain label.";
      }
      leaf dampened-times {
        type uint8;
        description
          "Number of times that MAC duplication occurs.";
      }
      leaf suppress-flag {
        type boolean;
        description
          "Flag indicating whether MAC duplication is suppressed.";
      }
      leaf last-source {
        type string {
          length "1..100";
        }
        description
          "Source port.";
      }
      leaf peer-ip {
        type inet:ipv4-address-no-zone;
        description
          "Peer IP address of a PW.";
      }
      leaf vc-id {
        type uint32 {
          range "1..4294967295";
        }
        description
          "PW ID used to uniquely identify a VC.";
      }
      leaf vc-type {
        type evpn:live_ncs_l2vpn-encapsulate-type;
        description
          "Encapsulation type of a PW.";
      }
      leaf suppress-time {
        type yang:date-and-time;
        description
          "Date and time when MAC duplication was suppressed.";
      }
    }
  }

  grouping live_ncs_label-stacks-type {
    description
      "Label stack.";
    list label-stack {
      key "label-stack level";
      description
        "Operational data of the EVPN label stack.";
      leaf label-stack {
        type uint32 {
          range "1..4294967295";
        }
        description
          "Label stack index.";
      }
      leaf level {
        type uint32 {
          range "1..4294967295";
        }
        description
          "Label level.";
      }
      leaf type {
        type string {
          length "1..20";
        }
        description
          "Label type.";
      }
      leaf label {
        type string {
          length "1..20";
        }
        description
          "Label value.";
      }
      leaf out-interface {
        type leafref {
          path "/ncs:devices/ncs:device/ncs:live-status/ifm:ifm/ifm:interfaces/ifm:interface/ifm:name" {
            tailf:xpath-root 3;
          }
        }
        description
          "Outbound interface name.";
      }
    }
  }

  grouping live_ncs_routing-table-type {
    description
      "Routing table infomation.";
    leaf nexthop {
      type inet:ip-address-no-zone;
      description
        "Next-hop address to which packets are sent.";
    }
    leaf local-preference {
      type uint32;
      description
        "Local priority. The attribute is only fit for the routes from IBGP peer, not suit for which of EBGP peer.";
    }
    leaf protocol-preferred-value {
      type uint32 {
        range "0..4294967295";
      }
      description
        "Preferred value of a protocol.";
    }
    leaf route-preference {
      type uint8 {
        range "0..255";
      }
      description
        "Preference of a route.";
    }
    leaf route-worse-reason {
      type string {
        length "1..50";
      }
      description
        "Reason why a route is not selected.";
    }
    leaf as-path {
      type string {
        length "1..300";
      }
      description
        "List of the ASs that packets pass through.";
    }
    leaf origin {
      type evpn:live_ncs_bgp-origin-type;
      description
        "Origin of a route.";
    }
    leaf med {
      type uint32 {
        range "0..4294967295";
      }
      description
        "Route MED in the attribute node. The attribute is only fit for the routes from EBGP peer, not suit for which of IBGP peer.";
    }
    leaf route-flag {
      type string {
        length "1..100";
      }
      description
        "Route flag that contains a string of characters.";
    }
    leaf advertised-peers {
      type string {
        length "1..300";
      }
      description
        "List of sending peers.";
    }
    leaf route-duration-time {
      type uint32;
      description
        "Time stamp of a route.";
    }
    leaf pmsi {
      type string {
        length "1..300";
      }
      description
        "PMSI attribute.";
    }
    leaf other-attribute {
      type string {
        length "1..300";
      }
      description
        "Other attribute.";
    }
    leaf private-route {
      type string {
        length "1..300";
      }
      description
        "Private route attribute.";
    }
    leaf outbound-interface {
      type string {
        length "1..63";
      }
      description
        "Name of the outbound interface of a route.";
    }
    leaf remote-route-id {
      type inet:ipv4-address-no-zone;
      description
        "Router ID of a peer.";
    }
    leaf community {
      type string {
        length "1..300";
      }
      description
        "Community attribute.";
    }
    leaf ext-community {
      type string {
        length "1..300";
      }
      description
        "Extended community attribute.";
    }
    leaf ipv6-ext-community {
      type string {
        length "1..300";
      }
      description
        "IPv6 extended community attribute.";
    }
    leaf large-community {
      type string {
        length "1..200";
      }
      description
        "Large-community attribute information.";
    }
    leaf cluster-list {
      type string {
        length "1..300";
      }
      description
        "List of Cluster IDs.";
    }
    leaf relay-nexthop {
      type inet:ip-address-no-zone;
      description
        "Iterated next hop.";
    }
    leaf relay-tunnel-name {
      type string {
        length "1..44";
      }
      description
        "Name of an iteration tunnel.";
    }
    leaf in-label {
      type uint32 {
        range "0..4294967295";
      }
      description
        "In-label.";
    }
    leaf out-label {
      type uint32 {
        range "0..4294967295";
      }
      description
        "Out-label.";
    }
    leaf originator {
      type inet:ipv4-address-no-zone;
      description
        "Router ID of the route initiator.";
    }
  }

  grouping mac-duplication-infos-type {
    description
      "Information aggregation about MAC addresses that are duplicate in an EVPN instance.";
    list mac-duplication-info {
      key "mac-address bd-id";
      description
        "Operational state of information about MAC addresses that are duplicate in an EVPN instance.";
      leaf mac-address {
        type pub-type:mac-address;
        description
          "MAC address.";
      }
      leaf bd-id {
        type uint32 {
          range "1..16777215";
        }
        description
          "Bridge domain ID.";
      }
      leaf bd-tag {
        type uint32 {
          range "1..4094";
        }
        description
          "Bridge domain label.";
      }
      leaf dampened-times {
        type uint8;
        description
          "Number of times that MAC duplication occurs.";
      }
      leaf suppress-flag {
        type boolean;
        description
          "Flag indicating whether MAC duplication is suppressed.";
      }
      leaf last-source {
        type string {
          length "1..100";
        }
        description
          "Source port.";
      }
      leaf peer-ip {
        type inet:ipv4-address-no-zone;
        description
          "Peer IP address of a PW.";
      }
      leaf vc-id {
        type uint32 {
          range "1..4294967295";
        }
        description
          "PW ID used to uniquely identify a VC.";
      }
      leaf vc-type {
        type evpn:l2vpn-encapsulate-type;
        description
          "Encapsulation type of a PW.";
      }
      leaf suppress-time {
        type yang:date-and-time;
        description
          "Date and time when MAC duplication was suppressed.";
      }
    }
  }

  grouping label-stacks-type {
    description
      "Label stack.";
    list label-stack {
      key "label-stack level";
      description
        "Operational data of the EVPN label stack.";
      leaf label-stack {
        type uint32 {
          range "1..4294967295";
        }
        description
          "Label stack index.";
      }
      leaf level {
        type uint32 {
          range "1..4294967295";
        }
        description
          "Label level.";
      }
      leaf type {
        type string {
          length "1..20";
        }
        description
          "Label type.";
      }
      leaf label {
        type string {
          length "1..20";
        }
        description
          "Label value.";
      }
      leaf out-interface {
        type leafref {
          path "/ncs:devices/ncs:device/ncs:config/ifm:ifm/ifm:interfaces/ifm:interface/ifm:name" {
            tailf:xpath-root 3;
          }
        }
        description
          "Outbound interface name.";
      }
    }
  }

  grouping routing-table-type {
    description
      "Routing table infomation.";
    leaf nexthop {
      type inet:ip-address-no-zone;
      description
        "Next-hop address to which packets are sent.";
    }
    leaf local-preference {
      type uint32;
      description
        "Local priority. The attribute is only fit for the routes from IBGP peer, not suit for which of EBGP peer.";
    }
    leaf protocol-preferred-value {
      type uint32 {
        range "0..4294967295";
      }
      description
        "Preferred value of a protocol.";
    }
    leaf route-preference {
      type uint8 {
        range "0..255";
      }
      description
        "Preference of a route.";
    }
    leaf route-worse-reason {
      type string {
        length "1..50";
      }
      description
        "Reason why a route is not selected.";
    }
    leaf as-path {
      type string {
        length "1..300";
      }
      description
        "List of the ASs that packets pass through.";
    }
    leaf origin {
      type evpn:bgp-origin-type;
      description
        "Origin of a route.";
    }
    leaf med {
      type uint32 {
        range "0..4294967295";
      }
      description
        "Route MED in the attribute node. The attribute is only fit for the routes from EBGP peer, not suit for which of IBGP peer.";
    }
    leaf route-flag {
      type string {
        length "1..100";
      }
      description
        "Route flag that contains a string of characters.";
    }
    leaf advertised-peers {
      type string {
        length "1..300";
      }
      description
        "List of sending peers.";
    }
    leaf route-duration-time {
      type uint32;
      description
        "Time stamp of a route.";
    }
    leaf pmsi {
      type string {
        length "1..300";
      }
      description
        "PMSI attribute.";
    }
    leaf other-attribute {
      type string {
        length "1..300";
      }
      description
        "Other attribute.";
    }
    leaf private-route {
      type string {
        length "1..300";
      }
      description
        "Private route attribute.";
    }
    leaf outbound-interface {
      type string {
        length "1..63";
      }
      description
        "Name of the outbound interface of a route.";
    }
    leaf remote-route-id {
      type inet:ipv4-address-no-zone;
      description
        "Router ID of a peer.";
    }
    leaf community {
      type string {
        length "1..300";
      }
      description
        "Community attribute.";
    }
    leaf ext-community {
      type string {
        length "1..300";
      }
      description
        "Extended community attribute.";
    }
    leaf ipv6-ext-community {
      type string {
        length "1..300";
      }
      description
        "IPv6 extended community attribute.";
    }
    leaf large-community {
      type string {
        length "1..200";
      }
      description
        "Large-community attribute information.";
    }
    leaf cluster-list {
      type string {
        length "1..300";
      }
      description
        "List of Cluster IDs.";
    }
    leaf relay-nexthop {
      type inet:ip-address-no-zone;
      description
        "Iterated next hop.";
    }
    leaf relay-tunnel-name {
      type string {
        length "1..44";
      }
      description
        "Name of an iteration tunnel.";
    }
    leaf in-label {
      type uint32 {
        range "0..4294967295";
      }
      description
        "In-label.";
    }
    leaf out-label {
      type uint32 {
        range "0..4294967295";
      }
      description
        "Out-label.";
    }
    leaf originator {
      type inet:ipv4-address-no-zone;
      description
        "Router ID of the route initiator.";
    }
  }

  augment "/ncs:devices/ncs:device/ncs:rpc" {
    container rpc-reset-evpn-mac-duplication {
      tailf:ncs-device-type "netconf";
      tailf:display-when "not(../../ncs:module) or ../../ncs:module[ncs:name='huawei-evpn']";
      tailf:action reset-evpn-mac-duplication {
        tailf:actionpoint ncsproxy {
          tailf:internal;
        }
        description
          "Reset EVPN MAC duplication.";
        ext:node-ref "/evpn:evpn/evpn:instances/evpn:instance/evpn:normal-evpn/evpn:mac-duplication-infos";
        ext:node-ref "/evpn:evpn/evpn:instances/evpn:instance/evpn:bd-evpn/evpn:mac-duplication-infos";
        input {
          leaf name {
            type ncs_rpc_notif_name-type;
            mandatory true;
            description
              "EVPN instance name.";
          }
          leaf bd-id {
            type uint32 {
              range "1..16777215";
            }
            description
              "BD ID.";
          }
          leaf mac-address {
            type pub-type:ncs_rpc_notif_mac-address;
            description
              "MAC address.";
          }
        }
      }
    }
  }
  augment "/ncs:devices/ncs:device-group/ncs:ned-id/ncs:rpc" {
    container rpc-reset-evpn-mac-duplication {
      tailf:ncs-device-type "netconf";
      tailf:display-when "/ncs:devices/ncs:device[ncs:name=current()/../../../ncs:member]/ncs:module[ncs:name='huawei-evpn']";
      tailf:action reset-evpn-mac-duplication {
        tailf:actionpoint ncsproxy {
          tailf:internal;
        }
        description
          "Reset EVPN MAC duplication.";
        ext:node-ref "/evpn:evpn/evpn:instances/evpn:instance/evpn:normal-evpn/evpn:mac-duplication-infos";
        ext:node-ref "/evpn:evpn/evpn:instances/evpn:instance/evpn:bd-evpn/evpn:mac-duplication-infos";
        input {
          leaf name {
            type ncs_rpc_notif_name-type;
            mandatory true;
            description
              "EVPN instance name.";
          }
          leaf bd-id {
            type uint32 {
              range "1..16777215";
            }
            description
              "BD ID.";
          }
          leaf mac-address {
            type pub-type:ncs_rpc_notif_mac-address;
            description
              "MAC address.";
          }
        }
      }
    }
  }
  augment "/ncs:devices/ncs:device/ncs:config" {
    container evpn {
      tailf:ncs-device-type "netconf";
      tailf:display-when "not(../../ncs:module) or ../../ncs:module[ncs:name='huawei-evpn']";
      description
        "Configure of EVPN.";
      container base-process {
        description
          "Configure of EVPN base process.";
        leaf redundancy-mode {
          type redundancy-mode;
          default "all-active";
          description
            "Redundancy mode.";
        }
        leaf source-address {
          ext:operation-exclude "update";
          type inet:ipv4-address-no-zone;
          description
            "Source address.";
        }
        leaf evpn-overlay {
          type boolean;
          must "(../evpn-overlay!='true' and not(../../instances/instance)) or ../evpn-overlay='true'" {
            tailf:xpath-root 3;
          }
          default "false";
          description
            "Enable/disable EVPN overlay.";
        }
      }
      container site {
        presence "evpn view";
        description
          "Enable/disable global EVPN configuration.";
        leaf df-election-mode {
          type df-election-mode;
          default "per-interface";
          description
            "Global configuration DF election mode.";
        }
        leaf vpws-df-election-mode {
          type vpws-df-election-mode;
          default "per-interface";
          description
            "VPWS DF select mode.";
        }
        leaf ac-influnced-enable {
          type boolean;
          default "false";
          description
            "Enable/disable AC state influenced DF mode.";
        }
        leaf ad-per-es-split {
          type ad-per-es-route-divmode;
          default "dont-divide-rt";
          description
            "EVPN AD per ES route split.";
        }
        leaf irb-reoriginated {
          type boolean;
          default "false";
          description
            "Enable/disable IRB reoriginated without bridge domain.";
        }
        leaf vlan-extend-private-enable {
          type boolean;
          default "false";
          description
            "Enable/disable VLAN extend extcommunity to carry VLAN in MAC routes.";
        }
        leaf vlan-extend-redirect-enable {
          type boolean;
          default "false";
          description
            "Enable/disable VLAN extend extcommunity to redirect to the same ESI interface.";
        }
        leaf local-remote-frr-enable {
          type boolean;
          default "false";
          description
            "Enable/disable local MAC and remote MAC to form FRR.";
        }
        leaf bypass-vxlan-enable {
          type boolean;
          default "false";
          description
            "Enable/disable bypass VXLAN extcommunity, use for allow all-active device to form bypass VXLAN.";
        }
        leaf alm-threshold {
          type uint32 {
            range "1..4294967295";
          }
          description
            "Specify the alarm route threshold.";
        }
        leaf recovery-percentage {
          when '../alm-threshold' {
            tailf:xpath-root 3;
          }
          type uint32 {
            range "1..95";
          }
          units "%";
          default "80";
          description
            "Specify the alarm route recovery percentage.";
        }
        leaf local-remote-vpws-frr-enable {
          type boolean;
          default "false";
          description
            "Enable/disable the local and remote FRR for EVPN VPWS.";
        }
        leaf remote-vpws-frr-enable {
          type boolean;
          default "false";
          description
            "Enable/disable the remote FRR for EVPN VPWS.";
        }
        leaf irb-split-group {
          type boolean;
          default "true";
          description
            "Enable/disable IRB advertise under split group.";
        }
        leaf compatible {
          type boolean;
          default "false";
          description
            "Enable/disable IRB routing rebirth into ARP routing and prefix routing.";
        }
        leaf advertising-vxlan-tunnel-mac {
          type boolean;
          default "false";
          description
            "Enable/disable advertising MAC routes learned by VXLAN tunnel.";
        }
        leaf advertise-suppressed-route {
          type boolean;
          default "false";
          description
            "Enable/disable advertising suppressed detail route.";
        }
        leaf routerid-extend-private-enable {
          type boolean;
          default "false";
          description
            "Enable/disable router ID extend extcommunity for carrying router ID in EVPN routes.";
        }
        leaf mac-duplication-enable {
          type boolean;
          default "true";
          description
            "Enable/disable mac-duplication.";
        }
        container mac-duplication {
          description
            "Configure MAC duplication.";
          leaf period {
            type uint8 {
              range "3..10";
            }
            default "5";
            description
              "Number of times that MAC duplication is detected in a period.";
          }
          leaf cycle {
            type uint16 {
              range "60..900";
            }
            units "s";
            must '../cycle mod 10 = 0' {
              tailf:xpath-root 3;
            }
            default "180";
            description
              "Interval at which MAC duplication is detected.";
          }
          leaf recycle {
            type uint16 {
              range "120..3600";
            }
            units "s";
            must '../recycle mod 10 = 0' {
              tailf:xpath-root 3;
            }
            default "540";
            description
              "Period after which suppression on MAC duplication is removed.";
          }
        }
        container static-esis {
          description
            "List of static ESI.";
          list static-esi {
            key "esi";
            description
              "Configure instance of static ESI.";
            leaf esi {
              type esi;
              description
                "Static ESI, in the format of 00xx.xxxx.xxxx.xxxx.xxxx, in which x ranges from 0 to F. A static ESI cannot be all 0s. To clear a static ESI, enter a space.";
            }
            leaf redundancy-mode {
              type esi-redundancy-mode;
              default "none";
              description
                "Redundancy mode.";
            }
            leaf df-election-type {
              type df-election-type;
              default "default";
              description
                "The DF election type of ESI.";
            }
            leaf preference {
              when "../df-election-type='preference-based'" {
                tailf:xpath-root 3;
              }
              type uint16 {
                range "0..65535";
              }
              default "32767";
              description
                "The preference of ESI.";
            }
            leaf non-revertive {
              when "../df-election-type='preference-based'" {
                tailf:xpath-root 3;
              }
              type boolean;
              default "false";
              description
                "Enable/disable non-revertive mode.";
            }
            leaf df-election {
              when "../redundancy-mode='single-active'" {
                tailf:xpath-root 3;
              }
              type boolean;
              default "false";
              description
                "Enable/disable DF election mode.";
            }
          }
        }
        container dynamic-esis {
          description
            "List of dynamic ESI.";
          list dynamic-esi {
            key "esi-name";
            description
              "Configure instance of dynamic ESI.";
            leaf esi-name {
              type string {
                length "1..31";
              }
              description
                "Dynamic ESI name is a string of 1 to 31 characters, which begins with a-z or A-Z.";
            }
            leaf redundancy-mode {
              type esi-redundancy-mode;
              default "none";
              description
                "Redundancy mode.";
            }
            leaf df-election-type {
              type df-election-type;
              default "default";
              description
                "The DF election type of ESI.";
            }
            leaf preference {
              when "../df-election-type='preference-based'" {
                tailf:xpath-root 3;
              }
              type uint16 {
                range "0..65535";
              }
              default "32767";
              description
                "The preference of ESI.";
            }
            leaf non-revertive {
              when "../df-election-type='preference-based'" {
                tailf:xpath-root 3;
              }
              type boolean;
              default "false";
              description
                "Enable/disable non-revertive mode.";
            }
          }
        }
      }
      container instances {
        description
          "List of EVPN instance.";
        list instance {
          key "name";
          unique "normal-evpn/rd";
          unique "b-evpn/rd";
          unique "bd-evpn/rd";
          unique "vpws-evpn/rd";
          description
            "Configure EVPN instance.";
          leaf name {
            type name-type {
              length "1..31";
            }
            must "../name!='_public_'" {
              tailf:xpath-root 3;
            }
            description
              "EVPN instance name.";
          }
          leaf type {
            ext:operation-exclude "update|delete";
            type evpn-type;
            default "normal";
            description
              "The value specifies the type of EVPN instance.";
          }
          // NCS drop config false leaf 'label-policy'
          container normal-evpn {
            when "../type = 'normal'" {
              tailf:xpath-root 3;
            }
            description
              "Configure normal mode of EVPN instance.";
            leaf description {
              type string {
                length "1..63";
                pattern '([^?]*)';
              }
              description
                "The description for EVPN instance.";
            }
            leaf rd {
              ext:operation-exclude "update";
              type string {
                length "3..21";
              }
              description
                "An EVPN instance address family takes effect only after it is configured with an RD. The RD can be in any of the following formats:
                 1. 16-bit AS number:32-bit user-defined number, 101:3 for example. A 16-bit AS number ranges from 0 to 65535, and a user-defined number ranges from 0 to 4294967295. The AS number and user-defined number cannot be both 0s. This means that the RD value cannot be 0:0.
                 2. 32-bit IP address:16-bit user-defined number, 192.168.122.15:1 for example. The IP address ranges from 0.0.0.0 to 255.255.255.255, and the user-defined number ranges from 0 to 65535.
                 3. 32-bit AS number:16-bit user-defined number, 10.11:3 for example. A 32-bit AS number ranges from 0.0 to 65535.65535 or from 0 to 4294967295, and a user-defined number ranges from 0 to 65535. The AS number and user-defined number cannot be both 0s. This means that the RD value cannot be 0.0:0.";
            }
            leaf tunnel-policy-name {
              when '../rd' {
                tailf:xpath-root 3;
              }
              type leafref {
                path "/ncs:devices/ncs:device/ncs:config/tnlm:tunnel-management/tnlm:tunnel-policys/tnlm:tunnel-policy/tnlm:name" {
                  tailf:xpath-root 3;
                }
              }
              must "not(/tnlm:tunnel-management/tnlm:tunnel-policys/tnlm:tunnel-policy[tnlm:name=current()]/tnlm:ipv6-set/tnlm:select-sequence/tnlm:select-tunnel-types/tnlm:select-tunnel-type) and /tnlm:tunnel-management/tnlm:tunnel-policys/tnlm:tunnel-policy[tnlm:name=current()]/tnlm:ipv4-set/tnlm:select-sequence/tnlm:select-tunnel-types/tnlm:select-tunnel-type[tnlm:type!='gre']" {
                tailf:xpath-root 3;
              }
              description
                "Tunnel policy name.";
            }
            leaf import-policy-name {
              when '../rd' {
                tailf:xpath-root 3;
              }
              type leafref {
                path "/ncs:devices/ncs:device/ncs:config/rtp:routing-policy/rtp:policy-definitions/rtp:policy-definition/rtp:name" {
                  tailf:xpath-root 3;
                }
              }
              description
                "The name of specify import route policy.";
            }
            leaf export-policy-name {
              when '../rd' {
                tailf:xpath-root 3;
              }
              type leafref {
                path "/ncs:devices/ncs:device/ncs:config/rtp:routing-policy/rtp:policy-definitions/rtp:policy-definition/rtp:name" {
                  tailf:xpath-root 3;
                }
              }
              description
                "The name of specify export route policy.";
            }
            leaf local-remote-frr {
              type local-remote-frr-enable-type;
              default "default";
              description
                "Enable/disable local MAC and remote MAC to form FRR.";
            }
            leaf mac-balance-enable {
              type boolean;
              default "false";
              description
                "Enable/disable MAC balance.";
            }
            leaf isolate-spoken {
              type isolate-spoken-type;
              default "default";
              description
                "Forwarding isolation between AC interfaces under EVPN.";
            }
            leaf export-acl-name-or-id {
              type leafref {
                path "/ncs:devices/ncs:device/ncs:config/acl:acl/acl:groups/acl:group/acl:identity" {
                  tailf:xpath-root 3;
                }
              }
              description
                "Name or number of an IPv4 ACL used by a filtering policy to filter the routes to be advertised to a specified peer. The number ranges from 4000 to 4999, and the name must start with a letter.";
            }
            leaf import-acl-name-or-id {
              type leafref {
                path "/ncs:devices/ncs:device/ncs:config/acl:acl/acl:groups/acl:group/acl:identity" {
                  tailf:xpath-root 3;
                }
              }
              description
                "Name or number of an IPv4 ACL used by a filtering policy to filter the routes received from a specified peer. The number ranges from 4000 to 4999, and the name must start with a letter. By default, no ACL-based filtering policy is configured, and therefore all EVN BGP routes can be accepted.";
            }
            leaf etree-enable {
              type boolean;
              default "false";
              description
                "Enable/disable EVPN E-Tree.";
            }
            leaf control-word {
              type boolean;
              default "false";
              description
                "Enable/disable EVPN control word.";
            }
            container rts {
              when '../rd' {
                tailf:xpath-root 3;
              }
              description
                "List of RTs.";
              list rt {
                key "vrf-rt-type vrf-rt-value";
                description
                  "Configure RTs to control route advertisement between network nodes. Before sending a VPN route to a PE, the local PE adds an Export RT to the route. After receiving a route from another PE, the local PE compares the local Import RT and the Export RT carried in the VPN route and adds the route to the VPN instance only when the two RTs are the same.";
                leaf vrf-rt-type {
                  type vrf-rt-type;
                  description
                    "RT type (export-extcommunity or import-extcommunity)
                     export-extcommunity: Specifies the value of the extended community attribute of the route from an outbound interface to the destination VPN.
                     import-extcommunity: Specifies the value of the extended community attribute. Routes with such an extended community value can be accepted.";
                }
                leaf vrf-rt-value {
                  type string {
                    length "3..21";
                  }
                  description
                    "RT value, in any of the following formats:
                     1. 16-bit AS number:32-bit user-defined number, 1:3 for example. A 16-bit AS number ranges from 0 to 65535, and a user-defined number ranges from 0 to 4294967295. The AS number and user-defined number cannot be both 0s. This means that the VPN Target value cannot be 0:0.
                     2. 32-bit IP address:16-bit user-defined number, 192.168.122.15:1 for example. The IP address ranges from 0.0.0.0 to 255.255.255.255, and the user-defined number ranges from 0 to 65535.
                     3. 32-bit AS number:16-bit user-defined number, 10.11:3 for example. A 32-bit AS number ranges from 0.0 to 65535.65535 or from 0 to 4294967295, and a user-defined number ranges from 0 to 65535. The AS number and user-defined number cannot be both 0s. This means that the VPN Target value cannot be 0.0:0.";
                }
              }
            }
            container mac-duplication {
              presence "normal MAC duplication";
              description
                "Enable/disable MAC duplication.";
              leaf period {
                type uint8 {
                  range "3..10";
                }
                must '(../period and ../cycle) or (not(../period) and not(../cycle))' {
                  tailf:xpath-root 3;
                }
                description
                  "Number of times that MAC duplication is detected in a period.";
              }
              leaf cycle {
                type uint16 {
                  range "60..900";
                }
                units "s";
                must '(../cycle mod 10 = 0) and ((../period and ../cycle) or (not(../period) and not(../cycle)))' {
                  tailf:xpath-root 3;
                }
                description
                  "Interval at which MAC duplication is detected. The value must be a multiple of 10.";
              }
              leaf recycle {
                type uint16 {
                  range "120..3600";
                }
                units "s";
                must '../recycle mod 10 = 0' {
                  tailf:xpath-root 3;
                }
                description
                  "Period after which suppression on MAC duplication is removed. The value must be a multiple of 10.";
              }
              leaf blackhole {
                type boolean;
                default "false";
                description
                  "Enable/disable a blackhole flag.";
              }
            }
            // NCS drop config false container 'mac-duplication-infos'
          }
          container b-evpn {
            when "../type = 'b-evpn'" {
              tailf:xpath-root 3;
            }
            description
              "Configure backbone mode of EVPN instance.";
            leaf description {
              type string {
                length "1..63";
                pattern '([^?]*)';
              }
              description
                "The description for EVPN instance.";
            }
            leaf rd {
              ext:operation-exclude "update";
              type string {
                length "3..21";
              }
              description
                "An EVPN instance address family takes effect only after it is configured with an RD. The RD can be in any of the following formats:
                 1. 16-bit AS number:32-bit user-defined number, 101:3 for example. A 16-bit AS number ranges from 0 to 65535, and a user-defined number ranges from 0 to 4294967295. The AS number and user-defined number cannot be both 0s. This means that the RD value cannot be 0:0.
                 2. 32-bit IP address:16-bit user-defined number, 192.168.122.15:1 for example. The IP address ranges from 0.0.0.0 to 255.255.255.255, and the user-defined number ranges from 0 to 65535.
                 3. 32-bit AS number:16-bit user-defined number, 10.11:3 for example. A 32-bit AS number ranges from 0.0 to 65535.65535 or from 0 to 4294967295, and a user-defined number ranges from 0 to 65535. The AS number and user-defined number cannot be both 0s. This means that the RD value cannot be 0.0:0.";
            }
            leaf bmac {
              when '../rd' {
                tailf:xpath-root 3;
              }
              type pub-type:mac-address {
                length "0..255";
              }
              description
                "Backbone bridging source MAC.";
            }
            leaf tunnel-policy-name {
              when '../rd' {
                tailf:xpath-root 3;
              }
              type leafref {
                path "/ncs:devices/ncs:device/ncs:config/tnlm:tunnel-management/tnlm:tunnel-policys/tnlm:tunnel-policy/tnlm:name" {
                  tailf:xpath-root 3;
                }
              }
              must "not(/tnlm:tunnel-management/tnlm:tunnel-policys/tnlm:tunnel-policy[tnlm:name=current()]/tnlm:ipv6-set/tnlm:select-sequence/tnlm:select-tunnel-types/tnlm:select-tunnel-type) and /tnlm:tunnel-management/tnlm:tunnel-policys/tnlm:tunnel-policy[tnlm:name=current()]/tnlm:ipv4-set/tnlm:select-sequence/tnlm:select-tunnel-types/tnlm:select-tunnel-type[tnlm:type!='gre'] and /tnlm:tunnel-management/tnlm:tunnel-policys/tnlm:tunnel-policy[tnlm:name=current()]/tnlm:ipv4-set/tnlm:select-sequence/tnlm:select-tunnel-types/tnlm:select-tunnel-type[tnlm:type!='sr-te-policy'] and /tnlm:tunnel-management/tnlm:tunnel-policys/tnlm:tunnel-policy[tnlm:name=current()]/tnlm:ipv4-set/tnlm:select-sequence/tnlm:select-tunnel-types/tnlm:select-tunnel-type[tnlm:type!='bgp']" {
                tailf:xpath-root 3;
              }
              description
                "Tunnel policy name.";
            }
            container rts {
              when '../rd' {
                tailf:xpath-root 3;
              }
              description
                "List of RTs.";
              list rt {
                key "vrf-rt-type vrf-rt-value";
                description
                  "Configure RTs to control route advertisement between network nodes. Before sending a VPN route to a PE, the local PE adds an Export RT to the route. After receiving a route from another PE, the local PE compares the local Import RT and the Export RT carried in the VPN route and adds the route to the VPN instance only when the two RTs are the same.";
                leaf vrf-rt-type {
                  type vrf-rt-type;
                  description
                    "RT type (export-extcommunity or import-extcommunity)
                     export-extcommunity: Specifies the value of the extended community attribute of the route from an outbound interface to the destination VPN.
                     import-extcommunity: Specifies the value of the extended community attribute. Routes with such an extended community value can be accepted.";
                }
                leaf vrf-rt-value {
                  type string {
                    length "3..21";
                  }
                  description
                    "RT value, in any of the following formats:
                     1. 16-bit AS number:32-bit user-defined number, 1:3 for example. A 16-bit AS number ranges from 0 to 65535, and a user-defined number ranges from 0 to 4294967295. The AS number and user-defined number cannot be both 0s. This means that the VPN Target value cannot be 0:0.
                     2. 32-bit IP address:16-bit user-defined number, 192.168.122.15:1 for example. The IP address ranges from 0.0.0.0 to 255.255.255.255, and the user-defined number ranges from 0 to 65535.
                     3. 32-bit AS number:16-bit user-defined number, 10.11:3 for example. A 32-bit AS number ranges from 0.0 to 65535.65535 or from 0 to 4294967295, and a user-defined number ranges from 0 to 65535. The AS number and user-defined number cannot be both 0s. This means that the VPN Target value cannot be 0.0:0.";
                }
              }
            }
          }
          container i-evpn {
            when "../type = 'i-evpn'" {
              tailf:xpath-root 3;
            }
            description
              "Configure PBB EVPN instance.";
            leaf description {
              type string {
                length "1..63";
                pattern '([^?]*)';
              }
              description
                "The description for EVPN instance.";
            }
            leaf tag {
              ext:operation-exclude "update";
              type uint32 {
                range "0..16777215";
              }
              description
                "Specify an I-SID.";
            }
            leaf b-evpn-name {
              ext:operation-exclude "update";
              when '../tag' {
                tailf:xpath-root 3;
              }
              type leafref {
                path "/ncs:devices/ncs:device/ncs:config/evpn:evpn/evpn:instances/evpn:instance/evpn:name" {
                  tailf:xpath-root 3;
                }
              }
              must "/evpn:evpn/evpn:instances/evpn:instance[evpn:name=current()]/evpn:type='b-evpn'" {
                tailf:xpath-root 3;
              }
              description
                "Binding an I-EVPN instance with a B-EVPN instance.";
            }
            leaf bmac {
              when '../tag' {
                tailf:xpath-root 3;
              }
              type pub-type:mac-address {
                length "0..255";
              }
              description
                "Backbone bridging source MAC.";
            }
          }
          container bd-evpn {
            when "../type = 'bd-evpn'" {
              tailf:xpath-root 3;
            }
            description
              "Configure BD exclusive mode of EVPN instance.";
            leaf description {
              type string {
                length "1..63";
                pattern '([^?]*)';
              }
              description
                "The description for EVPN instance.";
            }
            leaf rd {
              ext:operation-exclude "update";
              type string {
                length "3..21";
              }
              description
                "An EVPN instance address family takes effect only after it is configured with an RD. The RD can be in any of the following formats:
                 1. 16-bit AS number:32-bit user-defined number, 101:3 for example. A 16-bit AS number ranges from 0 to 65535, and a user-defined number ranges from 0 to 4294967295. The AS number and user-defined number cannot be both 0s. This means that the RD value cannot be 0:0.
                 2. 32-bit IP address:16-bit user-defined number, 192.168.122.15:1 for example. The IP address ranges from 0.0.0.0 to 255.255.255.255, and the user-defined number ranges from 0 to 65535.
                 3. 32-bit AS number:16-bit user-defined number, 10.11:3 for example. A 32-bit AS number ranges from 0.0 to 65535.65535 or from 0 to 4294967295, and a user-defined number ranges from 0 to 65535. The AS number and user-defined number cannot be both 0s. This means that the RD value cannot be 0.0:0.";
            }
            leaf import-policy-name {
              when '../rd' {
                tailf:xpath-root 3;
              }
              type leafref {
                path "/ncs:devices/ncs:device/ncs:config/rtp:routing-policy/rtp:policy-definitions/rtp:policy-definition/rtp:name" {
                  tailf:xpath-root 3;
                }
              }
              description
                "The name of specify import route policy.";
            }
            leaf export-policy-name {
              when '../rd' {
                tailf:xpath-root 3;
              }
              type leafref {
                path "/ncs:devices/ncs:device/ncs:config/rtp:routing-policy/rtp:policy-definitions/rtp:policy-definition/rtp:name" {
                  tailf:xpath-root 3;
                }
              }
              description
                "The name of specify export route policy.";
            }
            leaf tunnel-policy-name {
              when '../rd' {
                tailf:xpath-root 3;
              }
              type leafref {
                path "/ncs:devices/ncs:device/ncs:config/tnlm:tunnel-management/tnlm:tunnel-policys/tnlm:tunnel-policy/tnlm:name" {
                  tailf:xpath-root 3;
                }
              }
              must "(not(/tnlm:tunnel-management/tnlm:tunnel-policys/tnlm:tunnel-policy[tnlm:name=current()]/tnlm:ipv6-set/tnlm:select-sequence) or (/tnlm:tunnel-management/tnlm:tunnel-policys/tnlm:tunnel-policy[tnlm:name=current()]/tnlm:ipv6-set/tnlm:select-sequence and /tnlm:tunnel-management/tnlm:tunnel-policys/tnlm:tunnel-policy[tnlm:name=current()]/tnlm:ipv6-set/tnlm:select-sequence/tnlm:select-tunnel-types/tnlm:select-tunnel-type[tnlm:type!='srv6-te-policy-group'])) and (not(/tnlm:tunnel-management/tnlm:tunnel-policys/tnlm:tunnel-policy[tnlm:name=current()]/tnlm:ipv4-set/tnlm:select-sequence) or (/tnlm:tunnel-management/tnlm:tunnel-policys/tnlm:tunnel-policy[tnlm:name=current()]/tnlm:ipv4-set/tnlm:select-sequence and /tnlm:tunnel-management/tnlm:tunnel-policys/tnlm:tunnel-policy[tnlm:name=current()]/tnlm:ipv4-set/tnlm:select-sequence/tnlm:select-tunnel-types/tnlm:select-tunnel-type[tnlm:type!='gre']))" {
                tailf:xpath-root 3;
              }
              description
                "Tunnel policy name.";
            }
            leaf local-remote-frr {
              type local-remote-frr-enable-type;
              default "default";
              description
                "Enable local MAC and remote MAC to form FRR.";
            }
            leaf default-color {
              when '../rd' {
                tailf:xpath-root 3;
              }
              type uint32 {
                range "0..4294967295";
              }
              description
                "Set default color for nexthop iteration.";
            }
            leaf mac-balance-enable {
              type boolean;
              default "false";
              description
                "Enable/disable MAC balance.";
            }
            leaf export-acl-name-or-id {
              type leafref {
                path "/ncs:devices/ncs:device/ncs:config/acl:acl/acl:groups/acl:group/acl:identity" {
                  tailf:xpath-root 3;
                }
              }
              description
                "Name or number of an IPv4 ACL used by a filtering policy to filter the routes to be advertised to a specified peer. The number ranges from 4000 to 4999, and the name must start with a letter. By default, no ACL-based filtering policy is configured, and therefore all EVN BGP routes can be advertised.";
            }
            leaf import-acl-name-or-id {
              type leafref {
                path "/ncs:devices/ncs:device/ncs:config/acl:acl/acl:groups/acl:group/acl:identity" {
                  tailf:xpath-root 3;
                }
              }
              description
                "Name or number of an IPv4 ACL used by a filtering policy to filter the routes received from a specified peer. The number ranges from 4000 to 4999, and the name must start with a letter. By default, no ACL-based filtering policy is configured, and therefore all EVN BGP routes can be accepted.";
            }
            leaf bypass-vxlan {
              type bypass-vxlan-enable-type;
              default "default";
              description
                "Enable bypass VXLAN capability.";
            }
            leaf etree-enable {
              type boolean;
              default "false";
              description
                "Enable/disable EVPN E-Tree.";
            }
            leaf srv6-mode {
              when '../rd' {
                tailf:xpath-root 3;
              }
              type srv6-mode;
              must "../control-word!='true'" {
                tailf:xpath-root 3;
              }
              description
                "SRv6 iteration mode.";
            }
            leaf down-switch {
              when "../rd and ../srv6-mode='te'" {
                tailf:xpath-root 3;
              }
              type boolean;
              default "false";
              description
                "Enable/disable switch TE to BE if the associated TE tunnel goes down.";
            }
            leaf control-word {
              type boolean;
              must "(../control-word='true' and not(../srv6-mode)) or ../control-word!='true'" {
                tailf:xpath-root 3;
              }
              default "false";
              description
                "Enable/disable EVPN control word.";
            }
            leaf mac-route-advertise {
              type mac-route-no-advertise-type;
              default "enable";
              description
                "Enable/disable local MAC routes from being advertised.";
            }
            leaf arp-route-generate-mac {
              type mac-route-no-advertise-type;
              default "disable";
              description
                "Enable/disable MAC/IP route to generate MAC.";
            }
            leaf mac-only-route-generate {
              type mac-route-no-advertise-type;
              default "enable";
              description
                "Enable/disable the function of generating EVPN MAC routes when both MAC address entries and ARP/ND entries contain local MAC addresses.";
            }
            leaf mac-frr-keep {
              type boolean;
              default "true";
              description
                "Enable/disable the function of keeping MAC to form FRR.";
            }
            container rts {
              when '../rd' {
                tailf:xpath-root 3;
              }
              description
                "List of RTs.";
              list rt {
                key "vrf-rt-type vrf-rt-value";
                description
                  "Configure RTs to control route advertisement between network nodes. Before sending a VPN route to a PE, the local PE adds an Export RT to the route. After receiving a route from another PE, the local PE compares the local Import RT and the Export RT carried in the VPN route and adds the route to the VPN instance only when the two RTs are the same.";
                leaf vrf-rt-type {
                  type vrf-rt-type;
                  description
                    "RT type (export-extcommunity or import-extcommunity)
                     export-extcommunity: Specifies the value of the extended community attribute of the route from an outbound interface to the destination VPN.
                     import-extcommunity: Specifies the value of the extended community attribute. Routes with such an extended community value can be accepted.";
                }
                leaf vrf-rt-value {
                  type string {
                    length "3..21";
                  }
                  description
                    "RT value, in any of the following formats:
                     1. 16-bit AS number:32-bit user-defined number, 1:3 for example. A 16-bit AS number ranges from 0 to 65535, and a user-defined number ranges from 0 to 4294967295. The AS number and user-defined number cannot be both 0s. This means that the VPN Target value cannot be 0:0.
                     2. 32-bit IP address:16-bit user-defined number, 192.168.122.15:1 for example. The IP address ranges from 0.0.0.0 to 255.255.255.255, and the user-defined number ranges from 0 to 65535.
                     3. 32-bit AS number:16-bit user-defined number, 10.11:3 for example. A 32-bit AS number ranges from 0.0 to 65535.65535 or from 0 to 4294967295, and a user-defined number ranges from 0 to 65535. The AS number and user-defined number cannot be both 0s. This means that the VPN Target value cannot be 0.0:0.";
                }
              }
            }
            container mac-duplication {
              presence "bd MAC duplication";
              description
                "Enable/disable MAC duplication.";
              leaf period {
                type uint8 {
                  range "3..10";
                }
                must '(../period and ../cycle) or (not(../period) and not(../cycle))' {
                  tailf:xpath-root 3;
                }
                description
                  "Number of times that MAC duplication is detected in a period.";
              }
              leaf cycle {
                type uint16 {
                  range "60..900";
                }
                units "s";
                must '(../cycle mod 10 = 0) and ((../period and ../cycle) or (not(../period) and not(../cycle)))' {
                  tailf:xpath-root 3;
                }
                description
                  "Interval at which MAC duplication is detected. The value must be a multiple of 10.";
              }
              leaf recycle {
                type uint16 {
                  range "120..3600";
                }
                units "s";
                must '../recycle mod 10 = 0' {
                  tailf:xpath-root 3;
                }
                description
                  "Period after which suppression on MAC duplication is removed. The value must be a multiple of 10.";
              }
              leaf blackhole {
                type boolean;
                default "false";
                description
                  "Enable/disable a blackhole flag.";
              }
              leaf source-blackhole {
                when "../blackhole='true'" {
                  tailf:xpath-root 3;
                }
                type boolean;
                default "false";
                description
                  "Enable/disable blackhole flag. After MAC duplication is suppressed, if a blackhole flag is set, the source port is blocked. If no blackhole flag is set, the source port is not blocked.";
              }
            }
            // NCS drop config false container 'mac-duplication-infos'
            container inclusive-provider-tunnel {
              presence "EVI-IPMSI view";
              description
                "Enable/disable mLDP P2MP configuration.";
              container root {
                presence "EVI-IPMSI view";
                description
                  "Enable/disable mLDP P2MP root configuration.";
                leaf data-switch-disable {
                  type boolean;
                  default "false";
                  description
                    "Enable/disable data switch configuration.";
                }
                leaf data-delay-time {
                  type uint32 {
                    range "1..300";
                  }
                  units "s";
                  description
                    "Set a hold-off time for an mLDP P2MP tunnel to go Up.";
                }
                container p2mp {
                  presence "MLDP P2MP view";
                  description
                    "Enable/disable mLDP P2MP configuration.";
                  leaf root-ip {
                    type inet:ipv4-address-no-zone;
                    description
                      "Root address of P2MP tunnel.";
                  }
                  // NCS drop config false leaf 'opaque-value'
                  // NCS drop config false leaf state
                }
              }
              container leaf {
                presence "EVI-IPMSI view";
                description
                  "Enable/disable mLDP P2MP leaf configuration.";
                // NCS drop config false leaf 'opaque-value'
                // NCS drop config false leaf state
                container use-next-hops {
                  description
                    "List of root addresses for leaf node.";
                  list use-next-hop {
                    key "root-ip";
                    description
                      "Configure root address for leaf node.";
                    leaf root-ip {
                      type inet:ipv4-address-no-zone;
                      description
                        "Root address for leaf node.";
                    }
                  }
                }
              }
            }
          }
          container vpws-evpn {
            when "../type = 'vpws-evpn'" {
              tailf:xpath-root 3;
            }
            description
              "Configure VPWS mode of EVPN instance.";
            leaf description {
              type string {
                length "1..63";
                pattern '([^?]*)';
              }
              description
                "The description for EVPN instance.";
            }
            leaf rd {
              ext:operation-exclude "update";
              type string {
                length "3..21";
              }
              description
                "An EVPN instance address family takes effect only after it is configured with an RD. The RD can be in any of the following formats:
                 1. 16-bit AS number:32-bit user-defined number, 101:3 for example. A 16-bit AS number ranges from 0 to 65535, and a user-defined number ranges from 0 to 4294967295. The AS number and user-defined number cannot be both 0s. This means that the RD value cannot be 0:0.
                 2. 32-bit IP address:16-bit user-defined number, 192.168.122.15:1 for example. The IP address ranges from 0.0.0.0 to 255.255.255.255, and the user-defined number ranges from 0 to 65535.
                 3. 32-bit AS number:16-bit user-defined number, 10.11:3 for example. A 32-bit AS number ranges from 0.0 to 65535.65535 or from 0 to 4294967295, and a user-defined number ranges from 0 to 65535. The AS number and user-defined number cannot be both 0s. This means that the RD value cannot be 0.0:0.";
            }
            leaf import-policy-name {
              when '../rd' {
                tailf:xpath-root 3;
              }
              type leafref {
                path "/ncs:devices/ncs:device/ncs:config/rtp:routing-policy/rtp:policy-definitions/rtp:policy-definition/rtp:name" {
                  tailf:xpath-root 3;
                }
              }
              description
                "The name of specify import route policy.";
            }
            leaf export-policy-name {
              when '../rd' {
                tailf:xpath-root 3;
              }
              type leafref {
                path "/ncs:devices/ncs:device/ncs:config/rtp:routing-policy/rtp:policy-definitions/rtp:policy-definition/rtp:name" {
                  tailf:xpath-root 3;
                }
              }
              description
                "The name of specify export route policy.";
            }
            leaf tunnel-policy-name {
              when '../rd' {
                tailf:xpath-root 3;
              }
              type leafref {
                path "/ncs:devices/ncs:device/ncs:config/tnlm:tunnel-management/tnlm:tunnel-policys/tnlm:tunnel-policy/tnlm:name" {
                  tailf:xpath-root 3;
                }
              }
              must "(not(/tnlm:tunnel-management/tnlm:tunnel-policys/tnlm:tunnel-policy[tnlm:name=current()]/tnlm:ipv6-set/tnlm:select-sequence) or (/tnlm:tunnel-management/tnlm:tunnel-policys/tnlm:tunnel-policy[tnlm:name=current()]/tnlm:ipv6-set/tnlm:select-sequence and /tnlm:tunnel-management/tnlm:tunnel-policys/tnlm:tunnel-policy[tnlm:name=current()]/tnlm:ipv6-set/tnlm:select-sequence/tnlm:select-tunnel-types/tnlm:select-tunnel-type[tnlm:type!='srv6-te-policy-group'])) and (not(/tnlm:tunnel-management/tnlm:tunnel-policys/tnlm:tunnel-policy[tnlm:name=current()]/tnlm:ipv4-set/tnlm:select-sequence) or (/tnlm:tunnel-management/tnlm:tunnel-policys/tnlm:tunnel-policy[tnlm:name=current()]/tnlm:ipv4-set/tnlm:select-sequence and /tnlm:tunnel-management/tnlm:tunnel-policys/tnlm:tunnel-policy[tnlm:name=current()]/tnlm:ipv4-set/tnlm:select-sequence/tnlm:select-tunnel-types/tnlm:select-tunnel-type[tnlm:type!='gre']))" {
                tailf:xpath-root 3;
              }
              description
                "Tunnel policy name.";
            }
            leaf local-remote-frr {
              type local-remote-frr-enable-type;
              default "default";
              description
                "Enable local MAC and remote MAC to form FRR.";
            }
            leaf remote-frr {
              type local-remote-frr-enable-type;
              default "default";
              description
                "Enable remote MAC to form FRR.";
            }
            leaf default-color {
              when '../rd' {
                tailf:xpath-root 3;
              }
              type uint32 {
                range "0..4294967295";
              }
              description
                "Set default color for nexthop iteration.";
            }
            leaf export-acl-name-or-id {
              type leafref {
                path "/ncs:devices/ncs:device/ncs:config/acl:acl/acl:groups/acl:group/acl:identity" {
                  tailf:xpath-root 3;
                }
              }
              description
                "Name or number of an IPv4 ACL used by a filtering policy to filter the routes to be advertised to a specified peer. The number ranges from 4000 to 4999, and the name must start with a letter. By default, no ACL-based filtering policy is configured, and therefore all EVN BGP routes can be advertised.";
            }
            leaf import-acl-name-or-id {
              type leafref {
                path "/ncs:devices/ncs:device/ncs:config/acl:acl/acl:groups/acl:group/acl:identity" {
                  tailf:xpath-root 3;
                }
              }
              description
                "Name or number of an IPv4 ACL used by a filtering policy to filter the routes received from a specified peer. The number ranges from 4000 to 4999, and the name must start with a letter. By default, no ACL-based filtering policy is configured, and therefore all EVN BGP routes can be accepted.";
            }
            leaf timer-revert-delay {
              when '../rd' {
                tailf:xpath-root 3;
              }
              type uint32 {
                range "0..3600";
              }
              units "s";
              default "0";
              description
                "Set delay time of selecting routes in production.";
            }
            leaf srv6-mode {
              when '../rd' {
                tailf:xpath-root 3;
              }
              type srv6-mode;
              description
                "SRv6 iteration mode.";
            }
            leaf down-switch {
              when "../rd and ../srv6-mode='te'" {
                tailf:xpath-root 3;
              }
              type boolean;
              default "false";
              description
                "Enable/disable TE to BE if the associated TE tunnel goes down.";
            }
            container rts {
              when '../rd' {
                tailf:xpath-root 3;
              }
              description
                "List of RTs.";
              list rt {
                key "vrf-rt-type vrf-rt-value";
                description
                  "Configure RTs to control route advertisement between network nodes. Before sending a VPN route to a PE, the local PE adds an Export RT to the route. After receiving a route from another PE, the local PE compares the local Import RT and the Export RT carried in the VPN route and adds the route to the VPN instance only when the two RTs are the same.";
                leaf vrf-rt-type {
                  type vrf-rt-type;
                  description
                    "RT type (export-extcommunity or import-extcommunity)
                     export-extcommunity: Specifies the value of the extended community attribute of the route from an outbound interface to the destination VPN.
                     import-extcommunity: Specifies the value of the extended community attribute. Routes with such an extended community value can be accepted.";
                }
                leaf vrf-rt-value {
                  type string {
                    length "3..21";
                  }
                  description
                    "RT value, in any of the following formats:
                     1. 16-bit AS number:32-bit user-defined number, 1:3 for example. A 16-bit AS number ranges from 0 to 65535, and a user-defined number ranges from 0 to 4294967295. The AS number and user-defined number cannot be both 0s. This means that the VPN Target value cannot be 0:0.
                     2. 32-bit IP address:16-bit user-defined number, 192.168.122.15:1 for example. The IP address ranges from 0.0.0.0 to 255.255.255.255, and the user-defined number ranges from 0 to 65535.
                     3. 32-bit AS number:16-bit user-defined number, 10.11:3 for example. A 32-bit AS number ranges from 0.0 to 65535.65535 or from 0 to 4294967295, and a user-defined number ranges from 0 to 65535. The AS number and user-defined number cannot be both 0s. This means that the VPN Target value cannot be 0.0:0.";
                }
              }
            }
          }
          // NCS drop config false container 'tunnel-infos'
          // NCS drop config false container 'mac-route-infos'
          // NCS drop config false container 'per-instance-label'
          // NCS drop config false container 'df-infos'
          // NCS drop config false container 'df-timer-info'
          // NCS drop config false container 'esi-advance'
          // NCS drop config false container 'mac-routes'
          // NCS drop config false container 'ad-routes'
          // NCS drop config false container 'es-routes'
          // NCS drop config false container 'inclusive-routes'
        }
      }
      // NCS drop config false container 'remote-sids'
      // NCS drop config false container 'default-parameter'
      // NCS drop config false container 'recover-timers'
      // NCS drop config false container 'track-peer-timer-infos'
    }
  }
  augment "/ncs:devices/ncs:device/ncs:live-status" {
    container evpn {
      tailf:ncs-device-type "netconf";
      tailf:display-when "not(../../ncs:module) or ../../ncs:module[ncs:name='huawei-evpn'] or (../../ncs:live-status-protocol[not(ncs:capability)]) or (../../ncs:live-status-protocol/ncs:capability/ncs:module[.='huawei-evpn'])";
      description
        "Configure of EVPN.";
      container base-process {
        description
          "Configure of EVPN base process.";
        leaf redundancy-mode {
          type live_ncs_redundancy-mode;
          // NCS drop default statement
          description
            "Redundancy mode.";
        }
        leaf source-address {
          ext:operation-exclude "update";
          type inet:ipv4-address-no-zone;
          description
            "Source address.";
        }
        leaf evpn-overlay {
          type boolean;
          // NCS drop must statement
          // NCS drop default statement
          description
            "Enable/disable EVPN overlay.";
        }
      }
      container site {
        presence "evpn view";
        description
          "Enable/disable global EVPN configuration.";
        leaf df-election-mode {
          type live_ncs_df-election-mode;
          // NCS drop default statement
          description
            "Global configuration DF election mode.";
        }
        leaf vpws-df-election-mode {
          type live_ncs_vpws-df-election-mode;
          // NCS drop default statement
          description
            "VPWS DF select mode.";
        }
        leaf ac-influnced-enable {
          type boolean;
          // NCS drop default statement
          description
            "Enable/disable AC state influenced DF mode.";
        }
        leaf ad-per-es-split {
          type live_ncs_ad-per-es-route-divmode;
          // NCS drop default statement
          description
            "EVPN AD per ES route split.";
        }
        leaf irb-reoriginated {
          type boolean;
          // NCS drop default statement
          description
            "Enable/disable IRB reoriginated without bridge domain.";
        }
        leaf vlan-extend-private-enable {
          type boolean;
          // NCS drop default statement
          description
            "Enable/disable VLAN extend extcommunity to carry VLAN in MAC routes.";
        }
        leaf vlan-extend-redirect-enable {
          type boolean;
          // NCS drop default statement
          description
            "Enable/disable VLAN extend extcommunity to redirect to the same ESI interface.";
        }
        leaf local-remote-frr-enable {
          type boolean;
          // NCS drop default statement
          description
            "Enable/disable local MAC and remote MAC to form FRR.";
        }
        leaf bypass-vxlan-enable {
          type boolean;
          // NCS drop default statement
          description
            "Enable/disable bypass VXLAN extcommunity, use for allow all-active device to form bypass VXLAN.";
        }
        leaf alm-threshold {
          type uint32 {
            range "1..4294967295";
          }
          description
            "Specify the alarm route threshold.";
        }
        leaf recovery-percentage {
          // NCS drop when statement
          type uint32 {
            range "1..95";
          }
          units "%";
          // NCS drop default statement
          description
            "Specify the alarm route recovery percentage.";
        }
        leaf local-remote-vpws-frr-enable {
          type boolean;
          // NCS drop default statement
          description
            "Enable/disable the local and remote FRR for EVPN VPWS.";
        }
        leaf remote-vpws-frr-enable {
          type boolean;
          // NCS drop default statement
          description
            "Enable/disable the remote FRR for EVPN VPWS.";
        }
        leaf irb-split-group {
          type boolean;
          // NCS drop default statement
          description
            "Enable/disable IRB advertise under split group.";
        }
        leaf compatible {
          type boolean;
          // NCS drop default statement
          description
            "Enable/disable IRB routing rebirth into ARP routing and prefix routing.";
        }
        leaf advertising-vxlan-tunnel-mac {
          type boolean;
          // NCS drop default statement
          description
            "Enable/disable advertising MAC routes learned by VXLAN tunnel.";
        }
        leaf advertise-suppressed-route {
          type boolean;
          // NCS drop default statement
          description
            "Enable/disable advertising suppressed detail route.";
        }
        leaf routerid-extend-private-enable {
          type boolean;
          // NCS drop default statement
          description
            "Enable/disable router ID extend extcommunity for carrying router ID in EVPN routes.";
        }
        leaf mac-duplication-enable {
          type boolean;
          // NCS drop default statement
          description
            "Enable/disable mac-duplication.";
        }
        container mac-duplication {
          description
            "Configure MAC duplication.";
          leaf period {
            type uint8 {
              range "3..10";
            }
            // NCS drop default statement
            description
              "Number of times that MAC duplication is detected in a period.";
          }
          leaf cycle {
            type uint16 {
              range "60..900";
            }
            units "s";
            // NCS drop must statement
            // NCS drop default statement
            description
              "Interval at which MAC duplication is detected.";
          }
          leaf recycle {
            type uint16 {
              range "120..3600";
            }
            units "s";
            // NCS drop must statement
            // NCS drop default statement
            description
              "Period after which suppression on MAC duplication is removed.";
          }
        }
        container static-esis {
          description
            "List of static ESI.";
          list static-esi {
            key "esi";
            description
              "Configure instance of static ESI.";
            leaf esi {
              type live_ncs_esi;
              description
                "Static ESI, in the format of 00xx.xxxx.xxxx.xxxx.xxxx, in which x ranges from 0 to F. A static ESI cannot be all 0s. To clear a static ESI, enter a space.";
            }
            leaf redundancy-mode {
              type live_ncs_esi-redundancy-mode;
              // NCS drop default statement
              description
                "Redundancy mode.";
            }
            leaf df-election-type {
              type live_ncs_df-election-type;
              // NCS drop default statement
              description
                "The DF election type of ESI.";
            }
            leaf preference {
              // NCS drop when statement
              type uint16 {
                range "0..65535";
              }
              // NCS drop default statement
              description
                "The preference of ESI.";
            }
            leaf non-revertive {
              // NCS drop when statement
              type boolean;
              // NCS drop default statement
              description
                "Enable/disable non-revertive mode.";
            }
            leaf df-election {
              // NCS drop when statement
              type boolean;
              // NCS drop default statement
              description
                "Enable/disable DF election mode.";
            }
          }
        }
        container dynamic-esis {
          description
            "List of dynamic ESI.";
          list dynamic-esi {
            key "esi-name";
            description
              "Configure instance of dynamic ESI.";
            leaf esi-name {
              type string {
                length "1..31";
              }
              description
                "Dynamic ESI name is a string of 1 to 31 characters, which begins with a-z or A-Z.";
            }
            leaf redundancy-mode {
              type live_ncs_esi-redundancy-mode;
              // NCS drop default statement
              description
                "Redundancy mode.";
            }
            leaf df-election-type {
              type live_ncs_df-election-type;
              // NCS drop default statement
              description
                "The DF election type of ESI.";
            }
            leaf preference {
              // NCS drop when statement
              type uint16 {
                range "0..65535";
              }
              // NCS drop default statement
              description
                "The preference of ESI.";
            }
            leaf non-revertive {
              // NCS drop when statement
              type boolean;
              // NCS drop default statement
              description
                "Enable/disable non-revertive mode.";
            }
          }
        }
      }
      container instances {
        description
          "List of EVPN instance.";
        list instance {
          key "name";
          unique "normal-evpn/rd";
          unique "b-evpn/rd";
          unique "bd-evpn/rd";
          unique "vpws-evpn/rd";
          description
            "Configure EVPN instance.";
          leaf name {
            type live_ncs_name-type;
            // NCS drop must statement
            description
              "EVPN instance name.";
          }
          leaf type {
            ext:operation-exclude "update|delete";
            type live_ncs_evpn-type;
            // NCS drop default statement
            description
              "The value specifies the type of EVPN instance.";
          }
          leaf label-policy {
            // NCS drop when statement
            type live_ncs_evpn-apply-label-mode;
            description
              "Label policy of the EVPN instance.";
          }
          container normal-evpn {
            // NCS drop when statement
            description
              "Configure normal mode of EVPN instance.";
            leaf description {
              type string {
                length "1..63";
                pattern '([^?]*)';
              }
              description
                "The description for EVPN instance.";
            }
            leaf rd {
              ext:operation-exclude "update";
              type string {
                length "3..21";
              }
              description
                "An EVPN instance address family takes effect only after it is configured with an RD. The RD can be in any of the following formats:
                 1. 16-bit AS number:32-bit user-defined number, 101:3 for example. A 16-bit AS number ranges from 0 to 65535, and a user-defined number ranges from 0 to 4294967295. The AS number and user-defined number cannot be both 0s. This means that the RD value cannot be 0:0.
                 2. 32-bit IP address:16-bit user-defined number, 192.168.122.15:1 for example. The IP address ranges from 0.0.0.0 to 255.255.255.255, and the user-defined number ranges from 0 to 65535.
                 3. 32-bit AS number:16-bit user-defined number, 10.11:3 for example. A 32-bit AS number ranges from 0.0 to 65535.65535 or from 0 to 4294967295, and a user-defined number ranges from 0 to 65535. The AS number and user-defined number cannot be both 0s. This means that the RD value cannot be 0.0:0.";
            }
            leaf tunnel-policy-name {
              // NCS drop when statement
              type leafref {
                path "/ncs:devices/ncs:device/ncs:live-status/tnlm:tunnel-management/tnlm:tunnel-policys/tnlm:tunnel-policy/tnlm:name" {
                  tailf:xpath-root 3;
                }
              }
              // NCS drop must statement
              description
                "Tunnel policy name.";
            }
            leaf import-policy-name {
              // NCS drop when statement
              type leafref {
                path "/ncs:devices/ncs:device/ncs:live-status/rtp:routing-policy/rtp:policy-definitions/rtp:policy-definition/rtp:name" {
                  tailf:xpath-root 3;
                }
              }
              description
                "The name of specify import route policy.";
            }
            leaf export-policy-name {
              // NCS drop when statement
              type leafref {
                path "/ncs:devices/ncs:device/ncs:live-status/rtp:routing-policy/rtp:policy-definitions/rtp:policy-definition/rtp:name" {
                  tailf:xpath-root 3;
                }
              }
              description
                "The name of specify export route policy.";
            }
            leaf local-remote-frr {
              type live_ncs_local-remote-frr-enable-type;
              // NCS drop default statement
              description
                "Enable/disable local MAC and remote MAC to form FRR.";
            }
            leaf mac-balance-enable {
              type boolean;
              // NCS drop default statement
              description
                "Enable/disable MAC balance.";
            }
            leaf isolate-spoken {
              type live_ncs_isolate-spoken-type;
              // NCS drop default statement
              description
                "Forwarding isolation between AC interfaces under EVPN.";
            }
            leaf export-acl-name-or-id {
              type leafref {
                path "/ncs:devices/ncs:device/ncs:live-status/acl:acl/acl:groups/acl:group/acl:identity" {
                  tailf:xpath-root 3;
                }
              }
              description
                "Name or number of an IPv4 ACL used by a filtering policy to filter the routes to be advertised to a specified peer. The number ranges from 4000 to 4999, and the name must start with a letter.";
            }
            leaf import-acl-name-or-id {
              type leafref {
                path "/ncs:devices/ncs:device/ncs:live-status/acl:acl/acl:groups/acl:group/acl:identity" {
                  tailf:xpath-root 3;
                }
              }
              description
                "Name or number of an IPv4 ACL used by a filtering policy to filter the routes received from a specified peer. The number ranges from 4000 to 4999, and the name must start with a letter. By default, no ACL-based filtering policy is configured, and therefore all EVN BGP routes can be accepted.";
            }
            leaf etree-enable {
              type boolean;
              // NCS drop default statement
              description
                "Enable/disable EVPN E-Tree.";
            }
            leaf control-word {
              type boolean;
              // NCS drop default statement
              description
                "Enable/disable EVPN control word.";
            }
            container rts {
              // NCS drop when statement
              description
                "List of RTs.";
              list rt {
                key "vrf-rt-type vrf-rt-value";
                description
                  "Configure RTs to control route advertisement between network nodes. Before sending a VPN route to a PE, the local PE adds an Export RT to the route. After receiving a route from another PE, the local PE compares the local Import RT and the Export RT carried in the VPN route and adds the route to the VPN instance only when the two RTs are the same.";
                leaf vrf-rt-type {
                  type live_ncs_vrf-rt-type;
                  description
                    "RT type (export-extcommunity or import-extcommunity)
                     export-extcommunity: Specifies the value of the extended community attribute of the route from an outbound interface to the destination VPN.
                     import-extcommunity: Specifies the value of the extended community attribute. Routes with such an extended community value can be accepted.";
                }
                leaf vrf-rt-value {
                  type string {
                    length "3..21";
                  }
                  description
                    "RT value, in any of the following formats:
                     1. 16-bit AS number:32-bit user-defined number, 1:3 for example. A 16-bit AS number ranges from 0 to 65535, and a user-defined number ranges from 0 to 4294967295. The AS number and user-defined number cannot be both 0s. This means that the VPN Target value cannot be 0:0.
                     2. 32-bit IP address:16-bit user-defined number, 192.168.122.15:1 for example. The IP address ranges from 0.0.0.0 to 255.255.255.255, and the user-defined number ranges from 0 to 65535.
                     3. 32-bit AS number:16-bit user-defined number, 10.11:3 for example. A 32-bit AS number ranges from 0.0 to 65535.65535 or from 0 to 4294967295, and a user-defined number ranges from 0 to 65535. The AS number and user-defined number cannot be both 0s. This means that the VPN Target value cannot be 0.0:0.";
                }
              }
            }
            container mac-duplication {
              presence "normal MAC duplication";
              description
                "Enable/disable MAC duplication.";
              leaf period {
                type uint8 {
                  range "3..10";
                }
                // NCS drop must statement
                description
                  "Number of times that MAC duplication is detected in a period.";
              }
              leaf cycle {
                type uint16 {
                  range "60..900";
                }
                units "s";
                // NCS drop must statement
                description
                  "Interval at which MAC duplication is detected. The value must be a multiple of 10.";
              }
              leaf recycle {
                type uint16 {
                  range "120..3600";
                }
                units "s";
                // NCS drop must statement
                description
                  "Period after which suppression on MAC duplication is removed. The value must be a multiple of 10.";
              }
              leaf blackhole {
                type boolean;
                // NCS drop default statement
                description
                  "Enable/disable a blackhole flag.";
              }
            }
            container mac-duplication-infos {
              description
                "Operational state of information aggregation about MAC addresses that are duplicate in an EVPN instance.";
              uses live_ncs_mac-duplication-infos-type;
            }
          }
          container b-evpn {
            // NCS drop when statement
            description
              "Configure backbone mode of EVPN instance.";
            leaf description {
              type string {
                length "1..63";
                pattern '([^?]*)';
              }
              description
                "The description for EVPN instance.";
            }
            leaf rd {
              ext:operation-exclude "update";
              type string {
                length "3..21";
              }
              description
                "An EVPN instance address family takes effect only after it is configured with an RD. The RD can be in any of the following formats:
                 1. 16-bit AS number:32-bit user-defined number, 101:3 for example. A 16-bit AS number ranges from 0 to 65535, and a user-defined number ranges from 0 to 4294967295. The AS number and user-defined number cannot be both 0s. This means that the RD value cannot be 0:0.
                 2. 32-bit IP address:16-bit user-defined number, 192.168.122.15:1 for example. The IP address ranges from 0.0.0.0 to 255.255.255.255, and the user-defined number ranges from 0 to 65535.
                 3. 32-bit AS number:16-bit user-defined number, 10.11:3 for example. A 32-bit AS number ranges from 0.0 to 65535.65535 or from 0 to 4294967295, and a user-defined number ranges from 0 to 65535. The AS number and user-defined number cannot be both 0s. This means that the RD value cannot be 0.0:0.";
            }
            leaf bmac {
              // NCS drop when statement
              type pub-type:live_ncs_mac-address;
              description
                "Backbone bridging source MAC.";
            }
            leaf tunnel-policy-name {
              // NCS drop when statement
              type leafref {
                path "/ncs:devices/ncs:device/ncs:live-status/tnlm:tunnel-management/tnlm:tunnel-policys/tnlm:tunnel-policy/tnlm:name" {
                  tailf:xpath-root 3;
                }
              }
              // NCS drop must statement
              description
                "Tunnel policy name.";
            }
            container rts {
              // NCS drop when statement
              description
                "List of RTs.";
              list rt {
                key "vrf-rt-type vrf-rt-value";
                description
                  "Configure RTs to control route advertisement between network nodes. Before sending a VPN route to a PE, the local PE adds an Export RT to the route. After receiving a route from another PE, the local PE compares the local Import RT and the Export RT carried in the VPN route and adds the route to the VPN instance only when the two RTs are the same.";
                leaf vrf-rt-type {
                  type live_ncs_vrf-rt-type;
                  description
                    "RT type (export-extcommunity or import-extcommunity)
                     export-extcommunity: Specifies the value of the extended community attribute of the route from an outbound interface to the destination VPN.
                     import-extcommunity: Specifies the value of the extended community attribute. Routes with such an extended community value can be accepted.";
                }
                leaf vrf-rt-value {
                  type string {
                    length "3..21";
                  }
                  description
                    "RT value, in any of the following formats:
                     1. 16-bit AS number:32-bit user-defined number, 1:3 for example. A 16-bit AS number ranges from 0 to 65535, and a user-defined number ranges from 0 to 4294967295. The AS number and user-defined number cannot be both 0s. This means that the VPN Target value cannot be 0:0.
                     2. 32-bit IP address:16-bit user-defined number, 192.168.122.15:1 for example. The IP address ranges from 0.0.0.0 to 255.255.255.255, and the user-defined number ranges from 0 to 65535.
                     3. 32-bit AS number:16-bit user-defined number, 10.11:3 for example. A 32-bit AS number ranges from 0.0 to 65535.65535 or from 0 to 4294967295, and a user-defined number ranges from 0 to 65535. The AS number and user-defined number cannot be both 0s. This means that the VPN Target value cannot be 0.0:0.";
                }
              }
            }
          }
          container i-evpn {
            // NCS drop when statement
            description
              "Configure PBB EVPN instance.";
            leaf description {
              type string {
                length "1..63";
                pattern '([^?]*)';
              }
              description
                "The description for EVPN instance.";
            }
            leaf tag {
              ext:operation-exclude "update";
              type uint32 {
                range "0..16777215";
              }
              description
                "Specify an I-SID.";
            }
            leaf b-evpn-name {
              ext:operation-exclude "update";
              // NCS drop when statement
              type leafref {
                path "/ncs:devices/ncs:device/ncs:live-status/evpn:evpn/evpn:instances/evpn:instance/evpn:name" {
                  tailf:xpath-root 3;
                }
              }
              // NCS drop must statement
              description
                "Binding an I-EVPN instance with a B-EVPN instance.";
            }
            leaf bmac {
              // NCS drop when statement
              type pub-type:live_ncs_mac-address;
              description
                "Backbone bridging source MAC.";
            }
          }
          container bd-evpn {
            // NCS drop when statement
            description
              "Configure BD exclusive mode of EVPN instance.";
            leaf description {
              type string {
                length "1..63";
                pattern '([^?]*)';
              }
              description
                "The description for EVPN instance.";
            }
            leaf rd {
              ext:operation-exclude "update";
              type string {
                length "3..21";
              }
              description
                "An EVPN instance address family takes effect only after it is configured with an RD. The RD can be in any of the following formats:
                 1. 16-bit AS number:32-bit user-defined number, 101:3 for example. A 16-bit AS number ranges from 0 to 65535, and a user-defined number ranges from 0 to 4294967295. The AS number and user-defined number cannot be both 0s. This means that the RD value cannot be 0:0.
                 2. 32-bit IP address:16-bit user-defined number, 192.168.122.15:1 for example. The IP address ranges from 0.0.0.0 to 255.255.255.255, and the user-defined number ranges from 0 to 65535.
                 3. 32-bit AS number:16-bit user-defined number, 10.11:3 for example. A 32-bit AS number ranges from 0.0 to 65535.65535 or from 0 to 4294967295, and a user-defined number ranges from 0 to 65535. The AS number and user-defined number cannot be both 0s. This means that the RD value cannot be 0.0:0.";
            }
            leaf import-policy-name {
              // NCS drop when statement
              type leafref {
                path "/ncs:devices/ncs:device/ncs:live-status/rtp:routing-policy/rtp:policy-definitions/rtp:policy-definition/rtp:name" {
                  tailf:xpath-root 3;
                }
              }
              description
                "The name of specify import route policy.";
            }
            leaf export-policy-name {
              // NCS drop when statement
              type leafref {
                path "/ncs:devices/ncs:device/ncs:live-status/rtp:routing-policy/rtp:policy-definitions/rtp:policy-definition/rtp:name" {
                  tailf:xpath-root 3;
                }
              }
              description
                "The name of specify export route policy.";
            }
            leaf tunnel-policy-name {
              // NCS drop when statement
              type leafref {
                path "/ncs:devices/ncs:device/ncs:live-status/tnlm:tunnel-management/tnlm:tunnel-policys/tnlm:tunnel-policy/tnlm:name" {
                  tailf:xpath-root 3;
                }
              }
              // NCS drop must statement
              description
                "Tunnel policy name.";
            }
            leaf local-remote-frr {
              type live_ncs_local-remote-frr-enable-type;
              // NCS drop default statement
              description
                "Enable local MAC and remote MAC to form FRR.";
            }
            leaf default-color {
              // NCS drop when statement
              type uint32 {
                range "0..4294967295";
              }
              description
                "Set default color for nexthop iteration.";
            }
            leaf mac-balance-enable {
              type boolean;
              // NCS drop default statement
              description
                "Enable/disable MAC balance.";
            }
            leaf export-acl-name-or-id {
              type leafref {
                path "/ncs:devices/ncs:device/ncs:live-status/acl:acl/acl:groups/acl:group/acl:identity" {
                  tailf:xpath-root 3;
                }
              }
              description
                "Name or number of an IPv4 ACL used by a filtering policy to filter the routes to be advertised to a specified peer. The number ranges from 4000 to 4999, and the name must start with a letter. By default, no ACL-based filtering policy is configured, and therefore all EVN BGP routes can be advertised.";
            }
            leaf import-acl-name-or-id {
              type leafref {
                path "/ncs:devices/ncs:device/ncs:live-status/acl:acl/acl:groups/acl:group/acl:identity" {
                  tailf:xpath-root 3;
                }
              }
              description
                "Name or number of an IPv4 ACL used by a filtering policy to filter the routes received from a specified peer. The number ranges from 4000 to 4999, and the name must start with a letter. By default, no ACL-based filtering policy is configured, and therefore all EVN BGP routes can be accepted.";
            }
            leaf bypass-vxlan {
              type live_ncs_bypass-vxlan-enable-type;
              // NCS drop default statement
              description
                "Enable bypass VXLAN capability.";
            }
            leaf etree-enable {
              type boolean;
              // NCS drop default statement
              description
                "Enable/disable EVPN E-Tree.";
            }
            leaf srv6-mode {
              // NCS drop when statement
              type live_ncs_srv6-mode;
              // NCS drop must statement
              description
                "SRv6 iteration mode.";
            }
            leaf down-switch {
              // NCS drop when statement
              type boolean;
              // NCS drop default statement
              description
                "Enable/disable switch TE to BE if the associated TE tunnel goes down.";
            }
            leaf control-word {
              type boolean;
              // NCS drop must statement
              // NCS drop default statement
              description
                "Enable/disable EVPN control word.";
            }
            leaf mac-route-advertise {
              type live_ncs_mac-route-no-advertise-type;
              // NCS drop default statement
              description
                "Enable/disable local MAC routes from being advertised.";
            }
            leaf arp-route-generate-mac {
              type live_ncs_mac-route-no-advertise-type;
              // NCS drop default statement
              description
                "Enable/disable MAC/IP route to generate MAC.";
            }
            leaf mac-only-route-generate {
              type live_ncs_mac-route-no-advertise-type;
              // NCS drop default statement
              description
                "Enable/disable the function of generating EVPN MAC routes when both MAC address entries and ARP/ND entries contain local MAC addresses.";
            }
            leaf mac-frr-keep {
              type boolean;
              // NCS drop default statement
              description
                "Enable/disable the function of keeping MAC to form FRR.";
            }
            container rts {
              // NCS drop when statement
              description
                "List of RTs.";
              list rt {
                key "vrf-rt-type vrf-rt-value";
                description
                  "Configure RTs to control route advertisement between network nodes. Before sending a VPN route to a PE, the local PE adds an Export RT to the route. After receiving a route from another PE, the local PE compares the local Import RT and the Export RT carried in the VPN route and adds the route to the VPN instance only when the two RTs are the same.";
                leaf vrf-rt-type {
                  type live_ncs_vrf-rt-type;
                  description
                    "RT type (export-extcommunity or import-extcommunity)
                     export-extcommunity: Specifies the value of the extended community attribute of the route from an outbound interface to the destination VPN.
                     import-extcommunity: Specifies the value of the extended community attribute. Routes with such an extended community value can be accepted.";
                }
                leaf vrf-rt-value {
                  type string {
                    length "3..21";
                  }
                  description
                    "RT value, in any of the following formats:
                     1. 16-bit AS number:32-bit user-defined number, 1:3 for example. A 16-bit AS number ranges from 0 to 65535, and a user-defined number ranges from 0 to 4294967295. The AS number and user-defined number cannot be both 0s. This means that the VPN Target value cannot be 0:0.
                     2. 32-bit IP address:16-bit user-defined number, 192.168.122.15:1 for example. The IP address ranges from 0.0.0.0 to 255.255.255.255, and the user-defined number ranges from 0 to 65535.
                     3. 32-bit AS number:16-bit user-defined number, 10.11:3 for example. A 32-bit AS number ranges from 0.0 to 65535.65535 or from 0 to 4294967295, and a user-defined number ranges from 0 to 65535. The AS number and user-defined number cannot be both 0s. This means that the VPN Target value cannot be 0.0:0.";
                }
              }
            }
            container mac-duplication {
              presence "bd MAC duplication";
              description
                "Enable/disable MAC duplication.";
              leaf period {
                type uint8 {
                  range "3..10";
                }
                // NCS drop must statement
                description
                  "Number of times that MAC duplication is detected in a period.";
              }
              leaf cycle {
                type uint16 {
                  range "60..900";
                }
                units "s";
                // NCS drop must statement
                description
                  "Interval at which MAC duplication is detected. The value must be a multiple of 10.";
              }
              leaf recycle {
                type uint16 {
                  range "120..3600";
                }
                units "s";
                // NCS drop must statement
                description
                  "Period after which suppression on MAC duplication is removed. The value must be a multiple of 10.";
              }
              leaf blackhole {
                type boolean;
                // NCS drop default statement
                description
                  "Enable/disable a blackhole flag.";
              }
              leaf source-blackhole {
                // NCS drop when statement
                type boolean;
                // NCS drop default statement
                description
                  "Enable/disable blackhole flag. After MAC duplication is suppressed, if a blackhole flag is set, the source port is blocked. If no blackhole flag is set, the source port is not blocked.";
              }
            }
            container mac-duplication-infos {
              description
                "Operational state of information aggregation about MAC addresses that are duplicate in an EVPN instance.";
              uses live_ncs_mac-duplication-infos-type;
            }
            container inclusive-provider-tunnel {
              presence "EVI-IPMSI view";
              description
                "Enable/disable mLDP P2MP configuration.";
              container root {
                presence "EVI-IPMSI view";
                description
                  "Enable/disable mLDP P2MP root configuration.";
                leaf data-switch-disable {
                  type boolean;
                  // NCS drop default statement
                  description
                    "Enable/disable data switch configuration.";
                }
                leaf data-delay-time {
                  type uint32 {
                    range "1..300";
                  }
                  units "s";
                  description
                    "Set a hold-off time for an mLDP P2MP tunnel to go Up.";
                }
                container p2mp {
                  presence "MLDP P2MP view";
                  description
                    "Enable/disable mLDP P2MP configuration.";
                  leaf root-ip {
                    type inet:ipv4-address-no-zone;
                    description
                      "Root address of P2MP tunnel.";
                  }
                  leaf opaque-value {
                    type string {
                      length "1..4096";
                    }
                    description
                      "Opaque value (in the TLV format) that is carried in packets and is not decoded.";
                  }
                  leaf state {
                    type live_ncs_evpn-state;
                    description
                      "P2MP tunnel status.";
                  }
                }
              }
              container leaf {
                presence "EVI-IPMSI view";
                description
                  "Enable/disable mLDP P2MP leaf configuration.";
                leaf opaque-value {
                  type string {
                    length "1..4096";
                  }
                  description
                    "Original opaque value in a message. The value is displayed in the format of TLV.";
                }
                leaf state {
                  type live_ncs_evpn-state;
                  description
                    "P2MP tunnel status.";
                }
                container use-next-hops {
                  description
                    "List of root addresses for leaf node.";
                  list use-next-hop {
                    key "root-ip";
                    description
                      "Configure root address for leaf node.";
                    leaf root-ip {
                      type inet:ipv4-address-no-zone;
                      description
                        "Root address for leaf node.";
                    }
                  }
                }
              }
            }
          }
          container vpws-evpn {
            // NCS drop when statement
            description
              "Configure VPWS mode of EVPN instance.";
            leaf description {
              type string {
                length "1..63";
                pattern '([^?]*)';
              }
              description
                "The description for EVPN instance.";
            }
            leaf rd {
              ext:operation-exclude "update";
              type string {
                length "3..21";
              }
              description
                "An EVPN instance address family takes effect only after it is configured with an RD. The RD can be in any of the following formats:
                 1. 16-bit AS number:32-bit user-defined number, 101:3 for example. A 16-bit AS number ranges from 0 to 65535, and a user-defined number ranges from 0 to 4294967295. The AS number and user-defined number cannot be both 0s. This means that the RD value cannot be 0:0.
                 2. 32-bit IP address:16-bit user-defined number, 192.168.122.15:1 for example. The IP address ranges from 0.0.0.0 to 255.255.255.255, and the user-defined number ranges from 0 to 65535.
                 3. 32-bit AS number:16-bit user-defined number, 10.11:3 for example. A 32-bit AS number ranges from 0.0 to 65535.65535 or from 0 to 4294967295, and a user-defined number ranges from 0 to 65535. The AS number and user-defined number cannot be both 0s. This means that the RD value cannot be 0.0:0.";
            }
            leaf import-policy-name {
              // NCS drop when statement
              type leafref {
                path "/ncs:devices/ncs:device/ncs:live-status/rtp:routing-policy/rtp:policy-definitions/rtp:policy-definition/rtp:name" {
                  tailf:xpath-root 3;
                }
              }
              description
                "The name of specify import route policy.";
            }
            leaf export-policy-name {
              // NCS drop when statement
              type leafref {
                path "/ncs:devices/ncs:device/ncs:live-status/rtp:routing-policy/rtp:policy-definitions/rtp:policy-definition/rtp:name" {
                  tailf:xpath-root 3;
                }
              }
              description
                "The name of specify export route policy.";
            }
            leaf tunnel-policy-name {
              // NCS drop when statement
              type leafref {
                path "/ncs:devices/ncs:device/ncs:live-status/tnlm:tunnel-management/tnlm:tunnel-policys/tnlm:tunnel-policy/tnlm:name" {
                  tailf:xpath-root 3;
                }
              }
              // NCS drop must statement
              description
                "Tunnel policy name.";
            }
            leaf local-remote-frr {
              type live_ncs_local-remote-frr-enable-type;
              // NCS drop default statement
              description
                "Enable local MAC and remote MAC to form FRR.";
            }
            leaf remote-frr {
              type live_ncs_local-remote-frr-enable-type;
              // NCS drop default statement
              description
                "Enable remote MAC to form FRR.";
            }
            leaf default-color {
              // NCS drop when statement
              type uint32 {
                range "0..4294967295";
              }
              description
                "Set default color for nexthop iteration.";
            }
            leaf export-acl-name-or-id {
              type leafref {
                path "/ncs:devices/ncs:device/ncs:live-status/acl:acl/acl:groups/acl:group/acl:identity" {
                  tailf:xpath-root 3;
                }
              }
              description
                "Name or number of an IPv4 ACL used by a filtering policy to filter the routes to be advertised to a specified peer. The number ranges from 4000 to 4999, and the name must start with a letter. By default, no ACL-based filtering policy is configured, and therefore all EVN BGP routes can be advertised.";
            }
            leaf import-acl-name-or-id {
              type leafref {
                path "/ncs:devices/ncs:device/ncs:live-status/acl:acl/acl:groups/acl:group/acl:identity" {
                  tailf:xpath-root 3;
                }
              }
              description
                "Name or number of an IPv4 ACL used by a filtering policy to filter the routes received from a specified peer. The number ranges from 4000 to 4999, and the name must start with a letter. By default, no ACL-based filtering policy is configured, and therefore all EVN BGP routes can be accepted.";
            }
            leaf timer-revert-delay {
              // NCS drop when statement
              type uint32 {
                range "0..3600";
              }
              units "s";
              // NCS drop default statement
              description
                "Set delay time of selecting routes in production.";
            }
            leaf srv6-mode {
              // NCS drop when statement
              type live_ncs_srv6-mode;
              description
                "SRv6 iteration mode.";
            }
            leaf down-switch {
              // NCS drop when statement
              type boolean;
              // NCS drop default statement
              description
                "Enable/disable TE to BE if the associated TE tunnel goes down.";
            }
            container rts {
              // NCS drop when statement
              description
                "List of RTs.";
              list rt {
                key "vrf-rt-type vrf-rt-value";
                description
                  "Configure RTs to control route advertisement between network nodes. Before sending a VPN route to a PE, the local PE adds an Export RT to the route. After receiving a route from another PE, the local PE compares the local Import RT and the Export RT carried in the VPN route and adds the route to the VPN instance only when the two RTs are the same.";
                leaf vrf-rt-type {
                  type live_ncs_vrf-rt-type;
                  description
                    "RT type (export-extcommunity or import-extcommunity)
                     export-extcommunity: Specifies the value of the extended community attribute of the route from an outbound interface to the destination VPN.
                     import-extcommunity: Specifies the value of the extended community attribute. Routes with such an extended community value can be accepted.";
                }
                leaf vrf-rt-value {
                  type string {
                    length "3..21";
                  }
                  description
                    "RT value, in any of the following formats:
                     1. 16-bit AS number:32-bit user-defined number, 1:3 for example. A 16-bit AS number ranges from 0 to 65535, and a user-defined number ranges from 0 to 4294967295. The AS number and user-defined number cannot be both 0s. This means that the VPN Target value cannot be 0:0.
                     2. 32-bit IP address:16-bit user-defined number, 192.168.122.15:1 for example. The IP address ranges from 0.0.0.0 to 255.255.255.255, and the user-defined number ranges from 0 to 65535.
                     3. 32-bit AS number:16-bit user-defined number, 10.11:3 for example. A 32-bit AS number ranges from 0.0 to 65535.65535 or from 0 to 4294967295, and a user-defined number ranges from 0 to 65535. The AS number and user-defined number cannot be both 0s. This means that the VPN Target value cannot be 0.0:0.";
                }
              }
            }
          }
          container tunnel-infos {
            description
              "List of tunnel informations.";
            list tunnel-info {
              key "type peer-ip id";
              description
                "Operational state of tunnel informations.";
              leaf type {
                type live_ncs_tunnel-type;
                description
                  "Tunnel's type.";
              }
              leaf peer-ip {
                type inet:ip-address-no-zone;
                description
                  "Nexthop address through which the packet has to be sent.";
              }
              leaf id {
                type uint32 {
                  range "0..4294967295";
                }
                description
                  "Tunnel's ID.";
              }
              leaf color {
                type uint32 {
                  range "0..4294967295";
                }
                description
                  "Color information for tunnel.";
              }
              leaf name {
                type string {
                  length "0..256";
                }
                description
                  "Tunnel's name.";
              }
            }
          }
          container mac-route-infos {
            description
              "List of MAC routes.";
            list mac-route-info {
              key "prefix";
              description
                "Statistics of of MAC routes.";
              leaf prefix {
                type live_ncs_mac-prefix;
                description
                  "MAC route prefix.";
              }
              container label-stacks {
                description
                  "Statistics of EVPN label stacks.";
                uses evpn:live_ncs_label-stacks-type;
              }
            }
          }
          container per-instance-label {
            // NCS drop when statement
            description
              "Operational data of label shared by all private network routes in the EVPN instance.";
            leaf unicast-label {
              type uint32;
              description
                "Label shared by unicast routes in the EVPN instance.";
            }
            leaf bum-label {
              type uint32;
              description
                "Label shared by bum routes in the EVPN instance.";
            }
            leaf bypass-label {
              type uint32;
              description
                "Label shared by bypass routes in the EVPN instance.";
            }
          }
          container df-infos {
            description
              "List of DF info.";
            list df-info {
              key "esi";
              description
                "Operational data of the Df information.";
              leaf esi {
                type live_ncs_esi;
                description
                  "ESI, in the format of 00xx.xxxx.xxxx.xxxx.xxxx, in which x ranges from 0 to F. A static ESI cannot be all 0s.";
              }
              leaf df-result {
                type live_ncs_df-result;
                description
                  "DF result.";
              }
              container pref-elec-infos {
                description
                  "List of information about DF election.";
                list pref-elec-info {
                  key "origin-ip";
                  description
                    "Operational data of DF election information.";
                  leaf origin-ip {
                    type inet:ip-address-no-zone;
                    description
                      "Source IP address of a PE.";
                  }
                  leaf df-result {
                    type live_ncs_df-election-result;
                    description
                      "DF election result, which can be DF or buckup DF.";
                  }
                  leaf preference {
                    type uint16 {
                      range "1..65535";
                    }
                    // NCS drop default statement
                    description
                      "Preference of ESI.";
                  }
                  leaf dp {
                    type uint8;
                    description
                      "The non-preemption mode is used for DF election.";
                  }
                  leaf ac-df {
                    type uint8;
                    description
                      "The AC status affects DF election.";
                  }
                }
              }
            }
          }
          container df-timer-info {
            description
              "Operational data of Df timer information.";
            container esi-infos {
              description
                "List of displaying the information of the ESI Df timer.";
              list esi-info {
                key "esi";
                description
                  "Operational data of the ESI Df timer information.";
                leaf esi {
                  type live_ncs_esi;
                  description
                    "ESI, in the format of 00xx.xxxx.xxxx.xxxx.xxxx, in which x ranges from 0 to F. A static ESI cannot be all 0s.";
                }
                leaf timer-type {
                  type live_ncs_df-timer-type;
                  description
                    "Timer type.";
                }
                leaf timer-state {
                  type live_ncs_df-timer-mode;
                  description
                    "DF timer status.";
                }
                leaf time-left {
                  type uint32;
                  description
                    "Remaining time in second before the DF timer expires.";
                }
              }
            }
            container interface-infos {
              description
                "List of displaying the information of the interface Df timer.";
              list interface-info {
                key "interface-name";
                description
                  "Operational data of the interface Df timer information.";
                leaf interface-name {
                  type leafref {
                    path "/ncs:devices/ncs:device/ncs:live-status/ifm:ifm/ifm:interfaces/ifm:interface/ifm:name" {
                      tailf:xpath-root 3;
                    }
                  }
                  description
                    "The interface name.";
                }
                leaf bd-id {
                  type uint32;
                  description
                    "BD ID.";
                }
                leaf timer-type {
                  type live_ncs_df-timer-type;
                  description
                    "Timer type.";
                }
                leaf timer-state {
                  type live_ncs_df-timer-mode;
                  description
                    "DF timer status.";
                }
                leaf time-left {
                  type uint32;
                  description
                    "Remaining time in second before the DF timer expires.";
                }
              }
            }
            container pw-infos {
              description
                "List of displaying the information of the PW Df timer.";
              list pw-info {
                key "peer-ip vc-id vc-type";
                description
                  "Operational data of the PW Df timer information.";
                leaf peer-ip {
                  type leafref {
                    path "/ncs:devices/ncs:device/ncs:live-status/l2vpn:l2vpn/l2vpn:instances/l2vpn:instance/l2vpn:vpls/l2vpn:ldp-signaling/l2vpn:pws/l2vpn:pw/l2vpn:peer-ip" {
                      tailf:xpath-root 3;
                    }
                  }
                  description
                    "Peer IP address.";
                }
                leaf vc-id {
                  type leafref {
                    path "/ncs:devices/ncs:device/ncs:live-status/l2vpn:l2vpn/l2vpn:instances/l2vpn:instance/l2vpn:vpls/l2vpn:ldp-signaling/l2vpn:pws/l2vpn:pw/l2vpn:negotiation-vc-id" {
                      tailf:xpath-root 3;
                    }
                  }
                  description
                    "PW ID used to uniquely identify a VC.";
                }
                leaf vc-type {
                  type leafref {
                    path "/ncs:devices/ncs:device/ncs:live-status/l2vpn:l2vpn/l2vpn:instances/l2vpn:instance/l2vpn:vpls/l2vpn:ldp-signaling/l2vpn:pws/l2vpn:pw/l2vpn:encapsulation-type" {
                      tailf:xpath-root 3;
                    }
                  }
                  description
                    "Encapsulation type of a VPLS PW.";
                }
                leaf timer-type {
                  type live_ncs_df-timer-type;
                  description
                    "Timer type.";
                }
                leaf timer-state {
                  type live_ncs_df-timer-mode;
                  description
                    "DF timer status.";
                }
                leaf time-left {
                  type uint32;
                  description
                    "Remaining time in second before the DF timer expires.";
                }
              }
            }
          }
          container esi-advance {
            description
              "Operational data of the advanced information of an ESI.";
            container locals {
              description
                "List of displaying the advanced information for a local ESI.";
              list local {
                key "esi";
                description
                  "Operational data of the advanced information of a local ESI.";
                leaf esi {
                  type live_ncs_esi;
                  description
                    "ESI, in the format of 00xx.xxxx.xxxx.xxxx.xxxx, in which x ranges from 0 to F. A static ESI cannot be all 0s.";
                }
                leaf topology {
                  type live_ncs_topology;
                  description
                    "Network topology identified by an ESI.";
                }
              }
            }
            container remotes {
              description
                "List of displaying the advanced information for a remote ESI.";
              list remote {
                key "esi remote-peer";
                description
                  "Operational data of the advanced information of a remote ESI.";
                leaf esi {
                  type live_ncs_esi;
                  description
                    "ESI, in the format of 00xx.xxxx.xxxx.xxxx.xxxx, in which x ranges from 0 to F. A static ESI cannot be all 0s.";
                }
                leaf remote-peer {
                  type inet:ip-address-no-zone;
                  description
                    "IP address of a peer PE.";
                }
                leaf topology {
                  type live_ncs_topology;
                  description
                    "Network topology identified by an ESI.";
                }
              }
            }
          }
          container mac-routes {
            description
              "List of MAC routes.";
            list mac-route {
              key "prefix rd from route-type-flag";
              description
                "Statistics of MAC routes.";
              leaf prefix {
                type live_ncs_mac-prefix;
                description
                  "MAC route prefix.";
              }
              leaf rd {
                type string {
                  length "3..21";
                }
                description
                  "Route distinguisher.";
              }
              leaf from {
                type inet:ip-address-no-zone;
                description
                  "Source peer that sends a route.";
              }
              leaf route-type-flag {
                type live_ncs_best-flag-type;
                description
                  "Route type.";
              }
              leaf source-address-family {
                type evpn:live_ncs_address-family-type;
                description
                  "Source address family.";
              }
              leaf mpls-label1 {
                type uint32 {
                  range "0..4294967295";
                }
                description
                  "Label1, it means L2 VNI for MAC Route and L3 VNI for Prefix Route.";
              }
              leaf mpls-label2 {
                type uint32 {
                  range "0..4294967295";
                }
                description
                  "Label2, it means L3 VNI for MAC Route.";
              }
              leaf frr-out-interface {
                type string {
                  length "1..64";
                }
                description
                  "Local-remote frr direct out-interface.";
              }
              leaf frr-nexthop {
                type inet:ip-address-no-zone;
                description
                  "Local-remote frr nexthop.";
              }
              leaf frr-out-tunnel-name {
                type string {
                  length "1..64";
                }
                description
                  "Local-Remote Frr Tunnel Out-Interface.";
              }
              leaf prefix-sid {
                type inet:ipv6-address-no-zone;
                description
                  "Prefix-SID attribute.";
              }
              leaf bypass-prefix-sid {
                type inet:ipv6-address-no-zone;
                description
                  "Bypass Prefix-SID attribute.";
              }
              leaf effect-nexthop {
                type inet:ip-address-no-zone;
                description
                  "Effective nexthop.";
              }
              leaf redirect-out-interface {
                type string {
                  length "1..64";
                }
                description
                  "Redirect out-interface.";
              }
              uses live_ncs_routing-table-type {
                description
                  "Routing table infomation.";
              }
              container direct-pw-info {
                description
                  "Operational data of direct outbound interface.";
                leaf peer-ip {
                  type inet:ipv4-address-no-zone;
                  description
                    "Peer IP address of a PW.";
                }
                leaf vc-id {
                  type uint32 {
                    range "1..4294967295";
                  }
                  description
                    "VC ID.";
                }
                leaf vc-type {
                  type evpn:live_ncs_l2vpn-encapsulate-type;
                  description
                    "Encapsulation type of a PW.";
                }
              }
            }
          }
          container ad-routes {
            description
              "List of AD routes.";
            list ad-route {
              key "prefix rd from route-type-flag";
              description
                "Statistics of AD routes.";
              leaf prefix {
                type live_ncs_ad-prefix;
                description
                  "AD route prefix.";
              }
              leaf rd {
                type string {
                  length "3..21";
                }
                description
                  "Route distinguisher.";
              }
              leaf from {
                type inet:ip-address-no-zone;
                description
                  "Source peer that sends a route.";
              }
              leaf route-type-flag {
                type live_ncs_best-flag-type;
                description
                  "Route type.";
              }
              leaf prefix-sid {
                type inet:ipv6-address-no-zone;
                description
                  "Prefix-SID attribute.";
              }
              leaf bypass-prefix-sid {
                type inet:ipv6-address-no-zone;
                description
                  "Bypass Prefix-SID attribute.";
              }
              uses live_ncs_routing-table-type {
                description
                  "Routing table infomation.";
              }
            }
          }
          container es-routes {
            description
              "List of ES routes.";
            list es-route {
              key "prefix rd from route-type-flag";
              description
                "Statistics of ES routes.";
              leaf prefix {
                type live_ncs_es-prefix;
                description
                  "ES route prefix.";
              }
              leaf rd {
                type string {
                  length "3..21";
                }
                description
                  "Route distinguisher.";
              }
              leaf from {
                type inet:ip-address-no-zone;
                description
                  "Source peer that sends a route.";
              }
              leaf route-type-flag {
                type live_ncs_best-flag-type;
                description
                  "Route type.";
              }
              uses live_ncs_routing-table-type {
                description
                  "Routing table infomation.";
              }
            }
          }
          container inclusive-routes {
            description
              "List of inclusive routes.";
            list inclusive-route {
              key "prefix rd from route-type-flag";
              description
                "Statistics of inclusive routes.";
              leaf prefix {
                type live_ncs_inclusive-prefix;
                description
                  "Inclusive route prefix.";
              }
              leaf rd {
                type string {
                  length "3..21";
                }
                description
                  "Route distinguisher.";
              }
              leaf from {
                type inet:ip-address-no-zone;
                description
                  "Source peer that sends a route.";
              }
              leaf route-type-flag {
                type live_ncs_best-flag-type;
                description
                  "Route type.";
              }
              leaf prefix-sid {
                type inet:ipv6-address-no-zone;
                description
                  "Prefix-SID attribute.";
              }
              uses live_ncs_routing-table-type {
                description
                  "Routing table infomation.";
              }
            }
          }
        }
      }
      container remote-sids {
        description
          "List of remote SID.";
        list remote-sid {
          key "remote-sid";
          description
            "Operational data of remote SID.";
          leaf remote-sid {
            type inet:ipv6-address-no-zone;
            description
              "Remote SID attribute.";
          }
          leaf locator-sid {
            type inet:ipv6-address-no-zone;
            description
              "Locator SID.";
          }
          leaf locator-mask-length {
            type uint8 {
              range "0..128";
            }
            description
              "Specify the mask length of a locator SID.";
          }
          leaf evpn-type {
            type live_ncs_evpn-type;
            description
              "The value specifies the Type of EVPN instance. The value must be normal/i-evpn/b-evpn/bd-evpn/vpws-evpn.";
          }
          leaf evpn-name {
            type live_ncs_name-type;
            description
              "EVPN instance name.";
          }
          leaf bd-id {
            type uint32 {
              range "0..16777215";
            }
            description
              "The identification of the BD.";
          }
          leaf evpl-id {
            type uint32 {
              range "1..16777215";
            }
            description
              "The identification of the EVPL instance.";
          }
        }
      }
      container default-parameter {
        description
          "Operational data of EVPN initial configuration information.";
        leaf access-mode {
          type live_ncs_acess-mode;
          description
            "EVPN access Mode.";
        }
        leaf service-mode {
          type live_ncs_service-mode;
          description
            "EVPN interface service Mode.";
        }
        leaf apply-label-mode {
          type live_ncs_apply-label-mode;
          description
            "EVPN apply label Mode.";
        }
      }
      container recover-timers {
        description
          "List of EVPN recover timer informations.";
        list recover-timer {
          key "name";
          description
            "Operational state of EVPN recover timer informations.";
          leaf name {
            type leafref {
              path "/ncs:devices/ncs:device/ncs:live-status/ifm:ifm/ifm:interfaces/ifm:interface/ifm:name" {
                tailf:xpath-root 3;
              }
            }
            description
              "The interface name.";
          }
          leaf mode {
            type live_ncs_timer-mode;
            description
              "Mode of EVPN recover timer.";
          }
          leaf begin-time {
            type yang:date-and-time;
            description
              "Begin time of EVPN recover timer.";
          }
          leaf end-time {
            type yang:date-and-time;
            description
              "End time of EVPN recover timer.";
          }
          leaf time-left {
            type uint32;
            units "s";
            description
              "Time left of EVPN recover timer.";
          }
        }
      }
      container track-peer-timer-infos {
        description
          "List of EVPN track peer timer informations.";
        list track-peer-timer-info {
          key "esi";
          description
            "Operational state of EVPN track peer timer informations.";
          leaf esi {
            type live_ncs_esi;
            description
              "ESI, in the format of 00xx.xxxx.xxxx.xxxx.xxxx, in which x ranges from 0 to F. A static ESI cannot be all 0s.";
          }
          leaf timer-type {
            type live_ncs_timer-type;
            description
              "Timer type.";
          }
          leaf timer-state {
            type live_ncs_timer-mode;
            description
              "Timer status.";
          }
          leaf time-left {
            type uint32;
            units "s";
            description
              "Remaining time.";
          }
        }
      }
    }
  }
  augment "/ncs:devices/ncs:template/ncs:ned-id/ncs:config" {
    container evpn {
      description
        "Configure of EVPN.";
      container base-process {
        description
          "Configure of EVPN base process.";
        leaf redundancy-mode {
          type ncs_template_redundancy-mode;
          // NCS drop default statement
          description
            "Redundancy mode.";
        }
        leaf source-address {
          ext:operation-exclude "update";
          type string;
          description
            "Source address.";
        }
        leaf evpn-overlay {
          type string;
          // NCS drop must statement
          // NCS drop default statement
          description
            "Enable/disable EVPN overlay.";
        }
      }
      container site {
        presence "evpn view";
        description
          "Enable/disable global EVPN configuration.";
        leaf df-election-mode {
          type ncs_template_df-election-mode;
          // NCS drop default statement
          description
            "Global configuration DF election mode.";
        }
        leaf vpws-df-election-mode {
          type ncs_template_vpws-df-election-mode;
          // NCS drop default statement
          description
            "VPWS DF select mode.";
        }
        leaf ac-influnced-enable {
          type string;
          // NCS drop default statement
          description
            "Enable/disable AC state influenced DF mode.";
        }
        leaf ad-per-es-split {
          type ncs_template_ad-per-es-route-divmode;
          // NCS drop default statement
          description
            "EVPN AD per ES route split.";
        }
        leaf irb-reoriginated {
          type string;
          // NCS drop default statement
          description
            "Enable/disable IRB reoriginated without bridge domain.";
        }
        leaf vlan-extend-private-enable {
          type string;
          // NCS drop default statement
          description
            "Enable/disable VLAN extend extcommunity to carry VLAN in MAC routes.";
        }
        leaf vlan-extend-redirect-enable {
          type string;
          // NCS drop default statement
          description
            "Enable/disable VLAN extend extcommunity to redirect to the same ESI interface.";
        }
        leaf local-remote-frr-enable {
          type string;
          // NCS drop default statement
          description
            "Enable/disable local MAC and remote MAC to form FRR.";
        }
        leaf bypass-vxlan-enable {
          type string;
          // NCS drop default statement
          description
            "Enable/disable bypass VXLAN extcommunity, use for allow all-active device to form bypass VXLAN.";
        }
        leaf alm-threshold {
          type string;
          description
            "Specify the alarm route threshold.";
        }
        leaf recovery-percentage {
          // NCS drop when statement
          type string;
          units "%";
          // NCS drop default statement
          description
            "Specify the alarm route recovery percentage.";
        }
        leaf local-remote-vpws-frr-enable {
          type string;
          // NCS drop default statement
          description
            "Enable/disable the local and remote FRR for EVPN VPWS.";
        }
        leaf remote-vpws-frr-enable {
          type string;
          // NCS drop default statement
          description
            "Enable/disable the remote FRR for EVPN VPWS.";
        }
        leaf irb-split-group {
          type string;
          // NCS drop default statement
          description
            "Enable/disable IRB advertise under split group.";
        }
        leaf compatible {
          type string;
          // NCS drop default statement
          description
            "Enable/disable IRB routing rebirth into ARP routing and prefix routing.";
        }
        leaf advertising-vxlan-tunnel-mac {
          type string;
          // NCS drop default statement
          description
            "Enable/disable advertising MAC routes learned by VXLAN tunnel.";
        }
        leaf advertise-suppressed-route {
          type string;
          // NCS drop default statement
          description
            "Enable/disable advertising suppressed detail route.";
        }
        leaf routerid-extend-private-enable {
          type string;
          // NCS drop default statement
          description
            "Enable/disable router ID extend extcommunity for carrying router ID in EVPN routes.";
        }
        leaf mac-duplication-enable {
          type string;
          // NCS drop default statement
          description
            "Enable/disable mac-duplication.";
        }
        container mac-duplication {
          description
            "Configure MAC duplication.";
          leaf period {
            type string;
            // NCS drop default statement
            description
              "Number of times that MAC duplication is detected in a period.";
          }
          leaf cycle {
            type string;
            units "s";
            // NCS drop must statement
            // NCS drop default statement
            description
              "Interval at which MAC duplication is detected.";
          }
          leaf recycle {
            type string;
            units "s";
            // NCS drop must statement
            // NCS drop default statement
            description
              "Period after which suppression on MAC duplication is removed.";
          }
        }
        container static-esis {
          description
            "List of static ESI.";
          list static-esi {
            // NCS patched for predictable order
            ordered-by user;
            key "esi";
            description
              "Configure instance of static ESI.";
            leaf esi {
              type ncs_template_esi;
              description
                "Static ESI, in the format of 00xx.xxxx.xxxx.xxxx.xxxx, in which x ranges from 0 to F. A static ESI cannot be all 0s. To clear a static ESI, enter a space.";
            }
            leaf redundancy-mode {
              type ncs_template_esi-redundancy-mode;
              // NCS drop default statement
              description
                "Redundancy mode.";
            }
            leaf df-election-type {
              type ncs_template_df-election-type;
              // NCS drop default statement
              description
                "The DF election type of ESI.";
            }
            leaf preference {
              // NCS drop when statement
              type string;
              // NCS drop default statement
              description
                "The preference of ESI.";
            }
            leaf non-revertive {
              // NCS drop when statement
              type string;
              // NCS drop default statement
              description
                "Enable/disable non-revertive mode.";
            }
            leaf df-election {
              // NCS drop when statement
              type string;
              // NCS drop default statement
              description
                "Enable/disable DF election mode.";
            }
          }
        }
        container dynamic-esis {
          description
            "List of dynamic ESI.";
          list dynamic-esi {
            // NCS patched for predictable order
            ordered-by user;
            key "esi-name";
            description
              "Configure instance of dynamic ESI.";
            leaf esi-name {
              type string;
              description
                "Dynamic ESI name is a string of 1 to 31 characters, which begins with a-z or A-Z.";
            }
            leaf redundancy-mode {
              type ncs_template_esi-redundancy-mode;
              // NCS drop default statement
              description
                "Redundancy mode.";
            }
            leaf df-election-type {
              type ncs_template_df-election-type;
              // NCS drop default statement
              description
                "The DF election type of ESI.";
            }
            leaf preference {
              // NCS drop when statement
              type string;
              // NCS drop default statement
              description
                "The preference of ESI.";
            }
            leaf non-revertive {
              // NCS drop when statement
              type string;
              // NCS drop default statement
              description
                "Enable/disable non-revertive mode.";
            }
          }
        }
      }
      container instances {
        description
          "List of EVPN instance.";
        list instance {
          // NCS patched for predictable order
          ordered-by user;
          key "name";
          unique "normal-evpn/rd";
          unique "b-evpn/rd";
          unique "bd-evpn/rd";
          unique "vpws-evpn/rd";
          description
            "Configure EVPN instance.";
          leaf name {
            type ncs_template_name-type;
            // NCS drop must statement
            description
              "EVPN instance name.";
          }
          leaf type {
            ext:operation-exclude "update|delete";
            type ncs_template_evpn-type;
            // NCS drop default statement
            description
              "The value specifies the type of EVPN instance.";
          }
          // NCS drop config false leaf 'label-policy'
          container normal-evpn {
            // NCS drop when statement
            description
              "Configure normal mode of EVPN instance.";
            leaf description {
              type string;
              description
                "The description for EVPN instance.";
            }
            leaf rd {
              ext:operation-exclude "update";
              type string;
              description
                "An EVPN instance address family takes effect only after it is configured with an RD. The RD can be in any of the following formats:
                 1. 16-bit AS number:32-bit user-defined number, 101:3 for example. A 16-bit AS number ranges from 0 to 65535, and a user-defined number ranges from 0 to 4294967295. The AS number and user-defined number cannot be both 0s. This means that the RD value cannot be 0:0.
                 2. 32-bit IP address:16-bit user-defined number, 192.168.122.15:1 for example. The IP address ranges from 0.0.0.0 to 255.255.255.255, and the user-defined number ranges from 0 to 65535.
                 3. 32-bit AS number:16-bit user-defined number, 10.11:3 for example. A 32-bit AS number ranges from 0.0 to 65535.65535 or from 0 to 4294967295, and a user-defined number ranges from 0 to 65535. The AS number and user-defined number cannot be both 0s. This means that the RD value cannot be 0.0:0.";
            }
            leaf tunnel-policy-name {
              // NCS drop when statement
              type string;
              // NCS drop must statement
              description
                "Tunnel policy name.";
            }
            leaf import-policy-name {
              // NCS drop when statement
              type string;
              description
                "The name of specify import route policy.";
            }
            leaf export-policy-name {
              // NCS drop when statement
              type string;
              description
                "The name of specify export route policy.";
            }
            leaf local-remote-frr {
              type ncs_template_local-remote-frr-enable-type;
              // NCS drop default statement
              description
                "Enable/disable local MAC and remote MAC to form FRR.";
            }
            leaf mac-balance-enable {
              type string;
              // NCS drop default statement
              description
                "Enable/disable MAC balance.";
            }
            leaf isolate-spoken {
              type ncs_template_isolate-spoken-type;
              // NCS drop default statement
              description
                "Forwarding isolation between AC interfaces under EVPN.";
            }
            leaf export-acl-name-or-id {
              type string;
              description
                "Name or number of an IPv4 ACL used by a filtering policy to filter the routes to be advertised to a specified peer. The number ranges from 4000 to 4999, and the name must start with a letter.";
            }
            leaf import-acl-name-or-id {
              type string;
              description
                "Name or number of an IPv4 ACL used by a filtering policy to filter the routes received from a specified peer. The number ranges from 4000 to 4999, and the name must start with a letter. By default, no ACL-based filtering policy is configured, and therefore all EVN BGP routes can be accepted.";
            }
            leaf etree-enable {
              type string;
              // NCS drop default statement
              description
                "Enable/disable EVPN E-Tree.";
            }
            leaf control-word {
              type string;
              // NCS drop default statement
              description
                "Enable/disable EVPN control word.";
            }
            container rts {
              // NCS drop when statement
              description
                "List of RTs.";
              list rt {
                // NCS patched for predictable order
                ordered-by user;
                key "vrf-rt-type vrf-rt-value";
                description
                  "Configure RTs to control route advertisement between network nodes. Before sending a VPN route to a PE, the local PE adds an Export RT to the route. After receiving a route from another PE, the local PE compares the local Import RT and the Export RT carried in the VPN route and adds the route to the VPN instance only when the two RTs are the same.";
                leaf vrf-rt-type {
                  type ncs_template_vrf-rt-type;
                  description
                    "RT type (export-extcommunity or import-extcommunity)
                     export-extcommunity: Specifies the value of the extended community attribute of the route from an outbound interface to the destination VPN.
                     import-extcommunity: Specifies the value of the extended community attribute. Routes with such an extended community value can be accepted.";
                }
                leaf vrf-rt-value {
                  type string;
                  description
                    "RT value, in any of the following formats:
                     1. 16-bit AS number:32-bit user-defined number, 1:3 for example. A 16-bit AS number ranges from 0 to 65535, and a user-defined number ranges from 0 to 4294967295. The AS number and user-defined number cannot be both 0s. This means that the VPN Target value cannot be 0:0.
                     2. 32-bit IP address:16-bit user-defined number, 192.168.122.15:1 for example. The IP address ranges from 0.0.0.0 to 255.255.255.255, and the user-defined number ranges from 0 to 65535.
                     3. 32-bit AS number:16-bit user-defined number, 10.11:3 for example. A 32-bit AS number ranges from 0.0 to 65535.65535 or from 0 to 4294967295, and a user-defined number ranges from 0 to 65535. The AS number and user-defined number cannot be both 0s. This means that the VPN Target value cannot be 0.0:0.";
                }
              }
            }
            container mac-duplication {
              presence "normal MAC duplication";
              description
                "Enable/disable MAC duplication.";
              leaf period {
                type string;
                // NCS drop must statement
                description
                  "Number of times that MAC duplication is detected in a period.";
              }
              leaf cycle {
                type string;
                units "s";
                // NCS drop must statement
                description
                  "Interval at which MAC duplication is detected. The value must be a multiple of 10.";
              }
              leaf recycle {
                type string;
                units "s";
                // NCS drop must statement
                description
                  "Period after which suppression on MAC duplication is removed. The value must be a multiple of 10.";
              }
              leaf blackhole {
                type string;
                // NCS drop default statement
                description
                  "Enable/disable a blackhole flag.";
              }
            }
            // NCS drop config false container 'mac-duplication-infos'
          }
          container b-evpn {
            // NCS drop when statement
            description
              "Configure backbone mode of EVPN instance.";
            leaf description {
              type string;
              description
                "The description for EVPN instance.";
            }
            leaf rd {
              ext:operation-exclude "update";
              type string;
              description
                "An EVPN instance address family takes effect only after it is configured with an RD. The RD can be in any of the following formats:
                 1. 16-bit AS number:32-bit user-defined number, 101:3 for example. A 16-bit AS number ranges from 0 to 65535, and a user-defined number ranges from 0 to 4294967295. The AS number and user-defined number cannot be both 0s. This means that the RD value cannot be 0:0.
                 2. 32-bit IP address:16-bit user-defined number, 192.168.122.15:1 for example. The IP address ranges from 0.0.0.0 to 255.255.255.255, and the user-defined number ranges from 0 to 65535.
                 3. 32-bit AS number:16-bit user-defined number, 10.11:3 for example. A 32-bit AS number ranges from 0.0 to 65535.65535 or from 0 to 4294967295, and a user-defined number ranges from 0 to 65535. The AS number and user-defined number cannot be both 0s. This means that the RD value cannot be 0.0:0.";
            }
            leaf bmac {
              // NCS drop when statement
              type pub-type:ncs_template_mac-address;
              description
                "Backbone bridging source MAC.";
            }
            leaf tunnel-policy-name {
              // NCS drop when statement
              type string;
              // NCS drop must statement
              description
                "Tunnel policy name.";
            }
            container rts {
              // NCS drop when statement
              description
                "List of RTs.";
              list rt {
                // NCS patched for predictable order
                ordered-by user;
                key "vrf-rt-type vrf-rt-value";
                description
                  "Configure RTs to control route advertisement between network nodes. Before sending a VPN route to a PE, the local PE adds an Export RT to the route. After receiving a route from another PE, the local PE compares the local Import RT and the Export RT carried in the VPN route and adds the route to the VPN instance only when the two RTs are the same.";
                leaf vrf-rt-type {
                  type ncs_template_vrf-rt-type;
                  description
                    "RT type (export-extcommunity or import-extcommunity)
                     export-extcommunity: Specifies the value of the extended community attribute of the route from an outbound interface to the destination VPN.
                     import-extcommunity: Specifies the value of the extended community attribute. Routes with such an extended community value can be accepted.";
                }
                leaf vrf-rt-value {
                  type string;
                  description
                    "RT value, in any of the following formats:
                     1. 16-bit AS number:32-bit user-defined number, 1:3 for example. A 16-bit AS number ranges from 0 to 65535, and a user-defined number ranges from 0 to 4294967295. The AS number and user-defined number cannot be both 0s. This means that the VPN Target value cannot be 0:0.
                     2. 32-bit IP address:16-bit user-defined number, 192.168.122.15:1 for example. The IP address ranges from 0.0.0.0 to 255.255.255.255, and the user-defined number ranges from 0 to 65535.
                     3. 32-bit AS number:16-bit user-defined number, 10.11:3 for example. A 32-bit AS number ranges from 0.0 to 65535.65535 or from 0 to 4294967295, and a user-defined number ranges from 0 to 65535. The AS number and user-defined number cannot be both 0s. This means that the VPN Target value cannot be 0.0:0.";
                }
              }
            }
          }
          container i-evpn {
            // NCS drop when statement
            description
              "Configure PBB EVPN instance.";
            leaf description {
              type string;
              description
                "The description for EVPN instance.";
            }
            leaf tag {
              ext:operation-exclude "update";
              type string;
              description
                "Specify an I-SID.";
            }
            leaf b-evpn-name {
              ext:operation-exclude "update";
              // NCS drop when statement
              type string;
              // NCS drop must statement
              description
                "Binding an I-EVPN instance with a B-EVPN instance.";
            }
            leaf bmac {
              // NCS drop when statement
              type pub-type:ncs_template_mac-address;
              description
                "Backbone bridging source MAC.";
            }
          }
          container bd-evpn {
            // NCS drop when statement
            description
              "Configure BD exclusive mode of EVPN instance.";
            leaf description {
              type string;
              description
                "The description for EVPN instance.";
            }
            leaf rd {
              ext:operation-exclude "update";
              type string;
              description
                "An EVPN instance address family takes effect only after it is configured with an RD. The RD can be in any of the following formats:
                 1. 16-bit AS number:32-bit user-defined number, 101:3 for example. A 16-bit AS number ranges from 0 to 65535, and a user-defined number ranges from 0 to 4294967295. The AS number and user-defined number cannot be both 0s. This means that the RD value cannot be 0:0.
                 2. 32-bit IP address:16-bit user-defined number, 192.168.122.15:1 for example. The IP address ranges from 0.0.0.0 to 255.255.255.255, and the user-defined number ranges from 0 to 65535.
                 3. 32-bit AS number:16-bit user-defined number, 10.11:3 for example. A 32-bit AS number ranges from 0.0 to 65535.65535 or from 0 to 4294967295, and a user-defined number ranges from 0 to 65535. The AS number and user-defined number cannot be both 0s. This means that the RD value cannot be 0.0:0.";
            }
            leaf import-policy-name {
              // NCS drop when statement
              type string;
              description
                "The name of specify import route policy.";
            }
            leaf export-policy-name {
              // NCS drop when statement
              type string;
              description
                "The name of specify export route policy.";
            }
            leaf tunnel-policy-name {
              // NCS drop when statement
              type string;
              // NCS drop must statement
              description
                "Tunnel policy name.";
            }
            leaf local-remote-frr {
              type ncs_template_local-remote-frr-enable-type;
              // NCS drop default statement
              description
                "Enable local MAC and remote MAC to form FRR.";
            }
            leaf default-color {
              // NCS drop when statement
              type string;
              description
                "Set default color for nexthop iteration.";
            }
            leaf mac-balance-enable {
              type string;
              // NCS drop default statement
              description
                "Enable/disable MAC balance.";
            }
            leaf export-acl-name-or-id {
              type string;
              description
                "Name or number of an IPv4 ACL used by a filtering policy to filter the routes to be advertised to a specified peer. The number ranges from 4000 to 4999, and the name must start with a letter. By default, no ACL-based filtering policy is configured, and therefore all EVN BGP routes can be advertised.";
            }
            leaf import-acl-name-or-id {
              type string;
              description
                "Name or number of an IPv4 ACL used by a filtering policy to filter the routes received from a specified peer. The number ranges from 4000 to 4999, and the name must start with a letter. By default, no ACL-based filtering policy is configured, and therefore all EVN BGP routes can be accepted.";
            }
            leaf bypass-vxlan {
              type ncs_template_bypass-vxlan-enable-type;
              // NCS drop default statement
              description
                "Enable bypass VXLAN capability.";
            }
            leaf etree-enable {
              type string;
              // NCS drop default statement
              description
                "Enable/disable EVPN E-Tree.";
            }
            leaf srv6-mode {
              // NCS drop when statement
              type ncs_template_srv6-mode;
              // NCS drop must statement
              description
                "SRv6 iteration mode.";
            }
            leaf down-switch {
              // NCS drop when statement
              type string;
              // NCS drop default statement
              description
                "Enable/disable switch TE to BE if the associated TE tunnel goes down.";
            }
            leaf control-word {
              type string;
              // NCS drop must statement
              // NCS drop default statement
              description
                "Enable/disable EVPN control word.";
            }
            leaf mac-route-advertise {
              type ncs_template_mac-route-no-advertise-type;
              // NCS drop default statement
              description
                "Enable/disable local MAC routes from being advertised.";
            }
            leaf arp-route-generate-mac {
              type ncs_template_mac-route-no-advertise-type;
              // NCS drop default statement
              description
                "Enable/disable MAC/IP route to generate MAC.";
            }
            leaf mac-only-route-generate {
              type ncs_template_mac-route-no-advertise-type;
              // NCS drop default statement
              description
                "Enable/disable the function of generating EVPN MAC routes when both MAC address entries and ARP/ND entries contain local MAC addresses.";
            }
            leaf mac-frr-keep {
              type string;
              // NCS drop default statement
              description
                "Enable/disable the function of keeping MAC to form FRR.";
            }
            container rts {
              // NCS drop when statement
              description
                "List of RTs.";
              list rt {
                // NCS patched for predictable order
                ordered-by user;
                key "vrf-rt-type vrf-rt-value";
                description
                  "Configure RTs to control route advertisement between network nodes. Before sending a VPN route to a PE, the local PE adds an Export RT to the route. After receiving a route from another PE, the local PE compares the local Import RT and the Export RT carried in the VPN route and adds the route to the VPN instance only when the two RTs are the same.";
                leaf vrf-rt-type {
                  type ncs_template_vrf-rt-type;
                  description
                    "RT type (export-extcommunity or import-extcommunity)
                     export-extcommunity: Specifies the value of the extended community attribute of the route from an outbound interface to the destination VPN.
                     import-extcommunity: Specifies the value of the extended community attribute. Routes with such an extended community value can be accepted.";
                }
                leaf vrf-rt-value {
                  type string;
                  description
                    "RT value, in any of the following formats:
                     1. 16-bit AS number:32-bit user-defined number, 1:3 for example. A 16-bit AS number ranges from 0 to 65535, and a user-defined number ranges from 0 to 4294967295. The AS number and user-defined number cannot be both 0s. This means that the VPN Target value cannot be 0:0.
                     2. 32-bit IP address:16-bit user-defined number, 192.168.122.15:1 for example. The IP address ranges from 0.0.0.0 to 255.255.255.255, and the user-defined number ranges from 0 to 65535.
                     3. 32-bit AS number:16-bit user-defined number, 10.11:3 for example. A 32-bit AS number ranges from 0.0 to 65535.65535 or from 0 to 4294967295, and a user-defined number ranges from 0 to 65535. The AS number and user-defined number cannot be both 0s. This means that the VPN Target value cannot be 0.0:0.";
                }
              }
            }
            container mac-duplication {
              presence "bd MAC duplication";
              description
                "Enable/disable MAC duplication.";
              leaf period {
                type string;
                // NCS drop must statement
                description
                  "Number of times that MAC duplication is detected in a period.";
              }
              leaf cycle {
                type string;
                units "s";
                // NCS drop must statement
                description
                  "Interval at which MAC duplication is detected. The value must be a multiple of 10.";
              }
              leaf recycle {
                type string;
                units "s";
                // NCS drop must statement
                description
                  "Period after which suppression on MAC duplication is removed. The value must be a multiple of 10.";
              }
              leaf blackhole {
                type string;
                // NCS drop default statement
                description
                  "Enable/disable a blackhole flag.";
              }
              leaf source-blackhole {
                // NCS drop when statement
                type string;
                // NCS drop default statement
                description
                  "Enable/disable blackhole flag. After MAC duplication is suppressed, if a blackhole flag is set, the source port is blocked. If no blackhole flag is set, the source port is not blocked.";
              }
            }
            // NCS drop config false container 'mac-duplication-infos'
            container inclusive-provider-tunnel {
              presence "EVI-IPMSI view";
              description
                "Enable/disable mLDP P2MP configuration.";
              container root {
                presence "EVI-IPMSI view";
                description
                  "Enable/disable mLDP P2MP root configuration.";
                leaf data-switch-disable {
                  type string;
                  // NCS drop default statement
                  description
                    "Enable/disable data switch configuration.";
                }
                leaf data-delay-time {
                  type string;
                  units "s";
                  description
                    "Set a hold-off time for an mLDP P2MP tunnel to go Up.";
                }
                container p2mp {
                  presence "MLDP P2MP view";
                  description
                    "Enable/disable mLDP P2MP configuration.";
                  leaf root-ip {
                    type string;
                    description
                      "Root address of P2MP tunnel.";
                  }
                  // NCS drop config false leaf 'opaque-value'
                  // NCS drop config false leaf state
                }
              }
              container leaf {
                presence "EVI-IPMSI view";
                description
                  "Enable/disable mLDP P2MP leaf configuration.";
                // NCS drop config false leaf 'opaque-value'
                // NCS drop config false leaf state
                container use-next-hops {
                  description
                    "List of root addresses for leaf node.";
                  list use-next-hop {
                    // NCS patched for predictable order
                    ordered-by user;
                    key "root-ip";
                    description
                      "Configure root address for leaf node.";
                    leaf root-ip {
                      type string;
                      description
                        "Root address for leaf node.";
                    }
                  }
                }
              }
            }
          }
          container vpws-evpn {
            // NCS drop when statement
            description
              "Configure VPWS mode of EVPN instance.";
            leaf description {
              type string;
              description
                "The description for EVPN instance.";
            }
            leaf rd {
              ext:operation-exclude "update";
              type string;
              description
                "An EVPN instance address family takes effect only after it is configured with an RD. The RD can be in any of the following formats:
                 1. 16-bit AS number:32-bit user-defined number, 101:3 for example. A 16-bit AS number ranges from 0 to 65535, and a user-defined number ranges from 0 to 4294967295. The AS number and user-defined number cannot be both 0s. This means that the RD value cannot be 0:0.
                 2. 32-bit IP address:16-bit user-defined number, 192.168.122.15:1 for example. The IP address ranges from 0.0.0.0 to 255.255.255.255, and the user-defined number ranges from 0 to 65535.
                 3. 32-bit AS number:16-bit user-defined number, 10.11:3 for example. A 32-bit AS number ranges from 0.0 to 65535.65535 or from 0 to 4294967295, and a user-defined number ranges from 0 to 65535. The AS number and user-defined number cannot be both 0s. This means that the RD value cannot be 0.0:0.";
            }
            leaf import-policy-name {
              // NCS drop when statement
              type string;
              description
                "The name of specify import route policy.";
            }
            leaf export-policy-name {
              // NCS drop when statement
              type string;
              description
                "The name of specify export route policy.";
            }
            leaf tunnel-policy-name {
              // NCS drop when statement
              type string;
              // NCS drop must statement
              description
                "Tunnel policy name.";
            }
            leaf local-remote-frr {
              type ncs_template_local-remote-frr-enable-type;
              // NCS drop default statement
              description
                "Enable local MAC and remote MAC to form FRR.";
            }
            leaf remote-frr {
              type ncs_template_local-remote-frr-enable-type;
              // NCS drop default statement
              description
                "Enable remote MAC to form FRR.";
            }
            leaf default-color {
              // NCS drop when statement
              type string;
              description
                "Set default color for nexthop iteration.";
            }
            leaf export-acl-name-or-id {
              type string;
              description
                "Name or number of an IPv4 ACL used by a filtering policy to filter the routes to be advertised to a specified peer. The number ranges from 4000 to 4999, and the name must start with a letter. By default, no ACL-based filtering policy is configured, and therefore all EVN BGP routes can be advertised.";
            }
            leaf import-acl-name-or-id {
              type string;
              description
                "Name or number of an IPv4 ACL used by a filtering policy to filter the routes received from a specified peer. The number ranges from 4000 to 4999, and the name must start with a letter. By default, no ACL-based filtering policy is configured, and therefore all EVN BGP routes can be accepted.";
            }
            leaf timer-revert-delay {
              // NCS drop when statement
              type string;
              units "s";
              // NCS drop default statement
              description
                "Set delay time of selecting routes in production.";
            }
            leaf srv6-mode {
              // NCS drop when statement
              type ncs_template_srv6-mode;
              description
                "SRv6 iteration mode.";
            }
            leaf down-switch {
              // NCS drop when statement
              type string;
              // NCS drop default statement
              description
                "Enable/disable TE to BE if the associated TE tunnel goes down.";
            }
            container rts {
              // NCS drop when statement
              description
                "List of RTs.";
              list rt {
                // NCS patched for predictable order
                ordered-by user;
                key "vrf-rt-type vrf-rt-value";
                description
                  "Configure RTs to control route advertisement between network nodes. Before sending a VPN route to a PE, the local PE adds an Export RT to the route. After receiving a route from another PE, the local PE compares the local Import RT and the Export RT carried in the VPN route and adds the route to the VPN instance only when the two RTs are the same.";
                leaf vrf-rt-type {
                  type ncs_template_vrf-rt-type;
                  description
                    "RT type (export-extcommunity or import-extcommunity)
                     export-extcommunity: Specifies the value of the extended community attribute of the route from an outbound interface to the destination VPN.
                     import-extcommunity: Specifies the value of the extended community attribute. Routes with such an extended community value can be accepted.";
                }
                leaf vrf-rt-value {
                  type string;
                  description
                    "RT value, in any of the following formats:
                     1. 16-bit AS number:32-bit user-defined number, 1:3 for example. A 16-bit AS number ranges from 0 to 65535, and a user-defined number ranges from 0 to 4294967295. The AS number and user-defined number cannot be both 0s. This means that the VPN Target value cannot be 0:0.
                     2. 32-bit IP address:16-bit user-defined number, 192.168.122.15:1 for example. The IP address ranges from 0.0.0.0 to 255.255.255.255, and the user-defined number ranges from 0 to 65535.
                     3. 32-bit AS number:16-bit user-defined number, 10.11:3 for example. A 32-bit AS number ranges from 0.0 to 65535.65535 or from 0 to 4294967295, and a user-defined number ranges from 0 to 65535. The AS number and user-defined number cannot be both 0s. This means that the VPN Target value cannot be 0.0:0.";
                }
              }
            }
          }
          // NCS drop config false container 'tunnel-infos'
          // NCS drop config false container 'mac-route-infos'
          // NCS drop config false container 'per-instance-label'
          // NCS drop config false container 'df-infos'
          // NCS drop config false container 'df-timer-info'
          // NCS drop config false container 'esi-advance'
          // NCS drop config false container 'mac-routes'
          // NCS drop config false container 'ad-routes'
          // NCS drop config false container 'es-routes'
          // NCS drop config false container 'inclusive-routes'
        }
      }
      // NCS drop config false container 'remote-sids'
      // NCS drop config false container 'default-parameter'
      // NCS drop config false container 'recover-timers'
      // NCS drop config false container 'track-peer-timer-infos'
    }
  }
  augment "/ncs:devices/ncs:template/ncs:ned-id/ncs:config/bd:bd/bd:instances/bd:instance" {
    description
      "BD bound to an EVPN instance.";
    container evpn {
      description
        "Configure BD bound to an EVPN instance.";
      leaf name {
        type string;
        // NCS drop must statement
        description
          "Configure BD instances bound to an BD exclusive mode EVPN instance.";
      }
      leaf esi {
        // NCS drop when statement
        type ncs_template_esi;
        // NCS drop must statement
        description
          "Static ESI, in the format of 00xx.xxxx.xxxx.xxxx.xxxx, in which x ranges from 0 to F. A static ESI cannot be all 0s. To clear a static ESI, enter a space.";
      }
      leaf tag {
        // NCS drop when statement
        type string;
        ext:operation-exclude "update";
        description
          "Specify the BD tag.";
      }
      leaf umr-originate {
        // NCS drop when statement
        type string;
        // NCS drop must statement
        // NCS drop default statement
        description
          "Enable/disable originate Unknown-MAC-Route.";
      }
      leaf detail-suppressed {
        // NCS drop when statement
        type string;
        // NCS drop default statement
        description
          "Enable/disable suppresse detail MAC route.";
      }
      leaf umr-forward {
        // NCS drop when statement
        type string;
        // NCS drop default statement
        description
          "Enable/disable process all-0 MAC route as Unknown-MAC-Route.";
      }
      container interface-track-peers {
        // NCS drop when statement
        description
          "List of track peer.";
        list interface-track-peer {
          // NCS patched for predictable order
          ordered-by user;
          key "es-track-address";
          description
            "Configure track peer information.";
          leaf es-track-address {
            type string;
            // NCS drop must statement
            description
              "Track peer address.";
          }
        }
      }
    }
  }
  augment "/ncs:devices/ncs:device/ncs:live-status/bd:bd/bd:instances/bd:instance" {
    description
      "BD bound to an EVPN instance.";
    container evpn {
      tailf:ncs-device-type "netconf";
      tailf:display-when "not(../../../../../ncs:module) or ../../../../../ncs:module[ncs:name='huawei-evpn'] or (../../../../../ncs:live-status-protocol[not(ncs:capability)]) or (../../../../../ncs:live-status-protocol/ncs:capability/ncs:module[.='huawei-evpn'])";
      description
        "Configure BD bound to an EVPN instance.";
      leaf name {
        type leafref {
          path "/ncs:devices/ncs:device/ncs:live-status/evpn:evpn/evpn:instances/evpn:instance/evpn:name" {
            tailf:xpath-root 3;
          }
        }
        // NCS drop must statement
        description
          "Configure BD instances bound to an BD exclusive mode EVPN instance.";
      }
      leaf esi {
        // NCS drop when statement
        type live_ncs_esi;
        // NCS drop must statement
        description
          "Static ESI, in the format of 00xx.xxxx.xxxx.xxxx.xxxx, in which x ranges from 0 to F. A static ESI cannot be all 0s. To clear a static ESI, enter a space.";
      }
      leaf tag {
        // NCS drop when statement
        type uint16 {
          range "1..4094";
        }
        ext:operation-exclude "update";
        description
          "Specify the BD tag.";
      }
      leaf umr-originate {
        // NCS drop when statement
        type boolean;
        // NCS drop must statement
        // NCS drop default statement
        description
          "Enable/disable originate Unknown-MAC-Route.";
      }
      leaf detail-suppressed {
        // NCS drop when statement
        type boolean;
        // NCS drop default statement
        description
          "Enable/disable suppresse detail MAC route.";
      }
      leaf umr-forward {
        // NCS drop when statement
        type boolean;
        // NCS drop default statement
        description
          "Enable/disable process all-0 MAC route as Unknown-MAC-Route.";
      }
      container interface-track-peers {
        // NCS drop when statement
        description
          "List of track peer.";
        list interface-track-peer {
          key "es-track-address";
          description
            "Configure track peer information.";
          leaf es-track-address {
            type leafref {
              path "/ncs:devices/ncs:device/ncs:live-status/ni:network-instance/ni:instances/ni:instance/bgp:bgp/bgp:base-process/bgp:peers/bgp:peer/bgp:address" {
                tailf:xpath-root 3;
              }
            }
            // NCS drop must statement
            description
              "Track peer address.";
          }
        }
      }
    }
  }
  augment "/ncs:devices/ncs:device/ncs:config/bd:bd/bd:instances/bd:instance" {
    description
      "BD bound to an EVPN instance.";
    container evpn {
      tailf:ncs-device-type "netconf";
      tailf:display-when "not(../../../../../ncs:module) or ../../../../../ncs:module[ncs:name='huawei-evpn']";
      description
        "Configure BD bound to an EVPN instance.";
      leaf name {
        type leafref {
          path "/ncs:devices/ncs:device/ncs:config/evpn:evpn/evpn:instances/evpn:instance/evpn:name" {
            tailf:xpath-root 3;
          }
        }
        must "(/evpn:evpn/evpn:instances/evpn:instance[evpn:name = current()]/evpn:type='bd-evpn') and not(/bd:bd/bd:instances/bd:instance[bd:id != current()/../../bd:id]/evpn:evpn[evpn:name = current()] and /bd:bd/bd:instances/bd:instance[bd:id != current()/../../bd:id]/evpn:evpn[evpn:tag = current()/../evpn:tag])" {
          tailf:xpath-root 3;
        }
        description
          "Configure BD instances bound to an BD exclusive mode EVPN instance.";
      }
      leaf esi {
        when '../name' {
          tailf:xpath-root 3;
        }
        type esi {
          length "1..24";
        }
        must "(../../nvo3:nvo3/nvo3:vni-list/nvo3:vni[../nvo3:split-horizon='true']) or ((../umr-originate='true') and not(/evpn:evpn/evpn:site/evpn:static-esis/evpn:static-esi[evpn:esi = current()]/evpn:redundancy-mode ='single-active'))" {
          tailf:xpath-root 3;
        }
        description
          "Static ESI, in the format of 00xx.xxxx.xxxx.xxxx.xxxx, in which x ranges from 0 to F. A static ESI cannot be all 0s. To clear a static ESI, enter a space.";
      }
      leaf tag {
        when '../name' {
          tailf:xpath-root 3;
        }
        type uint16 {
          range "1..4094";
        }
        ext:operation-exclude "update";
        description
          "Specify the BD tag.";
      }
      leaf umr-originate {
        when '../name' {
          tailf:xpath-root 3;
        }
        type boolean;
        must "(../umr-originate='true' and not(../../nvo3:nvo3/nvo3:vni-list/nvo3:vni) and not(/l2vpn:l2vpn/l2vpn:instances/l2vpn:instance/l2vpn:vpls/l2vpn:bds/l2vpn:bd[l2vpn:id=current()/../../bd:id])) or (../umr-originate='false')" {
          tailf:xpath-root 3;
        }
        default "false";
        description
          "Enable/disable originate Unknown-MAC-Route.";
      }
      leaf detail-suppressed {
        when "../umr-originate ='true'" {
          tailf:xpath-root 3;
        }
        type boolean;
        default "false";
        description
          "Enable/disable suppresse detail MAC route.";
      }
      leaf umr-forward {
        when '../name' {
          tailf:xpath-root 3;
        }
        type boolean;
        default "false";
        description
          "Enable/disable process all-0 MAC route as Unknown-MAC-Route.";
      }
      container interface-track-peers {
        when "(../name and ../../nvo3:nvo3/nvo3:vni-list/nvo3:vni[../nvo3:split-horizon='true'])" {
          tailf:xpath-root 3;
        }
        description
          "List of track peer.";
        list interface-track-peer {
          key "es-track-address";
          description
            "Configure track peer information.";
          leaf es-track-address {
            type leafref {
              path "/ncs:devices/ncs:device/ncs:config/ni:network-instance/ni:instances/ni:instance/bgp:bgp/bgp:base-process/bgp:peers/bgp:peer/bgp:address" {
                tailf:xpath-root 3;
              }
            }
            must "/ni:network-instance/ni:instances/ni:instance/bgp:bgp/bgp:base-process/bgp:peers/bgp:peer[bgp:address=current()]/bgp:afs/bgp:af[bgp:type='evpn']" {
              tailf:xpath-root 3;
            }
            description
              "Track peer address.";
          }
        }
      }
    }
  }
  augment "/ncs:devices/ncs:template/ncs:ned-id/ncs:config/bd:bd/bd:instances/bd:instance/bd:service-points/bd:service-point" {
    description
      "Configure the E-Tree leaf attribute of BD.";
    container evpn {
      description
        "Configure the E-Tree leaf attribute of BD.";
      leaf e-tree-leaf {
        type string;
        // NCS drop must statement
        // NCS drop default statement
        description
          "Enable/disable the E-Tree leaf attribute of BD.";
      }
    }
  }
  augment "/ncs:devices/ncs:device/ncs:live-status/bd:bd/bd:instances/bd:instance/bd:service-points/bd:service-point" {
    description
      "Configure the E-Tree leaf attribute of BD.";
    container evpn {
      tailf:ncs-device-type "netconf";
      tailf:display-when "not(../../../../../../../ncs:module) or ../../../../../../../ncs:module[ncs:name='huawei-evpn'] or (../../../../../../../ncs:live-status-protocol[not(ncs:capability)]) or (../../../../../../../ncs:live-status-protocol/ncs:capability/ncs:module[.='huawei-evpn'])";
      description
        "Configure the E-Tree leaf attribute of BD.";
      leaf e-tree-leaf {
        type boolean;
        // NCS drop must statement
        // NCS drop default statement
        description
          "Enable/disable the E-Tree leaf attribute of BD.";
      }
    }
  }
  augment "/ncs:devices/ncs:device/ncs:config/bd:bd/bd:instances/bd:instance/bd:service-points/bd:service-point" {
    description
      "Configure the E-Tree leaf attribute of BD.";
    container evpn {
      tailf:ncs-device-type "netconf";
      tailf:display-when "not(../../../../../../../ncs:module) or ../../../../../../../ncs:module[ncs:name='huawei-evpn']";
      description
        "Configure the E-Tree leaf attribute of BD.";
      leaf e-tree-leaf {
        type boolean;
        must "(../e-tree-leaf = 'true' and ../../../../evpn:evpn/evpn:name and /evpn:evpn/evpn:instances/evpn:instance[evpn:name=current()/../../../../evpn:evpn/evpn:name]/evpn:bd-evpn/evpn:etree-enable = 'true') or (../e-tree-leaf = 'false')" {
          tailf:xpath-root 3;
        }
        default "false";
        description
          "Enable/disable the E-Tree leaf attribute of BD.";
      }
    }
  }
  augment "/ncs:devices/ncs:template/ncs:ned-id/ncs:config/ni:network-instance/ni:instances/ni:instance/l3vpn:afs/l3vpn:af" {
    description
      "Configure EVPN.";
    container evpn {
      // NCS drop when statement
      description
        "Configure EVPN.";
      leaf import-policy-name {
        type string;
        description
          "Specifies the name of an import routing policy.";
      }
      leaf export-policy-name {
        type string;
        description
          "Specifies the name of an export routing policy.";
      }
      leaf mpls-routing {
        type string;
        // NCS drop default statement
        description
          "Enable/disable the EVPN MPLS layer 3 routing function.";
      }
      leaf tunnel-policy-name {
        type string;
        description
          "Specify tunnel policy name for EVPN.";
      }
      leaf default-color {
        type string;
        description
          "Set default color for nexthop iteration.";
      }
      leaf irb2ip {
        type ncs_template_irb2ip-enable-type;
        // NCS drop default statement
        description
          "Enable/disable IRB routing rebirth into prefix routing.";
      }
      container extend-vpn-targets {
        description
          "List of extended RTs.";
        list extend-vpn-target {
          // NCS patched for predictable order
          ordered-by user;
          key "vrf-rt-value vrf-rt-type";
          description
            "Configure RT (VPN Target) to control route advertisement between network nodes. Before sending a VPN route to a PE, the local PE adds an Export RT to the route. After receiving a route from another PE, the local PE determines whether the route will be added to the VPN instance based on the local Import RT and the Export RT that is added to the VPN route.";
          leaf vrf-rt-value {
            type string;
            description
              "The formats of a VPN target value are as follows:
               (1) 16-bit AS number : 32-bit user-defined number, for example, 1:3. An AS number ranges from 0 to 65535, and a user-defined number ranges from 0 to 4294967295. The AS number and user-defined number cannot be both 0s. This means that the VPN Target value cannot be 0:0.
               (2) 32-bit IP address: 16-bit user-defined number, for example: 192.168.122.15:1.The IP address ranges from 0.0.0.0 to 255.255.255.255, and the user-defined number ranges from 0 to 65535.
               (3) 32-bit AS number :16-bit user-defined number, for example, 10.11:3. An AS number ranges from 0.0 to 65535.65535 or 0 to 4294967295, and a user-defined number ranges from 0 to 65535. The AS number and user-defined number cannot be both 0s. This means that the VPN Target value cannot be 0.0:0.";
          }
          leaf vrf-rt-type {
            type ncs_template_vrf-rt-type;
            description
              "RT types are as follows:
               export-extcommunity: Specifies the value of the extended community attribute of the route from an outbound interface to the destination VPN. import-extcommunity: Receives routes that carry the specified extended community attribute value.";
          }
        }
      }
      // NCS drop config false container state
    }
  }
  augment "/ncs:devices/ncs:device/ncs:live-status/ni:network-instance/ni:instances/ni:instance/l3vpn:afs/l3vpn:af" {
    description
      "Configure EVPN.";
    container evpn {
      tailf:ncs-device-type "netconf";
      tailf:display-when "not(../../../../../../../ncs:module) or ../../../../../../../ncs:module[ncs:name='huawei-evpn'] or (../../../../../../../ncs:live-status-protocol[not(ncs:capability)]) or (../../../../../../../ncs:live-status-protocol/ncs:capability/ncs:module[.='huawei-evpn'])";
      // NCS drop when statement
      description
        "Configure EVPN.";
      leaf import-policy-name {
        type leafref {
          path "/ncs:devices/ncs:device/ncs:live-status/rtp:routing-policy/rtp:policy-definitions/rtp:policy-definition/rtp:name" {
            tailf:xpath-root 3;
          }
        }
        description
          "Specifies the name of an import routing policy.";
      }
      leaf export-policy-name {
        type leafref {
          path "/ncs:devices/ncs:device/ncs:live-status/rtp:routing-policy/rtp:policy-definitions/rtp:policy-definition/rtp:name" {
            tailf:xpath-root 3;
          }
        }
        description
          "Specifies the name of an export routing policy.";
      }
      leaf mpls-routing {
        type boolean;
        // NCS drop default statement
        description
          "Enable/disable the EVPN MPLS layer 3 routing function.";
      }
      leaf tunnel-policy-name {
        type leafref {
          path "/ncs:devices/ncs:device/ncs:live-status/tnlm:tunnel-management/tnlm:tunnel-policys/tnlm:tunnel-policy/tnlm:name" {
            tailf:xpath-root 3;
          }
        }
        description
          "Specify tunnel policy name for EVPN.";
      }
      leaf default-color {
        type uint32 {
          range "0..4294967295";
        }
        description
          "Set default color for nexthop iteration.";
      }
      leaf irb2ip {
        type live_ncs_irb2ip-enable-type;
        // NCS drop default statement
        description
          "Enable/disable IRB routing rebirth into prefix routing.";
      }
      container extend-vpn-targets {
        description
          "List of extended RTs.";
        list extend-vpn-target {
          key "vrf-rt-value vrf-rt-type";
          description
            "Configure RT (VPN Target) to control route advertisement between network nodes. Before sending a VPN route to a PE, the local PE adds an Export RT to the route. After receiving a route from another PE, the local PE determines whether the route will be added to the VPN instance based on the local Import RT and the Export RT that is added to the VPN route.";
          leaf vrf-rt-value {
            type string {
              length "3..21";
            }
            description
              "The formats of a VPN target value are as follows:
               (1) 16-bit AS number : 32-bit user-defined number, for example, 1:3. An AS number ranges from 0 to 65535, and a user-defined number ranges from 0 to 4294967295. The AS number and user-defined number cannot be both 0s. This means that the VPN Target value cannot be 0:0.
               (2) 32-bit IP address: 16-bit user-defined number, for example: 192.168.122.15:1.The IP address ranges from 0.0.0.0 to 255.255.255.255, and the user-defined number ranges from 0 to 65535.
               (3) 32-bit AS number :16-bit user-defined number, for example, 10.11:3. An AS number ranges from 0.0 to 65535.65535 or 0 to 4294967295, and a user-defined number ranges from 0 to 65535. The AS number and user-defined number cannot be both 0s. This means that the VPN Target value cannot be 0.0:0.";
          }
          leaf vrf-rt-type {
            type live_ncs_vrf-rt-type;
            description
              "RT types are as follows:
               export-extcommunity: Specifies the value of the extended community attribute of the route from an outbound interface to the destination VPN. import-extcommunity: Receives routes that carry the specified extended community attribute value.";
          }
        }
      }
      container state {
        description
          "Operational state of EVPN attribute.";
        leaf label {
          type uint32;
          description
            "EVPN label of the VPN instance address family.";
        }
      }
    }
  }
  augment "/ncs:devices/ncs:device/ncs:config/ni:network-instance/ni:instances/ni:instance/l3vpn:afs/l3vpn:af" {
    description
      "Configure EVPN.";
    container evpn {
      tailf:ncs-device-type "netconf";
      tailf:display-when "not(../../../../../../../ncs:module) or ../../../../../../../ncs:module[ncs:name='huawei-evpn']";
      when '../l3vpn:route-distinguisher' {
        tailf:xpath-root 3;
      }
      description
        "Configure EVPN.";
      leaf import-policy-name {
        type leafref {
          path "/ncs:devices/ncs:device/ncs:config/rtp:routing-policy/rtp:policy-definitions/rtp:policy-definition/rtp:name" {
            tailf:xpath-root 3;
          }
        }
        description
          "Specifies the name of an import routing policy.";
      }
      leaf export-policy-name {
        type leafref {
          path "/ncs:devices/ncs:device/ncs:config/rtp:routing-policy/rtp:policy-definitions/rtp:policy-definition/rtp:name" {
            tailf:xpath-root 3;
          }
        }
        description
          "Specifies the name of an export routing policy.";
      }
      leaf mpls-routing {
        type boolean;
        default "false";
        description
          "Enable/disable the EVPN MPLS layer 3 routing function.";
      }
      leaf tunnel-policy-name {
        type leafref {
          path "/ncs:devices/ncs:device/ncs:config/tnlm:tunnel-management/tnlm:tunnel-policys/tnlm:tunnel-policy/tnlm:name" {
            tailf:xpath-root 3;
          }
        }
        description
          "Specify tunnel policy name for EVPN.";
      }
      leaf default-color {
        type uint32 {
          range "0..4294967295";
        }
        description
          "Set default color for nexthop iteration.";
      }
      leaf irb2ip {
        type irb2ip-enable-type;
        default "default";
        description
          "Enable/disable IRB routing rebirth into prefix routing.";
      }
      container extend-vpn-targets {
        description
          "List of extended RTs.";
        list extend-vpn-target {
          key "vrf-rt-value vrf-rt-type";
          description
            "Configure RT (VPN Target) to control route advertisement between network nodes. Before sending a VPN route to a PE, the local PE adds an Export RT to the route. After receiving a route from another PE, the local PE determines whether the route will be added to the VPN instance based on the local Import RT and the Export RT that is added to the VPN route.";
          leaf vrf-rt-value {
            type string {
              length "3..21";
            }
            description
              "The formats of a VPN target value are as follows:
               (1) 16-bit AS number : 32-bit user-defined number, for example, 1:3. An AS number ranges from 0 to 65535, and a user-defined number ranges from 0 to 4294967295. The AS number and user-defined number cannot be both 0s. This means that the VPN Target value cannot be 0:0.
               (2) 32-bit IP address: 16-bit user-defined number, for example: 192.168.122.15:1.The IP address ranges from 0.0.0.0 to 255.255.255.255, and the user-defined number ranges from 0 to 65535.
               (3) 32-bit AS number :16-bit user-defined number, for example, 10.11:3. An AS number ranges from 0.0 to 65535.65535 or 0 to 4294967295, and a user-defined number ranges from 0 to 65535. The AS number and user-defined number cannot be both 0s. This means that the VPN Target value cannot be 0.0:0.";
          }
          leaf vrf-rt-type {
            type vrf-rt-type;
            description
              "RT types are as follows:
               export-extcommunity: Specifies the value of the extended community attribute of the route from an outbound interface to the destination VPN. import-extcommunity: Receives routes that carry the specified extended community attribute value.";
          }
        }
      }
      // NCS drop config false container state
    }
  }
  augment "/ncs:devices/ncs:template/ncs:ned-id/ncs:config/evpl:evpl/evpl:instances/evpl:instance" {
    description
      "EVPL instance bound to an EVPN instance.";
    container evpn {
      description
        "Configure EVPL instance bound to an EVPN instance.";
      leaf name {
        type string;
        // NCS drop must statement
        description
          "Configure EVPL instances bound to an EVPN instance.";
      }
      leaf local-service-id {
        ext:operation-exclude "update";
        // NCS drop when statement
        type string;
        // NCS drop must statement
        description
          "Configure the local SID.";
      }
      leaf remote-service-id {
        ext:operation-exclude "update";
        // NCS drop when statement
        type string;
        // NCS drop must statement
        description
          "Configure the remote SID.";
      }
      leaf ignore-match-mtu {
        // NCS drop when statement
        type string;
        // NCS drop default statement
        description
          "Enable/disable the ignore flag of matching MTU from peer device.";
      }
      leaf balancing-ignore-esi {
        // NCS drop when statement
        type string;
        // NCS drop default statement
        description
          "Enable/disable the ignore flag of ESI for load balance.";
      }
      leaf control-word {
        // NCS drop when statement
        type string;
        // NCS drop must statement
        // NCS drop default statement
        description
          "Enable/disable EVPL control word.";
      }
      // NCS drop config false container 'evpl-info'
      // NCS drop config false container 'evpl-peer-infos'
      // NCS drop config false container 'label-stacks'
    }
  }
  augment "/ncs:devices/ncs:device/ncs:live-status/evpl:evpl/evpl:instances/evpl:instance" {
    description
      "EVPL instance bound to an EVPN instance.";
    container evpn {
      tailf:ncs-device-type "netconf";
      tailf:display-when "not(../../../../../ncs:module) or ../../../../../ncs:module[ncs:name='huawei-evpn'] or (../../../../../ncs:live-status-protocol[not(ncs:capability)]) or (../../../../../ncs:live-status-protocol/ncs:capability/ncs:module[.='huawei-evpn'])";
      description
        "Configure EVPL instance bound to an EVPN instance.";
      leaf name {
        type leafref {
          path "/ncs:devices/ncs:device/ncs:live-status/evpn:evpn/evpn:instances/evpn:instance/evpn:name" {
            tailf:xpath-root 3;
          }
        }
        // NCS drop must statement
        description
          "Configure EVPL instances bound to an EVPN instance.";
      }
      leaf local-service-id {
        ext:operation-exclude "update";
        // NCS drop when statement
        type uint32 {
          range "1..16777215";
        }
        // NCS drop must statement
        description
          "Configure the local SID.";
      }
      leaf remote-service-id {
        ext:operation-exclude "update";
        // NCS drop when statement
        type uint32 {
          range "1..16777215";
        }
        // NCS drop must statement
        description
          "Configure the remote SID.";
      }
      leaf ignore-match-mtu {
        // NCS drop when statement
        type boolean;
        // NCS drop default statement
        description
          "Enable/disable the ignore flag of matching MTU from peer device.";
      }
      leaf balancing-ignore-esi {
        // NCS drop when statement
        type boolean;
        // NCS drop default statement
        description
          "Enable/disable the ignore flag of ESI for load balance.";
      }
      leaf control-word {
        // NCS drop when statement
        type boolean;
        // NCS drop must statement
        // NCS drop default statement
        description
          "Enable/disable EVPL control word.";
      }
      container evpl-info {
        description
          "Operational state of EVPL info.";
        leaf ac-interface {
          type leafref {
            path "/ncs:devices/ncs:device/ncs:live-status/ifm:ifm/ifm:interfaces/ifm:interface/ifm:name" {
              tailf:xpath-root 3;
            }
          }
          description
            "The AC interface bound to EVPL instance.";
        }
        leaf evpl-state {
          type live_ncs_evpl-state;
          description
            "The state of EVPL instance.";
        }
        leaf local-ctrl-word {
          type boolean;
          description
            "The local control word.";
        }
        leaf local-mtu {
          type uint16 {
            range "0..65535";
          }
          units "Byte";
          description
            "The value of local MTU, just from the interface which bound to the EVPL instance. If MTU is 0, it means the ignore flag of checking MTU is enabled.";
        }
        leaf local-reduancy-mode {
          type live_ncs_redundancy-mode;
          description
            "The local reduancy mode, which includes single-active and all-active modes.";
        }
        leaf local-df-state {
          type live_ncs_df-state;
          description
            "The local DF state.";
        }
        leaf remote-reduancy-mode {
          type live_ncs_redundancy-mode;
          description
            "The remote reduancy mode, which includes single-active and all-active modes.";
        }
        leaf remote-pri-df-num {
          type uint32 {
            range "0..4294967295";
          }
          description
            "Number of primary DFs.";
        }
        leaf remote-back-df-num {
          type uint32 {
            range "0..4294967295";
          }
          description
            "Number of backup DFs.";
        }
        leaf remote-none-df-num {
          type uint32 {
            range "0..4294967295";
          }
          description
            "Number of none DFs.";
        }
        leaf tunnel-type {
          type live_ncs_evpn-tunnel-type;
          description
            "The tunnel type of EVPN network.";
        }
        leaf evpl-type {
          type live_ncs_evpn-evpl-type;
          description
            "The type of EVPL.";
        }
        leaf if-last-up-time {
          type yang:date-and-time;
          description
            "The last up time of AC interface.";
        }
        leaf last-pri-time {
          type yang:date-and-time;
          description
            "The last time to be primary DF.";
        }
        leaf last-backup-time {
          type yang:date-and-time;
          description
            "The last time to be backup DF.";
        }
      }
      container evpl-peer-infos {
        description
          "List of EVPL peer info.";
        list evpl-peer-info {
          key "peer-ip nexthop-ip";
          description
            "Operational state of EVPL peer info.";
          leaf peer-ip {
            type inet:ip-address-no-zone;
            description
              "Peer IP address.";
          }
          leaf nexthop-ip {
            type inet:ip-address-no-zone;
            description
              "Original nexthop IP address.";
          }
          leaf remote-df-state {
            type live_ncs_df-state;
            description
              "Remote DF status.";
          }
          leaf remote-mtu {
            type uint32 {
              range "1..4294967295";
            }
            units "Byte";
            description
              "The value of remote MTU, just from the interface which bound to the EVPL instance. If MTU is 0, it means the ignore flag of checking MTU is enabled.";
          }
          leaf remote-ctrl-word {
            type boolean;
            description
              "The remote control word.";
          }
          leaf remote-esi {
            type live_ncs_esi;
            description
              "Remote ESI.";
          }
          leaf eline-role {
            type live_ncs_eline-role;
            description
              "The E-Line role.";
          }
          container tunnel-infos {
            description
              "List of EVPL peer tunnel informations.";
            list tunnel-info {
              key "id";
              description
                "Operational state of EVPL peer tunnel informations.";
              leaf id {
                type string {
                  length "1..20";
                }
                description
                  "Tunnel ID.";
              }
              leaf type {
                type live_ncs_evpl-tunnel-type;
                description
                  "Tunnel type.";
              }
            }
          }
        }
      }
      container label-stacks {
        description
          "Statistics of EVPN label stacks.";
        uses evpn:live_ncs_label-stacks-type;
      }
    }
  }
  augment "/ncs:devices/ncs:device/ncs:config/evpl:evpl/evpl:instances/evpl:instance" {
    description
      "EVPL instance bound to an EVPN instance.";
    container evpn {
      tailf:ncs-device-type "netconf";
      tailf:display-when "not(../../../../../ncs:module) or ../../../../../ncs:module[ncs:name='huawei-evpn']";
      description
        "Configure EVPL instance bound to an EVPN instance.";
      leaf name {
        type leafref {
          path "/ncs:devices/ncs:device/ncs:config/evpn:evpn/evpn:instances/evpn:instance/evpn:name" {
            tailf:xpath-root 3;
          }
        }
        must "/evpn:evpn/evpn:instances/evpn:instance[name=current()]/evpn:type='vpws-evpn' and /evpn:evpn/evpn:instances/evpn:instance[name=current()]/evpn:vpws-evpn/evpn:rd and ../../evpl:mode!='vxlan-mode'" {
          tailf:xpath-root 3;
        }
        description
          "Configure EVPL instances bound to an EVPN instance.";
      }
      leaf local-service-id {
        ext:operation-exclude "update";
        when '../name' {
          tailf:xpath-root 3;
        }
        type uint32 {
          range "1..16777215";
        }
        must '(../local-service-id and ../remote-service-id) or (not(../local-service-id) and not(../remote-service-id))' {
          tailf:xpath-root 3;
        }
        description
          "Configure the local SID.";
      }
      leaf remote-service-id {
        ext:operation-exclude "update";
        when '../name' {
          tailf:xpath-root 3;
        }
        type uint32 {
          range "1..16777215";
        }
        must '(../local-service-id and ../remote-service-id) or (not(../local-service-id) and not(../remote-service-id))' {
          tailf:xpath-root 3;
        }
        description
          "Configure the remote SID.";
      }
      leaf ignore-match-mtu {
        when '../name' {
          tailf:xpath-root 3;
        }
        type boolean;
        default "false";
        description
          "Enable/disable the ignore flag of matching MTU from peer device.";
      }
      leaf balancing-ignore-esi {
        when '../name' {
          tailf:xpath-root 3;
        }
        type boolean;
        default "false";
        description
          "Enable/disable the ignore flag of ESI for load balance.";
      }
      leaf control-word {
        when '../name' {
          tailf:xpath-root 3;
        }
        type boolean;
        must "(../control-word='true' and ../../evpl:mode='mpls-mode') or ../control-word!='true'" {
          tailf:xpath-root 3;
        }
        default "false";
        description
          "Enable/disable EVPL control word.";
      }
      // NCS drop config false container 'evpl-info'
      // NCS drop config false container 'evpl-peer-infos'
      // NCS drop config false container 'label-stacks'
    }
  }
  augment "/ncs:devices/ncs:template/ncs:ned-id/ncs:config/ifm:ifm/ifm:interfaces/ifm:interface" {
    description
      "Configure EVPN with the interface.";
    container evpn {
      description
        "Configure ESI interface.";
      leaf name {
        type string;
        // NCS drop must statement
        description
          "Configure EVPL instances bound to an EVPN instance.";
      }
      leaf pbb-source-mac {
        // NCS drop when statement
        type pub-type:ncs_template_mac-address;
        // NCS drop must statement
        description
          "Specifies a B-MAC address.";
      }
      leaf esi {
        // NCS drop when statement
        type ncs_template_esi;
        description
          "Static ESI, in the format of 00xx.xxxx.xxxx.xxxx.xxxx, in which x ranges from 0 to F. A static ESI cannot be all 0s. To clear a static ESI, enter a space.";
      }
      leaf esi-name {
        // NCS drop when statement
        type string;
        description
          "Dynamic ESI name is a string of 1 to 31 characters, which begins with a-z or A-Z.";
      }
      leaf es-recovery-timer {
        // NCS drop when statement
        type string;
        units "s";
        description
          "ES recovery timer.";
      }
      leaf track-bfd-name {
        // NCS drop when statement
        type string;
        description
          "Specify the BFD that track ESI peer.";
      }
      leaf e-tree-leaf {
        // NCS drop when statement
        type string;
        // NCS drop must statement
        // NCS drop default statement
        description
          "Enable/disable the E-Tree leaf attribute of interface.";
      }
      // NCS drop config false leaf state
      // NCS drop config false leaf 'vc-state'
    }
    container evpn-attribute {
      description
        "Configure EVPN attribute of interface.";
      container track-peers {
        // NCS drop when statement
        description
          "List of track peer.";
        list track-peer {
          // NCS patched for predictable order
          ordered-by user;
          key "es-track-address";
          description
            "Configure the track peer info.";
          leaf es-track-address {
            type string;
            // NCS drop must statement
            description
              "Track peer address.";
          }
        }
      }
    }
  }
  augment "/ncs:devices/ncs:device/ncs:live-status/ifm:ifm/ifm:interfaces/ifm:interface" {
    description
      "Configure EVPN with the interface.";
    container evpn {
      tailf:ncs-device-type "netconf";
      tailf:display-when "not(../../../../../ncs:module) or ../../../../../ncs:module[ncs:name='huawei-evpn'] or (../../../../../ncs:live-status-protocol[not(ncs:capability)]) or (../../../../../ncs:live-status-protocol/ncs:capability/ncs:module[.='huawei-evpn'])";
      description
        "Configure ESI interface.";
      leaf name {
        type leafref {
          path "/ncs:devices/ncs:device/ncs:live-status/evpn:evpn/evpn:instances/evpn:instance/evpn:name" {
            tailf:xpath-root 3;
          }
        }
        // NCS drop must statement
        description
          "Configure EVPL instances bound to an EVPN instance.";
      }
      leaf pbb-source-mac {
        // NCS drop when statement
        type pub-type:live_ncs_mac-address;
        // NCS drop must statement
        description
          "Specifies a B-MAC address.";
      }
      leaf esi {
        // NCS drop when statement
        type live_ncs_esi;
        description
          "Static ESI, in the format of 00xx.xxxx.xxxx.xxxx.xxxx, in which x ranges from 0 to F. A static ESI cannot be all 0s. To clear a static ESI, enter a space.";
      }
      leaf esi-name {
        // NCS drop when statement
        type leafref {
          path "/ncs:devices/ncs:device/ncs:live-status/evpn:evpn/evpn:site/evpn:dynamic-esis/evpn:dynamic-esi/evpn:esi-name" {
            tailf:xpath-root 3;
          }
        }
        description
          "Dynamic ESI name is a string of 1 to 31 characters, which begins with a-z or A-Z.";
      }
      leaf es-recovery-timer {
        // NCS drop when statement
        type uint32 {
          range "3..1200";
        }
        units "s";
        description
          "ES recovery timer.";
      }
      leaf track-bfd-name {
        // NCS drop when statement
        type leafref {
          path "/ncs:devices/ncs:device/ncs:live-status/bfd:bfd/bfd:sessions/bfd:session/bfd:name" {
            tailf:xpath-root 3;
          }
        }
        description
          "Specify the BFD that track ESI peer.";
      }
      leaf e-tree-leaf {
        // NCS drop when statement
        type boolean;
        // NCS drop must statement
        // NCS drop default statement
        description
          "Enable/disable the E-Tree leaf attribute of interface.";
      }
      leaf state {
        type evpn:live_ncs_interface-state;
        description
          "Interface state.";
      }
      leaf vc-state {
        type evpn:live_ncs_vc-state;
        description
          "VC state.";
      }
    }
    container evpn-attribute {
      tailf:ncs-device-type "netconf";
      tailf:display-when "not(../../../../../ncs:module) or ../../../../../ncs:module[ncs:name='huawei-evpn'] or (../../../../../ncs:live-status-protocol[not(ncs:capability)]) or (../../../../../ncs:live-status-protocol/ncs:capability/ncs:module[.='huawei-evpn'])";
      description
        "Configure EVPN attribute of interface.";
      container track-peers {
        // NCS drop when statement
        description
          "List of track peer.";
        list track-peer {
          key "es-track-address";
          description
            "Configure the track peer info.";
          leaf es-track-address {
            type leafref {
              path "/ncs:devices/ncs:device/ncs:live-status/ni:network-instance/ni:instances/ni:instance/bgp:bgp/bgp:base-process/bgp:peers/bgp:peer/bgp:address" {
                tailf:xpath-root 3;
              }
            }
            // NCS drop must statement
            description
              "Track peer address.";
          }
        }
      }
    }
  }
  augment "/ncs:devices/ncs:device/ncs:config/ifm:ifm/ifm:interfaces/ifm:interface" {
    description
      "Configure EVPN with the interface.";
    container evpn {
      tailf:ncs-device-type "netconf";
      tailf:display-when "not(../../../../../ncs:module) or ../../../../../ncs:module[ncs:name='huawei-evpn']";
      description
        "Configure ESI interface.";
      leaf name {
        type leafref {
          path "/ncs:devices/ncs:device/ncs:config/evpn:evpn/evpn:instances/evpn:instance/evpn:name" {
            tailf:xpath-root 3;
          }
        }
        must "/evpn:evpn/evpn:instances/evpn:instance[evpn:name=current()]/evpn:type='i-evpn' or /evpn:evpn/evpn:instances/evpn:instance[evpn:name=current()]/evpn:type='normal'" {
          tailf:xpath-root 3;
        }
        description
          "Configure EVPL instances bound to an EVPN instance.";
      }
      leaf pbb-source-mac {
        when '../name' {
          tailf:xpath-root 3;
        }
        type pub-type:mac-address;
        must "/evpn:evpn/evpn:instances/evpn:instance[evpn:name=current()/../evpn:name]/evpn:type='i-evpn'" {
          tailf:xpath-root 3;
        }
        description
          "Specifies a B-MAC address.";
      }
      leaf esi {
        when "(../../ifm:type='Ethernet') or (../../ifm:type='GigabitEthernet') or (../../ifm:type='Eth-Trunk') or (../../ifm:type='100GE') or (../../ifm:type='200GE') or (../../ifm:type='40GE') or (../../ifm:type='10GE') or (../../ifm:type='25GE') or (../../ifm:type='50GE') or (../../ifm:type='PW-VE') or (../../ifm:type='400GE')" {
          tailf:xpath-root 3;
        }
        type esi {
          length "1..24";
          pattern '( *(00([0-9a-fA-F]){2}\.(([0-9a-fA-F]){4}\.){3}(([0-9a-fA-F]){4}))? *)';
        }
        description
          "Static ESI, in the format of 00xx.xxxx.xxxx.xxxx.xxxx, in which x ranges from 0 to F. A static ESI cannot be all 0s. To clear a static ESI, enter a space.";
      }
      leaf esi-name {
        when "../../ifm:type='Eth-Trunk'" {
          tailf:xpath-root 3;
        }
        type leafref {
          path "/ncs:devices/ncs:device/ncs:config/evpn:evpn/evpn:site/evpn:dynamic-esis/evpn:dynamic-esi/evpn:esi-name" {
            tailf:xpath-root 3;
          }
        }
        description
          "Dynamic ESI name is a string of 1 to 31 characters, which begins with a-z or A-Z.";
      }
      leaf es-recovery-timer {
        when "(../../ifm:type='Ethernet') or (../../ifm:type='GigabitEthernet') or (../../ifm:type='Eth-Trunk') or (../../ifm:type='100GE') or (../../ifm:type='200GE') or (../../ifm:type='40GE') or (../../ifm:type='10GE') or (../../ifm:type='25GE') or (../../ifm:type='50GE') or (../../ifm:type='PW-VE') or (../../ifm:type='400GE')" {
          tailf:xpath-root 3;
        }
        type uint32 {
          range "3..1200";
        }
        units "s";
        description
          "ES recovery timer.";
      }
      leaf track-bfd-name {
        when "(../../ifm:type='Ethernet') or (../../ifm:type='GigabitEthernet') or (../../ifm:type='Eth-Trunk') or (../../ifm:type='100GE') or (../../ifm:type='200GE') or (../../ifm:type='40GE') or (../../ifm:type='10GE') or (../../ifm:type='25GE') or (../../ifm:type='50GE') or (../../ifm:type='PW-VE') or (../../ifm:type='400GE')" {
          tailf:xpath-root 3;
        }
        type leafref {
          path "/ncs:devices/ncs:device/ncs:config/bfd:bfd/bfd:sessions/bfd:session/bfd:name" {
            tailf:xpath-root 3;
          }
        }
        description
          "Specify the BFD that track ESI peer.";
      }
      leaf e-tree-leaf {
        when '../name' {
          tailf:xpath-root 3;
        }
        type boolean;
        must "(../e-tree-leaf = 'true' and /evpn:evpn/evpn:instances/evpn:instance[evpn:name=current()/../evpn:name]/evpn:normal-evpn/evpn:etree-enable='true') or (../e-tree-leaf = 'false')" {
          tailf:xpath-root 3;
        }
        default "false";
        description
          "Enable/disable the E-Tree leaf attribute of interface.";
      }
      // NCS drop config false leaf state
      // NCS drop config false leaf 'vc-state'
    }
    container evpn-attribute {
      tailf:ncs-device-type "netconf";
      tailf:display-when "not(../../../../../ncs:module) or ../../../../../ncs:module[ncs:name='huawei-evpn']";
      description
        "Configure EVPN attribute of interface.";
      container track-peers {
        when "(../../ifm:type='Eth-Trunk') or (../../ifm:type='PW-VE')" {
          tailf:xpath-root 3;
        }
        description
          "List of track peer.";
        list track-peer {
          key "es-track-address";
          description
            "Configure the track peer info.";
          leaf es-track-address {
            type leafref {
              path "/ncs:devices/ncs:device/ncs:config/ni:network-instance/ni:instances/ni:instance/bgp:bgp/bgp:base-process/bgp:peers/bgp:peer/bgp:address" {
                tailf:xpath-root 3;
              }
            }
            must "/ni:network-instance/ni:instances/ni:instance/bgp:bgp/bgp:base-process/bgp:peers/bgp:peer[bgp:address=current()]/bgp:afs/bgp:af[bgp:type='evpn']" {
              tailf:xpath-root 3;
            }
            description
              "Track peer address.";
          }
        }
      }
    }
  }
  augment "/ncs:devices/ncs:template/ncs:ned-id/ncs:config/l2vpn:l2vpn/l2vpn:instances/l2vpn:instance/l2vpn:vpls/l2vpn:ldp-signaling/l2vpn:pws/l2vpn:pw" {
    description
      "Configure the EVPN attributes of a PW.";
    container evpn {
      description
        "Configure the EVPN attributes of a PW.";
      leaf etree-leaf-enable {
        // NCS drop when statement
        type string;
        // NCS drop must statement
        // NCS drop default statement
        description
          "Enable/disable the E-Tree leaf attribute of a PW.";
      }
      leaf esi {
        // NCS drop when statement
        type string;
        // NCS drop must statement
        description
          "Static ESI, in the format of 00xx.xxxx.xxxx.xxxx.xxxx, in which x ranges from 0 to F. A static ESI cannot be all 0s. To clear a static ESI, enter a space.";
      }
      // NCS drop config false leaf state
    }
  }
  augment "/ncs:devices/ncs:device/ncs:live-status/l2vpn:l2vpn/l2vpn:instances/l2vpn:instance/l2vpn:vpls/l2vpn:ldp-signaling/l2vpn:pws/l2vpn:pw" {
    description
      "Configure the EVPN attributes of a PW.";
    container evpn {
      tailf:ncs-device-type "netconf";
      tailf:display-when "not(../../../../../../../../../ncs:module) or ../../../../../../../../../ncs:module[ncs:name='huawei-evpn'] or (../../../../../../../../../ncs:live-status-protocol[not(ncs:capability)]) or (../../../../../../../../../ncs:live-status-protocol/ncs:capability/ncs:module[.='huawei-evpn'])";
      description
        "Configure the EVPN attributes of a PW.";
      leaf etree-leaf-enable {
        // NCS drop when statement
        type boolean;
        // NCS drop must statement
        // NCS drop default statement
        description
          "Enable/disable the E-Tree leaf attribute of a PW.";
      }
      leaf esi {
        // NCS drop when statement
        type leafref {
          path "/ncs:devices/ncs:device/ncs:live-status/evpn:evpn/evpn:site/evpn:static-esis/evpn:static-esi/evpn:esi" {
            tailf:xpath-root 3;
          }
        }
        // NCS drop must statement
        description
          "Static ESI, in the format of 00xx.xxxx.xxxx.xxxx.xxxx, in which x ranges from 0 to F. A static ESI cannot be all 0s. To clear a static ESI, enter a space.";
      }
      leaf state {
        type l2vpn:live_ncs_l2vpn-pw-state;
        description
          "PW state.";
      }
    }
  }
  augment "/ncs:devices/ncs:device/ncs:config/l2vpn:l2vpn/l2vpn:instances/l2vpn:instance/l2vpn:vpls/l2vpn:ldp-signaling/l2vpn:pws/l2vpn:pw" {
    description
      "Configure the EVPN attributes of a PW.";
    container evpn {
      tailf:ncs-device-type "netconf";
      tailf:display-when "not(../../../../../../../../../ncs:module) or ../../../../../../../../../ncs:module[ncs:name='huawei-evpn']";
      description
        "Configure the EVPN attributes of a PW.";
      leaf etree-leaf-enable {
        when "../../../../../l2vpn:work-mode='bd-mode' and ../../l2vpn:upe='true' and ../../l2vpn:name" {
          tailf:xpath-root 3;
        }
        type boolean;
        must "(../etree-leaf-enable='true' and ../../../../../l2vpn:bds/l2vpn:bd/l2vpn:id and /bd:bd/bd:instances/bd:instance[bd:id=current()/../../../../../l2vpn:bds/l2vpn:bd/l2vpn:id]/evpn:evpn/evpn:name and /evpn:evpn/evpn:instances/evpn:instance[evpn:name=/bd:bd/bd:instances/bd:instance[bd:id=current()/../../../../../l2vpn:bds/l2vpn:bd/l2vpn:id]/evpn:evpn/evpn:name]/evpn:type='bd-evpn' and /evpn:evpn/evpn:instances/evpn:instance[evpn:name=/bd:bd/bd:instances/bd:instance[bd:id=current()/../../../../../l2vpn:bds/l2vpn:bd/l2vpn:id]/evpn:evpn/evpn:name]/evpn:bd-evpn/evpn:etree-enable='true') or ../etree-leaf-enable='false'" {
          tailf:xpath-root 3;
        }
        default "false";
        description
          "Enable/disable the E-Tree leaf attribute of a PW.";
      }
      leaf esi {
        when "../../../../../l2vpn:work-mode='bd-mode' and ../../l2vpn:upe='true' and ../../l2vpn:name" {
          tailf:xpath-root 3;
        }
        type leafref {
          path "/ncs:devices/ncs:device/ncs:config/evpn:evpn/evpn:site/evpn:static-esis/evpn:static-esi/evpn:esi" {
            tailf:xpath-root 3;
          }
        }
        must "/evpn:evpn/evpn:site/evpn:static-esis/evpn:static-esi[evpn:esi=current()/../evpn:esi]/evpn:redundancy-mode='single-active'" {
          tailf:xpath-root 3;
        }
        description
          "Static ESI, in the format of 00xx.xxxx.xxxx.xxxx.xxxx, in which x ranges from 0 to F. A static ESI cannot be all 0s. To clear a static ESI, enter a space.";
      }
      // NCS drop config false leaf state
    }
  }
}
