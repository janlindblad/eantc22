module huawei-system {
  // Generated by yanger -t ncs
  tailf:mount-id "huawei-nc-1.0:huawei-nc-1.0";
  tailf:ncs-device-type "netconf";

  namespace "urn:huawei:yang:huawei-system";
  prefix system;

  import huawei-pub-type {
    prefix pub-type;
  }
  import huawei-extension {
    prefix ext;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "System.";

  revision 2020-03-02 {
    description
      "Initial revision.";
    reference "Huawei private.";
  }
  ext:task-name "system";

  typedef ncs_template_risk-level-type {
    type string;
    description
      "Security risk level.";
  }

  typedef ncs_template_security-risk-type {
    type string;
    description
      "Security risk type.";
  }

  typedef ncs_rpc_notif_risk-level-type {
    type enumeration {
      enum "high" {
        value 0;
        description
          "High level.";
      }
      enum "medium" {
        value 1;
        description
          "Medium level.";
      }
      enum "low" {
        value 2;
        description
          "Low level.";
      }
    }
    description
      "Security risk level.";
  }

  typedef ncs_rpc_notif_security-risk-type {
    type enumeration {
      enum "insecure-algorithm" {
        value 0;
        description
          "Insecure algorithm type.";
      }
      enum "insecure-protocol" {
        value 1;
        description
          "Insecure protocol type.";
      }
      enum "insecure-configuration" {
        value 2;
        description
          "Insecure configuration type.";
      }
    }
    description
      "Security risk type.";
  }

  typedef live_ncs_risk-level-type {
    type enumeration {
      enum "high" {
        value 0;
        description
          "High level.";
      }
      enum "medium" {
        value 1;
        description
          "Medium level.";
      }
      enum "low" {
        value 2;
        description
          "Low level.";
      }
    }
    description
      "Security risk level.";
  }

  typedef live_ncs_security-risk-type {
    type enumeration {
      enum "insecure-algorithm" {
        value 0;
        description
          "Insecure algorithm type.";
      }
      enum "insecure-protocol" {
        value 1;
        description
          "Insecure protocol type.";
      }
      enum "insecure-configuration" {
        value 2;
        description
          "Insecure configuration type.";
      }
    }
    description
      "Security risk type.";
  }

  typedef risk-level-type {
    type enumeration {
      enum "high" {
        value 0;
        description
          "High level.";
      }
      enum "medium" {
        value 1;
        description
          "Medium level.";
      }
      enum "low" {
        value 2;
        description
          "Low level.";
      }
    }
    description
      "Security risk level.";
  }

  typedef security-risk-type {
    type enumeration {
      enum "insecure-algorithm" {
        value 0;
        description
          "Insecure algorithm type.";
      }
      enum "insecure-protocol" {
        value 1;
        description
          "Insecure protocol type.";
      }
      enum "insecure-configuration" {
        value 2;
        description
          "Insecure configuration type.";
      }
    }
    description
      "Security risk type.";
  }

  augment "/ncs:devices/ncs:device/ncs:config" {
    container system {
      tailf:ncs-device-type "netconf";
      tailf:display-when "not(../../ncs:module) or ../../ncs:module[ncs:name='huawei-system']";
      description
        "System.";
      container system-info {
        description
          "Configure system information.";
        leaf sys-name {
          type string {
            length "1..246";
          }
          default "HUAWEI";
          description
            "System name.";
        }
        leaf sys-contact {
          type string {
            length "1..255";
          }
          default "R&D Beijing, Huawei Technologies co.,Ltd.";
          description
            "System contact information.";
        }
        leaf sys-location {
          type string {
            length "1..255";
          }
          default "Beijing China";
          description
            "System location information.";
        }
        // NCS drop config false leaf 'sys-desc'
        // NCS drop config false leaf 'sys-object-id'
        // NCS drop config false leaf 'system-gmt-time'
        // NCS drop config false leaf 'sys-uptime'
        // NCS drop config false leaf 'sys-service'
        // NCS drop config false leaf 'platform-name'
        // NCS drop config false leaf 'platform-version'
        // NCS drop config false leaf 'product-name'
        // NCS drop config false leaf 'product-version'
        // NCS drop config false leaf uname
        // NCS drop config false leaf 'patch-version'
        // NCS drop config false leaf esn
        // NCS drop config false leaf mac
        // NCS drop config false leaf 'software-name'
      }
      // NCS drop config false container 'security-risks'
    }
  }
  augment "/ncs:devices/ncs:device/ncs:live-status" {
    container system {
      tailf:ncs-device-type "netconf";
      tailf:display-when "not(../../ncs:module) or ../../ncs:module[ncs:name='huawei-system'] or (../../ncs:live-status-protocol[not(ncs:capability)]) or (../../ncs:live-status-protocol/ncs:capability/ncs:module[.='huawei-system'])";
      description
        "System.";
      container system-info {
        description
          "Configure system information.";
        leaf sys-name {
          type string {
            length "1..246";
          }
          // NCS drop default statement
          description
            "System name.";
        }
        leaf sys-contact {
          type string {
            length "1..255";
          }
          // NCS drop default statement
          description
            "System contact information.";
        }
        leaf sys-location {
          type string {
            length "1..255";
          }
          // NCS drop default statement
          description
            "System location information.";
        }
        leaf sys-desc {
          type string {
            length "0..255";
          }
          description
            "Textual description of an entity.";
        }
        leaf sys-object-id {
          type string {
            length "0..255";
          }
          description
            "Entity OID.";
        }
        leaf system-gmt-time {
          type uint32;
          description
            "Current system time in UTC seconds.";
        }
        leaf sys-uptime {
          type pub-type:live_ncs_time-tick;
          description
            "Time elapses since the system is running.";
        }
        leaf sys-service {
          type bits {
            bit physical-layer {
              position 0;
              description
                "Physical layer.";
            }
            bit data-link-layer {
              position 1;
              description
                "Data Link layer.";
            }
            bit network-layer {
              position 2;
              description
                "Network layer.";
            }
            bit transport-layer {
              position 3;
              description
                "Transport layer.";
            }
            bit session-layer {
              position 4;
              description
                "Session layer.";
            }
            bit presentation-layer {
              position 5;
              description
                "Presentation layer.";
            }
            bit application-layer {
              position 6;
              description
                "Application layer.";
            }
          }
          description
            "Integer value which indicates the set of services that this entity offers.";
        }
        leaf platform-name {
          type string {
            length "0..255";
          }
          description
            "Name of a platform. For example, Huawei Versatile Routing Platform.";
        }
        leaf platform-version {
          type string {
            length "1..255";
          }
          description
            "Version of a platform. For example, VRP (R) Software, Version 8.10.";
        }
        leaf product-name {
          type string {
            length "0..255";
          }
          description
            "Name of a product. For example, Quidway NetEngine 5000E.";
        }
        leaf product-version {
          type string {
            length "1..255";
          }
          description
            "Product version. The version format is VxxRxxCxxSPxxx, for example, V800R002C01SPC001.";
        }
        leaf uname {
          type string {
            length "1..52";
          }
          description
            "The array device shall contain a name that identifies the hardware that the system is running on.";
        }
        leaf patch-version {
          type string {
            length "1..255";
          }
          description
            "Latest patch version. The version format is CPxxx/HPxxx, for example, CP001.";
        }
        leaf esn {
          type string {
            length "0..511";
          }
          description
            "Product ESN number.";
        }
        leaf mac {
          type pub-type:live_ncs_mac-address;
          description
            "System MAC address.";
        }
        leaf software-name {
          type string {
            length "4..255";
          }
          description
            "System software name. For example, VRPV800R019C10B210D1111_nos.cc.";
        }
      }
      container security-risks {
        description
          "List of security risk information.";
        list security-risk {
          key "level feature-name type content";
          description
            "Statistics of security risk.";
          leaf level {
            type live_ncs_risk-level-type;
            description
              "Security risk Level.";
          }
          leaf feature-name {
            type string {
              length "1..31";
            }
            description
              "Feature name.";
          }
          leaf type {
            type live_ncs_security-risk-type;
            description
              "Security risk type.";
          }
          leaf content {
            type string {
              length "1..511";
            }
            description
              "Risk information.";
          }
          leaf repair-action {
            type string {
              length "1..511";
            }
            description
              "Repair action.";
          }
        }
      }
    }
  }
  augment "/ncs:devices/ncs:template/ncs:ned-id/ncs:config" {
    container system {
      description
        "System.";
      container system-info {
        description
          "Configure system information.";
        leaf sys-name {
          type string;
          // NCS drop default statement
          description
            "System name.";
        }
        leaf sys-contact {
          type string;
          // NCS drop default statement
          description
            "System contact information.";
        }
        leaf sys-location {
          type string;
          // NCS drop default statement
          description
            "System location information.";
        }
        // NCS drop config false leaf 'sys-desc'
        // NCS drop config false leaf 'sys-object-id'
        // NCS drop config false leaf 'system-gmt-time'
        // NCS drop config false leaf 'sys-uptime'
        // NCS drop config false leaf 'sys-service'
        // NCS drop config false leaf 'platform-name'
        // NCS drop config false leaf 'platform-version'
        // NCS drop config false leaf 'product-name'
        // NCS drop config false leaf 'product-version'
        // NCS drop config false leaf uname
        // NCS drop config false leaf 'patch-version'
        // NCS drop config false leaf esn
        // NCS drop config false leaf mac
        // NCS drop config false leaf 'software-name'
      }
      // NCS drop config false container 'security-risks'
    }
  }
}
