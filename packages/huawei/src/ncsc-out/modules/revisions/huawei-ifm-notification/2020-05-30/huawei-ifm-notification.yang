module huawei-ifm-notification {
  // Generated by yanger -t ncs
  tailf:mount-id "huawei-nc-1.0:huawei-nc-1.0";
  tailf:ncs-device-type "netconf";

  yang-version 1;
  namespace "urn:huawei:yang:huawei-ifm-notification";
  prefix ifm-notification;

  import huawei-pub-type {
    prefix pub-type;
  }
  import huawei-extension {
    prefix ext;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Notification of ifm.";

  revision 2020-05-30 {
    description
      "Initial revision.";
    reference "Huawei private.";
  }
  ext:task-name "interface-mgr";

  typedef ncs_template_port-status {
    type string;
    description
      "Interface suppression status.";
  }

  typedef ncs_template_suppress-status {
    type string;
    description
      "Interface suppression status.";
  }

  typedef ncs_rpc_notif_port-status {
    type enumeration {
      enum "up" {
        value 1;
        description
          "The interface is in Up state.";
      }
      enum "down" {
        value 2;
        description
          "The interface is in Down state.";
      }
    }
    description
      "Interface suppression status.";
  }

  typedef ncs_rpc_notif_suppress-status {
    type enumeration {
      enum "unsuppress" {
        value 0;
        description
          "The interface is not suppressed.";
      }
      enum "suppress" {
        value 1;
        description
          "The interface is suppressed.";
      }
    }
    description
      "Interface suppression status.";
  }

  typedef live_ncs_port-status {
    type enumeration {
      enum "up" {
        value 1;
        description
          "The interface is in Up state.";
      }
      enum "down" {
        value 2;
        description
          "The interface is in Down state.";
      }
    }
    description
      "Interface suppression status.";
  }

  typedef live_ncs_suppress-status {
    type enumeration {
      enum "unsuppress" {
        value 0;
        description
          "The interface is not suppressed.";
      }
      enum "suppress" {
        value 1;
        description
          "The interface is suppressed.";
      }
    }
    description
      "Interface suppression status.";
  }

  typedef port-status {
    type enumeration {
      enum "up" {
        value 1;
        description
          "The interface is in Up state.";
      }
      enum "down" {
        value 2;
        description
          "The interface is in Down state.";
      }
    }
    description
      "Interface suppression status.";
  }

  typedef suppress-status {
    type enumeration {
      enum "unsuppress" {
        value 0;
        description
          "The interface is not suppressed.";
      }
      enum "suppress" {
        value 1;
        description
          "The interface is suppressed.";
      }
    }
    description
      "Interface suppression status.";
  }

  augment "/ncs:devices/ncs:device/ncs:notifications/ncs:received-notifications/ncs:notification/ncs:data" {
    container link-up {
      presence "";
      config false;
      description
        "The interface status changes.";
      leaf index {
        type uint32;
        // NCS drop mandatory statement
        description
          "Interface index.";
      }
      leaf admin-status {
        type ncs_rpc_notif_port-status;
        // NCS drop mandatory statement
        description
          "Configured interface status.";
      }
      leaf oper-status {
        type ncs_rpc_notif_port-status;
        // NCS drop mandatory statement
        description
          "Current interface status.";
      }
      leaf name {
        type pub-type:ncs_rpc_notif_if-name;
        // NCS drop mandatory statement
        description
          "Interface name.";
      }
      leaf reason-code {
        type uint32;
        // NCS drop mandatory statement
        description
          "Cause for trap generation.";
      }
      leaf main-if-name {
        type pub-type:ncs_rpc_notif_if-name;
        // NCS drop mandatory statement
        description
          "Name of the main interface.";
      }
    }
  }
  augment "/ncs:devices/ncs:device/ncs:notifications/ncs:received-notifications/ncs:notification/ncs:data" {
    container link-down {
      presence "";
      config false;
      description
        "The interface status changes.";
      leaf index {
        type uint32;
        // NCS drop mandatory statement
        description
          "Interface index.";
      }
      leaf admin-status {
        type ncs_rpc_notif_port-status;
        // NCS drop mandatory statement
        description
          "Configured interface status.";
      }
      leaf oper-status {
        type ncs_rpc_notif_port-status;
        // NCS drop mandatory statement
        description
          "Current interface status.";
      }
      leaf name {
        type pub-type:ncs_rpc_notif_if-name;
        // NCS drop mandatory statement
        description
          "Interface name.";
      }
      leaf reason-code {
        type uint32;
        // NCS drop mandatory statement
        description
          "Cause for trap generation.";
      }
      leaf main-if-name {
        type pub-type:ncs_rpc_notif_if-name;
        // NCS drop mandatory statement
        description
          "Name of the main interface.";
      }
    }
  }
  augment "/ncs:devices/ncs:device/ncs:notifications/ncs:received-notifications/ncs:notification/ncs:data" {
    container ipv6-if-state-change {
      presence "";
      config false;
      description
        "The IPv6 status changes.";
      leaf index {
        type uint32;
        // NCS drop mandatory statement
        description
          "Interface index.";
      }
      leaf name {
        type pub-type:ncs_rpc_notif_if-name;
        // NCS drop mandatory statement
        description
          "Indicates the interface name.";
      }
      leaf oper-status {
        type ncs_rpc_notif_port-status;
        // NCS drop mandatory statement
        description
          "Indicates the current status of an interface.";
      }
      leaf admin-status {
        type ncs_rpc_notif_port-status;
        // NCS drop mandatory statement
        description
          "Indicates the administrative status of an interface.";
      }
      leaf main-if-name {
        type pub-type:ncs_rpc_notif_if-name;
        // NCS drop mandatory statement
        description
          "Main interface name.";
      }
      leaf reason-code {
        type uint32;
        // NCS drop mandatory statement
        description
          "Cause for trap generation.";
      }
    }
  }
  augment "/ncs:devices/ncs:device/ncs:notifications/ncs:received-notifications/ncs:notification/ncs:data" {
    container physical-admin-if-up {
      presence "";
      config false;
      description
        "The physical manage interface physical status changes to up.";
      leaf index {
        type uint32;
        // NCS drop mandatory statement
        description
          "Interface index.";
      }
      leaf name {
        type pub-type:ncs_rpc_notif_if-name;
        // NCS drop mandatory statement
        description
          "Name of the physical management interface.";
      }
      leaf oper-status {
        type ncs_rpc_notif_port-status;
        // NCS drop mandatory statement
        description
          "Status of the physical management interface.";
      }
    }
  }
  augment "/ncs:devices/ncs:device/ncs:notifications/ncs:received-notifications/ncs:notification/ncs:data" {
    container physical-admin-if-down {
      presence "";
      config false;
      description
        "The physical manage interface physical status changes to down.";
      leaf index {
        type uint32;
        // NCS drop mandatory statement
        description
          "Interface index.";
      }
      leaf name {
        type pub-type:ncs_rpc_notif_if-name;
        // NCS drop mandatory statement
        description
          "Name of the physical management interface.";
      }
      leaf oper-status {
        type ncs_rpc_notif_port-status;
        // NCS drop mandatory statement
        description
          "Status of the physical management interface.";
      }
    }
  }
  augment "/ncs:devices/ncs:device/ncs:notifications/ncs:received-notifications/ncs:notification/ncs:data" {
    container if-damp-resume {
      presence "";
      config false;
      description
        "The state of interface changed from suppress to unsuppress.";
      leaf interface-name {
        type pub-type:ncs_rpc_notif_if-name;
        description
          "Interface name.";
      }
      leaf suppress-state {
        type ncs_rpc_notif_suppress-status;
        description
          "Interface suppression status: - 0: The interface is not suppressed. - 1: The interface is suppressed.";
      }
    }
  }
  augment "/ncs:devices/ncs:device/ncs:notifications/ncs:received-notifications/ncs:notification/ncs:data" {
    container if-damp-suppress {
      presence "";
      config false;
      description
        "The state of interface changed from unsuppress to suppress.";
      leaf interface-name {
        type pub-type:ncs_rpc_notif_if-name;
        description
          "Interface name.";
      }
      leaf suppress-state {
        type ncs_rpc_notif_suppress-status;
        description
          "Interface suppression status: - 0: The interface is not suppressed. - 1: The interface is suppressed.";
      }
    }
  }
  augment "/ncs:devices/ncs:device/ncs:notifications/ncs:received-notifications/ncs:notification/ncs:data" {
    container error-down-recovery {
      presence "";
      config false;
      description
        "Error-down recovered.";
      leaf index {
        type uint32;
        // NCS drop mandatory statement
        description
          "Index of an interface.";
      }
      leaf name {
        type pub-type:ncs_rpc_notif_if-name;
        // NCS drop mandatory statement
        description
          "Interface name.";
      }
      leaf cause {
        type string {
          length "1..50";
        }
        // NCS drop mandatory statement
        description
          "Cause of the errordown event.";
      }
      leaf recovery-type {
        type string {
          length "1..20";
        }
        // NCS drop mandatory statement
        description
          "Specifies the alarm clearance type. The value is auto recovery or Null. The alarm clearance type triggered by restarting an interface is auto recovery.";
      }
    }
  }
  augment "/ncs:devices/ncs:device/ncs:notifications/ncs:received-notifications/ncs:notification/ncs:data" {
    container error-down {
      presence "";
      config false;
      description
        "Error-down occurred.";
      leaf index {
        type uint32;
        // NCS drop mandatory statement
        description
          "Index of an interface.";
      }
      leaf name {
        type pub-type:ncs_rpc_notif_if-name;
        // NCS drop mandatory statement
        description
          "Interface name.";
      }
      leaf cause {
        type string {
          length "1..50";
        }
        // NCS drop mandatory statement
        description
          "Cause of the errordown event.";
      }
      leaf recovery-type {
        type string {
          length "1..20";
        }
        // NCS drop mandatory statement
        description
          "Specifies the alarm clearance type. The value is auto recovery or Null. The alarm clearance type triggered by restarting an interface is auto recovery.";
      }
    }
  }
  augment "/ncs:devices/ncs:device/ncs:netconf-notifications/ncs:received-notifications/ncs:notification/ncs:data" {
    container link-up {
      presence "";
      config false;
      description
        "The interface status changes.";
      leaf index {
        type uint32;
        // NCS drop mandatory statement
        description
          "Interface index.";
      }
      leaf admin-status {
        type ncs_rpc_notif_port-status;
        // NCS drop mandatory statement
        description
          "Configured interface status.";
      }
      leaf oper-status {
        type ncs_rpc_notif_port-status;
        // NCS drop mandatory statement
        description
          "Current interface status.";
      }
      leaf name {
        type pub-type:ncs_rpc_notif_if-name;
        // NCS drop mandatory statement
        description
          "Interface name.";
      }
      leaf reason-code {
        type uint32;
        // NCS drop mandatory statement
        description
          "Cause for trap generation.";
      }
      leaf main-if-name {
        type pub-type:ncs_rpc_notif_if-name;
        // NCS drop mandatory statement
        description
          "Name of the main interface.";
      }
    }
  }
  augment "/ncs:devices/ncs:device/ncs:netconf-notifications/ncs:received-notifications/ncs:notification/ncs:data" {
    container link-down {
      presence "";
      config false;
      description
        "The interface status changes.";
      leaf index {
        type uint32;
        // NCS drop mandatory statement
        description
          "Interface index.";
      }
      leaf admin-status {
        type ncs_rpc_notif_port-status;
        // NCS drop mandatory statement
        description
          "Configured interface status.";
      }
      leaf oper-status {
        type ncs_rpc_notif_port-status;
        // NCS drop mandatory statement
        description
          "Current interface status.";
      }
      leaf name {
        type pub-type:ncs_rpc_notif_if-name;
        // NCS drop mandatory statement
        description
          "Interface name.";
      }
      leaf reason-code {
        type uint32;
        // NCS drop mandatory statement
        description
          "Cause for trap generation.";
      }
      leaf main-if-name {
        type pub-type:ncs_rpc_notif_if-name;
        // NCS drop mandatory statement
        description
          "Name of the main interface.";
      }
    }
  }
  augment "/ncs:devices/ncs:device/ncs:netconf-notifications/ncs:received-notifications/ncs:notification/ncs:data" {
    container ipv6-if-state-change {
      presence "";
      config false;
      description
        "The IPv6 status changes.";
      leaf index {
        type uint32;
        // NCS drop mandatory statement
        description
          "Interface index.";
      }
      leaf name {
        type pub-type:ncs_rpc_notif_if-name;
        // NCS drop mandatory statement
        description
          "Indicates the interface name.";
      }
      leaf oper-status {
        type ncs_rpc_notif_port-status;
        // NCS drop mandatory statement
        description
          "Indicates the current status of an interface.";
      }
      leaf admin-status {
        type ncs_rpc_notif_port-status;
        // NCS drop mandatory statement
        description
          "Indicates the administrative status of an interface.";
      }
      leaf main-if-name {
        type pub-type:ncs_rpc_notif_if-name;
        // NCS drop mandatory statement
        description
          "Main interface name.";
      }
      leaf reason-code {
        type uint32;
        // NCS drop mandatory statement
        description
          "Cause for trap generation.";
      }
    }
  }
  augment "/ncs:devices/ncs:device/ncs:netconf-notifications/ncs:received-notifications/ncs:notification/ncs:data" {
    container physical-admin-if-up {
      presence "";
      config false;
      description
        "The physical manage interface physical status changes to up.";
      leaf index {
        type uint32;
        // NCS drop mandatory statement
        description
          "Interface index.";
      }
      leaf name {
        type pub-type:ncs_rpc_notif_if-name;
        // NCS drop mandatory statement
        description
          "Name of the physical management interface.";
      }
      leaf oper-status {
        type ncs_rpc_notif_port-status;
        // NCS drop mandatory statement
        description
          "Status of the physical management interface.";
      }
    }
  }
  augment "/ncs:devices/ncs:device/ncs:netconf-notifications/ncs:received-notifications/ncs:notification/ncs:data" {
    container physical-admin-if-down {
      presence "";
      config false;
      description
        "The physical manage interface physical status changes to down.";
      leaf index {
        type uint32;
        // NCS drop mandatory statement
        description
          "Interface index.";
      }
      leaf name {
        type pub-type:ncs_rpc_notif_if-name;
        // NCS drop mandatory statement
        description
          "Name of the physical management interface.";
      }
      leaf oper-status {
        type ncs_rpc_notif_port-status;
        // NCS drop mandatory statement
        description
          "Status of the physical management interface.";
      }
    }
  }
  augment "/ncs:devices/ncs:device/ncs:netconf-notifications/ncs:received-notifications/ncs:notification/ncs:data" {
    container if-damp-resume {
      presence "";
      config false;
      description
        "The state of interface changed from suppress to unsuppress.";
      leaf interface-name {
        type pub-type:ncs_rpc_notif_if-name;
        description
          "Interface name.";
      }
      leaf suppress-state {
        type ncs_rpc_notif_suppress-status;
        description
          "Interface suppression status: - 0: The interface is not suppressed. - 1: The interface is suppressed.";
      }
    }
  }
  augment "/ncs:devices/ncs:device/ncs:netconf-notifications/ncs:received-notifications/ncs:notification/ncs:data" {
    container if-damp-suppress {
      presence "";
      config false;
      description
        "The state of interface changed from unsuppress to suppress.";
      leaf interface-name {
        type pub-type:ncs_rpc_notif_if-name;
        description
          "Interface name.";
      }
      leaf suppress-state {
        type ncs_rpc_notif_suppress-status;
        description
          "Interface suppression status: - 0: The interface is not suppressed. - 1: The interface is suppressed.";
      }
    }
  }
  augment "/ncs:devices/ncs:device/ncs:netconf-notifications/ncs:received-notifications/ncs:notification/ncs:data" {
    container error-down-recovery {
      presence "";
      config false;
      description
        "Error-down recovered.";
      leaf index {
        type uint32;
        // NCS drop mandatory statement
        description
          "Index of an interface.";
      }
      leaf name {
        type pub-type:ncs_rpc_notif_if-name;
        // NCS drop mandatory statement
        description
          "Interface name.";
      }
      leaf cause {
        type string {
          length "1..50";
        }
        // NCS drop mandatory statement
        description
          "Cause of the errordown event.";
      }
      leaf recovery-type {
        type string {
          length "1..20";
        }
        // NCS drop mandatory statement
        description
          "Specifies the alarm clearance type. The value is auto recovery or Null. The alarm clearance type triggered by restarting an interface is auto recovery.";
      }
    }
  }
  augment "/ncs:devices/ncs:device/ncs:netconf-notifications/ncs:received-notifications/ncs:notification/ncs:data" {
    container error-down {
      presence "";
      config false;
      description
        "Error-down occurred.";
      leaf index {
        type uint32;
        // NCS drop mandatory statement
        description
          "Index of an interface.";
      }
      leaf name {
        type pub-type:ncs_rpc_notif_if-name;
        // NCS drop mandatory statement
        description
          "Interface name.";
      }
      leaf cause {
        type string {
          length "1..50";
        }
        // NCS drop mandatory statement
        description
          "Cause of the errordown event.";
      }
      leaf recovery-type {
        type string {
          length "1..20";
        }
        // NCS drop mandatory statement
        description
          "Specifies the alarm clearance type. The value is auto recovery or Null. The alarm clearance type triggered by restarting an interface is auto recovery.";
      }
    }
  }
}
