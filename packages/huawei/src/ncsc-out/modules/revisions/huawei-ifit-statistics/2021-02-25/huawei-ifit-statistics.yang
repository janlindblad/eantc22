module huawei-ifit-statistics {
  // Generated by yanger -t ncs
  tailf:mount-id "huawei-nc-1.0:huawei-nc-1.0";
  tailf:ncs-device-type "netconf";

  yang-version 1;
  namespace "urn:huawei:yang:huawei-ifit-statistics";
  prefix ifit-statistics;

  import huawei-ifit {
    prefix ifit;
  }
  import huawei-pub-type {
    prefix pub-type;
  }
  import ietf-inet-types {
    prefix inet;
  }
  import huawei-extension {
    prefix ext;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "IFIT statistics.";

  revision 2021-02-25 {
    description
      "Add new leafs of gtp measurement.";
    reference "Huawei private.";
  }
  revision 2020-08-28 {
    description
      "Add new container:flow-vpws-statistics.";
    reference "Huawei private.";
  }
  revision 2020-08-10 {
    description
      "Add new leaf:evpl-id.";
    reference "Huawei private.";
  }
  revision 2020-07-25 {
    description
      "Modify description: add new leafs of perpacket delay.";
    reference "Huawei private.";
  }
  revision 2020-03-05 {
    description
      "Modify description.";
    reference "Huawei private.";
  }
  revision 2019-12-28 {
    description
      "Add new leaf: if-index.";
    reference "Huawei private.";
  }
  revision 2019-10-12 {
    description
      "Add new containers: flow-peer-ip-statistics and flow-locator-statistics.";
    reference "Huawei private.";
  }
  revision 2019-05-17 {
    description
      "Init revision.";
    reference "Huawei private.";
  }
  ext:task-name "ifit";

  typedef ncs_template_address-family {
    type string;
    description
      "The type of IP address family.";
  }

  typedef ncs_template_vpn-type {
    type string;
    description
      "Type of VPN.";
  }

  typedef ncs_template_flow-direction {
    type string;
    description
      "Direction of an IFIT flow.";
  }

  typedef ncs_template_ifit-gtp-mode {
    type string;
    description
      "Mode of the IFIT GTP measurement.";
  }

  typedef ncs_rpc_notif_address-family {
    type enumeration {
      enum "ipv4" {
        value 0;
        description
          "IPv4 address family.";
      }
      enum "ipv6" {
        value 1;
        description
          "IPv6 address family.";
      }
    }
    description
      "The type of IP address family.";
  }

  typedef ncs_rpc_notif_vpn-type {
    type enumeration {
      enum "vpn" {
        value 0;
        description
          "L3VPN or L3EVPN.";
      }
      enum "evpn-vpws" {
        value 1;
        description
          "EVPN VPWS.";
      }
    }
    description
      "Type of VPN.";
  }

  typedef ncs_rpc_notif_flow-direction {
    type enumeration {
      enum "ingress" {
        value 1;
        description
          "Ingress of an IFIT flow.";
      }
      enum "transit-input" {
        value 2;
        description
          "TransitInput of an IFIT flow.";
      }
      enum "transit-output" {
        value 3;
        description
          "TransitOutput of an IFIT flow.";
      }
      enum "egress" {
        value 4;
        description
          "Egress of an IFIT flow.";
      }
    }
    description
      "Direction of an IFIT flow.";
  }

  typedef ncs_rpc_notif_ifit-gtp-mode {
    type enumeration {
      enum "disabled" {
        value 0;
        description
          "The IFIT GTP measurement is disabled.";
      }
      enum "enable" {
        value 1;
        description
          "The IFIT GTP measurement is enabled.";
      }
      enum "sn-enable" {
        value 2;
        description
          "The IFIT GTPU-SN measurement is enabled.";
      }
    }
    description
      "Mode of the IFIT GTP measurement.";
  }

  typedef live_ncs_address-family {
    type enumeration {
      enum "ipv4" {
        value 0;
        description
          "IPv4 address family.";
      }
      enum "ipv6" {
        value 1;
        description
          "IPv6 address family.";
      }
    }
    description
      "The type of IP address family.";
  }

  typedef live_ncs_vpn-type {
    type enumeration {
      enum "vpn" {
        value 0;
        description
          "L3VPN or L3EVPN.";
      }
      enum "evpn-vpws" {
        value 1;
        description
          "EVPN VPWS.";
      }
    }
    description
      "Type of VPN.";
  }

  typedef live_ncs_flow-direction {
    type enumeration {
      enum "ingress" {
        value 1;
        description
          "Ingress of an IFIT flow.";
      }
      enum "transit-input" {
        value 2;
        description
          "TransitInput of an IFIT flow.";
      }
      enum "transit-output" {
        value 3;
        description
          "TransitOutput of an IFIT flow.";
      }
      enum "egress" {
        value 4;
        description
          "Egress of an IFIT flow.";
      }
    }
    description
      "Direction of an IFIT flow.";
  }

  typedef live_ncs_ifit-gtp-mode {
    type enumeration {
      enum "disabled" {
        value 0;
        description
          "The IFIT GTP measurement is disabled.";
      }
      enum "enable" {
        value 1;
        description
          "The IFIT GTP measurement is enabled.";
      }
      enum "sn-enable" {
        value 2;
        description
          "The IFIT GTPU-SN measurement is enabled.";
      }
    }
    description
      "Mode of the IFIT GTP measurement.";
  }

  typedef address-family {
    type enumeration {
      enum "ipv4" {
        value 0;
        description
          "IPv4 address family.";
      }
      enum "ipv6" {
        value 1;
        description
          "IPv6 address family.";
      }
    }
    description
      "The type of IP address family.";
  }

  typedef vpn-type {
    type enumeration {
      enum "vpn" {
        value 0;
        description
          "L3VPN or L3EVPN.";
      }
      enum "evpn-vpws" {
        value 1;
        description
          "EVPN VPWS.";
      }
    }
    description
      "Type of VPN.";
  }

  typedef flow-direction {
    type enumeration {
      enum "ingress" {
        value 1;
        description
          "Ingress of an IFIT flow.";
      }
      enum "transit-input" {
        value 2;
        description
          "TransitInput of an IFIT flow.";
      }
      enum "transit-output" {
        value 3;
        description
          "TransitOutput of an IFIT flow.";
      }
      enum "egress" {
        value 4;
        description
          "Egress of an IFIT flow.";
      }
    }
    description
      "Direction of an IFIT flow.";
  }

  typedef ifit-gtp-mode {
    type enumeration {
      enum "disabled" {
        value 0;
        description
          "The IFIT GTP measurement is disabled.";
      }
      enum "enable" {
        value 1;
        description
          "The IFIT GTP measurement is enabled.";
      }
      enum "sn-enable" {
        value 2;
        description
          "The IFIT GTPU-SN measurement is enabled.";
      }
    }
    description
      "Mode of the IFIT GTP measurement.";
  }

  grouping ncs_template_statistics-data {
    leaf period-id {
      type string;
      description
        "Index of the statistics collection period of IFIT flows.";
    }
    leaf packet-count {
      type string;
      description
        "Number of packets transmitted within this period.";
    }
    leaf byte-count {
      type string;
      description
        "Number of bytes transmitted within this period.";
    }
    leaf timestamp-second {
      type string;
      description
        "Integer part of the number of seconds starting at 00:00:00 UTC on January 1, 1970.";
    }
    leaf timestamp-nanosecond {
      type string;
      description
        "Decimal part of the number of seconds starting at 00:00:00 UTC on January 1, 1970.";
    }
    description
      "The result data of IFIT statistics.";
  }

  grouping ncs_rpc_notif_statistics-data {
    leaf period-id {
      type uint64;
      description
        "Index of the statistics collection period of IFIT flows.";
    }
    leaf packet-count {
      type uint64;
      description
        "Number of packets transmitted within this period.";
    }
    leaf byte-count {
      type uint64;
      description
        "Number of bytes transmitted within this period.";
    }
    leaf timestamp-second {
      type uint32;
      description
        "Integer part of the number of seconds starting at 00:00:00 UTC on January 1, 1970.";
    }
    leaf timestamp-nanosecond {
      type uint32;
      description
        "Decimal part of the number of seconds starting at 00:00:00 UTC on January 1, 1970.";
    }
    description
      "The result data of IFIT statistics.";
  }

  grouping live_ncs_statistics-data {
    leaf period-id {
      type uint64;
      description
        "Index of the statistics collection period of IFIT flows.";
    }
    leaf packet-count {
      type uint64;
      description
        "Number of packets transmitted within this period.";
    }
    leaf byte-count {
      type uint64;
      description
        "Number of bytes transmitted within this period.";
    }
    leaf timestamp-second {
      type uint32;
      description
        "Integer part of the number of seconds starting at 00:00:00 UTC on January 1, 1970.";
    }
    leaf timestamp-nanosecond {
      type uint32;
      description
        "Decimal part of the number of seconds starting at 00:00:00 UTC on January 1, 1970.";
    }
    description
      "The result data of IFIT statistics.";
  }

  grouping statistics-data {
    leaf period-id {
      type uint64;
      description
        "Index of the statistics collection period of IFIT flows.";
    }
    leaf packet-count {
      type uint64;
      description
        "Number of packets transmitted within this period.";
    }
    leaf byte-count {
      type uint64;
      description
        "Number of bytes transmitted within this period.";
    }
    leaf timestamp-second {
      type uint32;
      description
        "Integer part of the number of seconds starting at 00:00:00 UTC on January 1, 1970.";
    }
    leaf timestamp-nanosecond {
      type uint32;
      description
        "Decimal part of the number of seconds starting at 00:00:00 UTC on January 1, 1970.";
    }
    description
      "The result data of IFIT statistics.";
  }

  augment "/ncs:devices/ncs:template/ncs:ned-id/ncs:config/ifit:ifit" {
    description
      "IFIT augment.";
    // NCS drop config false container 'flow-statistics'
    // NCS drop config false container 'flow-peer-ip-statistics'
    // NCS drop config false container 'flow-locator-statistics'
    // NCS drop config false container 'flow-hop-statistics'
    // NCS drop config false container 'flow-vpws-statistics'
  }
  augment "/ncs:devices/ncs:device/ncs:live-status/ifit:ifit" {
    description
      "IFIT augment.";
    container flow-statistics {
      tailf:ncs-device-type "netconf";
      tailf:display-when "not(../../../ncs:module) or ../../../ncs:module[ncs:name='huawei-ifit-statistics'] or (../../../ncs:live-status-protocol[not(ncs:capability)]) or (../../../ncs:live-status-protocol/ncs:capability/ncs:module[.='huawei-ifit-statistics'])";
      description
        "List of IFIT flow statistics.";
      list flow-statistic {
        key "flow-id direction";
        unique "address-family source-ip destination-ip source-mask destination-mask source-port destination-port protocol vpn-name if-index";
        description
          "Statistics of IFIT flow.";
        leaf flow-id {
          type uint64;
          description
            "The index of an IFIT flow.";
        }
        leaf direction {
          type live_ncs_flow-direction;
          description
            "Direction of an IFIT flow.";
        }
        leaf address-family {
          type live_ncs_address-family;
          description
            "The IP address family.";
        }
        leaf source-ip {
          type inet:ip-address-no-zone;
          description
            "Source IP address.";
        }
        leaf destination-ip {
          type inet:ip-address-no-zone;
          description
            "Destination IP address.";
        }
        leaf source-mask {
          type uint8;
          description
            "Mask of a source IP address.";
        }
        leaf destination-mask {
          type uint8;
          description
            "Mask of a destination IP address.";
        }
        leaf source-port {
          type uint16;
          description
            "Source port number.";
        }
        leaf destination-port {
          type uint16;
          description
            "Destination port number.";
        }
        leaf protocol {
          type uint8;
          description
            "Protocol number.";
        }
        leaf vpn-name {
          type pub-type:live_ncs_vrf-name;
          description
            "Name of VPN.";
        }
        leaf if-index {
          type uint32;
          description
            "Interface ID.";
        }
        leaf error-info {
          type uint8;
          description
            "Information of error.";
        }
        leaf interval {
          type uint16;
          units "s";
          description
            "Interval of an IFIT flow.";
        }
        leaf period-id {
          type uint64;
          description
            "Index of the statistics collection period of IFIT flows.";
        }
        leaf packet-count {
          type uint64;
          description
            "Number of packets transmitted within this period.";
        }
        leaf byte-count {
          type uint64;
          description
            "Number of bytes transmitted within this period.";
        }
        leaf timestamp-second {
          type uint32;
          description
            "Integer part of the number of seconds starting at 00:00:00 UTC on January 1, 1970.";
        }
        leaf timestamp-nanosecond {
          type uint32;
          description
            "Decimal part of the number of seconds starting at 00:00:00 UTC on January 1, 1970.";
        }
        leaf ttl {
          type uint8 {
            range "0..255";
          }
          description
            "The forwarding hops of an IFIT flow.";
        }
        leaf tunnel-if-index {
          type string {
            length "1..144";
          }
          description
            "The tunnel interface index of ECMP tunnel group.";
        }
        leaf dscp {
          type uint8;
          description
            "DSCP value.";
        }
        leaf cfg-id {
          type uint16;
          description
            "The CFG ID of LAG.";
        }
        leaf measure-mode {
          type uint8;
          description
            "The IFIT measure mode.";
        }
        leaf gtp-mode {
          type live_ncs_ifit-gtp-mode;
          description
            "The IFIT gtp measure mode.";
        }
        leaf gtp-te-id {
          type uint32;
          description
            "GTP te-id value.";
        }
        leaf disorder-count {
          type uint64;
          description
            "Number of disorder packets within all periods.";
        }
        leaf sn-packet-loss-count {
          type uint64;
          description
            "Number of loss packets calculated by sn within all periods.";
        }
      }
    }
    container flow-peer-ip-statistics {
      tailf:ncs-device-type "netconf";
      tailf:display-when "not(../../../ncs:module) or ../../../ncs:module[ncs:name='huawei-ifit-statistics'] or (../../../ncs:live-status-protocol[not(ncs:capability)]) or (../../../ncs:live-status-protocol/ncs:capability/ncs:module[.='huawei-ifit-statistics'])";
      description
        "List of IFIT flow peer IP statistics.";
      list flow-peer-ip-statistic {
        key "flow-id direction";
        description
          "Statistics of IFIT flow peer IP.";
        leaf flow-id {
          type uint64;
          description
            "The index of an IFIT flow.";
        }
        leaf direction {
          type live_ncs_flow-direction;
          description
            "Direction of an IFIT flow.";
        }
        leaf peer-ip {
          type inet:ip-address-no-zone;
          description
            "Peer IP address bound to a VPN instance.";
        }
        leaf vpn-type {
          type live_ncs_vpn-type;
          description
            "Type of VPN.";
        }
        leaf vpn-name {
          type pub-type:live_ncs_vrf-name;
          description
            "Name of VPN.";
        }
        leaf evpl-id {
          type uint32 {
            range "1..16777215";
          }
          description
            "The identification of the EVPL instance.";
        }
        leaf evpn-name {
          type string {
            length "1..31";
          }
          description
            "Name of EVPN.";
        }
        leaf error-info {
          type uint8;
          description
            "Information of error.";
        }
        leaf interval {
          type uint16;
          units "s";
          description
            "Interval of an IFIT flow.";
        }
        leaf if-index {
          type uint32;
          description
            "Interface ID.";
        }
        uses live_ncs_statistics-data;
        leaf ttl {
          type uint8 {
            range "0..255";
          }
          description
            "The forwarding hops of an IFIT flow.";
        }
      }
    }
    container flow-locator-statistics {
      tailf:ncs-device-type "netconf";
      tailf:display-when "not(../../../ncs:module) or ../../../ncs:module[ncs:name='huawei-ifit-statistics'] or (../../../ncs:live-status-protocol[not(ncs:capability)]) or (../../../ncs:live-status-protocol/ncs:capability/ncs:module[.='huawei-ifit-statistics'])";
      description
        "List of IFIT flow locator statistics.";
      list flow-locator-statistic {
        key "flow-id direction";
        description
          "Statistics of IFIT flow locator.";
        leaf flow-id {
          type uint64;
          description
            "The index of an IFIT flow.";
        }
        leaf direction {
          type live_ncs_flow-direction;
          description
            "Direction of an IFIT flow.";
        }
        leaf locator-prefix {
          type inet:ip-address-no-zone;
          description
            "The locator prefix.";
        }
        leaf prefix-length {
          type uint8;
          description
            "Length of prefix.";
        }
        leaf vpn-type {
          type live_ncs_vpn-type;
          description
            "Type of VPN.";
        }
        leaf vpn-name {
          type pub-type:live_ncs_vrf-name;
          description
            "Name of VPN.";
        }
        leaf evpl-id {
          type uint32 {
            range "1..16777215";
          }
          description
            "The identification of the EVPL instance.";
        }
        leaf evpn-name {
          type string {
            length "1..31";
          }
          description
            "Name of EVPN.";
        }
        leaf error-info {
          type uint8;
          description
            "Information of error.";
        }
        leaf interval {
          type uint16;
          units "s";
          description
            "Interval of an IFIT flow.";
        }
        leaf if-index {
          type uint32;
          description
            "Interface ID.";
        }
        uses live_ncs_statistics-data;
        leaf ttl {
          type uint8 {
            range "0..255";
          }
          description
            "The forwarding hops of an IFIT flow.";
        }
      }
    }
    container flow-hop-statistics {
      tailf:ncs-device-type "netconf";
      tailf:display-when "not(../../../ncs:module) or ../../../ncs:module[ncs:name='huawei-ifit-statistics'] or (../../../ncs:live-status-protocol[not(ncs:capability)]) or (../../../ncs:live-status-protocol/ncs:capability/ncs:module[.='huawei-ifit-statistics'])";
      description
        "List of IFIT flow hop statistics.";
      list flow-hop-statistic {
        key "flow-id direction";
        description
          "Statistics of IFIT flow hop.";
        leaf flow-id {
          type uint64;
          description
            "The index of an IFIT flow.";
        }
        leaf direction {
          type live_ncs_flow-direction;
          description
            "Direction of an IFIT flow.";
        }
        leaf if-index {
          type uint32;
          description
            "Interface ID.";
        }
        leaf error-info {
          type uint8;
          description
            "Information of error.";
        }
        leaf period-id {
          type uint64;
          description
            "Index of the statistics collection period of IFIT flows.";
        }
        leaf packet-count {
          type uint64;
          description
            "Number of packets transmitted within this period.";
        }
        leaf byte-count {
          type uint64;
          description
            "Number of bytes transmitted within this period.";
        }
        leaf timestamp-second {
          type uint32;
          description
            "Integer part of the number of seconds starting at 00:00:00 UTC on January 1, 1970.";
        }
        leaf timestamp-nanosecond {
          type uint32;
          description
            "Decimal part of the number of seconds starting at 00:00:00 UTC on January 1, 1970.";
        }
        leaf ttl {
          type uint8 {
            range "0..255";
          }
          description
            "The forwarding hops of an IFIT flow.";
        }
        leaf tunnel-if-index {
          type string {
            length "1..144";
          }
          description
            "The tunnel interface index of ECMP tunnel group.";
        }
        leaf cfg-id {
          type uint16;
          description
            "The CFG ID of LAG.";
        }
        leaf measure-mode {
          type uint8;
          description
            "The IFIT measure mode.";
        }
        leaf maximum-delay {
          type uint64;
          units "us";
          description
            "Maximum delay.";
        }
        leaf minimum-delay {
          type uint64;
          units "us";
          description
            "Minimum delay.";
        }
        leaf total-delay {
          type uint64;
          units "us";
          description
            "Total delay.";
        }
        leaf total-count {
          type uint64;
          description
            "The total count of packets.";
        }
        leaf disorder-count {
          type uint64;
          description
            "Number of disorder packets within all periods.";
        }
        leaf sn-packet-loss-count {
          type uint64;
          description
            "Number of loss packets calculated by sn within all periods.";
        }
      }
    }
    container flow-vpws-statistics {
      tailf:ncs-device-type "netconf";
      tailf:display-when "not(../../../ncs:module) or ../../../ncs:module[ncs:name='huawei-ifit-statistics'] or (../../../ncs:live-status-protocol[not(ncs:capability)]) or (../../../ncs:live-status-protocol/ncs:capability/ncs:module[.='huawei-ifit-statistics'])";
      description
        "List of IFIT vpws flow statistics.";
      list flow-vpws-statistic {
        key "flow-id direction";
        unique "if-index";
        description
          "Statistics of IFIT vpws flow.";
        leaf flow-id {
          type uint64;
          description
            "The index of an IFIT flow.";
        }
        leaf direction {
          type live_ncs_flow-direction;
          description
            "Direction of an IFIT flow.";
        }
        leaf if-index {
          type uint32;
          description
            "Interface ID.";
        }
        leaf error-info {
          type uint8;
          description
            "Information of error.";
        }
        leaf interval {
          type uint16;
          units "s";
          description
            "Interval of an IFIT flow.";
        }
        uses live_ncs_statistics-data;
        leaf tunnel-if-index {
          type string {
            length "1..144";
          }
          description
            "The tunnel interface index of ECMP tunnel group.";
        }
        leaf vpws-instance-id {
          type uint32;
          description
            "The instance id of virtual private wire service.";
        }
        leaf cfg-id {
          type uint16;
          description
            "The CFG ID of LAG.";
        }
        leaf measure-mode {
          type uint8;
          description
            "The IFIT measure mode.";
        }
      }
    }
  }
  augment "/ncs:devices/ncs:device/ncs:config/ifit:ifit" {
    description
      "IFIT augment.";
    // NCS drop config false container 'flow-statistics'
    // NCS drop config false container 'flow-peer-ip-statistics'
    // NCS drop config false container 'flow-locator-statistics'
    // NCS drop config false container 'flow-hop-statistics'
    // NCS drop config false container 'flow-vpws-statistics'
  }
}
