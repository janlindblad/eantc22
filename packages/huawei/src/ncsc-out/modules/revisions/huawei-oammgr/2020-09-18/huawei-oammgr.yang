module huawei-oammgr {
  // Generated by yanger -t ncs
  tailf:mount-id "huawei-nc-1.0:huawei-nc-1.0";
  tailf:ncs-device-type "netconf";

  namespace "urn:huawei:yang:huawei-oammgr";
  prefix oammgr;

  import huawei-extension {
    prefix ext;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Configure the operation, administration and maintenance (OAM) association function.";

  revision 2020-09-18 {
    description
      "Initial revision.";
    reference "Huawei private.";
  }
  ext:task-name "oammgr";

  augment "/ncs:devices/ncs:device/ncs:config" {
    container oammgr {
      tailf:ncs-device-type "netconf";
      tailf:display-when "not(../../ncs:module) or ../../ncs:module[ncs:name='huawei-oammgr']";
      presence "Enable OAMMGR";
      description
        "Configure the operation, administration and maintenance (OAM) association function.";
    }
  }
  augment "/ncs:devices/ncs:device/ncs:live-status" {
    container oammgr {
      tailf:ncs-device-type "netconf";
      tailf:display-when "not(../../ncs:module) or ../../ncs:module[ncs:name='huawei-oammgr'] or (../../ncs:live-status-protocol[not(ncs:capability)]) or (../../ncs:live-status-protocol/ncs:capability/ncs:module[.='huawei-oammgr'])";
      presence "Enable OAMMGR";
      description
        "Configure the operation, administration and maintenance (OAM) association function.";
    }
  }
  augment "/ncs:devices/ncs:template/ncs:ned-id/ncs:config" {
    container oammgr {
      presence "Enable OAMMGR";
      description
        "Configure the operation, administration and maintenance (OAM) association function.";
    }
  }
}
