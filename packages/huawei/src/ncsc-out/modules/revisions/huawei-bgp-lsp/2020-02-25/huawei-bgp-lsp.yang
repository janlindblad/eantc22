module huawei-bgp-lsp {
  // Generated by yanger -t ncs
  tailf:mount-id "huawei-nc-1.0:huawei-nc-1.0";
  tailf:ncs-device-type "netconf";

  yang-version 1;
  namespace "urn:huawei:yang:huawei-bgp-lsp";
  prefix bgp-lsp;

  import huawei-extension {
    prefix ext;
  }
  import ietf-inet-types {
    prefix inet;
  }
  import huawei-network-instance {
    prefix ni;
  }
  import huawei-mpls {
    prefix mpls;
  }
  import huawei-bfd {
    prefix bfd;
  }
  import huawei-routing-policy {
    prefix rtp;
  }
  import huawei-ifm {
    prefix ifm;
  }
  import huawei-bgp {
    prefix bgp;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Inter-AS routing protocol that exchanges Network Layer Reachability Information (NLRI) with other BGP systems.";

  revision 2020-02-25 {
    description
      "The YANG descriptions are modified according to new standards.";
    reference "Huawei private.";
  }
  revision 2019-03-22 {
    description
      "Initial revision.";
    reference "Huawei private.";
  }
  ext:task-name "bgp";

  typedef ncs_template_lsp-type {
    type string;
    description
      "The type of the BGP LSP.";
  }

  typedef ncs_template_lsp-frr-type {
    type string;
    description
      "The type of the bgpLspFrr.";
  }

  typedef ncs_template_label-operation-type {
    type string;
    description
      "The type of the bgpLabelOperation.";
  }

  typedef ncs_template_exp-mode-type {
    type string;
    description
      "The type of bgpcommExpMode.";
  }

  typedef ncs_template_bgp-bfd-trigger-type {
    type string;
    description
      "The type of BGP BFD trigger.";
  }

  typedef ncs_rpc_notif_lsp-type {
    type enumeration {
      enum "ingress" {
        value 1;
        description
          "Ingress of the BGP LSP.";
      }
      enum "transit" {
        value 2;
        description
          "Transit node of the BGP LSP.";
      }
      enum "egress" {
        value 4;
        description
          "Egress of the BGP LSP.";
      }
    }
    description
      "The type of the BGP LSP.";
  }

  typedef ncs_rpc_notif_lsp-frr-type {
    type enumeration {
      enum "primary" {
        value 1;
        description
          "Primary LSP type.";
      }
      enum "backup" {
        value 2;
        description
          "Backup LSP type.";
      }
    }
    description
      "The type of the bgpLspFrr.";
  }

  typedef ncs_rpc_notif_label-operation-type {
    type enumeration {
      enum "push" {
        value 0;
        description
          "Push a label.";
      }
      enum "swap" {
        value 1;
        description
          "Swap a Label.";
      }
      enum "pop" {
        value 2;
        description
          "Pop out a label.";
      }
      enum "swappush" {
        value 3;
        description
          "Swap a label and push a label.";
      }
      enum "popgo" {
        value 4;
        description
          "Packets are forwarded based on the next hop directly mapped to the
           label after label popping.";
      }
    }
    description
      "The type of the bgpLabelOperation.";
  }

  typedef ncs_rpc_notif_exp-mode-type {
    type enumeration {
      enum "null" {
        value 0;
        description
          "Default value.";
      }
      enum "pipe" {
        value 1;
        description
          "The priority of BGP labels is not modified, and the outer label is removed.";
      }
      enum "uniform" {
        value 2;
        description
          "The label priority of intra-AS tunnels is copied to the BGP label.";
      }
    }
    description
      "The type of bgpcommExpMode.";
  }

  typedef ncs_rpc_notif_bgp-bfd-trigger-type {
    type enumeration {
      enum "none" {
        value 0;
        description
          "No policy for establishing BGP BFD sessions is configured.";
      }
      enum "host" {
        value 1;
        description
          "Use host addresses to dynamically establish BGP BFD sessions.";
      }
      enum "ip-prefix" {
        value 2;
        description
          "IP prefix list used to dynamically establish a BFD session to monitor an LDP tunnel.";
      }
    }
    description
      "The type of BGP BFD trigger.";
  }

  typedef live_ncs_lsp-type {
    type enumeration {
      enum "ingress" {
        value 1;
        description
          "Ingress of the BGP LSP.";
      }
      enum "transit" {
        value 2;
        description
          "Transit node of the BGP LSP.";
      }
      enum "egress" {
        value 4;
        description
          "Egress of the BGP LSP.";
      }
    }
    description
      "The type of the BGP LSP.";
  }

  typedef live_ncs_lsp-frr-type {
    type enumeration {
      enum "primary" {
        value 1;
        description
          "Primary LSP type.";
      }
      enum "backup" {
        value 2;
        description
          "Backup LSP type.";
      }
    }
    description
      "The type of the bgpLspFrr.";
  }

  typedef live_ncs_label-operation-type {
    type enumeration {
      enum "push" {
        value 0;
        description
          "Push a label.";
      }
      enum "swap" {
        value 1;
        description
          "Swap a Label.";
      }
      enum "pop" {
        value 2;
        description
          "Pop out a label.";
      }
      enum "swappush" {
        value 3;
        description
          "Swap a label and push a label.";
      }
      enum "popgo" {
        value 4;
        description
          "Packets are forwarded based on the next hop directly mapped to the
           label after label popping.";
      }
    }
    description
      "The type of the bgpLabelOperation.";
  }

  typedef live_ncs_exp-mode-type {
    type enumeration {
      enum "null" {
        value 0;
        description
          "Default value.";
      }
      enum "pipe" {
        value 1;
        description
          "The priority of BGP labels is not modified, and the outer label is removed.";
      }
      enum "uniform" {
        value 2;
        description
          "The label priority of intra-AS tunnels is copied to the BGP label.";
      }
    }
    description
      "The type of bgpcommExpMode.";
  }

  typedef live_ncs_bgp-bfd-trigger-type {
    type enumeration {
      enum "none" {
        value 0;
        description
          "No policy for establishing BGP BFD sessions is configured.";
      }
      enum "host" {
        value 1;
        description
          "Use host addresses to dynamically establish BGP BFD sessions.";
      }
      enum "ip-prefix" {
        value 2;
        description
          "IP prefix list used to dynamically establish a BFD session to monitor an LDP tunnel.";
      }
    }
    description
      "The type of BGP BFD trigger.";
  }

  typedef lsp-type {
    type enumeration {
      enum "ingress" {
        value 1;
        description
          "Ingress of the BGP LSP.";
      }
      enum "transit" {
        value 2;
        description
          "Transit node of the BGP LSP.";
      }
      enum "egress" {
        value 4;
        description
          "Egress of the BGP LSP.";
      }
    }
    description
      "The type of the BGP LSP.";
  }

  typedef lsp-frr-type {
    type enumeration {
      enum "primary" {
        value 1;
        description
          "Primary LSP type.";
      }
      enum "backup" {
        value 2;
        description
          "Backup LSP type.";
      }
    }
    description
      "The type of the bgpLspFrr.";
  }

  typedef label-operation-type {
    type enumeration {
      enum "push" {
        value 0;
        description
          "Push a label.";
      }
      enum "swap" {
        value 1;
        description
          "Swap a Label.";
      }
      enum "pop" {
        value 2;
        description
          "Pop out a label.";
      }
      enum "swappush" {
        value 3;
        description
          "Swap a label and push a label.";
      }
      enum "popgo" {
        value 4;
        description
          "Packets are forwarded based on the next hop directly mapped to the
           label after label popping.";
      }
    }
    description
      "The type of the bgpLabelOperation.";
  }

  typedef exp-mode-type {
    type enumeration {
      enum "null" {
        value 0;
        description
          "Default value.";
      }
      enum "pipe" {
        value 1;
        description
          "The priority of BGP labels is not modified, and the outer label is removed.";
      }
      enum "uniform" {
        value 2;
        description
          "The label priority of intra-AS tunnels is copied to the BGP label.";
      }
    }
    description
      "The type of bgpcommExpMode.";
  }

  typedef bgp-bfd-trigger-type {
    type enumeration {
      enum "none" {
        value 0;
        description
          "No policy for establishing BGP BFD sessions is configured.";
      }
      enum "host" {
        value 1;
        description
          "Use host addresses to dynamically establish BGP BFD sessions.";
      }
      enum "ip-prefix" {
        value 2;
        description
          "IP prefix list used to dynamically establish a BFD session to monitor an LDP tunnel.";
      }
    }
    description
      "The type of BGP BFD trigger.";
  }

  grouping ncs_template_bgp-pipe-type {
    description
      "BGP pipe type.";
    leaf ttl-mode {
      type string;
      // NCS drop default statement
      description
        "Specifies the TTL mode, The available options are Uniform and Pipe. By default, the mode is Pipe.";
    }
  }

  grouping ncs_rpc_notif_bgp-pipe-type {
    description
      "BGP pipe type.";
    leaf ttl-mode {
      type enumeration {
        enum "pipe" {
          value 2;
          description
            "The priority of BGP labels is not modified, and the outer label is removed.";
        }
        enum "uniform" {
          value 1;
          description
            "The label priority of intra-AS tunnels is copied to the BGP label.";
        }
      }
      default "pipe";
      description
        "Specifies the TTL mode, The available options are Uniform and Pipe. By default, the mode is Pipe.";
    }
  }

  grouping live_ncs_bgp-pipe-type {
    description
      "BGP pipe type.";
    leaf ttl-mode {
      type enumeration {
        enum "pipe" {
          value 2;
          description
            "The priority of BGP labels is not modified, and the outer label is removed.";
        }
        enum "uniform" {
          value 1;
          description
            "The label priority of intra-AS tunnels is copied to the BGP label.";
        }
      }
      // NCS drop default statement
      description
        "Specifies the TTL mode, The available options are Uniform and Pipe. By default, the mode is Pipe.";
    }
  }

  grouping bgp-pipe-type {
    description
      "BGP pipe type.";
    leaf ttl-mode {
      type enumeration {
        enum "pipe" {
          value 2;
          description
            "The priority of BGP labels is not modified, and the outer label is removed.";
        }
        enum "uniform" {
          value 1;
          description
            "The label priority of intra-AS tunnels is copied to the BGP label.";
        }
      }
      default "pipe";
      description
        "Specifies the TTL mode, The available options are Uniform and Pipe. By default, the mode is Pipe.";
    }
  }

  augment "/ncs:devices/ncs:device/ncs:config" {
    container bgp-lsp {
      tailf:ncs-device-type "netconf";
      tailf:display-when "not(../../ncs:module) or ../../ncs:module[ncs:name='huawei-bgp-lsp']";
      description
        "BGP LSP configuration and query items.";
      container bfd {
        description
          "Configure dynamic BFD for BGP LSP.";
        container parameters {
          description
            "Configure parameters of BFD for BGP LSP.";
          leaf enable {
            when "/mpls:mpls/mpls:common/mpls:global/mpls:mpls-enable='true' and /bfd:bfd" {
              tailf:xpath-root 3;
            }
            type boolean;
            default "false";
            description
              "Enable/disable dynamic BFD for BGP LSP.";
          }
          leaf min-tx-interval {
            when "/mpls:mpls/mpls:common/mpls:global/mpls:mpls-enable='true'" {
              tailf:xpath-root 3;
            }
            type uint32 {
              range "3..20000";
            }
            units "ms";
            description
              "Interval at which BFD packets are sent.";
          }
          leaf min-rx-interval {
            when "/mpls:mpls/mpls:common/mpls:global/mpls:mpls-enable='true'" {
              tailf:xpath-root 3;
            }
            type uint32 {
              range "3..20000";
            }
            units "ms";
            description
              "Interval at which BFD packets are received.";
          }
          leaf detection-multiplier {
            when "/mpls:mpls/mpls:common/mpls:global/mpls:mpls-enable='true'" {
              tailf:xpath-root 3;
            }
            type uint32 {
              range "3..50";
            }
            default "3";
            description
              "BFD detection multiplier.";
          }
          leaf trigger {
            when "/mpls:mpls/mpls:common/mpls:global/mpls:mpls-enable='true' and /bfd:bfd" {
              tailf:xpath-root 3;
            }
            type bgp-bfd-trigger-type;
            must "( ../trigger='ip-prefix' and ../trigger-ip-prefix-name ) or not ( ../trigger='ip-prefix' or ../trigger-ip-prefix-name )" {
              tailf:xpath-root 3;
            }
            default "none";
            description
              "Configure a policy for creating BGP LSP BFD sessions.";
          }
          leaf trigger-ip-prefix-name {
            when "../trigger='ip-prefix'" {
              tailf:xpath-root 3;
            }
            type leafref {
              path "/ncs:devices/ncs:device/ncs:config/rtp:routing-policy/rtp:ipv4-prefix-filters/rtp:ipv4-prefix-filter/rtp:name" {
                tailf:xpath-root 3;
              }
            }
            description
              "To use an IP prefix list to dynamically create BFD sessions, specify a name of the IP prefix list.";
          }
        }
        // NCS drop config false container sessions
      }
      // NCS drop config false container states
    }
  }
  augment "/ncs:devices/ncs:device/ncs:live-status" {
    container bgp-lsp {
      tailf:ncs-device-type "netconf";
      tailf:display-when "not(../../ncs:module) or ../../ncs:module[ncs:name='huawei-bgp-lsp'] or (../../ncs:live-status-protocol[not(ncs:capability)]) or (../../ncs:live-status-protocol/ncs:capability/ncs:module[.='huawei-bgp-lsp'])";
      description
        "BGP LSP configuration and query items.";
      container bfd {
        description
          "Configure dynamic BFD for BGP LSP.";
        container parameters {
          description
            "Configure parameters of BFD for BGP LSP.";
          leaf enable {
            // NCS drop when statement
            type boolean;
            // NCS drop default statement
            description
              "Enable/disable dynamic BFD for BGP LSP.";
          }
          leaf min-tx-interval {
            // NCS drop when statement
            type uint32 {
              range "3..20000";
            }
            units "ms";
            description
              "Interval at which BFD packets are sent.";
          }
          leaf min-rx-interval {
            // NCS drop when statement
            type uint32 {
              range "3..20000";
            }
            units "ms";
            description
              "Interval at which BFD packets are received.";
          }
          leaf detection-multiplier {
            // NCS drop when statement
            type uint32 {
              range "3..50";
            }
            // NCS drop default statement
            description
              "BFD detection multiplier.";
          }
          leaf trigger {
            // NCS drop when statement
            type live_ncs_bgp-bfd-trigger-type;
            // NCS drop must statement
            // NCS drop default statement
            description
              "Configure a policy for creating BGP LSP BFD sessions.";
          }
          leaf trigger-ip-prefix-name {
            // NCS drop when statement
            type leafref {
              path "/ncs:devices/ncs:device/ncs:live-status/rtp:routing-policy/rtp:ipv4-prefix-filters/rtp:ipv4-prefix-filter/rtp:name" {
                tailf:xpath-root 3;
              }
            }
            description
              "To use an IP prefix list to dynamically create BFD sessions, specify a name of the IP prefix list.";
          }
        }
        container sessions {
          description
            "List of the sessions of dynamic BFD for BGP LSP.";
          list session {
            key "fec-address out-if-name next-hop index";
            description
              "Statistics of a session of dynamic BFD for BGP LSP.";
            leaf fec-address {
              type inet:ipv4-address-no-zone;
              description
                "Display the FEC address of the session of dynamic BFD for BGP LSP.";
            }
            leaf out-if-name {
              type leafref {
                path "/ncs:devices/ncs:device/ncs:live-status/ifm:ifm/ifm:interfaces/ifm:interface/ifm:name" {
                  tailf:xpath-root 3;
                }
              }
              description
                "Display the outbound interface of a BGP LSP.";
            }
            leaf next-hop {
              type inet:ipv4-address-no-zone;
              description
                "Display the next hop of a BGP LSP.";
            }
            leaf index {
              type uint32;
              description
                "Display the LSP index of a BGP LSP.";
            }
            leaf discriminator {
              type uint32;
              description
                "Display the BFD discriminator of the BFD session of dynamic BFD for BGP LSP.";
            }
            leaf state {
              type enumeration {
                enum "admin-down" {
                  value 0;
                  description
                    "The BGP LSP BFD session is administratively Down.";
                }
                enum "down" {
                  value 1;
                  description
                    "The BGP LSP BFD session is Down.";
                }
                enum "init" {
                  value 2;
                  description
                    "The BGP LSP BFD session is in initial state.";
                }
                enum "up" {
                  value 3;
                  description
                    "The BGP LSP BFD session is Up.";
                }
              }
              description
                "Display the BFD session state of dynamic BFD for BGP LSP.";
            }
            leaf min-tx-interval {
              type uint32;
              units "ms";
              description
                "Display the minimum interval at which BFD packets of the session of dynamic BFD for BGP LSP are sent.";
            }
            leaf min-rx-interval {
              type uint32;
              units "ms";
              description
                "Display the minimum interval at which BFD packets of the session of dynamic BFD for BGP LSP are received.";
            }
            leaf detection-multiplier {
              type uint32;
              description
                "Display the BFD detection multiplier of the BFD session of dynamic BFD for BGP LSP.";
            }
            leaf age {
              type uint32;
              units "s";
              description
                "Display the BFD session age of dynamic BFD for BGP LSP.";
            }
          }
        }
      }
      container states {
        description
          "List of BGP LSPs.";
        list state {
          key "vrf-name af destination-address prefix-length index type indirect-id frr-type";
          description
            "Operational state of BGP LSP.";
          leaf vrf-name {
            type leafref {
              path "/ncs:devices/ncs:device/ncs:live-status/ni:network-instance/ni:instances/ni:instance/ni:name" {
                tailf:xpath-root 3;
              }
            }
            description
              "VPN name of a BGP instance.";
          }
          leaf af {
            type bgp:live_ncs_af-type;
            description
              "Specifies the address family type of a BGP instance.";
          }
          leaf destination-address {
            type inet:ip-address-no-zone;
            description
              "Destination address of an LSP.";
          }
          leaf prefix-length {
            type uint32 {
              range "0..128";
            }
            description
              "Prefix length of the destination address of an LSP.";
          }
          leaf index {
            type uint32;
            description
              "LSP index.";
          }
          leaf type {
            type live_ncs_lsp-type;
            description
              "LSP type.";
          }
          leaf indirect-id {
            type string {
              length "1..50";
            }
            description
              "IndirectID.";
          }
          leaf frr-type {
            type live_ncs_lsp-frr-type;
            description
              "FRR role.";
          }
          leaf nexthop {
            type inet:ip-address-no-zone;
            description
              "Next hop of an LSP.";
          }
          leaf inbound-if-name {
            type leafref {
              path "/ncs:devices/ncs:device/ncs:live-status/ifm:ifm/ifm:interfaces/ifm:interface/ifm:name" {
                tailf:xpath-root 3;
              }
            }
            description
              "Inbound interface of an LSP.";
          }
          leaf outbound-if-name {
            type leafref {
              path "/ncs:devices/ncs:device/ncs:live-status/ifm:ifm/ifm:interfaces/ifm:interface/ifm:name" {
                tailf:xpath-root 3;
              }
            }
            description
              "Outbound interface of an LSP.";
          }
          leaf mtu {
            type uint32 {
              range "0..65535";
            }
            description
              "LSP MTU.";
          }
          leaf duration {
            type uint32;
            units "s";
            description
              "LSP duration.";
          }
          leaf in-label {
            type uint32;
            description
              "In-label of an LSP.";
          }
          leaf out-label {
            type uint32;
            description
              "Out-label of an LSP.";
          }
          leaf out-tunnel-index {
            type string {
              length "1..50";
            }
            description
              "Index of an outbound LSP.";
          }
          leaf label-operation {
            type live_ncs_label-operation-type;
            description
              "Label operation type.";
          }
          leaf qos-priority-mode {
            type live_ncs_exp-mode-type;
            description
              "QoS priority mode of an LSP.";
          }
          leaf tunnel-id {
            type string {
              length "1..50";
            }
            description
              "ID of an outbound LSP.";
          }
          leaf route-distinguisher {
            type string {
              length "3..21";
            }
            description
              "A VPN address family takes effect only after it is configured with an RD. The format of an RD is as follows:
               1. 16-bit AS number:32-bit user-defined number, for example, 101:3. An AS number ranges from 0 to 65535, and a user-defined number ranges from 0 to 4294967295. The AS number and user-defined number cannot be both 0s. This means that the RD value cannot be 0:0.
               2. 32-bit IP address:16-bit user-defined number, for example: 192.168.122.15:1. The IP address ranges from 0.0.0.0 to 255.255.255.255, and the user-defined number ranges from 0 to 65535.
               3. 32-bit AS number:16-bit user-defined number, for example, 10.11:3. An AS number ranges from 0.0 to 65535.65535 or from 0 to 4294967295, and a user-defined number ranges from 0 to 65535. The AS number and user-defined number cannot be both 0s. This means that the RD value cannot be 0.0:0.";
          }
          container tunnels {
            description
              "List of tunnel information.";
            list tunnel {
              key "value";
              description
                "Operational state of tunnel information.";
              leaf value {
                type string {
                  length "1..50";
                }
                description
                  "The tunnel-key.";
              }
            }
          }
        }
      }
    }
  }
  augment "/ncs:devices/ncs:template/ncs:ned-id/ncs:config" {
    container bgp-lsp {
      description
        "BGP LSP configuration and query items.";
      container bfd {
        description
          "Configure dynamic BFD for BGP LSP.";
        container parameters {
          description
            "Configure parameters of BFD for BGP LSP.";
          leaf enable {
            // NCS drop when statement
            type string;
            // NCS drop default statement
            description
              "Enable/disable dynamic BFD for BGP LSP.";
          }
          leaf min-tx-interval {
            // NCS drop when statement
            type string;
            units "ms";
            description
              "Interval at which BFD packets are sent.";
          }
          leaf min-rx-interval {
            // NCS drop when statement
            type string;
            units "ms";
            description
              "Interval at which BFD packets are received.";
          }
          leaf detection-multiplier {
            // NCS drop when statement
            type string;
            // NCS drop default statement
            description
              "BFD detection multiplier.";
          }
          leaf trigger {
            // NCS drop when statement
            type ncs_template_bgp-bfd-trigger-type;
            // NCS drop must statement
            // NCS drop default statement
            description
              "Configure a policy for creating BGP LSP BFD sessions.";
          }
          leaf trigger-ip-prefix-name {
            // NCS drop when statement
            type string;
            description
              "To use an IP prefix list to dynamically create BFD sessions, specify a name of the IP prefix list.";
          }
        }
        // NCS drop config false container sessions
      }
      // NCS drop config false container states
    }
  }
  augment "/ncs:devices/ncs:template/ncs:ned-id/ncs:config/mpls:mpls/mpls:common/mpls:global" {
    description
      "MPLS BGP global configuration.";
    container bgp-ttl-mode {
      // NCS drop when statement
      description
        "Configure the TTL mode. The available options are uniform and pipe.";
      uses ncs_template_bgp-pipe-type;
    }
  }
  augment "/ncs:devices/ncs:device/ncs:live-status/mpls:mpls/mpls:common/mpls:global" {
    description
      "MPLS BGP global configuration.";
    container bgp-ttl-mode {
      tailf:ncs-device-type "netconf";
      tailf:display-when "not(../../../../../ncs:module) or ../../../../../ncs:module[ncs:name='huawei-bgp-lsp'] or (../../../../../ncs:live-status-protocol[not(ncs:capability)]) or (../../../../../ncs:live-status-protocol/ncs:capability/ncs:module[.='huawei-bgp-lsp'])";
      // NCS drop when statement
      description
        "Configure the TTL mode. The available options are uniform and pipe.";
      uses live_ncs_bgp-pipe-type;
    }
  }
  augment "/ncs:devices/ncs:device/ncs:config/mpls:mpls/mpls:common/mpls:global" {
    description
      "MPLS BGP global configuration.";
    container bgp-ttl-mode {
      tailf:ncs-device-type "netconf";
      tailf:display-when "not(../../../../../ncs:module) or ../../../../../ncs:module[ncs:name='huawei-bgp-lsp']";
      when "/mpls:mpls/mpls:common/mpls:global/mpls:mpls-enable='true'" {
        tailf:xpath-root 3;
      }
      description
        "Configure the TTL mode. The available options are uniform and pipe.";
      uses bgp-pipe-type;
    }
  }
}
