module huawei-bgp-evpn {
  // Generated by yanger -t ncs
  tailf:mount-id "huawei-nc-1.0:huawei-nc-1.0";
  tailf:ncs-device-type "netconf";

  namespace "urn:huawei:yang:huawei-bgp-evpn";
  prefix bgp-evpn;

  import huawei-network-instance {
    prefix ni;
  }
  import huawei-bgp {
    prefix bgp;
  }
  import huawei-routing-policy {
    prefix rtp;
  }
  import huawei-bgp-routing-table {
    prefix bgp-rt;
  }
  import huawei-nvo3 {
    prefix nvo3;
  }
  import huawei-extension {
    prefix ext;
  }
  import huawei-pub-type {
    prefix pub-type;
  }
  import ietf-inet-types {
    prefix inet;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Configure BGP EVPN.";

  revision 2020-04-07 {
    description
      "EVPN module YANG file.";
    reference "Huawei private.";
  }
  revision 2019-03-22 {
    description
      "Initial revision.";
    reference "Huawei private.";
  }
  ext:task-name "evpnbgp";

  typedef ncs_template_advertise-encap-type {
    type string;
    description
      "Encapsulation type of packets.";
  }

  typedef ncs_template_srv6-mode {
    type string;
    description
      "SRv6 mode is BE or TE.";
  }

  typedef ncs_template_add-path-cap-type {
    type string;
    description
      "The type of add-path routes.";
  }

  typedef ncs_template_config-type {
    type string;
    description
      "Route server client.";
  }

  typedef ncs_template_route-limit-type {
    type string;
    description
      "The type of route limit.";
  }

  typedef ncs_template_es-ad-compatible-type {
    type string;
    description
      "Ethernet A-D per ES Route compatible type.";
  }

  typedef ncs_template_peer-comm-config-type {
    type string;
    description
      "State of the configuration on peer.";
  }

  typedef ncs_template_evpn-next-hop-mode {
    type string;
    description
      "BGP EVPN peer and peer group next hop mode.";
  }

  typedef ncs_template_apply-label-type {
    type string;
    description
      "BGP EVPN apply label type.";
  }

  typedef ncs_template_path-attr-treat-type {
    type string;
    description
      "Processing mode of path attribute.";
  }

  typedef ncs_template_select-depend-type {
    type string;
    description
      "The type of nexthop select depend.";
  }

  typedef ncs_template_select-depend-type-ext {
    type string;
    description
      "The type of nexthop select depend.";
  }

  typedef ncs_rpc_notif_advertise-encap-type {
    type enumeration {
      enum "vxlan" {
        value 1;
        description
          "VXLAN.";
      }
      enum "mpls" {
        value 2;
        description
          "MPLS.";
      }
      enum "srv6" {
        value 4;
        description
          "SRv6.";
      }
      enum "sd-wan" {
        value 5;
        description
          "SD-WAN.";
      }
    }
    description
      "Encapsulation type of packets.";
  }

  typedef ncs_rpc_notif_srv6-mode {
    type enumeration {
      enum "be" {
        value 1;
        description
          "SRv6 iteration mode is BE.";
      }
      enum "te" {
        value 2;
        description
          "SRv6 iteration mode is TE.";
      }
    }
    description
      "SRv6 mode is BE or TE.";
  }

  typedef ncs_rpc_notif_add-path-cap-type {
    type enumeration {
      enum "receive" {
        value 1;
        description
          "Support receiving add-path routes.";
      }
      enum "send" {
        value 2;
        description
          "Support sending add-path routes.";
      }
      enum "both" {
        value 3;
        description
          "Support receiving and sending add-path routes.";
      }
    }
    description
      "The type of add-path routes.";
  }

  typedef ncs_rpc_notif_config-type {
    type enumeration {
      enum "default" {
        value 0;
        description
          "Disable or inheritance group.";
      }
      enum "enable" {
        value 1;
        description
          "Explicit config enable.";
      }
      enum "disable" {
        value 2;
        description
          "Explicit config disable.";
      }
    }
    description
      "Route server client.";
  }

  typedef ncs_rpc_notif_route-limit-type {
    type enumeration {
      enum "noparameter" {
        value 0;
        description
          "Default value.";
      }
      enum "alert-only" {
        value 1;
        description
          "An alarm is generated and no additional routes will be accepted if the maximum number of routes allowed have been received.";
      }
      enum "idle-forever" {
        value 2;
        description
          "The connection that is interrupted is not automatically re-established if the maximum number of routes allowed have been received.";
      }
      enum "idle-timeout" {
        value 3;
        description
          "After the number of received routes exceeds the threshold and the timeout timer expires, the connection that is interrupted is automatically re-established.";
      }
    }
    description
      "The type of route limit.";
  }

  typedef ncs_rpc_notif_es-ad-compatible-type {
    type enumeration {
      enum "default" {
        value 0;
        description
          "Default ES AD compatible.";
      }
      enum "enable" {
        value 1;
        description
          "Enable ES AD compatible.";
      }
      enum "disable" {
        value 2;
        description
          "Disable ES AD compatible.";
      }
    }
    description
      "Ethernet A-D per ES Route compatible type.";
  }

  typedef ncs_rpc_notif_peer-comm-config-type {
    type enumeration {
      enum "default" {
        value 0;
        description
          "Configuration on peer was default.";
      }
      enum "enable" {
        value 1;
        description
          "Configuration on peer was enable.";
      }
      enum "disable" {
        value 2;
        description
          "Configuration on peer was disable.";
      }
    }
    description
      "State of the configuration on peer.";
  }

  typedef ncs_rpc_notif_evpn-next-hop-mode {
    type enumeration {
      enum "null" {
        value 0;
        description
          "The next hop is not changed.";
      }
      enum "local" {
        value 1;
        description
          "The next hop is changed to the local IP address.";
      }
      enum "invariable" {
        value 2;
        description
          "Prevent the device from changing the next hop of each imported IGP route when advertising it to its EVPN peers.";
      }
    }
    description
      "BGP EVPN peer and peer group next hop mode.";
  }

  typedef ncs_rpc_notif_apply-label-type {
    type enumeration {
      enum "per-route" {
        value 0;
        description
          "Per-route label allocation.";
      }
      enum "per-nexthop" {
        value 1;
        description
          "Per-next-hop label allocation.";
      }
    }
    description
      "BGP EVPN apply label type.";
  }

  typedef ncs_rpc_notif_path-attr-treat-type {
    type enumeration {
      enum "normal" {
        value 0;
        description
          "Processing mode of normal path attribute.";
      }
    }
    description
      "Processing mode of path attribute.";
  }

  typedef ncs_rpc_notif_select-depend-type {
    type enumeration {
      enum "depend-tunnel" {
        value 1;
        description
          "Routing-dependent tunnel iteration.";
      }
      enum "depend-ip" {
        value 2;
        description
          "Routing-dependent IP iteration.";
      }
    }
    description
      "The type of nexthop select depend.";
  }

  typedef ncs_rpc_notif_select-depend-type-ext {
    type enumeration {
      enum "depend-tunnel" {
        value 1;
        description
          "Routing-dependent tunnel iteration.";
      }
      enum "depend-ip" {
        value 2;
        description
          "Routing-dependent IP iteration.";
      }
      enum "depend-none" {
        value 3;
        description
          "Routing-dependent ignore.";
      }
    }
    description
      "The type of nexthop select depend.";
  }

  typedef live_ncs_advertise-encap-type {
    type enumeration {
      enum "vxlan" {
        value 1;
        description
          "VXLAN.";
      }
      enum "mpls" {
        value 2;
        description
          "MPLS.";
      }
      enum "srv6" {
        value 4;
        description
          "SRv6.";
      }
      enum "sd-wan" {
        value 5;
        description
          "SD-WAN.";
      }
    }
    description
      "Encapsulation type of packets.";
  }

  typedef live_ncs_srv6-mode {
    type enumeration {
      enum "be" {
        value 1;
        description
          "SRv6 iteration mode is BE.";
      }
      enum "te" {
        value 2;
        description
          "SRv6 iteration mode is TE.";
      }
    }
    description
      "SRv6 mode is BE or TE.";
  }

  typedef live_ncs_add-path-cap-type {
    type enumeration {
      enum "receive" {
        value 1;
        description
          "Support receiving add-path routes.";
      }
      enum "send" {
        value 2;
        description
          "Support sending add-path routes.";
      }
      enum "both" {
        value 3;
        description
          "Support receiving and sending add-path routes.";
      }
    }
    description
      "The type of add-path routes.";
  }

  typedef live_ncs_config-type {
    type enumeration {
      enum "default" {
        value 0;
        description
          "Disable or inheritance group.";
      }
      enum "enable" {
        value 1;
        description
          "Explicit config enable.";
      }
      enum "disable" {
        value 2;
        description
          "Explicit config disable.";
      }
    }
    description
      "Route server client.";
  }

  typedef live_ncs_route-limit-type {
    type enumeration {
      enum "noparameter" {
        value 0;
        description
          "Default value.";
      }
      enum "alert-only" {
        value 1;
        description
          "An alarm is generated and no additional routes will be accepted if the maximum number of routes allowed have been received.";
      }
      enum "idle-forever" {
        value 2;
        description
          "The connection that is interrupted is not automatically re-established if the maximum number of routes allowed have been received.";
      }
      enum "idle-timeout" {
        value 3;
        description
          "After the number of received routes exceeds the threshold and the timeout timer expires, the connection that is interrupted is automatically re-established.";
      }
    }
    description
      "The type of route limit.";
  }

  typedef live_ncs_es-ad-compatible-type {
    type enumeration {
      enum "default" {
        value 0;
        description
          "Default ES AD compatible.";
      }
      enum "enable" {
        value 1;
        description
          "Enable ES AD compatible.";
      }
      enum "disable" {
        value 2;
        description
          "Disable ES AD compatible.";
      }
    }
    description
      "Ethernet A-D per ES Route compatible type.";
  }

  typedef live_ncs_peer-comm-config-type {
    type enumeration {
      enum "default" {
        value 0;
        description
          "Configuration on peer was default.";
      }
      enum "enable" {
        value 1;
        description
          "Configuration on peer was enable.";
      }
      enum "disable" {
        value 2;
        description
          "Configuration on peer was disable.";
      }
    }
    description
      "State of the configuration on peer.";
  }

  typedef live_ncs_evpn-next-hop-mode {
    type enumeration {
      enum "null" {
        value 0;
        description
          "The next hop is not changed.";
      }
      enum "local" {
        value 1;
        description
          "The next hop is changed to the local IP address.";
      }
      enum "invariable" {
        value 2;
        description
          "Prevent the device from changing the next hop of each imported IGP route when advertising it to its EVPN peers.";
      }
    }
    description
      "BGP EVPN peer and peer group next hop mode.";
  }

  typedef live_ncs_apply-label-type {
    type enumeration {
      enum "per-route" {
        value 0;
        description
          "Per-route label allocation.";
      }
      enum "per-nexthop" {
        value 1;
        description
          "Per-next-hop label allocation.";
      }
    }
    description
      "BGP EVPN apply label type.";
  }

  typedef live_ncs_path-attr-treat-type {
    type enumeration {
      enum "normal" {
        value 0;
        description
          "Processing mode of normal path attribute.";
      }
    }
    description
      "Processing mode of path attribute.";
  }

  typedef live_ncs_select-depend-type {
    type enumeration {
      enum "depend-tunnel" {
        value 1;
        description
          "Routing-dependent tunnel iteration.";
      }
      enum "depend-ip" {
        value 2;
        description
          "Routing-dependent IP iteration.";
      }
    }
    description
      "The type of nexthop select depend.";
  }

  typedef live_ncs_select-depend-type-ext {
    type enumeration {
      enum "depend-tunnel" {
        value 1;
        description
          "Routing-dependent tunnel iteration.";
      }
      enum "depend-ip" {
        value 2;
        description
          "Routing-dependent IP iteration.";
      }
      enum "depend-none" {
        value 3;
        description
          "Routing-dependent ignore.";
      }
    }
    description
      "The type of nexthop select depend.";
  }

  typedef advertise-encap-type {
    type enumeration {
      enum "vxlan" {
        value 1;
        description
          "VXLAN.";
      }
      enum "mpls" {
        value 2;
        description
          "MPLS.";
      }
      enum "srv6" {
        value 4;
        description
          "SRv6.";
      }
      enum "sd-wan" {
        value 5;
        description
          "SD-WAN.";
      }
    }
    description
      "Encapsulation type of packets.";
  }

  typedef srv6-mode {
    type enumeration {
      enum "be" {
        value 1;
        description
          "SRv6 iteration mode is BE.";
      }
      enum "te" {
        value 2;
        description
          "SRv6 iteration mode is TE.";
      }
    }
    description
      "SRv6 mode is BE or TE.";
  }

  typedef add-path-cap-type {
    type enumeration {
      enum "receive" {
        value 1;
        description
          "Support receiving add-path routes.";
      }
      enum "send" {
        value 2;
        description
          "Support sending add-path routes.";
      }
      enum "both" {
        value 3;
        description
          "Support receiving and sending add-path routes.";
      }
    }
    description
      "The type of add-path routes.";
  }

  typedef config-type {
    type enumeration {
      enum "default" {
        value 0;
        description
          "Disable or inheritance group.";
      }
      enum "enable" {
        value 1;
        description
          "Explicit config enable.";
      }
      enum "disable" {
        value 2;
        description
          "Explicit config disable.";
      }
    }
    description
      "Route server client.";
  }

  typedef route-limit-type {
    type enumeration {
      enum "noparameter" {
        value 0;
        description
          "Default value.";
      }
      enum "alert-only" {
        value 1;
        description
          "An alarm is generated and no additional routes will be accepted if the maximum number of routes allowed have been received.";
      }
      enum "idle-forever" {
        value 2;
        description
          "The connection that is interrupted is not automatically re-established if the maximum number of routes allowed have been received.";
      }
      enum "idle-timeout" {
        value 3;
        description
          "After the number of received routes exceeds the threshold and the timeout timer expires, the connection that is interrupted is automatically re-established.";
      }
    }
    description
      "The type of route limit.";
  }

  typedef es-ad-compatible-type {
    type enumeration {
      enum "default" {
        value 0;
        description
          "Default ES AD compatible.";
      }
      enum "enable" {
        value 1;
        description
          "Enable ES AD compatible.";
      }
      enum "disable" {
        value 2;
        description
          "Disable ES AD compatible.";
      }
    }
    description
      "Ethernet A-D per ES Route compatible type.";
  }

  typedef peer-comm-config-type {
    type enumeration {
      enum "default" {
        value 0;
        description
          "Configuration on peer was default.";
      }
      enum "enable" {
        value 1;
        description
          "Configuration on peer was enable.";
      }
      enum "disable" {
        value 2;
        description
          "Configuration on peer was disable.";
      }
    }
    description
      "State of the configuration on peer.";
  }

  typedef evpn-next-hop-mode {
    type enumeration {
      enum "null" {
        value 0;
        description
          "The next hop is not changed.";
      }
      enum "local" {
        value 1;
        description
          "The next hop is changed to the local IP address.";
      }
      enum "invariable" {
        value 2;
        description
          "Prevent the device from changing the next hop of each imported IGP route when advertising it to its EVPN peers.";
      }
    }
    description
      "BGP EVPN peer and peer group next hop mode.";
  }

  typedef apply-label-type {
    type enumeration {
      enum "per-route" {
        value 0;
        description
          "Per-route label allocation.";
      }
      enum "per-nexthop" {
        value 1;
        description
          "Per-next-hop label allocation.";
      }
    }
    description
      "BGP EVPN apply label type.";
  }

  typedef path-attr-treat-type {
    type enumeration {
      enum "normal" {
        value 0;
        description
          "Processing mode of normal path attribute.";
      }
    }
    description
      "Processing mode of path attribute.";
  }

  typedef select-depend-type {
    type enumeration {
      enum "depend-tunnel" {
        value 1;
        description
          "Routing-dependent tunnel iteration.";
      }
      enum "depend-ip" {
        value 2;
        description
          "Routing-dependent IP iteration.";
      }
    }
    description
      "The type of nexthop select depend.";
  }

  typedef select-depend-type-ext {
    type enumeration {
      enum "depend-tunnel" {
        value 1;
        description
          "Routing-dependent tunnel iteration.";
      }
      enum "depend-ip" {
        value 2;
        description
          "Routing-dependent IP iteration.";
      }
      enum "depend-none" {
        value 3;
        description
          "Routing-dependent ignore.";
      }
    }
    description
      "The type of nexthop select depend.";
  }

  augment "/ncs:devices/ncs:template/ncs:ned-id/ncs:config/ni:network-instance/ni:instances/ni:instance/bgp:bgp/bgp:base-process/bgp:peers/bgp:peer/bgp:afs/bgp:af" {
    description
      "Augment for an L2VPN instance and EVPN association.";
    container l2vpn-evpn {
      // NCS drop when statement
      // NCS drop must statement
      // NCS drop must statement
      // NCS drop must statement
      description
        "Configure peer EVPN.";
      leaf group-name {
        ext:operation-exclude "update";
        type string;
        // NCS drop must statement
        // NCS drop must statement
        // NCS drop must statement
        description
          "Configure a name for a peer group. By default, BGP peers join no peer group. BGP peers distinguish the peer group type when joining a peer group. IBGP peers cannot join an EBGP peer group. After a peer is deleted from the peer group, the peer is disabled from the address family. The object cannot be modified.";
      }
      leaf allow-as-loop {
        type string;
        description
          "Allow repetitive local AS numbers. By default, repetitive local AS numbers are not allowed.";
      }
      leaf reflect-client {
        // NCS drop when statement
        type string;
        // NCS drop default statement
        description
          "Enable/disable the local device as a route reflector (RR) and a peer or peer group as its client. This configuration is applicable between IBGP peers only. The configurations of RRs and its clients in an address family are valid only in this address family. Therefore, it is recommended to configure RRs and its clients in the specified address family that is required.";
      }
      choice import-policy-type {
        description
          "Set route policy or filter.";
        case rtp-ref {
          description
            "Route policy.";
          leaf import-policy {
            type string;
            description
              "Specify the filtering policy applied to the routes learned from a peer. By default, no such policy is specified.";
          }
        }
      }
      choice export-policy-type {
        description
          "Set route policy or filter.";
        case rtp-ref {
          description
            "Route policy.";
          leaf export-policy {
            type string;
            description
              "Specify the filtering policy applied to the routes to be advertised to a peer. By default, no such policy is specified.";
          }
        }
      }
      leaf advertise-community {
        type string;
        // NCS drop default statement
        description
          "Enable/disable advertise community attribute to a peer or peer group.";
      }
      leaf advertise-large-community {
        type ncs_template_config-type;
        // NCS drop default statement
        description
          "Enable large-community attribute advertisement. By default, the function is not configured on any peer. The Link-state address family and the RPD address family do not support this element.";
      }
      leaf advertise-arp {
        type string;
        // NCS drop default statement
        description
          "Enable/disable advertise ARP route.";
      }
      leaf advertise-irb {
        type string;
        // NCS drop default statement
        description
          "Enable/disable advertise IRB route.";
      }
      leaf advertise-irbv6 {
        type string;
        // NCS drop default statement
        description
          "Enable/disable advertise IRBv6 route.";
      }
      leaf advertise-nd {
        type string;
        // NCS drop default statement
        description
          "Enable/disable advertise ND route.";
      }
      leaf advertise-encap-type {
        type ncs_template_advertise-encap-type;
        // NCS drop default statement
        description
          "Encapsulation type of packets.";
      }
      leaf advertise-add-path-mode {
        type ncs_template_add-path-cap-type;
        description
          "Enable add-path route advertisement to a peer.";
      }
      leaf advertise-add-path-num {
        type string;
        description
          "Number of add-path routes that can be advertised to a peer.";
      }
      leaf advertise-suppressed-route {
        type string;
        // NCS drop default statement
        description
          "Enable/disable advertising suppressed-detail-route.";
      }
      // NCS drop config false leaf 'advertise-suppressed-route-status'
      leaf all-route-limit {
        type string;
        // NCS drop default statement
        description
          "Enable/disable all routing overflow alarm received from the specified peer.";
      }
      leaf mac-route-limit {
        type string;
        // NCS drop default statement
        description
          "Enable/disable MAC routing overflow alarm received from the specified peer.";
      }
      leaf route-limit {
        // NCS drop when statement
        type string;
        description
          "Configure the maximum number of routes that can be accepted from a peer.";
      }
      leaf route-limit-percent {
        // NCS drop when statement
        type string;
        // NCS drop default statement
        description
          "Specify the percentage of routes when a router starts to generate an alarm.";
      }
      leaf route-limit-type {
        // NCS drop when statement
        type ncs_template_route-limit-type;
        // NCS drop must statement
        // NCS drop default statement
        description
          "Set the processing method as alert-only, idle-forever, or idle-timeout when the number of routes exceeds the set threshold. When alert-only is used, only an alarm is generated when the number of routes exceeds the threshold. In this case, new routes are no longer accepted. When idle-forever is used, connections are not automatically reestablished after being cut off until BGP connections are reset if the number of routes exceeds the set threshold. When idle-timeout is used and the idle-timeout timer is specified, the connections are automatically reestablished after being cut off if the number of routes exceeds the set threshold. You can reset BGP connections to reestablish the connections before the idle-timeout times expires.";
      }
      leaf route-limit-idle-timeout {
        // NCS drop when statement
        type string;
        units "min";
        description
          "Enable/disable specify the value of the idle-timeout timer to automatically reestablish the connections after they are cut off when the number of routes exceeds the set threshold.";
      }
      leaf route-update-interval {
        type string;
        units "s";
        ext:dynamic-default {
          ext:default-value "15" {
            // NCS drop when statement
          }
          ext:default-value "30" {
            // NCS drop when statement
          }
        }
        description
          "Specify the minimum interval at which Update packets are sent. By default, the interval at which Update packets are sent to IBGP peers is 15s, and the interval at which Update packets are sent to EBGP peers is 30s.";
      }
      leaf reoriginate-route-enable {
        type string;
        // NCS drop default statement
        description
          "Enable/disable route regeneration.";
      }
      leaf reoriginate-vpnv4-route {
        type string;
        // NCS drop default statement
        description
          "Enable/disable VPNv4 route regeneration and advertisement.";
      }
      leaf reoriginate-mac-route {
        type string;
        // NCS drop default statement
        description
          "Enable/disable MAC route regeneration and advertisement.";
      }
      leaf reoriginate-mac-ip-route {
        type string;
        // NCS drop default statement
        description
          "Enable/disable MAC-IP route regeneration and advertisement.";
      }
      leaf reoriginate-mac-ipv6-route {
        type string;
        // NCS drop default statement
        description
          "Enable/disable reoriginating IRBv6 route of EVPN.";
      }
      leaf reoriginate-ip-route {
        type string;
        // NCS drop default statement
        description
          "Enable/disable IP route regeneration and advertisement.";
      }
      leaf reoriginate-ipv6-route {
        type string;
        // NCS drop default statement
        description
          "Enable/disable reoriginating IPv6 prefix route of EVPN.";
      }
      leaf reoriginate-vpnv6-route {
        type string;
        // NCS drop default statement
        description
          "Enable/disable reoriginating the route of VPNv6.";
      }
      leaf graceful-restart-static-timer {
        type string;
        units "s";
        description
          "Specifies the maximum time during which a peer waits for a BGP session reestablishment. In seconds.";
      }
      leaf es-ad-compatible {
        type ncs_template_es-ad-compatible-type;
        // NCS drop default statement
        description
          "Ethernet A-D per ES Route Compatible.";
      }
      leaf split-group-name {
        type string;
        description
          "Split group name.";
      }
      leaf vpn-orf-disable {
        type string;
        // NCS drop default statement
        description
          "Enable/disable VPN ORF.";
      }
      leaf upe-enable {
        type string;
        // NCS drop default statement
        description
          "Enable/disable the peer as an underlayer PE (UPE).";
      }
      leaf next-hop-mode {
        type ncs_template_evpn-next-hop-mode;
        // NCS drop default statement
        description
          "Enable next hop mode.";
      }
      leaf high-priority {
        type ncs_template_peer-comm-config-type;
        // NCS drop default statement
        description
          "Enable a higher priority to a specified peer.";
      }
      // NCS drop config false leaf 'high-priority-status'
      leaf preferred-value {
        type string;
        // NCS drop default statement
        description
          "Assign a preferred value for the routes learned from a specified peer. The value is an integer. After a preferred value is configured for the routes learned from a specified peer, all the routes that learnt from this peer will use this preferred value. When multiple routes reach the same address prefix, the route with the largest preferred value will be selected.";
      }
      leaf mac-detail-route-only {
        type bgp:ncs_template_peer-attr-enable-type;
        description
          "Enable/disable only advertising evpn detailed mac-route.";
      }
      // NCS drop config false leaf 'mac-detail-route-only-status'
      leaf advertise-srv6-locator {
        // NCS drop when statement
        type empty;
        description
          "Advertise SRv6 locator.";
      }
      // NCS drop config false container 'effect-state'
      container path-attribute-treats {
        description
          "List of modes in which specified path attributes are processed.";
        list path-attribute-treat {
          // NCS patched for predictable order
          ordered-by user;
          // NCS drop must statement
          key "treat-type";
          description
            "Configure mode in which specified path attributes are processed.";
          leaf treat-type {
            type ncs_template_path-attr-treat-type;
            description
              "Mode in which specified path attributes are processed.";
          }
          leaf discard-id-map {
            type pub-type:ncs_template_id-range;
            description
              "Specify a discard attribute ID list. The attribute ids which are not supported as follows: 1 (ORIGIN), 2 (AS_PATH), 3 (NEXT_HOP), 4 (MED), 5 (LOCAL_PREF), 6 (ATOMICAGGREGATE), 7 (AGGREGATOR), 8 (COMMUNITY), 9 (ORIGINATOR_ID), 10 (CLUSTER_LIST), 14 (MP_REACH_NLRI), 15 (MP_UNREACH_NLRI), 17 (AS4PATH), 18 (AS4AGGREGATOR).";
          }
          leaf withdraw-id-map {
            type pub-type:ncs_template_id-range;
            description
              "Specify a withdraw attribute ID list. The attribute ids which are not supported as follows: 1 (ORIGIN), 2 (AS_PATH), 3 (NEXT_HOP), 4 (MED), 5 (LOCAL_PREF), 6 (ATOMICAGGREGATE), 7 (AGGREGATOR), 8 (COMMUNITY), 9 (ORIGINATOR_ID), 10 (CLUSTER_LIST), 14 (MP_REACH_NLRI), 15 (MP_UNREACH_NLRI), 17 (AS4PATH), 18 (AS4AGGREGATOR).";
          }
          leaf unknown-id-map {
            type pub-type:ncs_template_id-range;
            description
              "Specify an unknown attribute ID list. The attribute ids which are not supported as follows: 1 (ORIGIN), 2 (AS_PATH), 3 (NEXT_HOP), 4 (MED), 5 (LOCAL_PREF), 6 (ATOMICAGGREGATE), 7 (AGGREGATOR), 8 (COMMUNITY), 9 (ORIGINATOR_ID), 10 (CLUSTER_LIST), 14 (MP_REACH_NLRI), 15 (MP_UNREACH_NLRI), 17 (AS4PATH), 18 (AS4AGGREGATOR).";
          }
        }
      }
    }
  }
  augment "/ncs:devices/ncs:device/ncs:live-status/ni:network-instance/ni:instances/ni:instance/bgp:bgp/bgp:base-process/bgp:peers/bgp:peer/bgp:afs/bgp:af" {
    description
      "Augment for an L2VPN instance and EVPN association.";
    container l2vpn-evpn {
      tailf:ncs-device-type "netconf";
      tailf:display-when "not(../../../../../../../../../../../ncs:module) or ../../../../../../../../../../../ncs:module[ncs:name='huawei-bgp-evpn'] or (../../../../../../../../../../../ncs:live-status-protocol[not(ncs:capability)]) or (../../../../../../../../../../../ncs:live-status-protocol/ncs:capability/ncs:module[.='huawei-bgp-evpn'])";
      // NCS drop when statement
      // NCS drop must statement
      // NCS drop must statement
      // NCS drop must statement
      description
        "Configure peer EVPN.";
      leaf group-name {
        ext:operation-exclude "update";
        type leafref {
          path "../../../../../../bgp:peer-groups/bgp:peer-group/bgp:name";
        }
        // NCS drop must statement
        // NCS drop must statement
        // NCS drop must statement
        description
          "Configure a name for a peer group. By default, BGP peers join no peer group. BGP peers distinguish the peer group type when joining a peer group. IBGP peers cannot join an EBGP peer group. After a peer is deleted from the peer group, the peer is disabled from the address family. The object cannot be modified.";
      }
      leaf allow-as-loop {
        type uint8 {
          range "1..10";
        }
        description
          "Allow repetitive local AS numbers. By default, repetitive local AS numbers are not allowed.";
      }
      leaf reflect-client {
        // NCS drop when statement
        type boolean;
        // NCS drop default statement
        description
          "Enable/disable the local device as a route reflector (RR) and a peer or peer group as its client. This configuration is applicable between IBGP peers only. The configurations of RRs and its clients in an address family are valid only in this address family. Therefore, it is recommended to configure RRs and its clients in the specified address family that is required.";
      }
      choice import-policy-type {
        description
          "Set route policy or filter.";
        case rtp-ref {
          description
            "Route policy.";
          leaf import-policy {
            type leafref {
              path "/ncs:devices/ncs:device/ncs:live-status/rtp:routing-policy/rtp:policy-definitions/rtp:policy-definition/rtp:name" {
                tailf:xpath-root 3;
              }
            }
            description
              "Specify the filtering policy applied to the routes learned from a peer. By default, no such policy is specified.";
          }
        }
      }
      choice export-policy-type {
        description
          "Set route policy or filter.";
        case rtp-ref {
          description
            "Route policy.";
          leaf export-policy {
            type leafref {
              path "/ncs:devices/ncs:device/ncs:live-status/rtp:routing-policy/rtp:policy-definitions/rtp:policy-definition/rtp:name" {
                tailf:xpath-root 3;
              }
            }
            description
              "Specify the filtering policy applied to the routes to be advertised to a peer. By default, no such policy is specified.";
          }
        }
      }
      leaf advertise-community {
        type boolean;
        // NCS drop default statement
        description
          "Enable/disable advertise community attribute to a peer or peer group.";
      }
      leaf advertise-large-community {
        type live_ncs_config-type;
        // NCS drop default statement
        description
          "Enable large-community attribute advertisement. By default, the function is not configured on any peer. The Link-state address family and the RPD address family do not support this element.";
      }
      leaf advertise-arp {
        type boolean;
        // NCS drop default statement
        description
          "Enable/disable advertise ARP route.";
      }
      leaf advertise-irb {
        type boolean;
        // NCS drop default statement
        description
          "Enable/disable advertise IRB route.";
      }
      leaf advertise-irbv6 {
        type boolean;
        // NCS drop default statement
        description
          "Enable/disable advertise IRBv6 route.";
      }
      leaf advertise-nd {
        type boolean;
        // NCS drop default statement
        description
          "Enable/disable advertise ND route.";
      }
      leaf advertise-encap-type {
        type live_ncs_advertise-encap-type;
        // NCS drop default statement
        description
          "Encapsulation type of packets.";
      }
      leaf advertise-add-path-mode {
        type live_ncs_add-path-cap-type;
        description
          "Enable add-path route advertisement to a peer.";
      }
      leaf advertise-add-path-num {
        type uint8 {
          range "2..128";
        }
        description
          "Number of add-path routes that can be advertised to a peer.";
      }
      leaf advertise-suppressed-route {
        type boolean;
        // NCS drop default statement
        description
          "Enable/disable advertising suppressed-detail-route.";
      }
      leaf advertise-suppressed-route-status {
        type boolean;
        // NCS drop default statement
        description
          "The effective status of advertising suppressed-detail-route.";
      }
      leaf all-route-limit {
        type boolean;
        // NCS drop default statement
        description
          "Enable/disable all routing overflow alarm received from the specified peer.";
      }
      leaf mac-route-limit {
        type boolean;
        // NCS drop default statement
        description
          "Enable/disable MAC routing overflow alarm received from the specified peer.";
      }
      leaf route-limit {
        // NCS drop when statement
        type uint32 {
          range "1..4294967295";
        }
        description
          "Configure the maximum number of routes that can be accepted from a peer.";
      }
      leaf route-limit-percent {
        // NCS drop when statement
        type uint8 {
          range "1..100";
        }
        // NCS drop default statement
        description
          "Specify the percentage of routes when a router starts to generate an alarm.";
      }
      leaf route-limit-type {
        // NCS drop when statement
        type live_ncs_route-limit-type;
        // NCS drop must statement
        // NCS drop default statement
        description
          "Set the processing method as alert-only, idle-forever, or idle-timeout when the number of routes exceeds the set threshold. When alert-only is used, only an alarm is generated when the number of routes exceeds the threshold. In this case, new routes are no longer accepted. When idle-forever is used, connections are not automatically reestablished after being cut off until BGP connections are reset if the number of routes exceeds the set threshold. When idle-timeout is used and the idle-timeout timer is specified, the connections are automatically reestablished after being cut off if the number of routes exceeds the set threshold. You can reset BGP connections to reestablish the connections before the idle-timeout times expires.";
      }
      leaf route-limit-idle-timeout {
        // NCS drop when statement
        type uint16 {
          range "1..1200";
        }
        units "min";
        description
          "Enable/disable specify the value of the idle-timeout timer to automatically reestablish the connections after they are cut off when the number of routes exceeds the set threshold.";
      }
      leaf route-update-interval {
        type uint16 {
          range "0..600";
        }
        units "s";
        ext:dynamic-default {
          ext:default-value "15" {
            // NCS drop when statement
          }
          ext:default-value "30" {
            // NCS drop when statement
          }
        }
        description
          "Specify the minimum interval at which Update packets are sent. By default, the interval at which Update packets are sent to IBGP peers is 15s, and the interval at which Update packets are sent to EBGP peers is 30s.";
      }
      leaf reoriginate-route-enable {
        type boolean;
        // NCS drop default statement
        description
          "Enable/disable route regeneration.";
      }
      leaf reoriginate-vpnv4-route {
        type boolean;
        // NCS drop default statement
        description
          "Enable/disable VPNv4 route regeneration and advertisement.";
      }
      leaf reoriginate-mac-route {
        type boolean;
        // NCS drop default statement
        description
          "Enable/disable MAC route regeneration and advertisement.";
      }
      leaf reoriginate-mac-ip-route {
        type boolean;
        // NCS drop default statement
        description
          "Enable/disable MAC-IP route regeneration and advertisement.";
      }
      leaf reoriginate-mac-ipv6-route {
        type boolean;
        // NCS drop default statement
        description
          "Enable/disable reoriginating IRBv6 route of EVPN.";
      }
      leaf reoriginate-ip-route {
        type boolean;
        // NCS drop default statement
        description
          "Enable/disable IP route regeneration and advertisement.";
      }
      leaf reoriginate-ipv6-route {
        type boolean;
        // NCS drop default statement
        description
          "Enable/disable reoriginating IPv6 prefix route of EVPN.";
      }
      leaf reoriginate-vpnv6-route {
        type boolean;
        // NCS drop default statement
        description
          "Enable/disable reoriginating the route of VPNv6.";
      }
      leaf graceful-restart-static-timer {
        type uint32 {
          range "3600..2147483647";
        }
        units "s";
        description
          "Specifies the maximum time during which a peer waits for a BGP session reestablishment. In seconds.";
      }
      leaf es-ad-compatible {
        type live_ncs_es-ad-compatible-type;
        // NCS drop default statement
        description
          "Ethernet A-D per ES Route Compatible.";
      }
      leaf split-group-name {
        type string {
          length "1..31";
        }
        description
          "Split group name.";
      }
      leaf vpn-orf-disable {
        type boolean;
        // NCS drop default statement
        description
          "Enable/disable VPN ORF.";
      }
      leaf upe-enable {
        type boolean;
        // NCS drop default statement
        description
          "Enable/disable the peer as an underlayer PE (UPE).";
      }
      leaf next-hop-mode {
        type live_ncs_evpn-next-hop-mode;
        // NCS drop default statement
        description
          "Enable next hop mode.";
      }
      leaf high-priority {
        type live_ncs_peer-comm-config-type;
        // NCS drop default statement
        description
          "Enable a higher priority to a specified peer.";
      }
      leaf high-priority-status {
        type boolean;
        // NCS drop default statement
        description
          "The effective status of higher priority to a specified peer.";
      }
      leaf preferred-value {
        type uint32 {
          range "0..65535";
        }
        // NCS drop default statement
        description
          "Assign a preferred value for the routes learned from a specified peer. The value is an integer. After a preferred value is configured for the routes learned from a specified peer, all the routes that learnt from this peer will use this preferred value. When multiple routes reach the same address prefix, the route with the largest preferred value will be selected.";
      }
      leaf mac-detail-route-only {
        type bgp:live_ncs_peer-attr-enable-type;
        description
          "Enable/disable only advertising evpn detailed mac-route.";
      }
      leaf mac-detail-route-only-status {
        type boolean;
        // NCS drop default statement
        description
          "The effective status of advertising evpn detailed mac-route.";
      }
      leaf advertise-srv6-locator {
        // NCS drop when statement
        type empty;
        description
          "Advertise SRv6 locator.";
      }
      container effect-state {
        description
          "Operational state of peer.";
        leaf advertise-srv6-locator {
          type boolean;
          description
            "Whether to advertise SRv6 locators on the EVPN peer.";
        }
      }
      container path-attribute-treats {
        description
          "List of modes in which specified path attributes are processed.";
        list path-attribute-treat {
          // NCS drop must statement
          key "treat-type";
          description
            "Configure mode in which specified path attributes are processed.";
          leaf treat-type {
            type live_ncs_path-attr-treat-type;
            description
              "Mode in which specified path attributes are processed.";
          }
          leaf discard-id-map {
            type pub-type:live_ncs_id-range;
            description
              "Specify a discard attribute ID list. The attribute ids which are not supported as follows: 1 (ORIGIN), 2 (AS_PATH), 3 (NEXT_HOP), 4 (MED), 5 (LOCAL_PREF), 6 (ATOMICAGGREGATE), 7 (AGGREGATOR), 8 (COMMUNITY), 9 (ORIGINATOR_ID), 10 (CLUSTER_LIST), 14 (MP_REACH_NLRI), 15 (MP_UNREACH_NLRI), 17 (AS4PATH), 18 (AS4AGGREGATOR).";
          }
          leaf withdraw-id-map {
            type pub-type:live_ncs_id-range;
            description
              "Specify a withdraw attribute ID list. The attribute ids which are not supported as follows: 1 (ORIGIN), 2 (AS_PATH), 3 (NEXT_HOP), 4 (MED), 5 (LOCAL_PREF), 6 (ATOMICAGGREGATE), 7 (AGGREGATOR), 8 (COMMUNITY), 9 (ORIGINATOR_ID), 10 (CLUSTER_LIST), 14 (MP_REACH_NLRI), 15 (MP_UNREACH_NLRI), 17 (AS4PATH), 18 (AS4AGGREGATOR).";
          }
          leaf unknown-id-map {
            type pub-type:live_ncs_id-range;
            description
              "Specify an unknown attribute ID list. The attribute ids which are not supported as follows: 1 (ORIGIN), 2 (AS_PATH), 3 (NEXT_HOP), 4 (MED), 5 (LOCAL_PREF), 6 (ATOMICAGGREGATE), 7 (AGGREGATOR), 8 (COMMUNITY), 9 (ORIGINATOR_ID), 10 (CLUSTER_LIST), 14 (MP_REACH_NLRI), 15 (MP_UNREACH_NLRI), 17 (AS4PATH), 18 (AS4AGGREGATOR).";
          }
        }
      }
    }
  }
  augment "/ncs:devices/ncs:device/ncs:config/ni:network-instance/ni:instances/ni:instance/bgp:bgp/bgp:base-process/bgp:peers/bgp:peer/bgp:afs/bgp:af" {
    description
      "Augment for an L2VPN instance and EVPN association.";
    container l2vpn-evpn {
      tailf:ncs-device-type "netconf";
      tailf:display-when "not(../../../../../../../../../../../ncs:module) or ../../../../../../../../../../../ncs:module[ncs:name='huawei-bgp-evpn']";
      when "../bgp:type = 'evpn' and ../../../../../../../ni:name='_public_'" {
        tailf:xpath-root 3;
      }
      must "(all-route-limit='true' and mac-route-limit='false' and route-limit) or (all-route-limit='false' and mac-route-limit='true' and route-limit) or (all-route-limit='false' and mac-route-limit='false')" {
        tailf:xpath-root 3;
      }
      must "not(advertise-arp = 'true' and advertise-irb = 'true')" {
        tailf:xpath-root 3;
      }
      must "not(advertise-nd = 'true' and advertise-irbv6 = 'true')" {
        tailf:xpath-root 3;
      }
      description
        "Configure peer EVPN.";
      leaf group-name {
        ext:operation-exclude "update";
        type leafref {
          path "../../../../../../bgp:peer-groups/bgp:peer-group/bgp:name";
        }
        must "(../../../../../../bgp:peer-groups/bgp:peer-group[bgp:name=current()]/bgp:type = 'ibgp' and ../../../../bgp:remote-as = /bgp:bgp/bgp:base-process/bgp:as) or (../../../../../../bgp:peer-groups/bgp:peer-group[bgp:name=current()]/bgp:type = 'ebgp' and ../../../../bgp:remote-as != /bgp:bgp/bgp:base-process/bgp:as)" {
          tailf:xpath-root 3;
        }
        must "../../../../../../bgp:peer-groups/bgp:peer-group[bgp:name=current()]/bgp:afs/bgp:af[bgp:type='evpn']" {
          tailf:xpath-root 3;
        }
        must "../../../../../../bgp:peer-groups/bgp:peer-group[bgp:name=current()]/bgp:peer-establish-mode = 'static'" {
          tailf:xpath-root 3;
        }
        description
          "Configure a name for a peer group. By default, BGP peers join no peer group. BGP peers distinguish the peer group type when joining a peer group. IBGP peers cannot join an EBGP peer group. After a peer is deleted from the peer group, the peer is disabled from the address family. The object cannot be modified.";
      }
      leaf allow-as-loop {
        type uint8 {
          range "1..10";
        }
        description
          "Allow repetitive local AS numbers. By default, repetitive local AS numbers are not allowed.";
      }
      leaf reflect-client {
        when '../../../../bgp:remote-as = /bgp:bgp/bgp:base-process/bgp:as' {
          tailf:xpath-root 3;
        }
        type boolean;
        default "false";
        description
          "Enable/disable the local device as a route reflector (RR) and a peer or peer group as its client. This configuration is applicable between IBGP peers only. The configurations of RRs and its clients in an address family are valid only in this address family. Therefore, it is recommended to configure RRs and its clients in the specified address family that is required.";
      }
      choice import-policy-type {
        description
          "Set route policy or filter.";
        case rtp-ref {
          description
            "Route policy.";
          leaf import-policy {
            type leafref {
              path "/ncs:devices/ncs:device/ncs:config/rtp:routing-policy/rtp:policy-definitions/rtp:policy-definition/rtp:name" {
                tailf:xpath-root 3;
              }
            }
            description
              "Specify the filtering policy applied to the routes learned from a peer. By default, no such policy is specified.";
          }
        }
      }
      choice export-policy-type {
        description
          "Set route policy or filter.";
        case rtp-ref {
          description
            "Route policy.";
          leaf export-policy {
            type leafref {
              path "/ncs:devices/ncs:device/ncs:config/rtp:routing-policy/rtp:policy-definitions/rtp:policy-definition/rtp:name" {
                tailf:xpath-root 3;
              }
            }
            description
              "Specify the filtering policy applied to the routes to be advertised to a peer. By default, no such policy is specified.";
          }
        }
      }
      leaf advertise-community {
        type boolean;
        default "false";
        description
          "Enable/disable advertise community attribute to a peer or peer group.";
      }
      leaf advertise-large-community {
        type config-type;
        default "default";
        description
          "Enable large-community attribute advertisement. By default, the function is not configured on any peer. The Link-state address family and the RPD address family do not support this element.";
      }
      leaf advertise-arp {
        type boolean;
        default "false";
        description
          "Enable/disable advertise ARP route.";
      }
      leaf advertise-irb {
        type boolean;
        default "false";
        description
          "Enable/disable advertise IRB route.";
      }
      leaf advertise-irbv6 {
        type boolean;
        default "false";
        description
          "Enable/disable advertise IRBv6 route.";
      }
      leaf advertise-nd {
        type boolean;
        default "false";
        description
          "Enable/disable advertise ND route.";
      }
      leaf advertise-encap-type {
        type advertise-encap-type;
        default "mpls";
        description
          "Encapsulation type of packets.";
      }
      leaf advertise-add-path-mode {
        type add-path-cap-type;
        description
          "Enable add-path route advertisement to a peer.";
      }
      leaf advertise-add-path-num {
        type uint8 {
          range "2..128";
        }
        description
          "Number of add-path routes that can be advertised to a peer.";
      }
      leaf advertise-suppressed-route {
        type boolean;
        default "false";
        description
          "Enable/disable advertising suppressed-detail-route.";
      }
      // NCS drop config false leaf 'advertise-suppressed-route-status'
      leaf all-route-limit {
        type boolean;
        default "false";
        description
          "Enable/disable all routing overflow alarm received from the specified peer.";
      }
      leaf mac-route-limit {
        type boolean;
        default "false";
        description
          "Enable/disable MAC routing overflow alarm received from the specified peer.";
      }
      leaf route-limit {
        when "(../all-route-limit='true' or ../mac-route-limit='true')" {
          tailf:xpath-root 3;
        }
        type uint32 {
          range "1..4294967295";
        }
        description
          "Configure the maximum number of routes that can be accepted from a peer.";
      }
      leaf route-limit-percent {
        when '../route-limit' {
          tailf:xpath-root 3;
        }
        type uint8 {
          range "1..100";
        }
        default "75";
        description
          "Specify the percentage of routes when a router starts to generate an alarm.";
      }
      leaf route-limit-type {
        when '../route-limit' {
          tailf:xpath-root 3;
        }
        type route-limit-type;
        must "(../route-limit-type = 'idle-timeout' and ../route-limit-idle-timeout) or (../route-limit-type = 'alert-only') or (../route-limit-type = 'idle-forever') or (../route-limit-type = 'noparameter')" {
          tailf:xpath-root 3;
        }
        default "noparameter";
        description
          "Set the processing method as alert-only, idle-forever, or idle-timeout when the number of routes exceeds the set threshold. When alert-only is used, only an alarm is generated when the number of routes exceeds the threshold. In this case, new routes are no longer accepted. When idle-forever is used, connections are not automatically reestablished after being cut off until BGP connections are reset if the number of routes exceeds the set threshold. When idle-timeout is used and the idle-timeout timer is specified, the connections are automatically reestablished after being cut off if the number of routes exceeds the set threshold. You can reset BGP connections to reestablish the connections before the idle-timeout times expires.";
      }
      leaf route-limit-idle-timeout {
        when "../route-limit-type = 'idle-timeout'" {
          tailf:xpath-root 3;
        }
        type uint16 {
          range "1..1200";
        }
        units "min";
        description
          "Enable/disable specify the value of the idle-timeout timer to automatically reestablish the connections after they are cut off when the number of routes exceeds the set threshold.";
      }
      leaf route-update-interval {
        type uint16 {
          range "0..600";
        }
        units "s";
        ext:dynamic-default {
          ext:default-value "15" {
            when '../../../../bgp:remote-as = /bgp:bgp/bgp:base-process/bgp:as' {
              tailf:xpath-root 3;
            }
          }
          ext:default-value "30" {
            when '../../../../bgp:remote-as != /bgp:bgp/bgp:base-process/bgp:as' {
              tailf:xpath-root 3;
            }
          }
        }
        description
          "Specify the minimum interval at which Update packets are sent. By default, the interval at which Update packets are sent to IBGP peers is 15s, and the interval at which Update packets are sent to EBGP peers is 30s.";
      }
      leaf reoriginate-route-enable {
        type boolean;
        default "false";
        description
          "Enable/disable route regeneration.";
      }
      leaf reoriginate-vpnv4-route {
        type boolean;
        default "false";
        description
          "Enable/disable VPNv4 route regeneration and advertisement.";
      }
      leaf reoriginate-mac-route {
        type boolean;
        default "false";
        description
          "Enable/disable MAC route regeneration and advertisement.";
      }
      leaf reoriginate-mac-ip-route {
        type boolean;
        default "false";
        description
          "Enable/disable MAC-IP route regeneration and advertisement.";
      }
      leaf reoriginate-mac-ipv6-route {
        type boolean;
        default "false";
        description
          "Enable/disable reoriginating IRBv6 route of EVPN.";
      }
      leaf reoriginate-ip-route {
        type boolean;
        default "false";
        description
          "Enable/disable IP route regeneration and advertisement.";
      }
      leaf reoriginate-ipv6-route {
        type boolean;
        default "false";
        description
          "Enable/disable reoriginating IPv6 prefix route of EVPN.";
      }
      leaf reoriginate-vpnv6-route {
        type boolean;
        default "false";
        description
          "Enable/disable reoriginating the route of VPNv6.";
      }
      leaf graceful-restart-static-timer {
        type uint32 {
          range "3600..2147483647";
        }
        units "s";
        description
          "Specifies the maximum time during which a peer waits for a BGP session reestablishment. In seconds.";
      }
      leaf es-ad-compatible {
        type es-ad-compatible-type;
        default "default";
        description
          "Ethernet A-D per ES Route Compatible.";
      }
      leaf split-group-name {
        type string {
          length "1..31";
        }
        description
          "Split group name.";
      }
      leaf vpn-orf-disable {
        type boolean;
        default "false";
        description
          "Enable/disable VPN ORF.";
      }
      leaf upe-enable {
        type boolean;
        default "false";
        description
          "Enable/disable the peer as an underlayer PE (UPE).";
      }
      leaf next-hop-mode {
        type evpn-next-hop-mode;
        default "null";
        description
          "Enable next hop mode.";
      }
      leaf high-priority {
        type peer-comm-config-type;
        default "default";
        description
          "Enable a higher priority to a specified peer.";
      }
      // NCS drop config false leaf 'high-priority-status'
      leaf preferred-value {
        type uint32 {
          range "0..65535";
        }
        default "0";
        description
          "Assign a preferred value for the routes learned from a specified peer. The value is an integer. After a preferred value is configured for the routes learned from a specified peer, all the routes that learnt from this peer will use this preferred value. When multiple routes reach the same address prefix, the route with the largest preferred value will be selected.";
      }
      leaf mac-detail-route-only {
        type bgp:peer-attr-enable-type;
        description
          "Enable/disable only advertising evpn detailed mac-route.";
      }
      // NCS drop config false leaf 'mac-detail-route-only-status'
      leaf advertise-srv6-locator {
        when "../advertise-encap-type='srv6'" {
          tailf:xpath-root 3;
        }
        type empty;
        description
          "Advertise SRv6 locator.";
      }
      // NCS drop config false container 'effect-state'
      container path-attribute-treats {
        description
          "List of modes in which specified path attributes are processed.";
        list path-attribute-treat {
          must 'discard-id-map or withdraw-id-map or unknown-id-map' {
            tailf:xpath-root 3;
          }
          key "treat-type";
          description
            "Configure mode in which specified path attributes are processed.";
          leaf treat-type {
            type path-attr-treat-type;
            description
              "Mode in which specified path attributes are processed.";
          }
          leaf discard-id-map {
            type pub-type:id-range {
              pattern '((25[0-5]|2[0-4][0-9]|1[0-9][0-9]|[1-9][0-9]|[0-9])?(-(25[0-5]|2[0-4][0-9]|1[0-9][0-9]|[1-9][0-9]|[0-9]))?(,((25[0-5]|2[0-4][0-9]|1[0-9][0-9]|[1-9][0-9]|[0-9])(-(25[0-5]|2[0-4][0-9]|1[0-9][0-9]|[1-9][0-9]|[0-9]))?))*)|((([\+|\-](25[0-5]|2[0-4][0-9]|1[0-9][0-9]|[1-9][0-9]|[0-9]))|([\+|\-]\((25[0-5]|2[0-4][0-9]|1[0-9][0-9]|[1-9][0-9]|[0-9])-(25[0-5]|2[0-4][0-9]|1[0-9][0-9]|[1-9][0-9]|[0-9])\)))?(,(([\+|\-](25[0-5]|2[0-4][0-9]|1[0-9][0-9]|[1-9][0-9]|[0-9]))|([\+|\-]\((25[0-5]|2[0-4][0-9]|1[0-9][0-9]|[1-9][0-9]|[0-9])-(25[0-5]|2[0-4][0-9]|1[0-9][0-9]|[1-9][0-9]|[0-9])\))))*)';
              ext:value-range "0..255";
            }
            description
              "Specify a discard attribute ID list. The attribute ids which are not supported as follows: 1 (ORIGIN), 2 (AS_PATH), 3 (NEXT_HOP), 4 (MED), 5 (LOCAL_PREF), 6 (ATOMICAGGREGATE), 7 (AGGREGATOR), 8 (COMMUNITY), 9 (ORIGINATOR_ID), 10 (CLUSTER_LIST), 14 (MP_REACH_NLRI), 15 (MP_UNREACH_NLRI), 17 (AS4PATH), 18 (AS4AGGREGATOR).";
          }
          leaf withdraw-id-map {
            type pub-type:id-range {
              pattern '((25[0-5]|2[0-4][0-9]|1[0-9][0-9]|[1-9][0-9]|[0-9])?(-(25[0-5]|2[0-4][0-9]|1[0-9][0-9]|[1-9][0-9]|[0-9]))?(,((25[0-5]|2[0-4][0-9]|1[0-9][0-9]|[1-9][0-9]|[0-9])(-(25[0-5]|2[0-4][0-9]|1[0-9][0-9]|[1-9][0-9]|[0-9]))?))*)|((([\+|\-](25[0-5]|2[0-4][0-9]|1[0-9][0-9]|[1-9][0-9]|[0-9]))|([\+|\-]\((25[0-5]|2[0-4][0-9]|1[0-9][0-9]|[1-9][0-9]|[0-9])-(25[0-5]|2[0-4][0-9]|1[0-9][0-9]|[1-9][0-9]|[0-9])\)))?(,(([\+|\-](25[0-5]|2[0-4][0-9]|1[0-9][0-9]|[1-9][0-9]|[0-9]))|([\+|\-]\((25[0-5]|2[0-4][0-9]|1[0-9][0-9]|[1-9][0-9]|[0-9])-(25[0-5]|2[0-4][0-9]|1[0-9][0-9]|[1-9][0-9]|[0-9])\))))*)';
              ext:value-range "0..255";
            }
            description
              "Specify a withdraw attribute ID list. The attribute ids which are not supported as follows: 1 (ORIGIN), 2 (AS_PATH), 3 (NEXT_HOP), 4 (MED), 5 (LOCAL_PREF), 6 (ATOMICAGGREGATE), 7 (AGGREGATOR), 8 (COMMUNITY), 9 (ORIGINATOR_ID), 10 (CLUSTER_LIST), 14 (MP_REACH_NLRI), 15 (MP_UNREACH_NLRI), 17 (AS4PATH), 18 (AS4AGGREGATOR).";
          }
          leaf unknown-id-map {
            type pub-type:id-range {
              pattern '((25[0-5]|2[0-4][0-9]|1[0-9][0-9]|[1-9][0-9]|[0-9])?(-(25[0-5]|2[0-4][0-9]|1[0-9][0-9]|[1-9][0-9]|[0-9]))?(,((25[0-5]|2[0-4][0-9]|1[0-9][0-9]|[1-9][0-9]|[0-9])(-(25[0-5]|2[0-4][0-9]|1[0-9][0-9]|[1-9][0-9]|[0-9]))?))*)|((([\+|\-](25[0-5]|2[0-4][0-9]|1[0-9][0-9]|[1-9][0-9]|[0-9]))|([\+|\-]\((25[0-5]|2[0-4][0-9]|1[0-9][0-9]|[1-9][0-9]|[0-9])-(25[0-5]|2[0-4][0-9]|1[0-9][0-9]|[1-9][0-9]|[0-9])\)))?(,(([\+|\-](25[0-5]|2[0-4][0-9]|1[0-9][0-9]|[1-9][0-9]|[0-9]))|([\+|\-]\((25[0-5]|2[0-4][0-9]|1[0-9][0-9]|[1-9][0-9]|[0-9])-(25[0-5]|2[0-4][0-9]|1[0-9][0-9]|[1-9][0-9]|[0-9])\))))*)';
              ext:value-range "0..255";
            }
            description
              "Specify an unknown attribute ID list. The attribute ids which are not supported as follows: 1 (ORIGIN), 2 (AS_PATH), 3 (NEXT_HOP), 4 (MED), 5 (LOCAL_PREF), 6 (ATOMICAGGREGATE), 7 (AGGREGATOR), 8 (COMMUNITY), 9 (ORIGINATOR_ID), 10 (CLUSTER_LIST), 14 (MP_REACH_NLRI), 15 (MP_UNREACH_NLRI), 17 (AS4PATH), 18 (AS4AGGREGATOR).";
          }
        }
      }
    }
  }
  augment "/ncs:devices/ncs:template/ncs:ned-id/ncs:config/ni:network-instance/ni:instances/ni:instance/bgp:bgp/bgp:base-process/bgp:peer-groups/bgp:peer-group/bgp:afs/bgp:af" {
    description
      "Augment for an L2VPN instance and EVPN association.";
    container l2vpn-evpn {
      // NCS drop when statement
      // NCS drop must statement
      // NCS drop must statement
      // NCS drop must statement
      description
        "Configure EVPN peer group.";
      leaf reflect-client {
        // NCS drop when statement
        type string;
        // NCS drop default statement
        description
          "Enable/disable the local device as a route reflector (RR) and a peer or peer group as its client. This configuration is applicable between IBGP peers only. The configurations of RRs and its clients in an address family are valid only in this address family. Therefore, it is recommended to configure RRs and its clients in the specified address family that is required.";
      }
      choice import-policy-type {
        description
          "Set route policy or filter.";
        case rtp-ref {
          description
            "Route policy.";
          leaf import-policy {
            type string;
            description
              "Specify the filtering policy applied to the routes learned from a peer. By default, no such policy is specified.";
          }
        }
      }
      choice export-policy-type {
        description
          "Set route policy or filter.";
        case rtp-ref {
          description
            "Route policy.";
          leaf export-policy {
            type string;
            description
              "Specify the filtering policy applied to the routes to be advertised to a peer. By default, no such policy is specified.";
          }
        }
      }
      leaf es-ad-compatible {
        type string;
        // NCS drop default statement
        description
          "Enable/disable ethernet A-D per ES route compatible.";
      }
      leaf split-group-name {
        type string;
        description
          "Split group name.";
      }
      leaf vpn-orf-disable {
        type string;
        // NCS drop default statement
        description
          "Enable/disable VPN ORF.";
      }
      leaf upe-enable {
        type string;
        // NCS drop default statement
        description
          "Enable/disable the peer as an underlayer PE (UPE).";
      }
      leaf next-hop-mode {
        type ncs_template_evpn-next-hop-mode;
        // NCS drop default statement
        description
          "Enable next hop mode.";
      }
      leaf advertise-community {
        type string;
        // NCS drop default statement
        description
          "Enable/disable an advertise the community attribute to a peer or peer group.";
      }
      leaf advertise-large-community {
        type string;
        // NCS drop default statement
        description
          "Enable/disable large-community attribute advertisement. The Link-state address family and the RPD address family do not support this element.";
      }
      leaf advertise-arp {
        type string;
        // NCS drop default statement
        description
          "Enable/disable the advertise ARP route when its value is true.";
      }
      leaf advertise-irb {
        type string;
        // NCS drop default statement
        description
          "Enable/disable the advertise IRB route when its value is true.";
      }
      leaf advertise-irbv6 {
        type string;
        // NCS drop default statement
        description
          "Enable/disable the advertise IRBv6 route when its value is true.";
      }
      leaf advertise-nd {
        type string;
        // NCS drop default statement
        description
          "Enable/disable advertise ND route when its value is true.";
      }
      leaf advertise-encap-type {
        type ncs_template_advertise-encap-type;
        // NCS drop default statement
        description
          "Encapsulation type of packets.";
      }
      leaf advertise-suppressed-route {
        type string;
        // NCS drop default statement
        description
          "Enable/disable advertising suppressed detail route.";
      }
      leaf advertise-add-path-mode {
        type ncs_template_add-path-cap-type;
        description
          "Enable add-path route advertisement to a peer.";
      }
      leaf advertise-add-path-num {
        type string;
        description
          "Number of add-path routes that can be advertised to a peer group.";
      }
      leaf all-route-limit {
        type string;
        // NCS drop default statement
        description
          "Enable/disable all routing overflow alarm received from the specified peer.";
      }
      leaf mac-route-limit {
        type string;
        // NCS drop default statement
        description
          "Enable/disable MAC routing overflow alarm received from the specified peer.";
      }
      leaf route-limit {
        // NCS drop when statement
        type string;
        description
          "Configure the maximum number of routes that can be accepted from a peer.";
      }
      leaf route-limit-percent {
        // NCS drop when statement
        type string;
        // NCS drop default statement
        description
          "Specify the percentage of routes when a router starts to generate an alarm.";
      }
      leaf route-limit-type {
        // NCS drop when statement
        type ncs_template_route-limit-type;
        // NCS drop must statement
        // NCS drop default statement
        description
          "Set the processing method as alert-only, idle-forever, or idle-timeout when the number of routes exceeds the set threshold. When alert-only is used, only an alarm is generated when the number of routes exceeds the threshold. In this case, new routes are no longer accepted. When idle-forever is used, connections are not automatically reestablished after being cut off until BGP connections are reset if the number of routes exceeds the set threshold. When idle-timeout is used and the idle-timeout timer is specified, the connections are automatically reestablished after being cut off if the number of routes exceeds the set threshold. You can reset BGP connections to reestablish the connections before the idle-timeout times expires.";
      }
      leaf route-limit-idle-timeout {
        // NCS drop when statement
        type string;
        units "min";
        description
          "Specify the value of the idle-timeout timer to automatically reestablish the connections after they are cut off when the number of routes exceeds the set threshold.";
      }
      leaf route-update-interval {
        type string;
        units "s";
        ext:dynamic-default {
          ext:default-value "15" {
            // NCS drop when statement
          }
          ext:default-value "30" {
            // NCS drop when statement
          }
        }
        description
          "Specify the minimum interval at which Update packets are sent. By default, the interval at which Update packets are sent to IBGP peers is 15s, and the interval at which Update packets are sent to EBGP peers is 30s.";
      }
      leaf reoriginated-route-enable {
        type string;
        // NCS drop default statement
        description
          "Enable/disable route regeneration.";
      }
      leaf reoriginated-mac-route {
        type string;
        // NCS drop default statement
        description
          "Enable/disable MAC route regeneration and advertisement.";
      }
      leaf reoriginated-mac-ip-route {
        type string;
        // NCS drop default statement
        description
          "Enable/disable MAC-IP route regeneration and advertisement.";
      }
      leaf reoriginated-mac-ipv6-route {
        type string;
        // NCS drop default statement
        description
          "Enable/disable reoriginating IRBv6 route of EVPN.";
      }
      leaf reoriginated-ip-route {
        type string;
        // NCS drop default statement
        description
          "Enable/disable IP route regeneration and advertisement.";
      }
      leaf reoriginated-ipv6-route {
        type string;
        // NCS drop default statement
        description
          "Enable/disable reoriginating IPv6 prefix route of EVPN.";
      }
      leaf reoriginated-vpnv4-route {
        type string;
        // NCS drop default statement
        description
          "Enable/disable VPNv4 route regeneration and advertisement.";
      }
      leaf reoriginated-vpnv6-route {
        type string;
        // NCS drop default statement
        description
          "Enable/disable reoriginating the route of VPNv6.";
      }
      leaf high-priority {
        type string;
        // NCS drop default statement
        description
          "Enable/disable routes received from a specified peer have a higher priority.";
      }
      leaf preferred-value {
        type string;
        // NCS drop default statement
        description
          "Assign a preferred value for the routes learned from a specified peer. The value is an integer. After a preferred value is configured for the routes learned from a specified peer, all the routes that learnt from this peer will use this preferred value. When multiple routes reach the same address prefix, the route with the largest preferred value will be selected.";
      }
      leaf mac-detail-route-only {
        type string;
        // NCS drop default statement
        description
          "Enable/disable only advertising evpn detailed mac-route.";
      }
      leaf advertise-srv6-locator {
        // NCS drop when statement
        type empty;
        description
          "Advertise SRv6 locator.";
      }
    }
  }
  augment "/ncs:devices/ncs:device/ncs:live-status/ni:network-instance/ni:instances/ni:instance/bgp:bgp/bgp:base-process/bgp:peer-groups/bgp:peer-group/bgp:afs/bgp:af" {
    description
      "Augment for an L2VPN instance and EVPN association.";
    container l2vpn-evpn {
      tailf:ncs-device-type "netconf";
      tailf:display-when "not(../../../../../../../../../../../ncs:module) or ../../../../../../../../../../../ncs:module[ncs:name='huawei-bgp-evpn'] or (../../../../../../../../../../../ncs:live-status-protocol[not(ncs:capability)]) or (../../../../../../../../../../../ncs:live-status-protocol/ncs:capability/ncs:module[.='huawei-bgp-evpn'])";
      // NCS drop when statement
      // NCS drop must statement
      // NCS drop must statement
      // NCS drop must statement
      description
        "Configure EVPN peer group.";
      leaf reflect-client {
        // NCS drop when statement
        type boolean;
        // NCS drop default statement
        description
          "Enable/disable the local device as a route reflector (RR) and a peer or peer group as its client. This configuration is applicable between IBGP peers only. The configurations of RRs and its clients in an address family are valid only in this address family. Therefore, it is recommended to configure RRs and its clients in the specified address family that is required.";
      }
      choice import-policy-type {
        description
          "Set route policy or filter.";
        case rtp-ref {
          description
            "Route policy.";
          leaf import-policy {
            type leafref {
              path "/ncs:devices/ncs:device/ncs:live-status/rtp:routing-policy/rtp:policy-definitions/rtp:policy-definition/rtp:name" {
                tailf:xpath-root 3;
              }
            }
            description
              "Specify the filtering policy applied to the routes learned from a peer. By default, no such policy is specified.";
          }
        }
      }
      choice export-policy-type {
        description
          "Set route policy or filter.";
        case rtp-ref {
          description
            "Route policy.";
          leaf export-policy {
            type leafref {
              path "/ncs:devices/ncs:device/ncs:live-status/rtp:routing-policy/rtp:policy-definitions/rtp:policy-definition/rtp:name" {
                tailf:xpath-root 3;
              }
            }
            description
              "Specify the filtering policy applied to the routes to be advertised to a peer. By default, no such policy is specified.";
          }
        }
      }
      leaf es-ad-compatible {
        type boolean;
        // NCS drop default statement
        description
          "Enable/disable ethernet A-D per ES route compatible.";
      }
      leaf split-group-name {
        type string {
          length "1..31";
        }
        description
          "Split group name.";
      }
      leaf vpn-orf-disable {
        type boolean;
        // NCS drop default statement
        description
          "Enable/disable VPN ORF.";
      }
      leaf upe-enable {
        type boolean;
        // NCS drop default statement
        description
          "Enable/disable the peer as an underlayer PE (UPE).";
      }
      leaf next-hop-mode {
        type live_ncs_evpn-next-hop-mode;
        // NCS drop default statement
        description
          "Enable next hop mode.";
      }
      leaf advertise-community {
        type boolean;
        // NCS drop default statement
        description
          "Enable/disable an advertise the community attribute to a peer or peer group.";
      }
      leaf advertise-large-community {
        type boolean;
        // NCS drop default statement
        description
          "Enable/disable large-community attribute advertisement. The Link-state address family and the RPD address family do not support this element.";
      }
      leaf advertise-arp {
        type boolean;
        // NCS drop default statement
        description
          "Enable/disable the advertise ARP route when its value is true.";
      }
      leaf advertise-irb {
        type boolean;
        // NCS drop default statement
        description
          "Enable/disable the advertise IRB route when its value is true.";
      }
      leaf advertise-irbv6 {
        type boolean;
        // NCS drop default statement
        description
          "Enable/disable the advertise IRBv6 route when its value is true.";
      }
      leaf advertise-nd {
        type boolean;
        // NCS drop default statement
        description
          "Enable/disable advertise ND route when its value is true.";
      }
      leaf advertise-encap-type {
        type live_ncs_advertise-encap-type;
        // NCS drop default statement
        description
          "Encapsulation type of packets.";
      }
      leaf advertise-suppressed-route {
        type boolean;
        // NCS drop default statement
        description
          "Enable/disable advertising suppressed detail route.";
      }
      leaf advertise-add-path-mode {
        type live_ncs_add-path-cap-type;
        description
          "Enable add-path route advertisement to a peer.";
      }
      leaf advertise-add-path-num {
        type uint8 {
          range "2..128";
        }
        description
          "Number of add-path routes that can be advertised to a peer group.";
      }
      leaf all-route-limit {
        type boolean;
        // NCS drop default statement
        description
          "Enable/disable all routing overflow alarm received from the specified peer.";
      }
      leaf mac-route-limit {
        type boolean;
        // NCS drop default statement
        description
          "Enable/disable MAC routing overflow alarm received from the specified peer.";
      }
      leaf route-limit {
        // NCS drop when statement
        type uint32 {
          range "1..4294967295";
        }
        description
          "Configure the maximum number of routes that can be accepted from a peer.";
      }
      leaf route-limit-percent {
        // NCS drop when statement
        type uint8 {
          range "1..100";
        }
        // NCS drop default statement
        description
          "Specify the percentage of routes when a router starts to generate an alarm.";
      }
      leaf route-limit-type {
        // NCS drop when statement
        type live_ncs_route-limit-type;
        // NCS drop must statement
        // NCS drop default statement
        description
          "Set the processing method as alert-only, idle-forever, or idle-timeout when the number of routes exceeds the set threshold. When alert-only is used, only an alarm is generated when the number of routes exceeds the threshold. In this case, new routes are no longer accepted. When idle-forever is used, connections are not automatically reestablished after being cut off until BGP connections are reset if the number of routes exceeds the set threshold. When idle-timeout is used and the idle-timeout timer is specified, the connections are automatically reestablished after being cut off if the number of routes exceeds the set threshold. You can reset BGP connections to reestablish the connections before the idle-timeout times expires.";
      }
      leaf route-limit-idle-timeout {
        // NCS drop when statement
        type uint16 {
          range "1..1200";
        }
        units "min";
        description
          "Specify the value of the idle-timeout timer to automatically reestablish the connections after they are cut off when the number of routes exceeds the set threshold.";
      }
      leaf route-update-interval {
        type uint16 {
          range "0..600";
        }
        units "s";
        ext:dynamic-default {
          ext:default-value "15" {
            // NCS drop when statement
          }
          ext:default-value "30" {
            // NCS drop when statement
          }
        }
        description
          "Specify the minimum interval at which Update packets are sent. By default, the interval at which Update packets are sent to IBGP peers is 15s, and the interval at which Update packets are sent to EBGP peers is 30s.";
      }
      leaf reoriginated-route-enable {
        type boolean;
        // NCS drop default statement
        description
          "Enable/disable route regeneration.";
      }
      leaf reoriginated-mac-route {
        type boolean;
        // NCS drop default statement
        description
          "Enable/disable MAC route regeneration and advertisement.";
      }
      leaf reoriginated-mac-ip-route {
        type boolean;
        // NCS drop default statement
        description
          "Enable/disable MAC-IP route regeneration and advertisement.";
      }
      leaf reoriginated-mac-ipv6-route {
        type boolean;
        // NCS drop default statement
        description
          "Enable/disable reoriginating IRBv6 route of EVPN.";
      }
      leaf reoriginated-ip-route {
        type boolean;
        // NCS drop default statement
        description
          "Enable/disable IP route regeneration and advertisement.";
      }
      leaf reoriginated-ipv6-route {
        type boolean;
        // NCS drop default statement
        description
          "Enable/disable reoriginating IPv6 prefix route of EVPN.";
      }
      leaf reoriginated-vpnv4-route {
        type boolean;
        // NCS drop default statement
        description
          "Enable/disable VPNv4 route regeneration and advertisement.";
      }
      leaf reoriginated-vpnv6-route {
        type boolean;
        // NCS drop default statement
        description
          "Enable/disable reoriginating the route of VPNv6.";
      }
      leaf high-priority {
        type boolean;
        // NCS drop default statement
        description
          "Enable/disable routes received from a specified peer have a higher priority.";
      }
      leaf preferred-value {
        type uint32 {
          range "0..65535";
        }
        // NCS drop default statement
        description
          "Assign a preferred value for the routes learned from a specified peer. The value is an integer. After a preferred value is configured for the routes learned from a specified peer, all the routes that learnt from this peer will use this preferred value. When multiple routes reach the same address prefix, the route with the largest preferred value will be selected.";
      }
      leaf mac-detail-route-only {
        type boolean;
        // NCS drop default statement
        description
          "Enable/disable only advertising evpn detailed mac-route.";
      }
      leaf advertise-srv6-locator {
        // NCS drop when statement
        type empty;
        description
          "Advertise SRv6 locator.";
      }
    }
  }
  augment "/ncs:devices/ncs:device/ncs:config/ni:network-instance/ni:instances/ni:instance/bgp:bgp/bgp:base-process/bgp:peer-groups/bgp:peer-group/bgp:afs/bgp:af" {
    description
      "Augment for an L2VPN instance and EVPN association.";
    container l2vpn-evpn {
      tailf:ncs-device-type "netconf";
      tailf:display-when "not(../../../../../../../../../../../ncs:module) or ../../../../../../../../../../../ncs:module[ncs:name='huawei-bgp-evpn']";
      when "(../bgp:type = 'evpn' and ../../../../../../../ni:name='_public_')" {
        tailf:xpath-root 3;
      }
      must "(all-route-limit='true' and mac-route-limit='false' and route-limit) or (all-route-limit='false' and mac-route-limit='true' and route-limit) or (all-route-limit='false' and mac-route-limit='false')" {
        tailf:xpath-root 3;
      }
      must "not(advertise-arp = 'true' and advertise-irb = 'true')" {
        tailf:xpath-root 3;
      }
      must "not(advertise-nd = 'true' and advertise-irbv6 = 'true')" {
        tailf:xpath-root 3;
      }
      description
        "Configure EVPN peer group.";
      leaf reflect-client {
        when "../../../../bgp:type = 'ibgp'" {
          tailf:xpath-root 3;
        }
        type boolean;
        default "false";
        description
          "Enable/disable the local device as a route reflector (RR) and a peer or peer group as its client. This configuration is applicable between IBGP peers only. The configurations of RRs and its clients in an address family are valid only in this address family. Therefore, it is recommended to configure RRs and its clients in the specified address family that is required.";
      }
      choice import-policy-type {
        description
          "Set route policy or filter.";
        case rtp-ref {
          description
            "Route policy.";
          leaf import-policy {
            type leafref {
              path "/ncs:devices/ncs:device/ncs:config/rtp:routing-policy/rtp:policy-definitions/rtp:policy-definition/rtp:name" {
                tailf:xpath-root 3;
              }
            }
            description
              "Specify the filtering policy applied to the routes learned from a peer. By default, no such policy is specified.";
          }
        }
      }
      choice export-policy-type {
        description
          "Set route policy or filter.";
        case rtp-ref {
          description
            "Route policy.";
          leaf export-policy {
            type leafref {
              path "/ncs:devices/ncs:device/ncs:config/rtp:routing-policy/rtp:policy-definitions/rtp:policy-definition/rtp:name" {
                tailf:xpath-root 3;
              }
            }
            description
              "Specify the filtering policy applied to the routes to be advertised to a peer. By default, no such policy is specified.";
          }
        }
      }
      leaf es-ad-compatible {
        type boolean;
        default "false";
        description
          "Enable/disable ethernet A-D per ES route compatible.";
      }
      leaf split-group-name {
        type string {
          length "1..31";
        }
        description
          "Split group name.";
      }
      leaf vpn-orf-disable {
        type boolean;
        default "false";
        description
          "Enable/disable VPN ORF.";
      }
      leaf upe-enable {
        type boolean;
        default "false";
        description
          "Enable/disable the peer as an underlayer PE (UPE).";
      }
      leaf next-hop-mode {
        type evpn-next-hop-mode;
        default "null";
        description
          "Enable next hop mode.";
      }
      leaf advertise-community {
        type boolean;
        default "false";
        description
          "Enable/disable an advertise the community attribute to a peer or peer group.";
      }
      leaf advertise-large-community {
        type boolean;
        default "false";
        description
          "Enable/disable large-community attribute advertisement. The Link-state address family and the RPD address family do not support this element.";
      }
      leaf advertise-arp {
        type boolean;
        default "false";
        description
          "Enable/disable the advertise ARP route when its value is true.";
      }
      leaf advertise-irb {
        type boolean;
        default "false";
        description
          "Enable/disable the advertise IRB route when its value is true.";
      }
      leaf advertise-irbv6 {
        type boolean;
        default "false";
        description
          "Enable/disable the advertise IRBv6 route when its value is true.";
      }
      leaf advertise-nd {
        type boolean;
        default "false";
        description
          "Enable/disable advertise ND route when its value is true.";
      }
      leaf advertise-encap-type {
        type advertise-encap-type;
        default "mpls";
        description
          "Encapsulation type of packets.";
      }
      leaf advertise-suppressed-route {
        type boolean;
        default "false";
        description
          "Enable/disable advertising suppressed detail route.";
      }
      leaf advertise-add-path-mode {
        type add-path-cap-type;
        description
          "Enable add-path route advertisement to a peer.";
      }
      leaf advertise-add-path-num {
        type uint8 {
          range "2..128";
        }
        description
          "Number of add-path routes that can be advertised to a peer group.";
      }
      leaf all-route-limit {
        type boolean;
        default "false";
        description
          "Enable/disable all routing overflow alarm received from the specified peer.";
      }
      leaf mac-route-limit {
        type boolean;
        default "false";
        description
          "Enable/disable MAC routing overflow alarm received from the specified peer.";
      }
      leaf route-limit {
        when "(../all-route-limit='true' or ../mac-route-limit='true')" {
          tailf:xpath-root 3;
        }
        type uint32 {
          range "1..4294967295";
        }
        description
          "Configure the maximum number of routes that can be accepted from a peer.";
      }
      leaf route-limit-percent {
        when '../route-limit' {
          tailf:xpath-root 3;
        }
        type uint8 {
          range "1..100";
        }
        default "75";
        description
          "Specify the percentage of routes when a router starts to generate an alarm.";
      }
      leaf route-limit-type {
        when '../route-limit' {
          tailf:xpath-root 3;
        }
        type route-limit-type;
        must "(../route-limit-type = 'idle-timeout' and ../route-limit-idle-timeout) or (../route-limit-type = 'alert-only') or (../route-limit-type = 'idle-forever') or (../route-limit-type = 'noparameter')" {
          tailf:xpath-root 3;
        }
        default "noparameter";
        description
          "Set the processing method as alert-only, idle-forever, or idle-timeout when the number of routes exceeds the set threshold. When alert-only is used, only an alarm is generated when the number of routes exceeds the threshold. In this case, new routes are no longer accepted. When idle-forever is used, connections are not automatically reestablished after being cut off until BGP connections are reset if the number of routes exceeds the set threshold. When idle-timeout is used and the idle-timeout timer is specified, the connections are automatically reestablished after being cut off if the number of routes exceeds the set threshold. You can reset BGP connections to reestablish the connections before the idle-timeout times expires.";
      }
      leaf route-limit-idle-timeout {
        when "../route-limit-type = 'idle-timeout'" {
          tailf:xpath-root 3;
        }
        type uint16 {
          range "1..1200";
        }
        units "min";
        description
          "Specify the value of the idle-timeout timer to automatically reestablish the connections after they are cut off when the number of routes exceeds the set threshold.";
      }
      leaf route-update-interval {
        type uint16 {
          range "0..600";
        }
        units "s";
        ext:dynamic-default {
          ext:default-value "15" {
            when "../../../../bgp:type = 'ibgp'" {
              tailf:xpath-root 3;
            }
          }
          ext:default-value "30" {
            when "../../../../bgp:type = 'ebgp'" {
              tailf:xpath-root 3;
            }
          }
        }
        description
          "Specify the minimum interval at which Update packets are sent. By default, the interval at which Update packets are sent to IBGP peers is 15s, and the interval at which Update packets are sent to EBGP peers is 30s.";
      }
      leaf reoriginated-route-enable {
        type boolean;
        default "false";
        description
          "Enable/disable route regeneration.";
      }
      leaf reoriginated-mac-route {
        type boolean;
        default "false";
        description
          "Enable/disable MAC route regeneration and advertisement.";
      }
      leaf reoriginated-mac-ip-route {
        type boolean;
        default "false";
        description
          "Enable/disable MAC-IP route regeneration and advertisement.";
      }
      leaf reoriginated-mac-ipv6-route {
        type boolean;
        default "false";
        description
          "Enable/disable reoriginating IRBv6 route of EVPN.";
      }
      leaf reoriginated-ip-route {
        type boolean;
        default "false";
        description
          "Enable/disable IP route regeneration and advertisement.";
      }
      leaf reoriginated-ipv6-route {
        type boolean;
        default "false";
        description
          "Enable/disable reoriginating IPv6 prefix route of EVPN.";
      }
      leaf reoriginated-vpnv4-route {
        type boolean;
        default "false";
        description
          "Enable/disable VPNv4 route regeneration and advertisement.";
      }
      leaf reoriginated-vpnv6-route {
        type boolean;
        default "false";
        description
          "Enable/disable reoriginating the route of VPNv6.";
      }
      leaf high-priority {
        type boolean;
        default "false";
        description
          "Enable/disable routes received from a specified peer have a higher priority.";
      }
      leaf preferred-value {
        type uint32 {
          range "0..65535";
        }
        default "0";
        description
          "Assign a preferred value for the routes learned from a specified peer. The value is an integer. After a preferred value is configured for the routes learned from a specified peer, all the routes that learnt from this peer will use this preferred value. When multiple routes reach the same address prefix, the route with the largest preferred value will be selected.";
      }
      leaf mac-detail-route-only {
        type boolean;
        default "false";
        description
          "Enable/disable only advertising evpn detailed mac-route.";
      }
      leaf advertise-srv6-locator {
        when "../advertise-encap-type='srv6'" {
          tailf:xpath-root 3;
        }
        type empty;
        description
          "Advertise SRv6 locator.";
      }
    }
  }
  augment "/ncs:devices/ncs:template/ncs:ned-id/ncs:config/ni:network-instance/ni:instances/ni:instance/bgp:bgp/bgp:base-process/bgp:afs/bgp:af" {
    description
      "Augment for an L2VPN instance and EVPN association.";
    container l2vpn-evpn {
      // NCS drop when statement
      description
        "Configure L2VPN-EVPN.";
      leaf policy-vpntarget {
        type string;
        // NCS drop default statement
        description
          "Enable/disable VPN target-based filtering for the received VPN routes. By default, VPN target-based filtering is enabled. Only the VPN route whose Export RT attribute matches the local Import RT attribute can be added to the routing table. This option can be used in the inter-AS VPN Option B solution and the ASBR MP-EBGP inter-AS L2VPN solution in Kompella mode.";
      }
      leaf add-path-select-num {
        type string;
        description
          "Number of add-path routes.";
      }
      leaf label-free-delay {
        type string;
        units "s";
        // NCS drop default statement
        description
          "Label free delay.";
      }
      leaf route-select-delay {
        type string;
        units "s";
        // NCS drop default statement
        description
          "Route selection delay.";
      }
      leaf exclusive-eviad-enable {
        // NCS drop when statement
        type string;
        // NCS drop default statement
        description
          "Enable/disable route selection delay for non-EVI-AD routes.";
      }
      leaf label-per-nexthop {
        type ncs_template_apply-label-type;
        // NCS drop default statement
        description
          "Apply label per nexthop enable.";
      }
      leaf auto-frr {
        type string;
        // NCS drop default statement
        description
          "Enable/disable Auto FRR.";
      }
      leaf detection-threshold {
        type string;
        // NCS drop default statement
        description
          "Specify the time in seconds lagging behind average when a peer is determined to be a slow peer.";
      }
      leaf absolute-detection-threshold {
        type string;
        // NCS drop default statement
        description
          "Specify the packet send delay time in second when a peer is determined to be a slow peer.";
      }
      leaf tunnel-selector {
        type string;
        description
          "Configure a tunnel selector and apply it to the BGP IPv4 unicast, BGP VPNv4 address families and BGP VPNv6 address families so that IPv4, VPNv4 and VPNv6 labeled routes can be iterated to tunnels based on the tunnel selector.";
      }
      leaf vpn-orf-enable {
        type string;
        // NCS drop default statement
        description
          "Enable/disable VPN-ORF capability.";
      }
      leaf nexthop-select-depend-type {
        type ncs_template_select-depend-type-ext;
        // NCS drop default statement
        description
          "In none mode, route selection does not depend on whether the next hop is reachable. In tunnel mode, the labeled EVPN route can participate in route selection only after its next hop is iterated to an LSP. In IP
           mode, the labeled EVPN route can participate in route selection only after its next hop is iterated to an IP address. By default, the labeled EVPN route can participate in route selection
           if its next hop can be iterated to an IP address, regardless of whether the LSP of the next hop exists. This allows the RR that is not enabled with MPLS to forward labeled routes. In non-RR
           networking or RR networking where the BGP next hop is changed, BGP needs to check whether there is an LSP destined for the next hop. If such an LSP is not found, BGP needs to establish an LSP in
           advance. If the default setting is adopted, a labeled EVPN route may be selected prior to LSP establishment. As a result, services are incorrectly switched before LSP establishment and
           service stability is affected. Therefore, allow route selection only after the labeled EVPN route is iterated to an LSP.";
      }
      leaf reflect-change-path {
        type string;
        // NCS drop default statement
        description
          "Enable/disable an RR to use an export policy to change route AS_Path.";
      }
      leaf rr-ext-community-filter {
        type string;
        description
          "Set the name of the extended community filter supported by an RR group. For the purpose of load balancing, only the IBGP route whose route-target extended community attribute meets the matching rules can be reflected.";
      }
      leaf time-df-delay {
        type string;
        units "s";
        // NCS drop default statement
        description
          "Specifies forwarder election delay-timer value. In seconds.";
      }
      leaf reflect-between-client {
        type string;
        // NCS drop default statement
        description
          "Enable/disable route reflection between clients. If clients of a route reflector (RR) are fully meshed, you can disable route reflection among clients to reduce the cost.";
      }
      leaf bestroute-igp-metric-ignore {
        type string;
        // NCS drop default statement
        description
          "Enable/disable EVPN to ignore the IGP cost of each EVPN route to the next hop in route selection. By default, an EVPN route with a smaller IGP cost to the next hop is preferred.";
      }
      choice reflector-type {
        description
          "Set IPv4 address or id.";
        case address {
          description
            "IPv4 address.";
          leaf reflector-cluster-ipv4 {
            type string;
            description
              "Set a cluster ID. The value is expressed in the format of an IPv4 address. Configuring multiple RRs in a cluster can enhance the stability of the network. If a cluster has more than one RR, select this option to set the same cluster ID for all the RRs to avoid routing loops. To allow clients to receive routes from RRs, ensure that the cluster ID of the RRs is different from the router ID of any client. If the cluster ID of the RRs is the same as the router ID of a client, the client will discard received routes.";
          }
        }
        case id {
          description
            "Set value.";
          leaf reflector-cluster-id {
            type string;
            description
              "Set a cluster ID. Configuring multiple RRs in a cluster can enhance the stability of the network. If a cluster has more than one RR, select this option to set the same cluster ID for all the RRs to avoid routing loops. To allow clients to receive routes from RRs, ensure that the cluster ID of the RRs is different from the router ID of any client. If the cluster ID of the RRs is the same as the router ID of a client, the client will discard received routes.";
          }
        }
      }
      container nexthop-recursive-lookup {
        description
          "Configure next hop iteration.";
        container common {
          description
            "Configure next hop iteration common options.";
          leaf restrain {
            type string;
            // NCS drop default statement
            description
              "Enable/disable the function to restrain next hop iteration in case of next hop flapping.";
          }
          leaf default-route {
            type string;
            // NCS drop default statement
            description
              "Enable/disable default route.";
          }
        }
        container delay {
          description
            "Configure time of next hop change responding delay.";
          leaf time {
            type string;
            units "s";
            // NCS drop must statement
            description
              "Specify the delay in responding to the next hop change.";
          }
          leaf no-critical-event-time {
            type string;
            units "s";
            // NCS drop must statement
            description
              "Specify the delay in responding to the next hop change on non critical relay change event.";
          }
        }
        container bit-error-detection {
          description
            "Configure EVPN bit-error detection parameters.";
          leaf enable {
            type string;
            // NCS drop must statement
            // NCS drop default statement
            description
              "Enable/disable association between bit error events and the adjustment of route attributes.";
          }
          leaf med {
            // NCS drop when statement
            type string;
            description
              "Specify the MED adjustment for EVPN routes used when a bit error event occurs.";
          }
          leaf local-preference {
            // NCS drop when statement
            type string;
            description
              "Specify the local preference adjustment for routes used when a bit error event occurs.";
          }
          leaf route-policy {
            // NCS drop when statement
            type string;
            description
              "Specify the name of route-policy for bit-error-triggered protection switching. The MED or local preference of only the routes that match the route-policy is adjusted.";
          }
        }
      }
      uses bgp:ncs_template_vrf-af-dampening-routes-ext;
    }
  }
  augment "/ncs:devices/ncs:device/ncs:live-status/ni:network-instance/ni:instances/ni:instance/bgp:bgp/bgp:base-process/bgp:afs/bgp:af" {
    description
      "Augment for an L2VPN instance and EVPN association.";
    container l2vpn-evpn {
      tailf:ncs-device-type "netconf";
      tailf:display-when "not(../../../../../../../../../ncs:module) or ../../../../../../../../../ncs:module[ncs:name='huawei-bgp-evpn'] or (../../../../../../../../../ncs:live-status-protocol[not(ncs:capability)]) or (../../../../../../../../../ncs:live-status-protocol/ncs:capability/ncs:module[.='huawei-bgp-evpn'])";
      // NCS drop when statement
      description
        "Configure L2VPN-EVPN.";
      leaf policy-vpntarget {
        type boolean;
        // NCS drop default statement
        description
          "Enable/disable VPN target-based filtering for the received VPN routes. By default, VPN target-based filtering is enabled. Only the VPN route whose Export RT attribute matches the local Import RT attribute can be added to the routing table. This option can be used in the inter-AS VPN Option B solution and the ASBR MP-EBGP inter-AS L2VPN solution in Kompella mode.";
      }
      leaf add-path-select-num {
        type uint8 {
          range "2..128";
        }
        description
          "Number of add-path routes.";
      }
      leaf label-free-delay {
        type uint8 {
          range "0..180";
        }
        units "s";
        // NCS drop default statement
        description
          "Label free delay.";
      }
      leaf route-select-delay {
        type uint16 {
          range "0..3600";
        }
        units "s";
        // NCS drop default statement
        description
          "Route selection delay.";
      }
      leaf exclusive-eviad-enable {
        // NCS drop when statement
        type boolean;
        // NCS drop default statement
        description
          "Enable/disable route selection delay for non-EVI-AD routes.";
      }
      leaf label-per-nexthop {
        type live_ncs_apply-label-type;
        // NCS drop default statement
        description
          "Apply label per nexthop enable.";
      }
      leaf auto-frr {
        type boolean;
        // NCS drop default statement
        description
          "Enable/disable Auto FRR.";
      }
      leaf detection-threshold {
        type uint16 {
          range "120..3600";
        }
        // NCS drop default statement
        description
          "Specify the time in seconds lagging behind average when a peer is determined to be a slow peer.";
      }
      leaf absolute-detection-threshold {
        type uint16 {
          range "3..3600";
        }
        // NCS drop default statement
        description
          "Specify the packet send delay time in second when a peer is determined to be a slow peer.";
      }
      leaf tunnel-selector {
        type leafref {
          path "/ncs:devices/ncs:device/ncs:live-status/rtp:routing-policy/rtp:tunnel-selectors/rtp:tunnel-selector/rtp:name" {
            tailf:xpath-root 3;
          }
        }
        description
          "Configure a tunnel selector and apply it to the BGP IPv4 unicast, BGP VPNv4 address families and BGP VPNv6 address families so that IPv4, VPNv4 and VPNv6 labeled routes can be iterated to tunnels based on the tunnel selector.";
      }
      leaf vpn-orf-enable {
        type boolean;
        // NCS drop default statement
        description
          "Enable/disable VPN-ORF capability.";
      }
      leaf nexthop-select-depend-type {
        type live_ncs_select-depend-type-ext;
        // NCS drop default statement
        description
          "In none mode, route selection does not depend on whether the next hop is reachable. In tunnel mode, the labeled EVPN route can participate in route selection only after its next hop is iterated to an LSP. In IP
           mode, the labeled EVPN route can participate in route selection only after its next hop is iterated to an IP address. By default, the labeled EVPN route can participate in route selection
           if its next hop can be iterated to an IP address, regardless of whether the LSP of the next hop exists. This allows the RR that is not enabled with MPLS to forward labeled routes. In non-RR
           networking or RR networking where the BGP next hop is changed, BGP needs to check whether there is an LSP destined for the next hop. If such an LSP is not found, BGP needs to establish an LSP in
           advance. If the default setting is adopted, a labeled EVPN route may be selected prior to LSP establishment. As a result, services are incorrectly switched before LSP establishment and
           service stability is affected. Therefore, allow route selection only after the labeled EVPN route is iterated to an LSP.";
      }
      leaf reflect-change-path {
        type boolean;
        // NCS drop default statement
        description
          "Enable/disable an RR to use an export policy to change route AS_Path.";
      }
      leaf rr-ext-community-filter {
        type leafref {
          path "/ncs:devices/ncs:device/ncs:live-status/rtp:routing-policy/rtp:ext-community-filters/rtp:ext-community-filter/rtp:name" {
            tailf:xpath-root 3;
          }
        }
        description
          "Set the name of the extended community filter supported by an RR group. For the purpose of load balancing, only the IBGP route whose route-target extended community attribute meets the matching rules can be reflected.";
      }
      leaf time-df-delay {
        type uint16 {
          range "0..1200";
        }
        units "s";
        // NCS drop default statement
        description
          "Specifies forwarder election delay-timer value. In seconds.";
      }
      leaf reflect-between-client {
        type boolean;
        // NCS drop default statement
        description
          "Enable/disable route reflection between clients. If clients of a route reflector (RR) are fully meshed, you can disable route reflection among clients to reduce the cost.";
      }
      leaf bestroute-igp-metric-ignore {
        type boolean;
        // NCS drop default statement
        description
          "Enable/disable EVPN to ignore the IGP cost of each EVPN route to the next hop in route selection. By default, an EVPN route with a smaller IGP cost to the next hop is preferred.";
      }
      choice reflector-type {
        description
          "Set IPv4 address or id.";
        case address {
          description
            "IPv4 address.";
          leaf reflector-cluster-ipv4 {
            type inet:ipv4-address-no-zone;
            description
              "Set a cluster ID. The value is expressed in the format of an IPv4 address. Configuring multiple RRs in a cluster can enhance the stability of the network. If a cluster has more than one RR, select this option to set the same cluster ID for all the RRs to avoid routing loops. To allow clients to receive routes from RRs, ensure that the cluster ID of the RRs is different from the router ID of any client. If the cluster ID of the RRs is the same as the router ID of a client, the client will discard received routes.";
          }
        }
        case id {
          description
            "Set value.";
          leaf reflector-cluster-id {
            type uint32 {
              range "1..4294967295";
            }
            description
              "Set a cluster ID. Configuring multiple RRs in a cluster can enhance the stability of the network. If a cluster has more than one RR, select this option to set the same cluster ID for all the RRs to avoid routing loops. To allow clients to receive routes from RRs, ensure that the cluster ID of the RRs is different from the router ID of any client. If the cluster ID of the RRs is the same as the router ID of a client, the client will discard received routes.";
          }
        }
      }
      container nexthop-recursive-lookup {
        description
          "Configure next hop iteration.";
        container common {
          description
            "Configure next hop iteration common options.";
          leaf restrain {
            type boolean;
            // NCS drop default statement
            description
              "Enable/disable the function to restrain next hop iteration in case of next hop flapping.";
          }
          leaf default-route {
            type boolean;
            // NCS drop default statement
            description
              "Enable/disable default route.";
          }
        }
        container delay {
          description
            "Configure time of next hop change responding delay.";
          leaf time {
            type uint8 {
              range "1..100";
            }
            units "s";
            // NCS drop must statement
            description
              "Specify the delay in responding to the next hop change.";
          }
          leaf no-critical-event-time {
            type uint8 {
              range "1..100";
            }
            units "s";
            // NCS drop must statement
            description
              "Specify the delay in responding to the next hop change on non critical relay change event.";
          }
        }
        container bit-error-detection {
          description
            "Configure EVPN bit-error detection parameters.";
          leaf enable {
            type boolean;
            // NCS drop must statement
            // NCS drop default statement
            description
              "Enable/disable association between bit error events and the adjustment of route attributes.";
          }
          leaf med {
            // NCS drop when statement
            type uint32 {
              range "1..4294967295";
            }
            description
              "Specify the MED adjustment for EVPN routes used when a bit error event occurs.";
          }
          leaf local-preference {
            // NCS drop when statement
            type uint32 {
              range "1..4294967295";
            }
            description
              "Specify the local preference adjustment for routes used when a bit error event occurs.";
          }
          leaf route-policy {
            // NCS drop when statement
            type leafref {
              path "/ncs:devices/ncs:device/ncs:live-status/rtp:routing-policy/rtp:policy-definitions/rtp:policy-definition/rtp:name" {
                tailf:xpath-root 3;
              }
            }
            description
              "Specify the name of route-policy for bit-error-triggered protection switching. The MED or local preference of only the routes that match the route-policy is adjusted.";
          }
        }
      }
      uses bgp:live_ncs_vrf-af-dampening-routes-ext;
    }
  }
  augment "/ncs:devices/ncs:device/ncs:config/ni:network-instance/ni:instances/ni:instance/bgp:bgp/bgp:base-process/bgp:afs/bgp:af" {
    description
      "Augment for an L2VPN instance and EVPN association.";
    container l2vpn-evpn {
      tailf:ncs-device-type "netconf";
      tailf:display-when "not(../../../../../../../../../ncs:module) or ../../../../../../../../../ncs:module[ncs:name='huawei-bgp-evpn']";
      when "(../bgp:type = 'evpn') and (../../../../../ni:name='_public_')" {
        tailf:xpath-root 3;
      }
      description
        "Configure L2VPN-EVPN.";
      leaf policy-vpntarget {
        type boolean;
        default "true";
        description
          "Enable/disable VPN target-based filtering for the received VPN routes. By default, VPN target-based filtering is enabled. Only the VPN route whose Export RT attribute matches the local Import RT attribute can be added to the routing table. This option can be used in the inter-AS VPN Option B solution and the ASBR MP-EBGP inter-AS L2VPN solution in Kompella mode.";
      }
      leaf add-path-select-num {
        type uint8 {
          range "2..128";
        }
        description
          "Number of add-path routes.";
      }
      leaf label-free-delay {
        type uint8 {
          range "0..180";
        }
        units "s";
        default "5";
        description
          "Label free delay.";
      }
      leaf route-select-delay {
        type uint16 {
          range "0..3600";
        }
        units "s";
        default "0";
        description
          "Route selection delay.";
      }
      leaf exclusive-eviad-enable {
        when '../route-select-delay!=0' {
          tailf:xpath-root 3;
        }
        type boolean;
        default "false";
        description
          "Enable/disable route selection delay for non-EVI-AD routes.";
      }
      leaf label-per-nexthop {
        type apply-label-type;
        default "per-route";
        description
          "Apply label per nexthop enable.";
      }
      leaf auto-frr {
        type boolean;
        default "false";
        description
          "Enable/disable Auto FRR.";
      }
      leaf detection-threshold {
        type uint16 {
          range "120..3600";
        }
        default "300";
        description
          "Specify the time in seconds lagging behind average when a peer is determined to be a slow peer.";
      }
      leaf absolute-detection-threshold {
        type uint16 {
          range "3..3600";
        }
        default "9";
        description
          "Specify the packet send delay time in second when a peer is determined to be a slow peer.";
      }
      leaf tunnel-selector {
        type leafref {
          path "/ncs:devices/ncs:device/ncs:config/rtp:routing-policy/rtp:tunnel-selectors/rtp:tunnel-selector/rtp:name" {
            tailf:xpath-root 3;
          }
        }
        description
          "Configure a tunnel selector and apply it to the BGP IPv4 unicast, BGP VPNv4 address families and BGP VPNv6 address families so that IPv4, VPNv4 and VPNv6 labeled routes can be iterated to tunnels based on the tunnel selector.";
      }
      leaf vpn-orf-enable {
        type boolean;
        default "false";
        description
          "Enable/disable VPN-ORF capability.";
      }
      leaf nexthop-select-depend-type {
        type select-depend-type-ext;
        default "depend-ip";
        description
          "In none mode, route selection does not depend on whether the next hop is reachable. In tunnel mode, the labeled EVPN route can participate in route selection only after its next hop is iterated to an LSP. In IP
           mode, the labeled EVPN route can participate in route selection only after its next hop is iterated to an IP address. By default, the labeled EVPN route can participate in route selection
           if its next hop can be iterated to an IP address, regardless of whether the LSP of the next hop exists. This allows the RR that is not enabled with MPLS to forward labeled routes. In non-RR
           networking or RR networking where the BGP next hop is changed, BGP needs to check whether there is an LSP destined for the next hop. If such an LSP is not found, BGP needs to establish an LSP in
           advance. If the default setting is adopted, a labeled EVPN route may be selected prior to LSP establishment. As a result, services are incorrectly switched before LSP establishment and
           service stability is affected. Therefore, allow route selection only after the labeled EVPN route is iterated to an LSP.";
      }
      leaf reflect-change-path {
        type boolean;
        default "false";
        description
          "Enable/disable an RR to use an export policy to change route AS_Path.";
      }
      leaf rr-ext-community-filter {
        type leafref {
          path "/ncs:devices/ncs:device/ncs:config/rtp:routing-policy/rtp:ext-community-filters/rtp:ext-community-filter/rtp:name" {
            tailf:xpath-root 3;
          }
        }
        description
          "Set the name of the extended community filter supported by an RR group. For the purpose of load balancing, only the IBGP route whose route-target extended community attribute meets the matching rules can be reflected.";
      }
      leaf time-df-delay {
        type uint16 {
          range "0..1200";
        }
        units "s";
        default "60";
        description
          "Specifies forwarder election delay-timer value. In seconds.";
      }
      leaf reflect-between-client {
        type boolean;
        default "true";
        description
          "Enable/disable route reflection between clients. If clients of a route reflector (RR) are fully meshed, you can disable route reflection among clients to reduce the cost.";
      }
      leaf bestroute-igp-metric-ignore {
        type boolean;
        default "false";
        description
          "Enable/disable EVPN to ignore the IGP cost of each EVPN route to the next hop in route selection. By default, an EVPN route with a smaller IGP cost to the next hop is preferred.";
      }
      choice reflector-type {
        description
          "Set IPv4 address or id.";
        case address {
          description
            "IPv4 address.";
          leaf reflector-cluster-ipv4 {
            type inet:ipv4-address-no-zone;
            description
              "Set a cluster ID. The value is expressed in the format of an IPv4 address. Configuring multiple RRs in a cluster can enhance the stability of the network. If a cluster has more than one RR, select this option to set the same cluster ID for all the RRs to avoid routing loops. To allow clients to receive routes from RRs, ensure that the cluster ID of the RRs is different from the router ID of any client. If the cluster ID of the RRs is the same as the router ID of a client, the client will discard received routes.";
          }
        }
        case id {
          description
            "Set value.";
          leaf reflector-cluster-id {
            type uint32 {
              range "1..4294967295";
            }
            description
              "Set a cluster ID. Configuring multiple RRs in a cluster can enhance the stability of the network. If a cluster has more than one RR, select this option to set the same cluster ID for all the RRs to avoid routing loops. To allow clients to receive routes from RRs, ensure that the cluster ID of the RRs is different from the router ID of any client. If the cluster ID of the RRs is the same as the router ID of a client, the client will discard received routes.";
          }
        }
      }
      container nexthop-recursive-lookup {
        description
          "Configure next hop iteration.";
        container common {
          description
            "Configure next hop iteration common options.";
          leaf restrain {
            type boolean;
            default "true";
            description
              "Enable/disable the function to restrain next hop iteration in case of next hop flapping.";
          }
          leaf default-route {
            type boolean;
            default "false";
            description
              "Enable/disable default route.";
          }
        }
        container delay {
          description
            "Configure time of next hop change responding delay.";
          leaf time {
            type uint8 {
              range "1..100";
            }
            units "s";
            must '(not(../no-critical-event-time) or (../no-critical-event-time >= ../time))' {
              tailf:xpath-root 3;
            }
            description
              "Specify the delay in responding to the next hop change.";
          }
          leaf no-critical-event-time {
            type uint8 {
              range "1..100";
            }
            units "s";
            must '(not(../time) or (../no-critical-event-time >= ../time))' {
              tailf:xpath-root 3;
            }
            description
              "Specify the delay in responding to the next hop change on non critical relay change event.";
          }
        }
        container bit-error-detection {
          description
            "Configure EVPN bit-error detection parameters.";
          leaf enable {
            type boolean;
            must "(../enable='false') or (../enable='true' and (../med or ../local-preference))" {
              tailf:xpath-root 3;
            }
            default "false";
            description
              "Enable/disable association between bit error events and the adjustment of route attributes.";
          }
          leaf med {
            when "../enable='true'" {
              tailf:xpath-root 3;
            }
            type uint32 {
              range "1..4294967295";
            }
            description
              "Specify the MED adjustment for EVPN routes used when a bit error event occurs.";
          }
          leaf local-preference {
            when "../enable='true'" {
              tailf:xpath-root 3;
            }
            type uint32 {
              range "1..4294967295";
            }
            description
              "Specify the local preference adjustment for routes used when a bit error event occurs.";
          }
          leaf route-policy {
            when "../enable='true'" {
              tailf:xpath-root 3;
            }
            type leafref {
              path "/ncs:devices/ncs:device/ncs:config/rtp:routing-policy/rtp:policy-definitions/rtp:policy-definition/rtp:name" {
                tailf:xpath-root 3;
              }
            }
            description
              "Specify the name of route-policy for bit-error-triggered protection switching. The MED or local preference of only the routes that match the route-policy is adjusted.";
          }
        }
      }
      uses bgp:vrf-af-dampening-routes-ext;
    }
  }
  augment "/ncs:devices/ncs:template/ncs:ned-id/ncs:config/ni:network-instance/ni:instances/ni:instance/bgp:bgp/bgp:base-process/bgp:afs/bgp:af/bgp:ipv4-unicast" {
    description
      "EVPN configuration.";
    container evpn {
      description
        "Configure EVPN IPv4.";
      container srv6 {
        // NCS drop when statement
        description
          "Configure segment-routing IPv6 for EVPN.";
        leaf mode {
          type ncs_template_srv6-mode;
          // NCS drop must statement
          description
            "SRv6 iteration mode.";
        }
        leaf down-switch {
          // NCS drop when statement
          type string;
          // NCS drop default statement
          description
            "Enable/disable switch TE to BE if the associated TE tunnel goes down.";
        }
      }
      container common {
        // NCS drop when statement
        description
          "Configure EVPN common attribute.";
        leaf reoriginate-disable {
          type string;
          // NCS drop default statement
          description
            "Enable/disable reoriginate capability.";
        }
      }
      container local-cross {
        // NCS drop when statement
        presence "Enable the EVPN instance to advertise routes to other VPN instances.";
        description
          "Configure EVPN local-cross attribute.";
        leaf remote-cross-route-enable {
          type string;
          // NCS drop default statement
          description
            "Enable/disable the use of remotely leaked routes in EVPN local route leaking.";
        }
      }
      container irb-asymmetric {
        // NCS drop when statement
        description
          "Configure IRB asymmetric mode.";
        leaf irb-asymmetric {
          type empty;
          description
            "Enable IRB asymmetric.";
        }
        leaf policy-name {
          // NCS drop when statement
          type string;
          description
            "The name of IRB asymmetric route policy.";
        }
      }
    }
  }
  augment "/ncs:devices/ncs:device/ncs:live-status/ni:network-instance/ni:instances/ni:instance/bgp:bgp/bgp:base-process/bgp:afs/bgp:af/bgp:ipv4-unicast" {
    description
      "EVPN configuration.";
    container evpn {
      tailf:ncs-device-type "netconf";
      tailf:display-when "not(../../../../../../../../../../ncs:module) or ../../../../../../../../../../ncs:module[ncs:name='huawei-bgp-evpn'] or (../../../../../../../../../../ncs:live-status-protocol[not(ncs:capability)]) or (../../../../../../../../../../ncs:live-status-protocol/ncs:capability/ncs:module[.='huawei-bgp-evpn'])";
      description
        "Configure EVPN IPv4.";
      container srv6 {
        // NCS drop when statement
        description
          "Configure segment-routing IPv6 for EVPN.";
        leaf mode {
          type live_ncs_srv6-mode;
          // NCS drop must statement
          description
            "SRv6 iteration mode.";
        }
        leaf down-switch {
          // NCS drop when statement
          type boolean;
          // NCS drop default statement
          description
            "Enable/disable switch TE to BE if the associated TE tunnel goes down.";
        }
      }
      container common {
        // NCS drop when statement
        description
          "Configure EVPN common attribute.";
        leaf reoriginate-disable {
          type boolean;
          // NCS drop default statement
          description
            "Enable/disable reoriginate capability.";
        }
      }
      container local-cross {
        // NCS drop when statement
        presence "Enable the EVPN instance to advertise routes to other VPN instances.";
        description
          "Configure EVPN local-cross attribute.";
        leaf remote-cross-route-enable {
          type boolean;
          // NCS drop default statement
          description
            "Enable/disable the use of remotely leaked routes in EVPN local route leaking.";
        }
      }
      container irb-asymmetric {
        // NCS drop when statement
        description
          "Configure IRB asymmetric mode.";
        leaf irb-asymmetric {
          type empty;
          description
            "Enable IRB asymmetric.";
        }
        leaf policy-name {
          // NCS drop when statement
          type leafref {
            path "/ncs:devices/ncs:device/ncs:live-status/rtp:routing-policy/rtp:policy-definitions/rtp:policy-definition/rtp:name" {
              tailf:xpath-root 3;
            }
          }
          description
            "The name of IRB asymmetric route policy.";
        }
      }
    }
  }
  augment "/ncs:devices/ncs:device/ncs:config/ni:network-instance/ni:instances/ni:instance/bgp:bgp/bgp:base-process/bgp:afs/bgp:af/bgp:ipv4-unicast" {
    description
      "EVPN configuration.";
    container evpn {
      tailf:ncs-device-type "netconf";
      tailf:display-when "not(../../../../../../../../../../ncs:module) or ../../../../../../../../../../ncs:module[ncs:name='huawei-bgp-evpn']";
      description
        "Configure EVPN IPv4.";
      container srv6 {
        when "../../../../../../../ni:name!='_public_'" {
          tailf:xpath-root 3;
        }
        description
          "Configure segment-routing IPv6 for EVPN.";
        leaf mode {
          type srv6-mode;
          must 'not (../../../../../../../../nvo3:nvo3/nvo3:vni-list)' {
            tailf:xpath-root 3;
          }
          description
            "SRv6 iteration mode.";
        }
        leaf down-switch {
          when "../mode='te'" {
            tailf:xpath-root 3;
          }
          type boolean;
          default "false";
          description
            "Enable/disable switch TE to BE if the associated TE tunnel goes down.";
        }
      }
      container common {
        when "../../../../../../../ni:name!='_public_'" {
          tailf:xpath-root 3;
        }
        description
          "Configure EVPN common attribute.";
        leaf reoriginate-disable {
          type boolean;
          default "false";
          description
            "Enable/disable reoriginate capability.";
        }
      }
      container local-cross {
        when "../../../../../../../ni:name!='_public_'" {
          tailf:xpath-root 3;
        }
        presence "Enable the EVPN instance to advertise routes to other VPN instances.";
        description
          "Configure EVPN local-cross attribute.";
        leaf remote-cross-route-enable {
          type boolean;
          default "false";
          description
            "Enable/disable the use of remotely leaked routes in EVPN local route leaking.";
        }
      }
      container irb-asymmetric {
        when "../../../../../../../ni:name!='_public_'" {
          tailf:xpath-root 3;
        }
        description
          "Configure IRB asymmetric mode.";
        leaf irb-asymmetric {
          type empty;
          description
            "Enable IRB asymmetric.";
        }
        leaf policy-name {
          when '../irb-asymmetric' {
            tailf:xpath-root 3;
          }
          type leafref {
            path "/ncs:devices/ncs:device/ncs:config/rtp:routing-policy/rtp:policy-definitions/rtp:policy-definition/rtp:name" {
              tailf:xpath-root 3;
            }
          }
          description
            "The name of IRB asymmetric route policy.";
        }
      }
    }
  }
  augment "/ncs:devices/ncs:template/ncs:ned-id/ncs:config/ni:network-instance/ni:instances/ni:instance/bgp:bgp/bgp:base-process/bgp:afs/bgp:af/bgp:ipv6-unicast" {
    description
      "EVPN configuration.";
    container evpn {
      description
        "Configure EVPN IPv6.";
      container srv6 {
        // NCS drop when statement
        description
          "Configure segment-routing IPv6 for EVPN.";
        leaf mode {
          type ncs_template_srv6-mode;
          // NCS drop must statement
          description
            "SRv6 iteration mode.";
        }
        leaf down-switch {
          // NCS drop when statement
          type string;
          // NCS drop default statement
          description
            "Enable/disable switch TE to BE if the associated TE tunnel goes down.";
        }
      }
      container common {
        // NCS drop when statement
        description
          "Configure EVPN common attribute.";
        leaf reoriginate-disable {
          type string;
          // NCS drop default statement
          description
            "Enable/disable reoriginate capability.";
        }
      }
      container local-cross {
        // NCS drop when statement
        presence "Enable the EVPN instance to advertise routes to other VPN instances.";
        description
          "Configure EVPN local-cross attribute.";
        leaf remote-cross-route-enable {
          type string;
          // NCS drop default statement
          description
            "Enable/disable the use of remotely leaked routes in EVPN local route leaking.";
        }
      }
      container irb-asymmetric {
        // NCS drop when statement
        description
          "Configure IRB asymmetric mode.";
        leaf irb-asymmetric {
          type empty;
          description
            "Enable IRB asymmetric.";
        }
        leaf policy-name {
          // NCS drop when statement
          type string;
          description
            "The name of IRB asymmetric route policy.";
        }
      }
    }
  }
  augment "/ncs:devices/ncs:device/ncs:live-status/ni:network-instance/ni:instances/ni:instance/bgp:bgp/bgp:base-process/bgp:afs/bgp:af/bgp:ipv6-unicast" {
    description
      "EVPN configuration.";
    container evpn {
      tailf:ncs-device-type "netconf";
      tailf:display-when "not(../../../../../../../../../../ncs:module) or ../../../../../../../../../../ncs:module[ncs:name='huawei-bgp-evpn'] or (../../../../../../../../../../ncs:live-status-protocol[not(ncs:capability)]) or (../../../../../../../../../../ncs:live-status-protocol/ncs:capability/ncs:module[.='huawei-bgp-evpn'])";
      description
        "Configure EVPN IPv6.";
      container srv6 {
        // NCS drop when statement
        description
          "Configure segment-routing IPv6 for EVPN.";
        leaf mode {
          type live_ncs_srv6-mode;
          // NCS drop must statement
          description
            "SRv6 iteration mode.";
        }
        leaf down-switch {
          // NCS drop when statement
          type boolean;
          // NCS drop default statement
          description
            "Enable/disable switch TE to BE if the associated TE tunnel goes down.";
        }
      }
      container common {
        // NCS drop when statement
        description
          "Configure EVPN common attribute.";
        leaf reoriginate-disable {
          type boolean;
          // NCS drop default statement
          description
            "Enable/disable reoriginate capability.";
        }
      }
      container local-cross {
        // NCS drop when statement
        presence "Enable the EVPN instance to advertise routes to other VPN instances.";
        description
          "Configure EVPN local-cross attribute.";
        leaf remote-cross-route-enable {
          type boolean;
          // NCS drop default statement
          description
            "Enable/disable the use of remotely leaked routes in EVPN local route leaking.";
        }
      }
      container irb-asymmetric {
        // NCS drop when statement
        description
          "Configure IRB asymmetric mode.";
        leaf irb-asymmetric {
          type empty;
          description
            "Enable IRB asymmetric.";
        }
        leaf policy-name {
          // NCS drop when statement
          type leafref {
            path "/ncs:devices/ncs:device/ncs:live-status/rtp:routing-policy/rtp:policy-definitions/rtp:policy-definition/rtp:name" {
              tailf:xpath-root 3;
            }
          }
          description
            "The name of IRB asymmetric route policy.";
        }
      }
    }
  }
  augment "/ncs:devices/ncs:device/ncs:config/ni:network-instance/ni:instances/ni:instance/bgp:bgp/bgp:base-process/bgp:afs/bgp:af/bgp:ipv6-unicast" {
    description
      "EVPN configuration.";
    container evpn {
      tailf:ncs-device-type "netconf";
      tailf:display-when "not(../../../../../../../../../../ncs:module) or ../../../../../../../../../../ncs:module[ncs:name='huawei-bgp-evpn']";
      description
        "Configure EVPN IPv6.";
      container srv6 {
        when "../../../../../../../ni:name!='_public_'" {
          tailf:xpath-root 3;
        }
        description
          "Configure segment-routing IPv6 for EVPN.";
        leaf mode {
          type srv6-mode;
          must 'not (../../../../../../../../nvo3:nvo3/nvo3:vni-list)' {
            tailf:xpath-root 3;
          }
          description
            "SRv6 iteration mode.";
        }
        leaf down-switch {
          when "../mode='te'" {
            tailf:xpath-root 3;
          }
          type boolean;
          default "false";
          description
            "Enable/disable switch TE to BE if the associated TE tunnel goes down.";
        }
      }
      container common {
        when "../../../../../../../ni:name!='_public_'" {
          tailf:xpath-root 3;
        }
        description
          "Configure EVPN common attribute.";
        leaf reoriginate-disable {
          type boolean;
          default "false";
          description
            "Enable/disable reoriginate capability.";
        }
      }
      container local-cross {
        when "../../../../../../../ni:name!='_public_'" {
          tailf:xpath-root 3;
        }
        presence "Enable the EVPN instance to advertise routes to other VPN instances.";
        description
          "Configure EVPN local-cross attribute.";
        leaf remote-cross-route-enable {
          type boolean;
          default "false";
          description
            "Enable/disable the use of remotely leaked routes in EVPN local route leaking.";
        }
      }
      container irb-asymmetric {
        when "../../../../../../../ni:name!='_public_'" {
          tailf:xpath-root 3;
        }
        description
          "Configure IRB asymmetric mode.";
        leaf irb-asymmetric {
          type empty;
          description
            "Enable IRB asymmetric.";
        }
        leaf policy-name {
          when '../irb-asymmetric' {
            tailf:xpath-root 3;
          }
          type leafref {
            path "/ncs:devices/ncs:device/ncs:config/rtp:routing-policy/rtp:policy-definitions/rtp:policy-definition/rtp:name" {
              tailf:xpath-root 3;
            }
          }
          description
            "The name of IRB asymmetric route policy.";
        }
      }
    }
  }
  augment "/ncs:devices/ncs:device/ncs:live-status/bgp:bgp/bgp:base-process/bgp-rt:bgp-route" {
    description
      "BGP routes information of EVPN address family.";
    container l2vpn-evpn {
      tailf:ncs-device-type "netconf";
      tailf:display-when "not(../../../../../ncs:module) or ../../../../../ncs:module[ncs:name='huawei-bgp-evpn'] or (../../../../../ncs:live-status-protocol[not(ncs:capability)]) or (../../../../../ncs:live-status-protocol/ncs:capability/ncs:module[.='huawei-bgp-evpn'])";
      description
        "Statistics of BGP routes information of EVPN address family.";
      container statistics {
        description
          "List of BGP routes information of EVPN address family.";
        list statistic {
          // NCS drop must statement
          key "vpn-name";
          description
            "BGP EVPN address family routes statistics.";
          leaf vpn-name {
            type leafref {
              path "/ncs:devices/ncs:device/ncs:live-status/ni:network-instance/ni:instances/ni:instance/ni:name" {
                tailf:xpath-root 3;
              }
            }
            description
              "VPN name of a BGP instance.";
          }
          leaf total-route-number {
            type uint32;
            description
              "Total number of EVPN routes.";
          }
          leaf ad-route-number {
            type uint32;
            description
              "Number of Ethernet Auto-Discovery routes.";
          }
          leaf mac-route-number {
            type uint32;
            description
              "Number of MAC/IP Advertisement routes.";
          }
          leaf include-route-number {
            type uint32;
            description
              "Number of Inclusive Multicast Ethernet Tag routes.";
          }
          leaf es-route-number {
            type uint32;
            description
              "Number of Ethernet Segment routes.";
          }
          leaf ip-prefix-route-number {
            type uint32;
            description
              "Number of IP Prefix routes.";
          }
          leaf smet-route-number {
            type uint32;
            description
              "Number of Selective Multicast Ethernet Tag routes.";
          }
          leaf igmp-join-route-number {
            type uint32;
            description
              "Number of IGMP Join Synch routes.";
          }
          leaf igmp-leave-route-number {
            type uint32;
            description
              "Number of IGMP Leave Synch routes.";
          }
        }
      }
    }
  }
}
