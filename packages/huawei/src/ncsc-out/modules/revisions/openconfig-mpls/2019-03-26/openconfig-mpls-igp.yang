submodule openconfig-mpls-igp {
  // Generated by yanger -t ncs
  tailf:mount-id "huawei-nc-1.0:huawei-nc-1.0";

  yang-version 1;
  belongs-to openconfig-mpls {
    prefix oc-mpls;
  }

  import openconfig-mpls-ldp {
    prefix oc-ldp;
  }
  import openconfig-extensions {
    prefix oc-ext;
  }
  import tailf-common {
    prefix tailf;
  }
  import tailf-ncs {
    prefix ncs;
  }

  organization
    "OpenConfig working group";
  contact
    "OpenConfig working group
     netopenconfig@googlegroups.com";
  description
    "Configuration generic configuration parameters for IGP-congruent
     LSPs";
  oc-ext:openconfig-version "3.0.1";

  revision 2018-11-21 {
    description
      "Add OpenConfig module metadata extensions.";
    reference "3.0.1";
  }
  revision 2018-07-02 {
    description
      "Add new RSVP-TE statistics, remove associated-rsvp-session
       leaf. Remove use of date-and-time.";
    reference "3.0.0";
  }
  revision 2018-06-16 {
    description
      "Included attributes for base LDP configuration.";
    reference "2.6.0";
  }
  revision 2018-06-13 {
    description
      "Add ttl-propagation to global MPLS config";
    reference "2.5.0";
  }
  revision 2018-06-05 {
    description
      "Fixed bugs in when statements on RSVP-TE attributes";
    reference "2.4.2";
  }
  revision 2017-08-24 {
    description
      "Minor formatting fixes.";
    reference "2.4.1";
  }
  revision 2017-06-21 {
    description
      "Add TC bits typedef.";
    reference "2.4.0";
  }
  revision 2017-03-22 {
    description
      "Add RSVP calculated-absolute-subscription-bw";
    reference "2.3.0";
  }
  revision 2017-01-26 {
    description
      "Add RSVP Tspec, clarify units for RSVP, remove unused LDP";
    reference "2.2.0";
  }
  revision 2016-12-15 {
    description
      "Add additional MPLS parameters";
    reference "2.1.0";
  }
  revision 2016-09-01 {
    description
      "Revisions based on implementation feedback";
    reference "2.0.0";
  }
  revision 2016-08-08 {
    description
      "Public release of MPLS models";
    reference "1.0.1";
  }

  grouping ncs_template_igp-lsp-common {
    description
      "common definitions for IGP-congruent LSPs";
  }

  grouping ncs_template_igp-lsp-setup {
    description
      "signaling protocol definitions for IGP-based LSPs";
    container path-setup-protocol {
      description
        "select and configure the signaling method for
          the LSP";
      uses oc-ldp:ncs_template_igp-lsp-ldp-setup;
    }
  }

  grouping ncs_rpc_notif_igp-lsp-common {
    description
      "common definitions for IGP-congruent LSPs";
  }

  grouping ncs_rpc_notif_igp-lsp-setup {
    description
      "signaling protocol definitions for IGP-based LSPs";
    container path-setup-protocol {
      description
        "select and configure the signaling method for
          the LSP";
      uses oc-ldp:ncs_rpc_notif_igp-lsp-ldp-setup;
    }
  }

  grouping live_ncs_igp-lsp-common {
    description
      "common definitions for IGP-congruent LSPs";
  }

  grouping live_ncs_igp-lsp-setup {
    description
      "signaling protocol definitions for IGP-based LSPs";
    container path-setup-protocol {
      description
        "select and configure the signaling method for
          the LSP";
      uses oc-ldp:live_ncs_igp-lsp-ldp-setup;
    }
  }

  grouping igp-lsp-common {
    description
      "common definitions for IGP-congruent LSPs";
  }

  grouping igp-lsp-setup {
    description
      "signaling protocol definitions for IGP-based LSPs";
    container path-setup-protocol {
      description
        "select and configure the signaling method for
          the LSP";
      uses oc-ldp:igp-lsp-ldp-setup;
    }
  }
}
