module huawei-network-instance {
  // Generated by yanger -t ncs
  tailf:mount-id "huawei-nc-1.0:huawei-nc-1.0";
  tailf:ncs-device-type "netconf";

  namespace "urn:huawei:yang:huawei-network-instance";
  prefix ni-huawei;

  import huawei-extension {
    prefix ext;
  }
  import ietf-inet-types {
    prefix inet;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Layer 3 Virtual Private Network (L3VPN). An L3VPN is a virtual private network set up over public networks by Internet Service Providers (ISPs) and Network Service Providers (NSPs).";

  revision 2020-03-10 {
    description
      "The YANG descriptions are modified according to new standards.";
    reference "Huawei private.";
  }
  revision 2019-04-28 {
    description
      "Initial revision.";
    reference "Huawei private.";
  }
  ext:task-name "l3vpn";

  augment "/ncs:devices/ncs:device/ncs:config" {
    container network-instance {
      tailf:ncs-device-type "netconf";
      tailf:display-when "not(../../ncs:module) or ../../ncs:module[ncs:name='huawei-network-instance']";
      description
        "Layer 3 Virtual Private Network (L3VPN). An L3VPN is a virtual private network set up over public networks by Internet Service Providers (ISPs) and Network Service Providers (NSPs).";
      container global {
        description
          "Configure the global layer 3 virtual private network (L3VPN).";
        leaf cfg-router-id {
          type inet:ipv4-address-no-zone;
          description
            "The router id of router manager.";
        }
        leaf as-notation-plain {
          type boolean;
          default "false";
          description
            "Enable/disable setting the display format of the BGP 4 byte as to be unformatted integer type.";
        }
        leaf route-distinguisher-auto-ip {
          type inet:ipv4-address-no-zone;
          description
            "Configure IP address to automatic route-distinguisher.";
        }
      }
      container instances {
        description
          "List of VPN instances. VPN instances are established to separate VPN routes from public network routes, and separate the routes of different VPNs. Some software features can be bound to multiple VPN instances so that multiple instances can provide a same feature. For example, RIP, OSPF, IS-IS, and BGP multiple instances.";
        list instance {
          key "name";
          description
            "Configure VPN instances. VPN instances are established to separate VPN routes from public network routes, and separate the routes of different VPNs. Multiple software features can be bound to multiple VPN instances to form a multi-instance that provides multiple features, for example, RIP multi-instance, OSPF multi-instance, IS-IS multi-instance, and BGP multi-instance. The _public_, dcn, ason, __mpp_vpn_inner__, __mpp_vpn_outer__, __mpp_vpn_inner_server__, and __LOCAL_OAM_VPN__ instances cannot be deleted.";
          ext:generated-by "system" {
            ext:filter "name = '_public_'";
            description
              "The public instance is generated automatically.";
          }
          leaf name {
            type string {
              length "1..31";
            }
            description
              "VPN instance name. It uniquely identifies a VPN instance. The name is a string of case-sensitive characters.";
          }
          leaf description {
            when "not(../name='_public_')" {
              tailf:xpath-root 3;
            }
            type string {
              length "1..242";
              pattern '([^?]*)';
            }
            description
              "The description of a VPN instance. The value is a string, spaces supported.";
          }
          // NCS drop config false leaf 'sys-router-id'
          // NCS drop config false leaf 'vrf-id'
        }
      }
    }
  }
  augment "/ncs:devices/ncs:device/ncs:live-status" {
    container network-instance {
      tailf:ncs-device-type "netconf";
      tailf:display-when "not(../../ncs:module) or ../../ncs:module[ncs:name='huawei-network-instance'] or (../../ncs:live-status-protocol[not(ncs:capability)]) or (../../ncs:live-status-protocol/ncs:capability/ncs:module[.='huawei-network-instance'])";
      description
        "Layer 3 Virtual Private Network (L3VPN). An L3VPN is a virtual private network set up over public networks by Internet Service Providers (ISPs) and Network Service Providers (NSPs).";
      container global {
        description
          "Configure the global layer 3 virtual private network (L3VPN).";
        leaf cfg-router-id {
          type inet:ipv4-address-no-zone;
          description
            "The router id of router manager.";
        }
        leaf as-notation-plain {
          type boolean;
          // NCS drop default statement
          description
            "Enable/disable setting the display format of the BGP 4 byte as to be unformatted integer type.";
        }
        leaf route-distinguisher-auto-ip {
          type inet:ipv4-address-no-zone;
          description
            "Configure IP address to automatic route-distinguisher.";
        }
      }
      container instances {
        description
          "List of VPN instances. VPN instances are established to separate VPN routes from public network routes, and separate the routes of different VPNs. Some software features can be bound to multiple VPN instances so that multiple instances can provide a same feature. For example, RIP, OSPF, IS-IS, and BGP multiple instances.";
        list instance {
          key "name";
          description
            "Configure VPN instances. VPN instances are established to separate VPN routes from public network routes, and separate the routes of different VPNs. Multiple software features can be bound to multiple VPN instances to form a multi-instance that provides multiple features, for example, RIP multi-instance, OSPF multi-instance, IS-IS multi-instance, and BGP multi-instance. The _public_, dcn, ason, __mpp_vpn_inner__, __mpp_vpn_outer__, __mpp_vpn_inner_server__, and __LOCAL_OAM_VPN__ instances cannot be deleted.";
          ext:generated-by "system" {
            ext:filter "name = '_public_'";
            description
              "The public instance is generated automatically.";
          }
          leaf name {
            type string {
              length "1..31";
            }
            description
              "VPN instance name. It uniquely identifies a VPN instance. The name is a string of case-sensitive characters.";
          }
          leaf description {
            // NCS drop when statement
            type string {
              length "1..242";
              pattern '([^?]*)';
            }
            description
              "The description of a VPN instance. The value is a string, spaces supported.";
          }
          leaf sys-router-id {
            type inet:ipv4-address-no-zone;
            description
              "The router id of current use.";
          }
          leaf vrf-id {
            type uint32;
            description
              "Vpn Instances ID.";
          }
        }
      }
    }
  }
  augment "/ncs:devices/ncs:template/ncs:ned-id/ncs:config" {
    container network-instance {
      description
        "Layer 3 Virtual Private Network (L3VPN). An L3VPN is a virtual private network set up over public networks by Internet Service Providers (ISPs) and Network Service Providers (NSPs).";
      container global {
        description
          "Configure the global layer 3 virtual private network (L3VPN).";
        leaf cfg-router-id {
          type string;
          description
            "The router id of router manager.";
        }
        leaf as-notation-plain {
          type string;
          // NCS drop default statement
          description
            "Enable/disable setting the display format of the BGP 4 byte as to be unformatted integer type.";
        }
        leaf route-distinguisher-auto-ip {
          type string;
          description
            "Configure IP address to automatic route-distinguisher.";
        }
      }
      container instances {
        description
          "List of VPN instances. VPN instances are established to separate VPN routes from public network routes, and separate the routes of different VPNs. Some software features can be bound to multiple VPN instances so that multiple instances can provide a same feature. For example, RIP, OSPF, IS-IS, and BGP multiple instances.";
        list instance {
          // NCS patched for predictable order
          ordered-by user;
          key "name";
          description
            "Configure VPN instances. VPN instances are established to separate VPN routes from public network routes, and separate the routes of different VPNs. Multiple software features can be bound to multiple VPN instances to form a multi-instance that provides multiple features, for example, RIP multi-instance, OSPF multi-instance, IS-IS multi-instance, and BGP multi-instance. The _public_, dcn, ason, __mpp_vpn_inner__, __mpp_vpn_outer__, __mpp_vpn_inner_server__, and __LOCAL_OAM_VPN__ instances cannot be deleted.";
          ext:generated-by "system" {
            ext:filter "name = '_public_'";
            description
              "The public instance is generated automatically.";
          }
          leaf name {
            type string;
            description
              "VPN instance name. It uniquely identifies a VPN instance. The name is a string of case-sensitive characters.";
          }
          leaf description {
            // NCS drop when statement
            type string;
            description
              "The description of a VPN instance. The value is a string, spaces supported.";
          }
          // NCS drop config false leaf 'sys-router-id'
          // NCS drop config false leaf 'vrf-id'
        }
      }
    }
  }
}
