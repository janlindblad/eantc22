module huawei-dhcp-notification {
  // Generated by yanger -t ncs
  tailf:mount-id "huawei-nc-1.0:huawei-nc-1.0";
  tailf:ncs-device-type "netconf";

  yang-version 1;
  namespace "urn:huawei:yang:huawei-dhcp-notification";
  prefix dhcp-notification;

  import huawei-extension {
    prefix ext;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Notification of DHCP-notification.";

  revision 2021-02-01 {
    description
      "Initial revision.";
    reference "Huawei private.";
  }
  ext:task-name "dhcp";

  augment "/ncs:devices/ncs:device/ncs:notifications/ncs:received-notifications/ncs:notification/ncs:data" {
    container v6-relay-ip-table-exhaust-resume {
      presence "";
      config false;
      description
        "The number of DHCPv6 relay IP entries on the device falls below 90% of the upper limit.";
      leaf max-number {
        type uint32;
        description
          "Maximum number of DHCPv6 relay IP entries on the device.";
      }
    }
  }
  augment "/ncs:devices/ncs:device/ncs:notifications/ncs:received-notifications/ncs:notification/ncs:data" {
    container v6-relay-ip-table-exhaust {
      presence "";
      config false;
      description
        "The number of DHCPv6 relay IP entries on the device reaches the upper limit.";
      leaf max-number {
        type uint32;
        description
          "Maximum number of DHCPv6 relay IP entries on the device.";
      }
    }
  }
  augment "/ncs:devices/ncs:device/ncs:notifications/ncs:received-notifications/ncs:notification/ncs:data" {
    container v6-relay-ip-table-threshold-resume {
      presence "";
      config false;
      description
        "The number of DHCPv6 relay IP entries on the device falls below 70% of the upper limit.";
      leaf current-number {
        type uint32;
        description
          "Number of DHCPv6 relay IP entries on the device.";
      }
      leaf max-number {
        type uint32;
        description
          "Maximum number of DHCPv6 relay IP entries on the device.";
      }
    }
  }
  augment "/ncs:devices/ncs:device/ncs:notifications/ncs:received-notifications/ncs:notification/ncs:data" {
    container v6-relay-ip-table-threshold {
      presence "";
      config false;
      description
        "The number of DHCPv6 relay IP entries on the device exceeds 80% of the upper limit.";
      leaf current-number {
        type uint32;
        description
          "Number of DHCPv6 relay IP entries on the device.";
      }
      leaf max-number {
        type uint32;
        description
          "Maximum number of DHCPv6 relay IP entries on the device.";
      }
    }
  }
  augment "/ncs:devices/ncs:device/ncs:notifications/ncs:received-notifications/ncs:notification/ncs:data" {
    container v6-relay-table-exhaust-resume {
      presence "";
      config false;
      description
        "The number of DHCPv6 relay entries on the device falls below 90% of the upper limit.";
      leaf max-number {
        type uint32;
        description
          "Maximum number of DHCPv6 relay entries on the device.";
      }
    }
  }
  augment "/ncs:devices/ncs:device/ncs:notifications/ncs:received-notifications/ncs:notification/ncs:data" {
    container v6-relay-table-exhaust {
      presence "";
      config false;
      description
        "The number of DHCPv6 relay entries on the device reaches the upper limit.";
      leaf max-number {
        type uint32;
        description
          "Maximum number of DHCPv6 relay entries on the device.";
      }
    }
  }
  augment "/ncs:devices/ncs:device/ncs:notifications/ncs:received-notifications/ncs:notification/ncs:data" {
    container v6-relay-table-threshold-resume {
      presence "";
      config false;
      description
        "The number of DHCPv6 relay entries on the device falls below 70% of the upper limit.";
      leaf current-number {
        type uint32;
        description
          "Number of DHCPv6 relay entries on the device.";
      }
      leaf max-number {
        type uint32;
        description
          "Maximum number of DHCPv6 relay entries on the device.";
      }
    }
  }
  augment "/ncs:devices/ncs:device/ncs:notifications/ncs:received-notifications/ncs:notification/ncs:data" {
    container v6-relay-table-threshold {
      presence "";
      config false;
      description
        "The number of DHCPv6 relay entries on the device exceeds 80% of the upper limit.";
      leaf current-number {
        type uint32;
        description
          "Number of DHCPv6 relay entries on the device.";
      }
      leaf max-number {
        type uint32;
        description
          "Maximum number of DHCPv6 relay entries on the device.";
      }
    }
  }
  augment "/ncs:devices/ncs:device/ncs:notifications/ncs:received-notifications/ncs:notification/ncs:data" {
    container snooping-binding-table-exhaust-resume {
      presence "";
      config false;
      description
        "The number of DHCP snooping entries on the device falls below 90% of the upper limit.";
      leaf max-number {
        type uint32;
        description
          "Maximum number of DHCP snooping entries on the device.";
      }
    }
  }
  augment "/ncs:devices/ncs:device/ncs:notifications/ncs:received-notifications/ncs:notification/ncs:data" {
    container snooping-binding-table-exhaust {
      presence "";
      config false;
      description
        "The number of DHCP snooping entries on the device reaches the upper limit.";
      leaf max-number {
        type uint32;
        description
          "Maximum number of DHCP snooping entries on the device.";
      }
    }
  }
  augment "/ncs:devices/ncs:device/ncs:notifications/ncs:received-notifications/ncs:notification/ncs:data" {
    container snooping-binding-table-threshold-resume {
      presence "";
      config false;
      description
        "The number of DHCP snooping entries on the device falls below 70% of the upper limit.";
      leaf current-number {
        type uint32;
        description
          "Number of DHCP snooping entries on the device.";
      }
      leaf max-number {
        type uint32;
        description
          "Maximum number of DHCP snooping entries on the device.";
      }
    }
  }
  augment "/ncs:devices/ncs:device/ncs:notifications/ncs:received-notifications/ncs:notification/ncs:data" {
    container snooping-binding-table-threshold {
      presence "";
      config false;
      description
        "The number of DHCP snooping entries on the device exceeds 80% of the upper limit.";
      leaf current-number {
        type uint32;
        description
          "Number of DHCP snooping entries on the device.";
      }
      leaf max-number {
        type uint32;
        description
          "Maximum number of DHCP snooping entries on the device.";
      }
    }
  }
  augment "/ncs:devices/ncs:device/ncs:notifications/ncs:received-notifications/ncs:notification/ncs:data" {
    container relay-ip-unnumbered-table-exhaust-resume {
      presence "";
      config false;
      description
        "The number of DHCP relay IP unnumbered entries on the device falls below 90% of the upper limit.";
      leaf max-number {
        type uint32;
        description
          "Maximum number of DHCP relay IP unnumbered entries on the device.";
      }
    }
  }
  augment "/ncs:devices/ncs:device/ncs:notifications/ncs:received-notifications/ncs:notification/ncs:data" {
    container relay-ip-unnumbered-table-exhaust {
      presence "";
      config false;
      description
        "The number of DHCP relay IP unnumbered entries on the device reaches the upper limit.";
      leaf max-number {
        type uint32;
        description
          "Maximum number of DHCP relay IP unnumbered entries on the device.";
      }
    }
  }
  augment "/ncs:devices/ncs:device/ncs:notifications/ncs:received-notifications/ncs:notification/ncs:data" {
    container relay-ip-unnumbered-table-threshold-resume {
      presence "";
      config false;
      description
        "The number of DHCP relay IP unnumbered entries on the device falls below 70% of the upper limit.";
      leaf current-number {
        type uint32;
        description
          "Number of DHCP relay IP unnumbered entries on the device.";
      }
      leaf max-number {
        type uint32;
        description
          "Maximum number of DHCP relay IP unnumbered entries on the device.";
      }
    }
  }
  augment "/ncs:devices/ncs:device/ncs:notifications/ncs:received-notifications/ncs:notification/ncs:data" {
    container relay-ip-unnumbered-table-threshold {
      presence "";
      config false;
      description
        "The number of DHCP relay IP unnumbered entries on the device exceeds 80% of the upper limit.";
      leaf current-number {
        type uint32;
        description
          "Number of DHCP relay IP unnumbered entries on the device.";
      }
      leaf max-number {
        type uint32;
        description
          "Maximum number of DHCP relay IP unnumbered entries on the device.";
      }
    }
  }
  augment "/ncs:devices/ncs:device/ncs:netconf-notifications/ncs:received-notifications/ncs:notification/ncs:data" {
    container v6-relay-ip-table-exhaust-resume {
      presence "";
      config false;
      description
        "The number of DHCPv6 relay IP entries on the device falls below 90% of the upper limit.";
      leaf max-number {
        type uint32;
        description
          "Maximum number of DHCPv6 relay IP entries on the device.";
      }
    }
  }
  augment "/ncs:devices/ncs:device/ncs:netconf-notifications/ncs:received-notifications/ncs:notification/ncs:data" {
    container v6-relay-ip-table-exhaust {
      presence "";
      config false;
      description
        "The number of DHCPv6 relay IP entries on the device reaches the upper limit.";
      leaf max-number {
        type uint32;
        description
          "Maximum number of DHCPv6 relay IP entries on the device.";
      }
    }
  }
  augment "/ncs:devices/ncs:device/ncs:netconf-notifications/ncs:received-notifications/ncs:notification/ncs:data" {
    container v6-relay-ip-table-threshold-resume {
      presence "";
      config false;
      description
        "The number of DHCPv6 relay IP entries on the device falls below 70% of the upper limit.";
      leaf current-number {
        type uint32;
        description
          "Number of DHCPv6 relay IP entries on the device.";
      }
      leaf max-number {
        type uint32;
        description
          "Maximum number of DHCPv6 relay IP entries on the device.";
      }
    }
  }
  augment "/ncs:devices/ncs:device/ncs:netconf-notifications/ncs:received-notifications/ncs:notification/ncs:data" {
    container v6-relay-ip-table-threshold {
      presence "";
      config false;
      description
        "The number of DHCPv6 relay IP entries on the device exceeds 80% of the upper limit.";
      leaf current-number {
        type uint32;
        description
          "Number of DHCPv6 relay IP entries on the device.";
      }
      leaf max-number {
        type uint32;
        description
          "Maximum number of DHCPv6 relay IP entries on the device.";
      }
    }
  }
  augment "/ncs:devices/ncs:device/ncs:netconf-notifications/ncs:received-notifications/ncs:notification/ncs:data" {
    container v6-relay-table-exhaust-resume {
      presence "";
      config false;
      description
        "The number of DHCPv6 relay entries on the device falls below 90% of the upper limit.";
      leaf max-number {
        type uint32;
        description
          "Maximum number of DHCPv6 relay entries on the device.";
      }
    }
  }
  augment "/ncs:devices/ncs:device/ncs:netconf-notifications/ncs:received-notifications/ncs:notification/ncs:data" {
    container v6-relay-table-exhaust {
      presence "";
      config false;
      description
        "The number of DHCPv6 relay entries on the device reaches the upper limit.";
      leaf max-number {
        type uint32;
        description
          "Maximum number of DHCPv6 relay entries on the device.";
      }
    }
  }
  augment "/ncs:devices/ncs:device/ncs:netconf-notifications/ncs:received-notifications/ncs:notification/ncs:data" {
    container v6-relay-table-threshold-resume {
      presence "";
      config false;
      description
        "The number of DHCPv6 relay entries on the device falls below 70% of the upper limit.";
      leaf current-number {
        type uint32;
        description
          "Number of DHCPv6 relay entries on the device.";
      }
      leaf max-number {
        type uint32;
        description
          "Maximum number of DHCPv6 relay entries on the device.";
      }
    }
  }
  augment "/ncs:devices/ncs:device/ncs:netconf-notifications/ncs:received-notifications/ncs:notification/ncs:data" {
    container v6-relay-table-threshold {
      presence "";
      config false;
      description
        "The number of DHCPv6 relay entries on the device exceeds 80% of the upper limit.";
      leaf current-number {
        type uint32;
        description
          "Number of DHCPv6 relay entries on the device.";
      }
      leaf max-number {
        type uint32;
        description
          "Maximum number of DHCPv6 relay entries on the device.";
      }
    }
  }
  augment "/ncs:devices/ncs:device/ncs:netconf-notifications/ncs:received-notifications/ncs:notification/ncs:data" {
    container snooping-binding-table-exhaust-resume {
      presence "";
      config false;
      description
        "The number of DHCP snooping entries on the device falls below 90% of the upper limit.";
      leaf max-number {
        type uint32;
        description
          "Maximum number of DHCP snooping entries on the device.";
      }
    }
  }
  augment "/ncs:devices/ncs:device/ncs:netconf-notifications/ncs:received-notifications/ncs:notification/ncs:data" {
    container snooping-binding-table-exhaust {
      presence "";
      config false;
      description
        "The number of DHCP snooping entries on the device reaches the upper limit.";
      leaf max-number {
        type uint32;
        description
          "Maximum number of DHCP snooping entries on the device.";
      }
    }
  }
  augment "/ncs:devices/ncs:device/ncs:netconf-notifications/ncs:received-notifications/ncs:notification/ncs:data" {
    container snooping-binding-table-threshold-resume {
      presence "";
      config false;
      description
        "The number of DHCP snooping entries on the device falls below 70% of the upper limit.";
      leaf current-number {
        type uint32;
        description
          "Number of DHCP snooping entries on the device.";
      }
      leaf max-number {
        type uint32;
        description
          "Maximum number of DHCP snooping entries on the device.";
      }
    }
  }
  augment "/ncs:devices/ncs:device/ncs:netconf-notifications/ncs:received-notifications/ncs:notification/ncs:data" {
    container snooping-binding-table-threshold {
      presence "";
      config false;
      description
        "The number of DHCP snooping entries on the device exceeds 80% of the upper limit.";
      leaf current-number {
        type uint32;
        description
          "Number of DHCP snooping entries on the device.";
      }
      leaf max-number {
        type uint32;
        description
          "Maximum number of DHCP snooping entries on the device.";
      }
    }
  }
  augment "/ncs:devices/ncs:device/ncs:netconf-notifications/ncs:received-notifications/ncs:notification/ncs:data" {
    container relay-ip-unnumbered-table-exhaust-resume {
      presence "";
      config false;
      description
        "The number of DHCP relay IP unnumbered entries on the device falls below 90% of the upper limit.";
      leaf max-number {
        type uint32;
        description
          "Maximum number of DHCP relay IP unnumbered entries on the device.";
      }
    }
  }
  augment "/ncs:devices/ncs:device/ncs:netconf-notifications/ncs:received-notifications/ncs:notification/ncs:data" {
    container relay-ip-unnumbered-table-exhaust {
      presence "";
      config false;
      description
        "The number of DHCP relay IP unnumbered entries on the device reaches the upper limit.";
      leaf max-number {
        type uint32;
        description
          "Maximum number of DHCP relay IP unnumbered entries on the device.";
      }
    }
  }
  augment "/ncs:devices/ncs:device/ncs:netconf-notifications/ncs:received-notifications/ncs:notification/ncs:data" {
    container relay-ip-unnumbered-table-threshold-resume {
      presence "";
      config false;
      description
        "The number of DHCP relay IP unnumbered entries on the device falls below 70% of the upper limit.";
      leaf current-number {
        type uint32;
        description
          "Number of DHCP relay IP unnumbered entries on the device.";
      }
      leaf max-number {
        type uint32;
        description
          "Maximum number of DHCP relay IP unnumbered entries on the device.";
      }
    }
  }
  augment "/ncs:devices/ncs:device/ncs:netconf-notifications/ncs:received-notifications/ncs:notification/ncs:data" {
    container relay-ip-unnumbered-table-threshold {
      presence "";
      config false;
      description
        "The number of DHCP relay IP unnumbered entries on the device exceeds 80% of the upper limit.";
      leaf current-number {
        type uint32;
        description
          "Number of DHCP relay IP unnumbered entries on the device.";
      }
      leaf max-number {
        type uint32;
        description
          "Maximum number of DHCP relay IP unnumbered entries on the device.";
      }
    }
  }
}
