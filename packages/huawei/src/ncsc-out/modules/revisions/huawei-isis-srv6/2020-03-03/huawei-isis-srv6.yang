module huawei-isis-srv6 {
  // Generated by yanger -t ncs
  tailf:mount-id "huawei-nc-1.0:huawei-nc-1.0";
  tailf:ncs-device-type "netconf";

  namespace "urn:huawei:yang:huawei-isis-srv6";
  prefix isis-srv6;

  import huawei-network-instance {
    prefix ni;
  }
  import huawei-isis {
    prefix isis;
  }
  import huawei-srv6 {
    prefix srv6;
  }
  import huawei-extension {
    prefix ext;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "ISIS segment routing IPv6 management.";

  revision 2020-03-03 {
    description
      "Modify the description.";
    reference "Huawei private.";
  }
  revision 2020-02-04 {
    description
      "Modify the description.";
    reference "Huawei private.";
  }
  revision 2019-04-04 {
    description
      "Initial revision.";
    reference "Huawei private.";
  }
  ext:task-name "isis";

  augment "/ncs:devices/ncs:template/ncs:ned-id/ncs:config/ni:network-instance/ni:instances/ni:instance/isis:isis/isis:sites/isis:site/isis:afs/isis:af" {
    description
      "ISIS segment routing IPv6 augment to ISIS.";
    container srv6 {
      // NCS drop when statement
      description
        "Configure ISIS segment routing IPv6.";
      container locators {
        description
          "List of segment routing IPv6 locator.";
        list locator {
          // NCS patched for predictable order
          ordered-by user;
          key "locator-name";
          description
            "Configure segment routing IPv6 locator.";
          leaf locator-name {
            type string;
            description
              "Enable ISIS segment routing IPv6 with specified Locator.";
          }
          leaf auto-sid {
            type string;
            // NCS drop default statement
            description
              "Enable/disable automatic application for SID.";
          }
        }
      }
      container avoid-microloop {
        // NCS drop when statement
        description
          "Configure IPv6 segment routing avoid microloop.";
        leaf enable {
          type string;
          // NCS drop default statement
          description
            "Enable/disable IPv6 segment routing avoid microloop.";
        }
        leaf delay-value {
          type string;
          // NCS drop default statement
          description
            "Set the route delivery delay for IPv6 segment routing avoid microloop.";
        }
      }
      container inter-level-protect {
        // NCS drop when statement
        description
          "Configure Inter-Level-Protect.";
        leaf enable-level1 {
          type string;
          // NCS drop default statement
          description
            "Enable/disable Level 1 Inter-Level-Protect.";
        }
        leaf preferred {
          type string;
          // NCS drop must statement
          // NCS drop default statement
          description
            "Enable/disable Inter-Level-Protect Preferred.";
        }
      }
    }
  }
  augment "/ncs:devices/ncs:device/ncs:live-status/ni:network-instance/ni:instances/ni:instance/isis:isis/isis:sites/isis:site/isis:afs/isis:af" {
    description
      "ISIS segment routing IPv6 augment to ISIS.";
    container srv6 {
      tailf:ncs-device-type "netconf";
      tailf:display-when "not(../../../../../../../../../../ncs:module) or ../../../../../../../../../../ncs:module[ncs:name='huawei-isis-srv6'] or (../../../../../../../../../../ncs:live-status-protocol[not(ncs:capability)]) or (../../../../../../../../../../ncs:live-status-protocol/ncs:capability/ncs:module[.='huawei-isis-srv6'])";
      // NCS drop when statement
      description
        "Configure ISIS segment routing IPv6.";
      container locators {
        description
          "List of segment routing IPv6 locator.";
        list locator {
          key "locator-name";
          description
            "Configure segment routing IPv6 locator.";
          leaf locator-name {
            type leafref {
              path "/ncs:devices/ncs:device/ncs:live-status/ni:network-instance/ni:instances/ni:instance/srv6:srv6/srv6:locators/srv6:locator/srv6:name" {
                tailf:xpath-root 3;
              }
            }
            description
              "Enable ISIS segment routing IPv6 with specified Locator.";
          }
          leaf auto-sid {
            type boolean;
            // NCS drop default statement
            description
              "Enable/disable automatic application for SID.";
          }
        }
      }
      container avoid-microloop {
        // NCS drop when statement
        description
          "Configure IPv6 segment routing avoid microloop.";
        leaf enable {
          type boolean;
          // NCS drop default statement
          description
            "Enable/disable IPv6 segment routing avoid microloop.";
        }
        leaf delay-value {
          type uint16 {
            range "1000..60000";
          }
          // NCS drop default statement
          description
            "Set the route delivery delay for IPv6 segment routing avoid microloop.";
        }
      }
      container inter-level-protect {
        // NCS drop when statement
        description
          "Configure Inter-Level-Protect.";
        leaf enable-level1 {
          type boolean;
          // NCS drop default statement
          description
            "Enable/disable Level 1 Inter-Level-Protect.";
        }
        leaf preferred {
          type boolean;
          // NCS drop must statement
          // NCS drop default statement
          description
            "Enable/disable Inter-Level-Protect Preferred.";
        }
      }
    }
  }
  augment "/ncs:devices/ncs:device/ncs:config/ni:network-instance/ni:instances/ni:instance/isis:isis/isis:sites/isis:site/isis:afs/isis:af" {
    description
      "ISIS segment routing IPv6 augment to ISIS.";
    container srv6 {
      tailf:ncs-device-type "netconf";
      tailf:display-when "not(../../../../../../../../../../ncs:module) or ../../../../../../../../../../ncs:module[ncs:name='huawei-isis-srv6']";
      when "../../../../../../ni:name='_public_' and ../isis:type='afipv6' and (../../../isis:cost-style='wide' or ../../../isis:cost-style='transition'  or ../../../isis:cost-style='wtransition')" {
        tailf:xpath-root 3;
      }
      description
        "Configure ISIS segment routing IPv6.";
      container locators {
        description
          "List of segment routing IPv6 locator.";
        list locator {
          key "locator-name";
          description
            "Configure segment routing IPv6 locator.";
          leaf locator-name {
            type leafref {
              path "/ncs:devices/ncs:device/ncs:config/ni:network-instance/ni:instances/ni:instance/srv6:srv6/srv6:locators/srv6:locator/srv6:name" {
                tailf:xpath-root 3;
              }
            }
            description
              "Enable ISIS segment routing IPv6 with specified Locator.";
          }
          leaf auto-sid {
            type boolean;
            default "true";
            description
              "Enable/disable automatic application for SID.";
          }
        }
      }
      container avoid-microloop {
        when '../locators/locator' {
          tailf:xpath-root 3;
        }
        description
          "Configure IPv6 segment routing avoid microloop.";
        leaf enable {
          type boolean;
          default "false";
          description
            "Enable/disable IPv6 segment routing avoid microloop.";
        }
        leaf delay-value {
          type uint16 {
            range "1000..60000";
          }
          default "5000";
          description
            "Set the route delivery delay for IPv6 segment routing avoid microloop.";
        }
      }
      container inter-level-protect {
        when "../../isis:frr/isis:enable='true' and ../locators/locator" {
          tailf:xpath-root 3;
        }
        description
          "Configure Inter-Level-Protect.";
        leaf enable-level1 {
          type boolean;
          default "false";
          description
            "Enable/disable Level 1 Inter-Level-Protect.";
        }
        leaf preferred {
          type boolean;
          must "../enable-level1='true' or ../preferred='false'" {
            tailf:xpath-root 3;
          }
          default "false";
          description
            "Enable/disable Inter-Level-Protect Preferred.";
        }
      }
    }
  }
}
