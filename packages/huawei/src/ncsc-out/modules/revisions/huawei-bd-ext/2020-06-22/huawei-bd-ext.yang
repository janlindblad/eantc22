module huawei-bd-ext {
  // Generated by yanger -t ncs
  tailf:mount-id "huawei-nc-1.0:huawei-nc-1.0";
  tailf:ncs-device-type "netconf";

  namespace "urn:huawei:yang:huawei-bd-ext";
  prefix bd-ext;

  import huawei-bd {
    prefix bd;
  }
  import huawei-qos {
    prefix qos;
  }
  import huawei-extension {
    prefix ext;
  }
  import huawei-ifm {
    prefix ifm;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "BD ext.";

  revision 2020-06-22 {
    description
      "Add reset-bd-ac-suppression-statistics.";
    reference "Huawei private.";
  }
  revision 2020-03-06 {
    description
      "Add pipe type.";
    reference "Huawei private.";
  }
  revision 2020-01-13 {
    description
      "Modify description.";
    reference "Huawei private.";
  }
  revision 2019-04-23 {
    description
      "Initial revision.";
    reference "Huawei private.";
  }
  ext:task-name "forwarding";

  typedef ncs_template_bd-pipe-mode {
    type string;
    description
      "BD pipe mode.";
  }

  typedef ncs_template_bd-service-class {
    type string;
    description
      "Description of CoS.";
  }

  typedef ncs_template_bd-color {
    type string;
    description
      "Description of packet color.";
  }

  typedef ncs_template_bd-trust-type {
    type string;
    description
      "Description of trust type.";
  }

  typedef ncs_rpc_notif_bd-pipe-mode {
    type enumeration {
      enum "pipe" {
        value 1;
        description
          "BD pipe mode.";
      }
      enum "shortpipe" {
        value 2;
        description
          "BD short pipe mode.";
      }
      enum "uniform" {
        value 3;
        description
          "BD uniform mode.";
      }
    }
    description
      "BD pipe mode.";
  }

  typedef ncs_rpc_notif_bd-service-class {
    type enumeration {
      enum "be" {
        value 0;
        description
          "Specify the CoS as BE.";
      }
      enum "af1" {
        value 1;
        description
          "Specify the CoS as AF1.";
      }
      enum "af2" {
        value 2;
        description
          "Specify the CoS as AF2.";
      }
      enum "af3" {
        value 3;
        description
          "Specify the CoS as AF3.";
      }
      enum "af4" {
        value 4;
        description
          "Specify the CoS as AF4.";
      }
      enum "ef" {
        value 5;
        description
          "Specify the CoS as EF.";
      }
      enum "cs6" {
        value 6;
        description
          "Specify the CoS as CS6.";
      }
      enum "cs7" {
        value 7;
        description
          "Specify the CoS as CS7.";
      }
    }
    description
      "Description of CoS.";
  }

  typedef ncs_rpc_notif_bd-color {
    type enumeration {
      enum "green" {
        value 0;
        description
          "Specify the packet color as green.";
      }
      enum "yellow" {
        value 1;
        description
          "Specify the packet color as yellow.";
      }
      enum "red" {
        value 2;
        description
          "Specify the packet color as red.";
      }
    }
    description
      "Description of packet color.";
  }

  typedef ncs_rpc_notif_bd-trust-type {
    type enumeration {
      enum "outpri" {
        value 0;
        description
          "Specify the trust type as OUTTER-VLAN-8021P.";
      }
      enum "inpri" {
        value 1;
        description
          "Specify the trust type as INNER-VLAN-8021P.";
      }
      enum "ipdscp" {
        value 2;
        description
          "Specify the trust type as IP-DSCP.";
      }
    }
    description
      "Description of trust type.";
  }

  typedef live_ncs_bd-pipe-mode {
    type enumeration {
      enum "pipe" {
        value 1;
        description
          "BD pipe mode.";
      }
      enum "shortpipe" {
        value 2;
        description
          "BD short pipe mode.";
      }
      enum "uniform" {
        value 3;
        description
          "BD uniform mode.";
      }
    }
    description
      "BD pipe mode.";
  }

  typedef live_ncs_bd-service-class {
    type enumeration {
      enum "be" {
        value 0;
        description
          "Specify the CoS as BE.";
      }
      enum "af1" {
        value 1;
        description
          "Specify the CoS as AF1.";
      }
      enum "af2" {
        value 2;
        description
          "Specify the CoS as AF2.";
      }
      enum "af3" {
        value 3;
        description
          "Specify the CoS as AF3.";
      }
      enum "af4" {
        value 4;
        description
          "Specify the CoS as AF4.";
      }
      enum "ef" {
        value 5;
        description
          "Specify the CoS as EF.";
      }
      enum "cs6" {
        value 6;
        description
          "Specify the CoS as CS6.";
      }
      enum "cs7" {
        value 7;
        description
          "Specify the CoS as CS7.";
      }
    }
    description
      "Description of CoS.";
  }

  typedef live_ncs_bd-color {
    type enumeration {
      enum "green" {
        value 0;
        description
          "Specify the packet color as green.";
      }
      enum "yellow" {
        value 1;
        description
          "Specify the packet color as yellow.";
      }
      enum "red" {
        value 2;
        description
          "Specify the packet color as red.";
      }
    }
    description
      "Description of packet color.";
  }

  typedef live_ncs_bd-trust-type {
    type enumeration {
      enum "outpri" {
        value 0;
        description
          "Specify the trust type as OUTTER-VLAN-8021P.";
      }
      enum "inpri" {
        value 1;
        description
          "Specify the trust type as INNER-VLAN-8021P.";
      }
      enum "ipdscp" {
        value 2;
        description
          "Specify the trust type as IP-DSCP.";
      }
    }
    description
      "Description of trust type.";
  }

  typedef bd-pipe-mode {
    type enumeration {
      enum "pipe" {
        value 1;
        description
          "BD pipe mode.";
      }
      enum "shortpipe" {
        value 2;
        description
          "BD short pipe mode.";
      }
      enum "uniform" {
        value 3;
        description
          "BD uniform mode.";
      }
    }
    description
      "BD pipe mode.";
  }

  typedef bd-service-class {
    type enumeration {
      enum "be" {
        value 0;
        description
          "Specify the CoS as BE.";
      }
      enum "af1" {
        value 1;
        description
          "Specify the CoS as AF1.";
      }
      enum "af2" {
        value 2;
        description
          "Specify the CoS as AF2.";
      }
      enum "af3" {
        value 3;
        description
          "Specify the CoS as AF3.";
      }
      enum "af4" {
        value 4;
        description
          "Specify the CoS as AF4.";
      }
      enum "ef" {
        value 5;
        description
          "Specify the CoS as EF.";
      }
      enum "cs6" {
        value 6;
        description
          "Specify the CoS as CS6.";
      }
      enum "cs7" {
        value 7;
        description
          "Specify the CoS as CS7.";
      }
    }
    description
      "Description of CoS.";
  }

  typedef bd-color {
    type enumeration {
      enum "green" {
        value 0;
        description
          "Specify the packet color as green.";
      }
      enum "yellow" {
        value 1;
        description
          "Specify the packet color as yellow.";
      }
      enum "red" {
        value 2;
        description
          "Specify the packet color as red.";
      }
    }
    description
      "Description of packet color.";
  }

  typedef bd-trust-type {
    type enumeration {
      enum "outpri" {
        value 0;
        description
          "Specify the trust type as OUTTER-VLAN-8021P.";
      }
      enum "inpri" {
        value 1;
        description
          "Specify the trust type as INNER-VLAN-8021P.";
      }
      enum "ipdscp" {
        value 2;
        description
          "Specify the trust type as IP-DSCP.";
      }
    }
    description
      "Description of trust type.";
  }

  augment "/ncs:devices/ncs:device/ncs:rpc" {
    container rpc-reset-bd-ac-suppression-statistics {
      tailf:ncs-device-type "netconf";
      tailf:display-when "not(../../ncs:module) or ../../ncs:module[ncs:name='huawei-bd-ext']";
      tailf:action reset-bd-ac-suppression-statistics {
        tailf:actionpoint ncsproxy {
          tailf:internal;
        }
        description
          "Reset AC suppression.";
        ext:node-ref "/bd:bd/bd:instances/bd:instance/bd:service-points/bd:service-point";
        input {
          leaf interface-name {
            type string;
            mandatory true;
            description
              "Interface name.";
          }
          leaf bd-id {
            type uint32 {
              range "1..16777215";
            }
            mandatory true;
            description
              "BD ID.";
          }
        }
      }
    }
  }
  augment "/ncs:devices/ncs:device-group/ncs:ned-id/ncs:rpc" {
    container rpc-reset-bd-ac-suppression-statistics {
      tailf:ncs-device-type "netconf";
      tailf:display-when "/ncs:devices/ncs:device[ncs:name=current()/../../../ncs:member]/ncs:module[ncs:name='huawei-bd-ext']";
      tailf:action reset-bd-ac-suppression-statistics {
        tailf:actionpoint ncsproxy {
          tailf:internal;
        }
        description
          "Reset AC suppression.";
        ext:node-ref "/bd:bd/bd:instances/bd:instance/bd:service-points/bd:service-point";
        input {
          leaf interface-name {
            type string;
            mandatory true;
            description
              "Interface name.";
          }
          leaf bd-id {
            type uint32 {
              range "1..16777215";
            }
            mandatory true;
            description
              "BD ID.";
          }
        }
      }
    }
  }
  augment "/ncs:devices/ncs:template/ncs:ned-id/ncs:config/bd:bd/bd:instances/bd:instance" {
    description
      "BD configuration.";
    container pipe {
      description
        "Configure the diffserv mode of bridge domain.";
      leaf split-mode {
        type string;
        // NCS drop must statement
        // NCS drop default statement
        description
          "Enable/disable split mode.";
      }
      leaf pipe-mode {
        // NCS drop when statement
        type ncs_template_bd-pipe-mode;
        // NCS drop must statement
        // NCS drop default statement
        description
          "Pipe mode.";
      }
      leaf ingress-pipe-mode {
        // NCS drop when statement
        type ncs_template_bd-pipe-mode;
        // NCS drop must statement
        // NCS drop default statement
        description
          "Ingress pipe mode.";
      }
      leaf egress-pipe-mode {
        // NCS drop when statement
        type ncs_template_bd-pipe-mode;
        // NCS drop must statement
        // NCS drop default statement
        description
          "Egress pipe mode.";
      }
      leaf service-class {
        // NCS drop when statement
        type ncs_template_bd-service-class;
        // NCS drop must statement
        // NCS drop default statement
        description
          "Service class.";
      }
      leaf color {
        // NCS drop when statement
        type ncs_template_bd-color;
        // NCS drop must statement
        // NCS drop default statement
        description
          "Color.";
      }
      leaf domain-name {
        // NCS drop when statement
        type string;
        // NCS drop must statement
        // NCS drop default statement
        description
          "Domain name.";
      }
      leaf trust-type {
        // NCS drop when statement
        type ncs_template_bd-trust-type;
        // NCS drop must statement
        // NCS drop default statement
        description
          "Trust type.";
      }
    }
    container reserve-if-switch {
      description
        "Configure BD broadcast fast switching.";
      leaf enable {
        type string;
        // NCS drop default statement
        description
          "Enable/disable the flag of BD broadcast fast switching.";
      }
    }
  }
  augment "/ncs:devices/ncs:device/ncs:live-status/bd:bd/bd:instances/bd:instance" {
    description
      "BD configuration.";
    container pipe {
      tailf:ncs-device-type "netconf";
      tailf:display-when "not(../../../../../ncs:module) or ../../../../../ncs:module[ncs:name='huawei-bd-ext'] or (../../../../../ncs:live-status-protocol[not(ncs:capability)]) or (../../../../../ncs:live-status-protocol/ncs:capability/ncs:module[.='huawei-bd-ext'])";
      description
        "Configure the diffserv mode of bridge domain.";
      leaf split-mode {
        type boolean;
        // NCS drop must statement
        // NCS drop default statement
        description
          "Enable/disable split mode.";
      }
      leaf pipe-mode {
        // NCS drop when statement
        type live_ncs_bd-pipe-mode;
        // NCS drop must statement
        // NCS drop default statement
        description
          "Pipe mode.";
      }
      leaf ingress-pipe-mode {
        // NCS drop when statement
        type live_ncs_bd-pipe-mode;
        // NCS drop must statement
        // NCS drop default statement
        description
          "Ingress pipe mode.";
      }
      leaf egress-pipe-mode {
        // NCS drop when statement
        type live_ncs_bd-pipe-mode;
        // NCS drop must statement
        // NCS drop default statement
        description
          "Egress pipe mode.";
      }
      leaf service-class {
        // NCS drop when statement
        type live_ncs_bd-service-class;
        // NCS drop must statement
        // NCS drop default statement
        description
          "Service class.";
      }
      leaf color {
        // NCS drop when statement
        type live_ncs_bd-color;
        // NCS drop must statement
        // NCS drop default statement
        description
          "Color.";
      }
      leaf domain-name {
        // NCS drop when statement
        type leafref {
          path "/ncs:devices/ncs:device/ncs:live-status/qos:qos/qos:classifier-template/qos:diffserv-domains/qos:diffserv-domain/qos:name" {
            tailf:xpath-root 3;
          }
        }
        // NCS drop must statement
        // NCS drop default statement
        description
          "Domain name.";
      }
      leaf trust-type {
        // NCS drop when statement
        type live_ncs_bd-trust-type;
        // NCS drop must statement
        // NCS drop default statement
        description
          "Trust type.";
      }
    }
    container reserve-if-switch {
      tailf:ncs-device-type "netconf";
      tailf:display-when "not(../../../../../ncs:module) or ../../../../../ncs:module[ncs:name='huawei-bd-ext'] or (../../../../../ncs:live-status-protocol[not(ncs:capability)]) or (../../../../../ncs:live-status-protocol/ncs:capability/ncs:module[.='huawei-bd-ext'])";
      description
        "Configure BD broadcast fast switching.";
      leaf enable {
        type boolean;
        // NCS drop default statement
        description
          "Enable/disable the flag of BD broadcast fast switching.";
      }
    }
  }
  augment "/ncs:devices/ncs:device/ncs:config/bd:bd/bd:instances/bd:instance" {
    description
      "BD configuration.";
    container pipe {
      tailf:ncs-device-type "netconf";
      tailf:display-when "not(../../../../../ncs:module) or ../../../../../ncs:module[ncs:name='huawei-bd-ext']";
      description
        "Configure the diffserv mode of bridge domain.";
      leaf split-mode {
        type boolean;
        must "((../split-mode='false' and not(../ingress-pipe-mode) and not(../egress-pipe-mode) and ../pipe-mode) or (../split-mode='true' and not(../pipe-mode) and ../ingress-pipe-mode and ../egress-pipe-mode and not(../ingress-pipe-mode='uniform' and ../egress-pipe-mode='uniform')))" {
          tailf:xpath-root 3;
        }
        default "false";
        description
          "Enable/disable split mode.";
      }
      leaf pipe-mode {
        when "../split-mode='false'" {
          tailf:xpath-root 3;
        }
        type bd-pipe-mode;
        must "(../split-mode='false') and ((../pipe-mode='pipe' and (../service-class) and (../color)) or (../pipe-mode='shortpipe' and (../service-class) and (../color) and (../domain-name)) or (../pipe-mode='uniform'))" {
          tailf:xpath-root 3;
        }
        default "uniform";
        description
          "Pipe mode.";
      }
      leaf ingress-pipe-mode {
        when "../split-mode='true'" {
          tailf:xpath-root 3;
        }
        type bd-pipe-mode;
        must "((../split-mode='true') and (((../service-class) and (../color) and (../ingress-pipe-mode='shortpipe' or ../ingress-pipe-mode='pipe')) or (../ingress-pipe-mode='uniform' and ../egress-pipe-mode!='uniform')))" {
          tailf:xpath-root 3;
        }
        default "uniform";
        description
          "Ingress pipe mode.";
      }
      leaf egress-pipe-mode {
        when "../split-mode='true'" {
          tailf:xpath-root 3;
        }
        type bd-pipe-mode;
        must "((../split-mode='true') and (((../domain-name) and (../trust-type) and (../egress-pipe-mode='shortpipe')) or (../egress-pipe-mode='pipe') or (../egress-pipe-mode='uniform' and ../ingress-pipe-mode!='uniform')))" {
          tailf:xpath-root 3;
        }
        default "uniform";
        description
          "Egress pipe mode.";
      }
      leaf service-class {
        when "(../pipe-mode='pipe' or ../pipe-mode='shortpipe' or ../ingress-pipe-mode='pipe' or ../ingress-pipe-mode='shortpipe')" {
          tailf:xpath-root 3;
        }
        type bd-service-class;
        must "(../pipe-mode='pipe' or ../pipe-mode='shortpipe' or ../ingress-pipe-mode='pipe' or ../ingress-pipe-mode='shortpipe')" {
          tailf:xpath-root 3;
        }
        default "be";
        description
          "Service class.";
      }
      leaf color {
        when "(../pipe-mode='pipe' or ../pipe-mode='shortpipe'  or ../ingress-pipe-mode='pipe' or ../ingress-pipe-mode='shortpipe')" {
          tailf:xpath-root 3;
        }
        type bd-color;
        must "(../pipe-mode='pipe' or ../pipe-mode='shortpipe' or ../ingress-pipe-mode='pipe' or ../ingress-pipe-mode='shortpipe')" {
          tailf:xpath-root 3;
        }
        default "green";
        description
          "Color.";
      }
      leaf domain-name {
        when "(../pipe-mode='shortpipe'  or ../egress-pipe-mode='shortpipe')" {
          tailf:xpath-root 3;
        }
        type leafref {
          path "/ncs:devices/ncs:device/ncs:config/qos:qos/qos:classifier-template/qos:diffserv-domains/qos:diffserv-domain/qos:name" {
            tailf:xpath-root 3;
          }
        }
        must "(../pipe-mode='shortpipe' or ../egress-pipe-mode='shortpipe')" {
          tailf:xpath-root 3;
        }
        default "default";
        description
          "Domain name.";
      }
      leaf trust-type {
        when "../egress-pipe-mode='shortpipe'" {
          tailf:xpath-root 3;
        }
        type bd-trust-type;
        must "../egress-pipe-mode='shortpipe'" {
          tailf:xpath-root 3;
        }
        default "outpri";
        description
          "Trust type.";
      }
    }
    container reserve-if-switch {
      tailf:ncs-device-type "netconf";
      tailf:display-when "not(../../../../../ncs:module) or ../../../../../ncs:module[ncs:name='huawei-bd-ext']";
      description
        "Configure BD broadcast fast switching.";
      leaf enable {
        type boolean;
        default "false";
        description
          "Enable/disable the flag of BD broadcast fast switching.";
      }
    }
  }
  augment "/ncs:devices/ncs:template/ncs:ned-id/ncs:config/bd:bd/bd:instances/bd:instance/bd:service-points/bd:service-point" {
    description
      "EVC service configuration.";
    // NCS drop config false container 'ac-suppression'
  }
  augment "/ncs:devices/ncs:device/ncs:live-status/bd:bd/bd:instances/bd:instance/bd:service-points/bd:service-point" {
    description
      "EVC service configuration.";
    container ac-suppression {
      tailf:ncs-device-type "netconf";
      tailf:display-when "not(../../../../../../../ncs:module) or ../../../../../../../ncs:module[ncs:name='huawei-bd-ext'] or (../../../../../../../ncs:live-status-protocol[not(ncs:capability)]) or (../../../../../../../ncs:live-status-protocol/ncs:capability/ncs:module[.='huawei-bd-ext'])";
      description
        "Statistics of the bridge domain AC suppression.";
      leaf time {
        type string {
          length "1..60";
        }
        description
          "AC suppression time.";
      }
      leaf unicast-inbound-flag {
        type boolean;
        // NCS drop default statement
        description
          "Unicast inbound suppression flag.";
      }
      leaf unicast-inbound-pass-packets {
        type uint64;
        description
          "Number of unknown unicast packets passed in the inbound direction of an AC interface.";
      }
      leaf unicast-inbound-pass-bytes {
        type uint64;
        description
          "Number of unknown unicast bytes passed in the inbound direction of an AC interface.";
      }
      leaf unicast-inbound-drop-packets {
        type uint64;
        description
          "Number of unknown unicast packets dropped in the inbound direction of an AC interface.";
      }
      leaf unicast-inbound-drop-bytes {
        type uint64;
        description
          "Number of unknown unicast bytes dropped in the inbound direction of an AC interface.";
      }
      leaf unicast-outbound-flag {
        type boolean;
        // NCS drop default statement
        description
          "Unicast outbound suppression flag.";
      }
      leaf unicast-outbound-pass-packets {
        type uint64;
        description
          "Number of unknown unicast packets passed in the outbound direction of an AC interface.";
      }
      leaf unicast-outbound-pass-bytes {
        type uint64;
        description
          "Number of unknown unicast bytes passed in the outbound direction of an AC interface.";
      }
      leaf unicast-outbound-drop-packets {
        type uint64;
        description
          "Number of unknown unicast packets dropped in the outbound direction of an AC interface.";
      }
      leaf unicast-outbound-drop-bytes {
        type uint64;
        description
          "Number of unknown unicast bytes dropped in the outbound direction of an AC interface.";
      }
      leaf multicast-inbound-flag {
        type boolean;
        // NCS drop default statement
        description
          "Multicast inbound suppression flag.";
      }
      leaf multicast-inbound-pass-packets {
        type uint64;
        description
          "Number of multicast packets passed in the inbound direction of an AC interface.";
      }
      leaf multicast-inbound-pass-bytes {
        type uint64;
        description
          "Number of multicast bytes passed in the inbound direction of an AC interface.";
      }
      leaf multicast-inbound-drop-packets {
        type uint64;
        description
          "Number of multicast packets dropped in the inbound direction of an AC interface.";
      }
      leaf multicast-inbound-drop-bytes {
        type uint64;
        description
          "Number of multicast bytes dropped in the inbound direction of an AC interface.";
      }
      leaf multicast-outbound-flag {
        type boolean;
        // NCS drop default statement
        description
          "Multicast outbound suppression flag.";
      }
      leaf multicast-outbound-pass-packets {
        type uint64;
        description
          "Number of multicast packets passed in the outbound direction of an AC interface.";
      }
      leaf multicast-outbound-pass-bytes {
        type uint64;
        description
          "Number of multicast bytes passed in the outbound direction of an AC interface.";
      }
      leaf multicast-outbound-drop-packets {
        type uint64;
        description
          "Number of multicast packets dropped in the outbound direction of an AC interface.";
      }
      leaf multicast-outbound-drop-bytes {
        type uint64;
        description
          "Number of multicast bytes dropped in the outbound direction of an AC interface.";
      }
      leaf broadcast-inbound-flag {
        type boolean;
        // NCS drop default statement
        description
          "Broadcast inbound suppression flag.";
      }
      leaf broadcast-inbound-pass-packets {
        type uint64;
        description
          "Number of broadcast packets passed in the inbound direction of an AC interface.";
      }
      leaf broadcast-inbound-pass-bytes {
        type uint64;
        description
          "Number of broadcast bytes passed in the inbound direction of an AC interface.";
      }
      leaf broadcast-inbound-drop-packets {
        type uint64;
        description
          "Number of broadcast packets dropped in the inbound direction of an AC interface.";
      }
      leaf broadcast-inbound-drop-bytes {
        type uint64;
        description
          "Number of broadcast bytes dropped in the inbound direction of an AC interface.";
      }
      leaf broadcast-outbound-flag {
        type boolean;
        // NCS drop default statement
        description
          "Broadcast outbound suppression flag.";
      }
      leaf broadcast-outbound-pass-packets {
        type uint64;
        description
          "Number of broadcast packets passed in the outbound direction of an AC interface.";
      }
      leaf broadcast-outbound-pass-bytes {
        type uint64;
        description
          "Number of broadcast bytes passed in the outbound direction of an AC interface.";
      }
      leaf broadcast-outbound-drop-packets {
        type uint64;
        description
          "Number of broadcast packets dropped in the outbound direction of an AC interface.";
      }
      leaf broadcast-outbound-drop-bytes {
        type uint64;
        description
          "Number of broadcast bytes dropped in the outbound direction of an AC interface.";
      }
    }
  }
  augment "/ncs:devices/ncs:device/ncs:config/bd:bd/bd:instances/bd:instance/bd:service-points/bd:service-point" {
    description
      "EVC service configuration.";
    // NCS drop config false container 'ac-suppression'
  }
}
