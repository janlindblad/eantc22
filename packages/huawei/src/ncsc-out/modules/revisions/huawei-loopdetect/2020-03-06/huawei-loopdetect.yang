module huawei-loopdetect {
  // Generated by yanger -t ncs
  tailf:mount-id "huawei-nc-1.0:huawei-nc-1.0";
  tailf:ncs-device-type "netconf";

  namespace "urn:huawei:yang:huawei-loopdetect";
  prefix loopdetect;

  import huawei-ifm {
    prefix ifm;
  }
  import huawei-extension {
    prefix ext;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Loopdetect.";

  revision 2020-03-06 {
    description
      "Change description.";
    reference "Huawei private.";
  }
  revision 2019-04-08 {
    description
      "Initial revision.";
    reference "Huawei private.";
  }
  ext:task-name "vlan";

  augment "/ncs:devices/ncs:device/ncs:config" {
    container loopdetect {
      tailf:ncs-device-type "netconf";
      tailf:display-when "not(../../ncs:module) or ../../ncs:module[ncs:name='huawei-loopdetect']";
      description
        "Loop detection.";
      container ldetect-global {
        presence "Enable global loop-detect.";
        description
          "Enable/disable global loop-detect.";
        leaf loose-identifier {
          type string {
            length "1..16";
          }
          description
            "Global loop-detect loose identifier.";
        }
      }
      container trigger-detect {
        description
          "Configure trigger detect.";
        container global {
          description
            "Configure global auto loop detection.";
          leaf enable {
            type boolean;
            default "false";
            description
              "Enable/disable global auto loop detection.";
          }
          leaf min-slot-up-time {
            type uint32 {
              range "1..100";
            }
            units "min";
            default "30";
            description
              "Min slot up time.";
          }
          leaf min-port-up-time {
            type uint32 {
              range "1..600";
            }
            units "min";
            default "10";
            description
              "Min port up time.";
          }
        }
      }
    }
  }
  augment "/ncs:devices/ncs:device/ncs:live-status" {
    container loopdetect {
      tailf:ncs-device-type "netconf";
      tailf:display-when "not(../../ncs:module) or ../../ncs:module[ncs:name='huawei-loopdetect'] or (../../ncs:live-status-protocol[not(ncs:capability)]) or (../../ncs:live-status-protocol/ncs:capability/ncs:module[.='huawei-loopdetect'])";
      description
        "Loop detection.";
      container ldetect-global {
        presence "Enable global loop-detect.";
        description
          "Enable/disable global loop-detect.";
        leaf loose-identifier {
          type string {
            length "1..16";
          }
          description
            "Global loop-detect loose identifier.";
        }
      }
      container trigger-detect {
        description
          "Configure trigger detect.";
        container global {
          description
            "Configure global auto loop detection.";
          leaf enable {
            type boolean;
            // NCS drop default statement
            description
              "Enable/disable global auto loop detection.";
          }
          leaf min-slot-up-time {
            type uint32 {
              range "1..100";
            }
            units "min";
            // NCS drop default statement
            description
              "Min slot up time.";
          }
          leaf min-port-up-time {
            type uint32 {
              range "1..600";
            }
            units "min";
            // NCS drop default statement
            description
              "Min port up time.";
          }
        }
      }
    }
  }
  augment "/ncs:devices/ncs:template/ncs:ned-id/ncs:config" {
    container loopdetect {
      description
        "Loop detection.";
      container ldetect-global {
        presence "Enable global loop-detect.";
        description
          "Enable/disable global loop-detect.";
        leaf loose-identifier {
          type string;
          description
            "Global loop-detect loose identifier.";
        }
      }
      container trigger-detect {
        description
          "Configure trigger detect.";
        container global {
          description
            "Configure global auto loop detection.";
          leaf enable {
            type string;
            // NCS drop default statement
            description
              "Enable/disable global auto loop detection.";
          }
          leaf min-slot-up-time {
            type string;
            units "min";
            // NCS drop default statement
            description
              "Min slot up time.";
          }
          leaf min-port-up-time {
            type string;
            units "min";
            // NCS drop default statement
            description
              "Min port up time.";
          }
        }
      }
    }
  }
  augment "/ncs:devices/ncs:template/ncs:ned-id/ncs:config/ifm:ifm/ifm:interfaces/ifm:interface" {
    description
      "Interface.";
    container loopdetect {
      description
        "Configure loop detection.";
      container mac-withdraw {
        presence "create loopdetect-mac-withdraw";
        description
          "Enable/disable loop-detect MAC-withdraw.";
      }
      container loopback-detect {
        presence "create  loopback-detect";
        description
          "Enable/disable loopback detect.";
        leaf block-time {
          type string;
          units "s";
          // NCS drop default statement
          description
            "Loopback detect block time.";
        }
      }
      container loop-detect {
        // NCS drop when statement
        presence "create loop-detect";
        description
          "Enable/disable loop detect instance.";
        leaf block-time-type {
          type string;
          description
            "Loop detect block time type.";
        }
        leaf block-time-value {
          // NCS drop when statement
          type string;
          units "s";
          // NCS drop mandatory statement
          description
            "Block time.";
        }
        leaf trigger-down {
          type string;
          // NCS drop default statement
          description
            "Enable/disable loop detect triggerdown.";
        }
        leaf packet-priority {
          type string;
          // NCS drop default statement
          description
            "Loop-detect protocol packet priority.";
        }
        leaf only-alarm {
          type string;
          // NCS drop default statement
          description
            "Enable/disable only send alarm with the interface block.";
        }
      }
    }
  }
  augment "/ncs:devices/ncs:device/ncs:live-status/ifm:ifm/ifm:interfaces/ifm:interface" {
    description
      "Interface.";
    container loopdetect {
      tailf:ncs-device-type "netconf";
      tailf:display-when "not(../../../../../ncs:module) or ../../../../../ncs:module[ncs:name='huawei-loopdetect'] or (../../../../../ncs:live-status-protocol[not(ncs:capability)]) or (../../../../../ncs:live-status-protocol/ncs:capability/ncs:module[.='huawei-loopdetect'])";
      description
        "Configure loop detection.";
      container mac-withdraw {
        presence "create loopdetect-mac-withdraw";
        description
          "Enable/disable loop-detect MAC-withdraw.";
      }
      container loopback-detect {
        presence "create  loopback-detect";
        description
          "Enable/disable loopback detect.";
        leaf block-time {
          type uint32 {
            range "5..1000";
          }
          units "s";
          // NCS drop default statement
          description
            "Loopback detect block time.";
        }
      }
      container loop-detect {
        // NCS drop when statement
        presence "create loop-detect";
        description
          "Enable/disable loop detect instance.";
        leaf block-time-type {
          type enumeration {
            enum "perp-block-time" {
              value 1;
              description
                "Perpetual block time.";
            }
            enum "norm-block-time" {
              value 2;
              description
                "Normal block time.";
            }
          }
          description
            "Loop detect block time type.";
        }
        leaf block-time-value {
          // NCS drop when statement
          type uint16 {
            range "1..255";
          }
          units "s";
          // NCS drop mandatory statement
          description
            "Block time.";
        }
        leaf trigger-down {
          type boolean;
          // NCS drop default statement
          description
            "Enable/disable loop detect triggerdown.";
        }
        leaf packet-priority {
          type uint32 {
            range "0..7";
          }
          // NCS drop default statement
          description
            "Loop-detect protocol packet priority.";
        }
        leaf only-alarm {
          type boolean;
          // NCS drop default statement
          description
            "Enable/disable only send alarm with the interface block.";
        }
      }
    }
  }
  augment "/ncs:devices/ncs:device/ncs:config/ifm:ifm/ifm:interfaces/ifm:interface" {
    description
      "Interface.";
    container loopdetect {
      tailf:ncs-device-type "netconf";
      tailf:display-when "not(../../../../../ncs:module) or ../../../../../ncs:module[ncs:name='huawei-loopdetect']";
      description
        "Configure loop detection.";
      container mac-withdraw {
        presence "create loopdetect-mac-withdraw";
        description
          "Enable/disable loop-detect MAC-withdraw.";
      }
      container loopback-detect {
        presence "create  loopback-detect";
        description
          "Enable/disable loopback detect.";
        leaf block-time {
          type uint32 {
            range "5..1000";
          }
          units "s";
          default "10";
          description
            "Loopback detect block time.";
        }
      }
      container loop-detect {
        when '/loopdetect:loopdetect/loopdetect:ldetect-global' {
          tailf:xpath-root 3;
        }
        presence "create loop-detect";
        description
          "Enable/disable loop detect instance.";
        leaf block-time-type {
          type enumeration {
            enum "perp-block-time" {
              value 1;
              description
                "Perpetual block time.";
            }
            enum "norm-block-time" {
              value 2;
              description
                "Normal block time.";
            }
          }
          description
            "Loop detect block time type.";
        }
        leaf block-time-value {
          when "../block-time-type='norm-block-time'" {
            tailf:xpath-root 3;
          }
          type uint16 {
            range "1..255";
          }
          units "s";
          mandatory true;
          description
            "Block time.";
        }
        leaf trigger-down {
          type boolean;
          default "false";
          description
            "Enable/disable loop detect triggerdown.";
        }
        leaf packet-priority {
          type uint32 {
            range "0..7";
          }
          default "6";
          description
            "Loop-detect protocol packet priority.";
        }
        leaf only-alarm {
          type boolean;
          default "false";
          description
            "Enable/disable only send alarm with the interface block.";
        }
      }
    }
  }
}
