module huawei-bras-said {
  // Generated by yanger -t ncs
  tailf:mount-id "huawei-nc-1.0:huawei-nc-1.0";
  tailf:ncs-device-type "netconf";

  namespace "urn:huawei:yang:huawei-bras-said";
  prefix bras-said;

  import huawei-extension {
    prefix ext;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Bras said.";

  revision 2020-03-18 {
    description
      "Modify description.";
    reference "Huawei private.";
  }
  revision 2019-04-10 {
    description
      "Initial revision.";
    reference "Huawei private.";
  }
  ext:task-name "aaa-access";

  augment "/ncs:devices/ncs:device/ncs:config" {
    container bras-said {
      tailf:ncs-device-type "netconf";
      tailf:display-when "not(../../ncs:module) or ../../ncs:module[ncs:name='huawei-bras-said']";
      description
        "Bras said.";
      container said-exclude-fail-codes {
        description
          "Configure the excluding of login failures with a specified cause code from being detected or diagnosed by SAID nodes. By default, a login failure is not excluded from the detection or diagnosis of SAID nodes.";
        leaf-list visible-code {
          type uint16 {
            range "1..741";
          }
          description
            "Configure the visible on-line failure cause type.";
        }
        leaf-list invisible-code {
          type uint16 {
            range "0..62";
          }
          description
            "Configure the sxternal invisible on-line failure cause type.";
        }
      }
      container said-parameter {
        description
          "Configure the user Access.";
        leaf increase-number-of-online-fail {
          type uint32 {
            range "100..256000";
          }
          default "10000";
          description
            "Sets the sepical increase number of online-fail.";
        }
        leaf recover-interval {
          type uint32 {
            range "1..180";
          }
          units "d";
          description
            "Sets the special days of interval between recover operations.";
        }
        leaf online-fail-number {
          type uint32 {
            range "1..256000";
          }
          default "10000";
          description
            "The sepical increase number of online-fail.";
        }
        leaf online-user-reduce-number {
          type uint32 {
            range "1..256000";
          }
          default "1000";
          description
            "The sepical reduce of online-user number.";
        }
        leaf online-success-rate {
          type uint32 {
            range "1..100";
          }
          units "%";
          default "30";
          description
            "The sepical rate of online success, unit is percent.";
        }
        leaf detect-by-user-number-reduce-ratio {
          type uint32 {
            range "0..100";
          }
          units "%";
          default "50";
          description
            "Accords to the number of users decreased the percentage of detection when the specified value. Only when the number of users is detected to reach the specified drop rate, it is considered that the SAID condition is satisfied and the diagnosis and recovery are continued.";
        }
        leaf detect-by-flow-speed-reduce-ratio {
          type uint32 {
            range "0..100";
          }
          units "%";
          default "50";
          description
            "Accords to the percentage drop in the flow rate when the specified value, Only when the traffic rate reduction is detected reaches the specified drop rate, it is considered that the SAID condition is satisfied and the diagnosis and recovery are continued.";
        }
        leaf said-enable {
          type boolean;
          default "true";
          description
            "Enable/disable SAID function.";
        }
      }
    }
  }
  augment "/ncs:devices/ncs:device/ncs:live-status" {
    container bras-said {
      tailf:ncs-device-type "netconf";
      tailf:display-when "not(../../ncs:module) or ../../ncs:module[ncs:name='huawei-bras-said'] or (../../ncs:live-status-protocol[not(ncs:capability)]) or (../../ncs:live-status-protocol/ncs:capability/ncs:module[.='huawei-bras-said'])";
      description
        "Bras said.";
      container said-exclude-fail-codes {
        description
          "Configure the excluding of login failures with a specified cause code from being detected or diagnosed by SAID nodes. By default, a login failure is not excluded from the detection or diagnosis of SAID nodes.";
        leaf-list visible-code {
          type uint16 {
            range "1..741";
          }
          description
            "Configure the visible on-line failure cause type.";
        }
        leaf-list invisible-code {
          type uint16 {
            range "0..62";
          }
          description
            "Configure the sxternal invisible on-line failure cause type.";
        }
      }
      container said-parameter {
        description
          "Configure the user Access.";
        leaf increase-number-of-online-fail {
          type uint32 {
            range "100..256000";
          }
          // NCS drop default statement
          description
            "Sets the sepical increase number of online-fail.";
        }
        leaf recover-interval {
          type uint32 {
            range "1..180";
          }
          units "d";
          description
            "Sets the special days of interval between recover operations.";
        }
        leaf online-fail-number {
          type uint32 {
            range "1..256000";
          }
          // NCS drop default statement
          description
            "The sepical increase number of online-fail.";
        }
        leaf online-user-reduce-number {
          type uint32 {
            range "1..256000";
          }
          // NCS drop default statement
          description
            "The sepical reduce of online-user number.";
        }
        leaf online-success-rate {
          type uint32 {
            range "1..100";
          }
          units "%";
          // NCS drop default statement
          description
            "The sepical rate of online success, unit is percent.";
        }
        leaf detect-by-user-number-reduce-ratio {
          type uint32 {
            range "0..100";
          }
          units "%";
          // NCS drop default statement
          description
            "Accords to the number of users decreased the percentage of detection when the specified value. Only when the number of users is detected to reach the specified drop rate, it is considered that the SAID condition is satisfied and the diagnosis and recovery are continued.";
        }
        leaf detect-by-flow-speed-reduce-ratio {
          type uint32 {
            range "0..100";
          }
          units "%";
          // NCS drop default statement
          description
            "Accords to the percentage drop in the flow rate when the specified value, Only when the traffic rate reduction is detected reaches the specified drop rate, it is considered that the SAID condition is satisfied and the diagnosis and recovery are continued.";
        }
        leaf said-enable {
          type boolean;
          // NCS drop default statement
          description
            "Enable/disable SAID function.";
        }
      }
    }
  }
  augment "/ncs:devices/ncs:template/ncs:ned-id/ncs:config" {
    container bras-said {
      description
        "Bras said.";
      container said-exclude-fail-codes {
        description
          "Configure the excluding of login failures with a specified cause code from being detected or diagnosed by SAID nodes. By default, a login failure is not excluded from the detection or diagnosis of SAID nodes.";
        leaf-list visible-code {
          // NCS patched for predictable order
          ordered-by user;
          type string;
          description
            "Configure the visible on-line failure cause type.";
        }
        leaf-list invisible-code {
          // NCS patched for predictable order
          ordered-by user;
          type string;
          description
            "Configure the sxternal invisible on-line failure cause type.";
        }
      }
      container said-parameter {
        description
          "Configure the user Access.";
        leaf increase-number-of-online-fail {
          type string;
          // NCS drop default statement
          description
            "Sets the sepical increase number of online-fail.";
        }
        leaf recover-interval {
          type string;
          units "d";
          description
            "Sets the special days of interval between recover operations.";
        }
        leaf online-fail-number {
          type string;
          // NCS drop default statement
          description
            "The sepical increase number of online-fail.";
        }
        leaf online-user-reduce-number {
          type string;
          // NCS drop default statement
          description
            "The sepical reduce of online-user number.";
        }
        leaf online-success-rate {
          type string;
          units "%";
          // NCS drop default statement
          description
            "The sepical rate of online success, unit is percent.";
        }
        leaf detect-by-user-number-reduce-ratio {
          type string;
          units "%";
          // NCS drop default statement
          description
            "Accords to the number of users decreased the percentage of detection when the specified value. Only when the number of users is detected to reach the specified drop rate, it is considered that the SAID condition is satisfied and the diagnosis and recovery are continued.";
        }
        leaf detect-by-flow-speed-reduce-ratio {
          type string;
          units "%";
          // NCS drop default statement
          description
            "Accords to the percentage drop in the flow rate when the specified value, Only when the traffic rate reduction is detected reaches the specified drop rate, it is considered that the SAID condition is satisfied and the diagnosis and recovery are continued.";
        }
        leaf said-enable {
          type string;
          // NCS drop default statement
          description
            "Enable/disable SAID function.";
        }
      }
    }
  }
}
