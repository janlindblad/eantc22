module huawei-masterkey {
  // Generated by yanger -t ncs
  tailf:mount-id "huawei-nc-1.0:huawei-nc-1.0";
  tailf:ncs-device-type "netconf";

  namespace "urn:huawei:yang:huawei-masterkey";
  prefix masterkey;

  import ietf-yang-types {
    prefix yang;
  }
  import huawei-pub-type {
    prefix pub-type;
  }
  import huawei-extension {
    prefix ext;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Master key.";

  revision 2020-03-20 {
    description
      "Fixed units and description problems.";
    reference "Huawei private.";
  }
  revision 2019-05-22 {
    description
      "Initial revision.";
    reference "Huawei private.";
  }
  ext:task-name "system";

  typedef ncs_template_mk-config-type {
    type string;
    description
      "The config type of master key.";
  }

  typedef ncs_template_mk-modify-result {
    type string;
    description
      "The status of operation.";
  }

  typedef ncs_rpc_notif_mk-config-type {
    type enumeration {
      enum "default" {
        value 1;
        description
          "Default master key.";
      }
      enum "user-defined" {
        value 2;
        description
          "User defined master key.";
      }
      enum "auto-update" {
        value 3;
        description
          "Auto update master key.";
      }
    }
    description
      "The config type of master key.";
  }

  typedef ncs_rpc_notif_mk-modify-result {
    type enumeration {
      enum "success" {
        value 1;
        description
          "Success.";
      }
      enum "operating" {
        value 2;
        description
          "Operating.";
      }
      enum "failure" {
        value 3;
        description
          "Failure.";
      }
    }
    description
      "The status of operation.";
  }

  typedef live_ncs_mk-config-type {
    type enumeration {
      enum "default" {
        value 1;
        description
          "Default master key.";
      }
      enum "user-defined" {
        value 2;
        description
          "User defined master key.";
      }
      enum "auto-update" {
        value 3;
        description
          "Auto update master key.";
      }
    }
    description
      "The config type of master key.";
  }

  typedef live_ncs_mk-modify-result {
    type enumeration {
      enum "success" {
        value 1;
        description
          "Success.";
      }
      enum "operating" {
        value 2;
        description
          "Operating.";
      }
      enum "failure" {
        value 3;
        description
          "Failure.";
      }
    }
    description
      "The status of operation.";
  }

  typedef mk-config-type {
    type enumeration {
      enum "default" {
        value 1;
        description
          "Default master key.";
      }
      enum "user-defined" {
        value 2;
        description
          "User defined master key.";
      }
      enum "auto-update" {
        value 3;
        description
          "Auto update master key.";
      }
    }
    description
      "The config type of master key.";
  }

  typedef mk-modify-result {
    type enumeration {
      enum "success" {
        value 1;
        description
          "Success.";
      }
      enum "operating" {
        value 2;
        description
          "Operating.";
      }
      enum "failure" {
        value 3;
        description
          "Failure.";
      }
    }
    description
      "The status of operation.";
  }

  augment "/ncs:devices/ncs:device/ncs:rpc" {
    container rpc-clear-masterkey {
      tailf:ncs-device-type "netconf";
      tailf:display-when "not(../../ncs:module) or ../../ncs:module[ncs:name='huawei-masterkey']";
      tailf:action clear-masterkey {
        tailf:actionpoint ncsproxy {
          tailf:internal;
        }
        description
          "Delete historical master key.";
        ext:node-ref "/masterkey";
      }
    }
  }
  augment "/ncs:devices/ncs:device-group/ncs:ned-id/ncs:rpc" {
    container rpc-clear-masterkey {
      tailf:ncs-device-type "netconf";
      tailf:display-when "/ncs:devices/ncs:device[ncs:name=current()/../../../ncs:member]/ncs:module[ncs:name='huawei-masterkey']";
      tailf:action clear-masterkey {
        tailf:actionpoint ncsproxy {
          tailf:internal;
        }
        description
          "Delete historical master key.";
        ext:node-ref "/masterkey";
      }
    }
  }
  augment "/ncs:devices/ncs:device/ncs:rpc" {
    container rpc-set-masterkey {
      tailf:ncs-device-type "netconf";
      tailf:display-when "not(../../ncs:module) or ../../ncs:module[ncs:name='huawei-masterkey']";
      tailf:action set-masterkey {
        tailf:actionpoint ncsproxy {
          tailf:internal;
        }
        description
          "Modify master key.";
        ext:node-ref "/masterkey";
        input {
          leaf new-masterkey {
            type pub-type:ncs_rpc_notif_password-extend;
            mandatory true;
            description
              "New master key.";
          }
        }
      }
    }
  }
  augment "/ncs:devices/ncs:device-group/ncs:ned-id/ncs:rpc" {
    container rpc-set-masterkey {
      tailf:ncs-device-type "netconf";
      tailf:display-when "/ncs:devices/ncs:device[ncs:name=current()/../../../ncs:member]/ncs:module[ncs:name='huawei-masterkey']";
      tailf:action set-masterkey {
        tailf:actionpoint ncsproxy {
          tailf:internal;
        }
        description
          "Modify master key.";
        ext:node-ref "/masterkey";
        input {
          leaf new-masterkey {
            type pub-type:ncs_rpc_notif_password-extend;
            mandatory true;
            description
              "New master key.";
          }
        }
      }
    }
  }
  augment "/ncs:devices/ncs:device/ncs:config" {
    container masterkey {
      tailf:ncs-device-type "netconf";
      tailf:display-when "not(../../ncs:module) or ../../ncs:module[ncs:name='huawei-masterkey']";
      description
        "Master key.";
      // NCS drop config false container 'current-type'
      // NCS drop config false container 'modify-result'
      container auto-update {
        description
          "Configure master key auto update.";
        leaf interval {
          type uint32 {
            range "1..3650";
          }
          units "d";
          description
            "Auto update interval.";
        }
      }
    }
  }
  augment "/ncs:devices/ncs:device/ncs:live-status" {
    container masterkey {
      tailf:ncs-device-type "netconf";
      tailf:display-when "not(../../ncs:module) or ../../ncs:module[ncs:name='huawei-masterkey'] or (../../ncs:live-status-protocol[not(ncs:capability)]) or (../../ncs:live-status-protocol/ncs:capability/ncs:module[.='huawei-masterkey'])";
      description
        "Master key.";
      container current-type {
        description
          "Operational state of master key current type.";
        leaf type {
          type live_ncs_mk-config-type;
          description
            "Master key current type.";
        }
      }
      container modify-result {
        description
          "Operational state of master key modify information.";
        leaf modify-start-time {
          type yang:date-and-time;
          description
            "Start time.";
        }
        leaf modify-end-time {
          type yang:date-and-time;
          description
            "End time.";
        }
        leaf modify-result {
          type live_ncs_mk-modify-result;
          description
            "Modify result.";
        }
        leaf modify-error-reason {
          type string {
            length "1..128";
          }
          description
            "Modify error reason.";
        }
      }
      container auto-update {
        description
          "Configure master key auto update.";
        leaf interval {
          type uint32 {
            range "1..3650";
          }
          units "d";
          description
            "Auto update interval.";
        }
      }
    }
  }
  augment "/ncs:devices/ncs:template/ncs:ned-id/ncs:config" {
    container masterkey {
      description
        "Master key.";
      // NCS drop config false container 'current-type'
      // NCS drop config false container 'modify-result'
      container auto-update {
        description
          "Configure master key auto update.";
        leaf interval {
          type string;
          units "d";
          description
            "Auto update interval.";
        }
      }
    }
  }
}
