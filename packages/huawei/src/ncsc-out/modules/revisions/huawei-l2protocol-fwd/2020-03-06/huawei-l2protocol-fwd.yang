module huawei-l2protocol-fwd {
  // Generated by yanger -t ncs
  tailf:mount-id "huawei-nc-1.0:huawei-nc-1.0";
  tailf:ncs-device-type "netconf";

  namespace "urn:huawei:yang:huawei-l2protocol-fwd";
  prefix l2protocol-fwd;

  import huawei-extension {
    prefix ext;
  }
  import huawei-ifm {
    prefix ifm;
  }
  import huawei-l2vpn {
    prefix l2vpn;
  }
  import huawei-devm {
    prefix devm;
  }
  import huawei-ethernet {
    prefix ethernet;
  }
  import huawei-bd {
    prefix bd;
  }
  import huawei-evpn {
    prefix evpn;
  }
  import huawei-evpl {
    prefix evpl;
  }
  import huawei-ifm-trunk {
    prefix ifm-trunk;
  }
  ext:task-name "l2cpmanagement";

  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Forwarding L2 protocol service.";

  revision 2020-03-06 {
    description
      "Change description.";
    reference "Huawei private.";
  }
  revision 2019-04-15 {
    description
      "Init revision.";
    reference "Huawei private.";
  }

  typedef ncs_template_action-type {
    type string;
    description
      "Link protocol transport action type.";
  }

  typedef ncs_template_vlan-action-type {
    type string;
    description
      "Link protocol transport action type.";
  }

  typedef ncs_template_mode {
    type string;
    description
      "Link protocol transport mode.";
  }

  typedef ncs_template_mode-evpn {
    type string;
    description
      "Link protocol transport mode.";
  }

  typedef ncs_template_vlan-protocol-type {
    type string;
    description
      "Link protocol transport protocol type.";
  }

  typedef ncs_template_protocol-type {
    type string;
    description
      "Link protocol transport protocol type.";
  }

  typedef ncs_template_link-protocol-status {
    type string;
    description
      "Link protocol transport state.";
  }

  typedef ncs_rpc_notif_action-type {
    type enumeration {
      enum "transport" {
        value 3;
        description
          "Link protocol transport.";
      }
      enum "transport-tagged" {
        value 4;
        description
          "Link protocol tagged transport.";
      }
      enum "forwarding" {
        value 1;
        description
          "Link protocol forwarding.";
      }
      enum "discard" {
        value 2;
        description
          "Link protocol discard.";
      }
    }
    description
      "Link protocol transport action type.";
  }

  typedef ncs_rpc_notif_vlan-action-type {
    type enumeration {
      enum "forwarding" {
        value 1;
        description
          "Link protocol forwarding.";
      }
    }
    description
      "Link protocol transport action type.";
  }

  typedef ncs_rpc_notif_mode {
    type enumeration {
      enum "normal" {
        value 0;
        description
          "Link protocol transport mode which does not aware VC type.";
      }
      enum "untag" {
        value 1;
        description
          "Link protocol transport mode which support untag packet.";
      }
    }
    description
      "Link protocol transport mode.";
  }

  typedef ncs_rpc_notif_mode-evpn {
    type enumeration {
      enum "normal" {
        value 0;
        description
          "Link protocol transport mode which does not aware VC type.";
      }
      enum "untag" {
        value 1;
        description
          "Link protocol transport mode which support untag packet.";
      }
    }
    description
      "Link protocol transport mode.";
  }

  typedef ncs_rpc_notif_vlan-protocol-type {
    type enumeration {
      enum "lacp" {
        value 1;
        description
          "Link Aggregation Control Protocol.";
      }
    }
    description
      "Link protocol transport protocol type.";
  }

  typedef ncs_rpc_notif_protocol-type {
    type enumeration {
      enum "bpdu" {
        value 4;
        description
          "Bridge protocol data unit.";
      }
      enum "lacp" {
        value 1;
        description
          "Link Aggregation Control Protocol.";
      }
      enum "lldp" {
        value 2;
        description
          "Link Layer Discovery Protocol.";
      }
      enum "cdp" {
        value 5;
        description
          "Cisco Discovery Protocol.";
      }
      enum "udld" {
        value 6;
        description
          "Unidirectional Link Detection.";
      }
    }
    description
      "Link protocol transport protocol type.";
  }

  typedef ncs_rpc_notif_link-protocol-status {
    type enumeration {
      enum "enable" {
        value 1;
        description
          "Link protocol transport function is enabled.";
      }
      enum "disable" {
        value 0;
        description
          "Link protocol transport function is disabled.";
      }
    }
    description
      "Link protocol transport state.";
  }

  typedef live_ncs_action-type {
    type enumeration {
      enum "transport" {
        value 3;
        description
          "Link protocol transport.";
      }
      enum "transport-tagged" {
        value 4;
        description
          "Link protocol tagged transport.";
      }
      enum "forwarding" {
        value 1;
        description
          "Link protocol forwarding.";
      }
      enum "discard" {
        value 2;
        description
          "Link protocol discard.";
      }
    }
    description
      "Link protocol transport action type.";
  }

  typedef live_ncs_vlan-action-type {
    type enumeration {
      enum "forwarding" {
        value 1;
        description
          "Link protocol forwarding.";
      }
    }
    description
      "Link protocol transport action type.";
  }

  typedef live_ncs_mode {
    type enumeration {
      enum "normal" {
        value 0;
        description
          "Link protocol transport mode which does not aware VC type.";
      }
      enum "untag" {
        value 1;
        description
          "Link protocol transport mode which support untag packet.";
      }
    }
    description
      "Link protocol transport mode.";
  }

  typedef live_ncs_mode-evpn {
    type enumeration {
      enum "normal" {
        value 0;
        description
          "Link protocol transport mode which does not aware VC type.";
      }
      enum "untag" {
        value 1;
        description
          "Link protocol transport mode which support untag packet.";
      }
    }
    description
      "Link protocol transport mode.";
  }

  typedef live_ncs_vlan-protocol-type {
    type enumeration {
      enum "lacp" {
        value 1;
        description
          "Link Aggregation Control Protocol.";
      }
    }
    description
      "Link protocol transport protocol type.";
  }

  typedef live_ncs_protocol-type {
    type enumeration {
      enum "bpdu" {
        value 4;
        description
          "Bridge protocol data unit.";
      }
      enum "lacp" {
        value 1;
        description
          "Link Aggregation Control Protocol.";
      }
      enum "lldp" {
        value 2;
        description
          "Link Layer Discovery Protocol.";
      }
      enum "cdp" {
        value 5;
        description
          "Cisco Discovery Protocol.";
      }
      enum "udld" {
        value 6;
        description
          "Unidirectional Link Detection.";
      }
    }
    description
      "Link protocol transport protocol type.";
  }

  typedef live_ncs_link-protocol-status {
    type enumeration {
      enum "enable" {
        value 1;
        description
          "Link protocol transport function is enabled.";
      }
      enum "disable" {
        value 0;
        description
          "Link protocol transport function is disabled.";
      }
    }
    description
      "Link protocol transport state.";
  }

  typedef action-type {
    type enumeration {
      enum "transport" {
        value 3;
        description
          "Link protocol transport.";
      }
      enum "transport-tagged" {
        value 4;
        description
          "Link protocol tagged transport.";
      }
      enum "forwarding" {
        value 1;
        description
          "Link protocol forwarding.";
      }
      enum "discard" {
        value 2;
        description
          "Link protocol discard.";
      }
    }
    description
      "Link protocol transport action type.";
  }

  typedef vlan-action-type {
    type enumeration {
      enum "forwarding" {
        value 1;
        description
          "Link protocol forwarding.";
      }
    }
    description
      "Link protocol transport action type.";
  }

  typedef mode {
    type enumeration {
      enum "normal" {
        value 0;
        description
          "Link protocol transport mode which does not aware VC type.";
      }
      enum "untag" {
        value 1;
        description
          "Link protocol transport mode which support untag packet.";
      }
    }
    description
      "Link protocol transport mode.";
  }

  typedef mode-evpn {
    type enumeration {
      enum "normal" {
        value 0;
        description
          "Link protocol transport mode which does not aware VC type.";
      }
      enum "untag" {
        value 1;
        description
          "Link protocol transport mode which support untag packet.";
      }
    }
    description
      "Link protocol transport mode.";
  }

  typedef vlan-protocol-type {
    type enumeration {
      enum "lacp" {
        value 1;
        description
          "Link Aggregation Control Protocol.";
      }
    }
    description
      "Link protocol transport protocol type.";
  }

  typedef protocol-type {
    type enumeration {
      enum "bpdu" {
        value 4;
        description
          "Bridge protocol data unit.";
      }
      enum "lacp" {
        value 1;
        description
          "Link Aggregation Control Protocol.";
      }
      enum "lldp" {
        value 2;
        description
          "Link Layer Discovery Protocol.";
      }
      enum "cdp" {
        value 5;
        description
          "Cisco Discovery Protocol.";
      }
      enum "udld" {
        value 6;
        description
          "Unidirectional Link Detection.";
      }
    }
    description
      "Link protocol transport protocol type.";
  }

  typedef link-protocol-status {
    type enumeration {
      enum "enable" {
        value 1;
        description
          "Link protocol transport function is enabled.";
      }
      enum "disable" {
        value 0;
        description
          "Link protocol transport function is disabled.";
      }
    }
    description
      "Link protocol transport state.";
  }

  grouping ncs_template_slot-linkprotocol-type {
    description
      "Transparent transmission of link-layer protocol information.";
    leaf lldp {
      type ncs_template_link-protocol-status;
      // NCS drop default statement
      description
        "Link Layer Discovery Protocol.";
    }
    leaf lacp {
      type ncs_template_link-protocol-status;
      // NCS drop default statement
      description
        "Link Aggregation Control Protocol.";
    }
    leaf oam {
      type ncs_template_link-protocol-status;
      // NCS drop default statement
      description
        "Operation, Administration and Maintenance Protocol.";
    }
    leaf esmc {
      type ncs_template_link-protocol-status;
      // NCS drop default statement
      description
        "Ethernet Synchronization Messaging Channel.";
    }
  }

  grouping ncs_rpc_notif_slot-linkprotocol-type {
    description
      "Transparent transmission of link-layer protocol information.";
    leaf lldp {
      type ncs_rpc_notif_link-protocol-status;
      default "disable";
      description
        "Link Layer Discovery Protocol.";
    }
    leaf lacp {
      type ncs_rpc_notif_link-protocol-status;
      default "disable";
      description
        "Link Aggregation Control Protocol.";
    }
    leaf oam {
      type ncs_rpc_notif_link-protocol-status;
      default "disable";
      description
        "Operation, Administration and Maintenance Protocol.";
    }
    leaf esmc {
      type ncs_rpc_notif_link-protocol-status;
      default "disable";
      description
        "Ethernet Synchronization Messaging Channel.";
    }
  }

  grouping live_ncs_slot-linkprotocol-type {
    description
      "Transparent transmission of link-layer protocol information.";
    leaf lldp {
      type live_ncs_link-protocol-status;
      // NCS drop default statement
      description
        "Link Layer Discovery Protocol.";
    }
    leaf lacp {
      type live_ncs_link-protocol-status;
      // NCS drop default statement
      description
        "Link Aggregation Control Protocol.";
    }
    leaf oam {
      type live_ncs_link-protocol-status;
      // NCS drop default statement
      description
        "Operation, Administration and Maintenance Protocol.";
    }
    leaf esmc {
      type live_ncs_link-protocol-status;
      // NCS drop default statement
      description
        "Ethernet Synchronization Messaging Channel.";
    }
  }

  grouping slot-linkprotocol-type {
    description
      "Transparent transmission of link-layer protocol information.";
    leaf lldp {
      type link-protocol-status;
      default "disable";
      description
        "Link Layer Discovery Protocol.";
    }
    leaf lacp {
      type link-protocol-status;
      default "disable";
      description
        "Link Aggregation Control Protocol.";
    }
    leaf oam {
      type link-protocol-status;
      default "disable";
      description
        "Operation, Administration and Maintenance Protocol.";
    }
    leaf esmc {
      type link-protocol-status;
      default "disable";
      description
        "Ethernet Synchronization Messaging Channel.";
    }
  }

  augment "/ncs:devices/ncs:template/ncs:ned-id/ncs:config/ifm:ifm/ifm:interfaces/ifm:interface/ethernet:ethernet/ethernet:main-interface/ethernet:l2-attribute" {
    description
      "Link protocol transport lacp.";
    container protocol-actions {
      // NCS drop when statement
      description
        "List of interface link protocol action.";
      list protocol-action {
        // NCS patched for predictable order
        ordered-by user;
        // NCS drop must statement
        key "protocol-type action";
        // NCS drop max-elements statement
        description
          "Configure link-protocol action.";
        leaf protocol-type {
          type ncs_template_vlan-protocol-type;
          description
            "Protocol type.";
        }
        leaf action {
          type ncs_template_vlan-action-type;
          description
            "Protocol action.";
        }
      }
    }
  }
  augment "/ncs:devices/ncs:device/ncs:live-status/ifm:ifm/ifm:interfaces/ifm:interface/ethernet:ethernet/ethernet:main-interface/ethernet:l2-attribute" {
    description
      "Link protocol transport lacp.";
    container protocol-actions {
      tailf:ncs-device-type "netconf";
      tailf:display-when "not(../../../../../../../../ncs:module) or ../../../../../../../../ncs:module[ncs:name='huawei-l2protocol-fwd'] or (../../../../../../../../ncs:live-status-protocol[not(ncs:capability)]) or (../../../../../../../../ncs:live-status-protocol/ncs:capability/ncs:module[.='huawei-l2protocol-fwd'])";
      // NCS drop when statement
      description
        "List of interface link protocol action.";
      list protocol-action {
        // NCS drop must statement
        key "protocol-type action";
        // NCS drop max-elements statement
        description
          "Configure link-protocol action.";
        leaf protocol-type {
          type live_ncs_vlan-protocol-type;
          description
            "Protocol type.";
        }
        leaf action {
          type live_ncs_vlan-action-type;
          description
            "Protocol action.";
        }
      }
    }
  }
  augment "/ncs:devices/ncs:device/ncs:config/ifm:ifm/ifm:interfaces/ifm:interface/ethernet:ethernet/ethernet:main-interface/ethernet:l2-attribute" {
    description
      "Link protocol transport lacp.";
    container protocol-actions {
      tailf:ncs-device-type "netconf";
      tailf:display-when "not(../../../../../../../../ncs:module) or ../../../../../../../../ncs:module[ncs:name='huawei-l2protocol-fwd']";
      when "../../../../ifm:type='Ethernet' or ../../../../ifm:type='GigabitEthernet' or ../../../../ifm:type='Eth-Trunk' or ../../../../ifm:type='100GE' or ../../../../ifm:type='XGigabitEthernet' or ../../../../ifm:type='40GE' or ../../../../ifm:type='10GE' or ../../../../ifm:type='400GE' or ../../../../ifm:type='25GE' or ../../../../ifm:type='FlexE' or ../../../../ifm:type='50GE' or ../../../../ifm:type='50|100GE'" {
        tailf:xpath-root 3;
      }
      description
        "List of interface link protocol action.";
      list protocol-action {
        must '../../ethernet:pvid or ../../ethernet:trunk-vlans' {
          tailf:xpath-root 3;
        }
        key "protocol-type action";
        max-elements 1;
        description
          "Configure link-protocol action.";
        leaf protocol-type {
          type vlan-protocol-type;
          description
            "Protocol type.";
        }
        leaf action {
          type vlan-action-type;
          description
            "Protocol action.";
        }
      }
    }
  }
  augment "/ncs:devices/ncs:template/ncs:ned-id/ncs:config/l2vpn:l2vpn/l2vpn:instances/l2vpn:instance/l2vpn:vpws-local-ccc/l2vpn:acs/l2vpn:ac" {
    description
      "L2 protocol service for VPWS.";
    container protocol-actions {
      description
        "List of interface link protocol action.";
      list protocol-action {
        // NCS patched for predictable order
        ordered-by user;
        // NCS drop must statement
        // NCS drop must statement
        // NCS drop must statement
        // NCS drop must statement
        // NCS drop must statement
        key "protocol-type action";
        description
          "Configure link-protocol action.";
        leaf protocol-type {
          type ncs_template_protocol-type;
          description
            "Protocol type.";
        }
        leaf action {
          type ncs_template_action-type;
          description
            "Protocol action.";
        }
        leaf mode {
          // NCS drop when statement
          type ncs_template_mode;
          // NCS drop mandatory statement
          description
            "Link-protocol transport mode.";
        }
      }
    }
  }
  augment "/ncs:devices/ncs:device/ncs:live-status/l2vpn:l2vpn/l2vpn:instances/l2vpn:instance/l2vpn:vpws-local-ccc/l2vpn:acs/l2vpn:ac" {
    description
      "L2 protocol service for VPWS.";
    container protocol-actions {
      tailf:ncs-device-type "netconf";
      tailf:display-when "not(../../../../../../../../ncs:module) or ../../../../../../../../ncs:module[ncs:name='huawei-l2protocol-fwd'] or (../../../../../../../../ncs:live-status-protocol[not(ncs:capability)]) or (../../../../../../../../ncs:live-status-protocol/ncs:capability/ncs:module[.='huawei-l2protocol-fwd'])";
      description
        "List of interface link protocol action.";
      list protocol-action {
        // NCS drop must statement
        // NCS drop must statement
        // NCS drop must statement
        // NCS drop must statement
        // NCS drop must statement
        key "protocol-type action";
        description
          "Configure link-protocol action.";
        leaf protocol-type {
          type live_ncs_protocol-type;
          description
            "Protocol type.";
        }
        leaf action {
          type live_ncs_action-type;
          description
            "Protocol action.";
        }
        leaf mode {
          // NCS drop when statement
          type live_ncs_mode;
          // NCS drop mandatory statement
          description
            "Link-protocol transport mode.";
        }
      }
    }
  }
  augment "/ncs:devices/ncs:device/ncs:config/l2vpn:l2vpn/l2vpn:instances/l2vpn:instance/l2vpn:vpws-local-ccc/l2vpn:acs/l2vpn:ac" {
    description
      "L2 protocol service for VPWS.";
    container protocol-actions {
      tailf:ncs-device-type "netconf";
      tailf:display-when "not(../../../../../../../../ncs:module) or ../../../../../../../../ncs:module[ncs:name='huawei-l2protocol-fwd']";
      description
        "List of interface link protocol action.";
      list protocol-action {
        must "/ifm:ifm/ifm:interfaces/ifm:interface[ifm:name=current()/../../l2vpn:interface-name]/ifm:type='Ethernet' or
/ifm:ifm/ifm:interfaces/ifm:interface[ifm:name=current()/../../l2vpn:interface-name]/ifm:type='GigabitEthernet' or
/ifm:ifm/ifm:interfaces/ifm:interface[ifm:name=current()/../../l2vpn:interface-name]/ifm:type='Eth-Trunk' or
/ifm:ifm/ifm:interfaces/ifm:interface[ifm:name=current()/../../l2vpn:interface-name]/ifm:type='100GE' or
/ifm:ifm/ifm:interfaces/ifm:interface[ifm:name=current()/../../l2vpn:interface-name]/ifm:type='XGigabitEthernet' or
/ifm:ifm/ifm:interfaces/ifm:interface[ifm:name=current()/../../l2vpn:interface-name]/ifm:type='40GE' or
/ifm:ifm/ifm:interfaces/ifm:interface[ifm:name=current()/../../l2vpn:interface-name]/ifm:type='10GE' or
/ifm:ifm/ifm:interfaces/ifm:interface[ifm:name=current()/../../l2vpn:interface-name]/ifm:type='400GE' or
/ifm:ifm/ifm:interfaces/ifm:interface[ifm:name=current()/../../l2vpn:interface-name]/ifm:type='25GE' or
/ifm:ifm/ifm:interfaces/ifm:interface[ifm:name=current()/../../l2vpn:interface-name]/ifm:type='FlexE' or
/ifm:ifm/ifm:interfaces/ifm:interface[ifm:name=current()/../../l2vpn:interface-name]/ifm:type='50GE' or
/ifm:ifm/ifm:interfaces/ifm:interface[ifm:name=current()/../../l2vpn:interface-name]/ifm:type='50|100GE'" {
          tailf:xpath-root 3;
        }
        must "(action='transport' and /ifm:ifm/ifm:interfaces/ifm:interface[ifm:name=current()/../../l2vpn:interface-name]/ifm:parent-name and
/ifm:ifm/ifm:interfaces/ifm:interface[ifm:name=current()/../../l2vpn:interface-name]/ifm:l2-mode-enable='false' and
/ifm:ifm/ifm:interfaces/ifm:interface[ifm:name=current()/../../l2vpn:interface-name]/ethernet:ethernet/ethernet:l3-sub-interface/ethernet:vlan-type-dot1q) or
(action='transport-tagged' and /ifm:ifm/ifm:interfaces/ifm:interface[ifm:name=current()/../../l2vpn:interface-name]/ifm:parent-name and
/ifm:ifm/ifm:interfaces/ifm:interface[ifm:name=current()/../../l2vpn:interface-name]/ifm:l2-mode-enable='false') or
(action='discard' and not (/ifm:ifm/ifm:interfaces/ifm:interface[ifm:name=current()/../../l2vpn:interface-name]/ifm:parent-name))" {
          tailf:xpath-root 3;
        }
        must "action='transport' or (action='transport-tagged' and (protocol-type='lacp' or protocol-type='lldp')) or (action='discard' and protocol-type='lacp')" {
          tailf:xpath-root 3;
        }
        must "(action='discard' and ((/ifm:ifm/ifm:interfaces/ifm:interface[ifm:name=current()/../../l2vpn:interface-name]/ifm:type!='Eth-Trunk') or ((/ifm:ifm/ifm:interfaces/ifm:interface[ifm:name=current()/../../l2vpn:interface-name]/ifm:type='Eth-Trunk') and (/ifm:ifm/ifm:interfaces/ifm:interface[ifm:name=current()/../../l2vpn:interface-name]/ifm-trunk:trunk/ifm-trunk:work-mode!='static')))) or (action!='discard')" {
          tailf:xpath-root 3;
        }
        must "mode!='untag' or (mode='untag' and /ifm:ifm/ifm:interfaces/ifm:interface[ifm:name=current()/../../l2vpn:interface-name]/ethernet:ethernet/ethernet:l3-sub-interface/ethernet:vlan-type-dot1q)" {
          tailf:xpath-root 3;
        }
        key "protocol-type action";
        description
          "Configure link-protocol action.";
        leaf protocol-type {
          type protocol-type;
          description
            "Protocol type.";
        }
        leaf action {
          type action-type;
          description
            "Protocol action.";
        }
        leaf mode {
          when "../action='transport'" {
            tailf:xpath-root 3;
          }
          type mode;
          mandatory true;
          description
            "Link-protocol transport mode.";
        }
      }
    }
  }
  augment "/ncs:devices/ncs:template/ncs:ned-id/ncs:config/l2vpn:l2vpn/l2vpn:instances/l2vpn:instance/l2vpn:vpws-remote-ccc/l2vpn:acs/l2vpn:ac" {
    description
      "L2 protocol service for VPWS.";
    container protocol-actions {
      description
        "List of interface link protocol action.";
      list protocol-action {
        // NCS patched for predictable order
        ordered-by user;
        // NCS drop must statement
        // NCS drop must statement
        // NCS drop must statement
        // NCS drop must statement
        // NCS drop must statement
        key "protocol-type action";
        description
          "Configure link-protocol action.";
        leaf protocol-type {
          type ncs_template_protocol-type;
          description
            "Protocol type.";
        }
        leaf action {
          type ncs_template_action-type;
          description
            "Protocol action.";
        }
        leaf mode {
          // NCS drop when statement
          type ncs_template_mode;
          // NCS drop mandatory statement
          description
            "Link-protocol transport mode.";
        }
      }
    }
  }
  augment "/ncs:devices/ncs:device/ncs:live-status/l2vpn:l2vpn/l2vpn:instances/l2vpn:instance/l2vpn:vpws-remote-ccc/l2vpn:acs/l2vpn:ac" {
    description
      "L2 protocol service for VPWS.";
    container protocol-actions {
      tailf:ncs-device-type "netconf";
      tailf:display-when "not(../../../../../../../../ncs:module) or ../../../../../../../../ncs:module[ncs:name='huawei-l2protocol-fwd'] or (../../../../../../../../ncs:live-status-protocol[not(ncs:capability)]) or (../../../../../../../../ncs:live-status-protocol/ncs:capability/ncs:module[.='huawei-l2protocol-fwd'])";
      description
        "List of interface link protocol action.";
      list protocol-action {
        // NCS drop must statement
        // NCS drop must statement
        // NCS drop must statement
        // NCS drop must statement
        // NCS drop must statement
        key "protocol-type action";
        description
          "Configure link-protocol action.";
        leaf protocol-type {
          type live_ncs_protocol-type;
          description
            "Protocol type.";
        }
        leaf action {
          type live_ncs_action-type;
          description
            "Protocol action.";
        }
        leaf mode {
          // NCS drop when statement
          type live_ncs_mode;
          // NCS drop mandatory statement
          description
            "Link-protocol transport mode.";
        }
      }
    }
  }
  augment "/ncs:devices/ncs:device/ncs:config/l2vpn:l2vpn/l2vpn:instances/l2vpn:instance/l2vpn:vpws-remote-ccc/l2vpn:acs/l2vpn:ac" {
    description
      "L2 protocol service for VPWS.";
    container protocol-actions {
      tailf:ncs-device-type "netconf";
      tailf:display-when "not(../../../../../../../../ncs:module) or ../../../../../../../../ncs:module[ncs:name='huawei-l2protocol-fwd']";
      description
        "List of interface link protocol action.";
      list protocol-action {
        must "/ifm:ifm/ifm:interfaces/ifm:interface[ifm:name=current()/../../l2vpn:interface-name]/ifm:type='Ethernet' or
/ifm:ifm/ifm:interfaces/ifm:interface[ifm:name=current()/../../l2vpn:interface-name]/ifm:type='GigabitEthernet' or
/ifm:ifm/ifm:interfaces/ifm:interface[ifm:name=current()/../../l2vpn:interface-name]/ifm:type='Eth-Trunk' or
/ifm:ifm/ifm:interfaces/ifm:interface[ifm:name=current()/../../l2vpn:interface-name]/ifm:type='100GE' or
/ifm:ifm/ifm:interfaces/ifm:interface[ifm:name=current()/../../l2vpn:interface-name]/ifm:type='XGigabitEthernet' or
/ifm:ifm/ifm:interfaces/ifm:interface[ifm:name=current()/../../l2vpn:interface-name]/ifm:type='40GE' or
/ifm:ifm/ifm:interfaces/ifm:interface[ifm:name=current()/../../l2vpn:interface-name]/ifm:type='10GE' or
/ifm:ifm/ifm:interfaces/ifm:interface[ifm:name=current()/../../l2vpn:interface-name]/ifm:type='400GE' or
/ifm:ifm/ifm:interfaces/ifm:interface[ifm:name=current()/../../l2vpn:interface-name]/ifm:type='25GE' or
/ifm:ifm/ifm:interfaces/ifm:interface[ifm:name=current()/../../l2vpn:interface-name]/ifm:type='FlexE' or
/ifm:ifm/ifm:interfaces/ifm:interface[ifm:name=current()/../../l2vpn:interface-name]/ifm:type='50GE' or
/ifm:ifm/ifm:interfaces/ifm:interface[ifm:name=current()/../../l2vpn:interface-name]/ifm:type='50|100GE'" {
          tailf:xpath-root 3;
        }
        must "(action='transport' and /ifm:ifm/ifm:interfaces/ifm:interface[ifm:name=current()/../../l2vpn:interface-name]/ifm:parent-name and
/ifm:ifm/ifm:interfaces/ifm:interface[ifm:name=current()/../../l2vpn:interface-name]/ifm:l2-mode-enable='false' and
/ifm:ifm/ifm:interfaces/ifm:interface[ifm:name=current()/../../l2vpn:interface-name]/ethernet:ethernet/ethernet:l3-sub-interface/ethernet:vlan-type-dot1q) or
(action='transport-tagged' and /ifm:ifm/ifm:interfaces/ifm:interface[ifm:name=current()/../../l2vpn:interface-name]/ifm:parent-name and
/ifm:ifm/ifm:interfaces/ifm:interface[ifm:name=current()/../../l2vpn:interface-name]/ifm:l2-mode-enable='false') or
(action='discard' and not (/ifm:ifm/ifm:interfaces/ifm:interface[ifm:name=current()/../../l2vpn:interface-name]/ifm:parent-name))" {
          tailf:xpath-root 3;
        }
        must "action='transport' or (action='transport-tagged' and (protocol-type='lacp' or protocol-type='lldp')) or (action='discard' and protocol-type='lacp')" {
          tailf:xpath-root 3;
        }
        must "(action='discard' and ((/ifm:ifm/ifm:interfaces/ifm:interface[ifm:name=current()/../../l2vpn:interface-name]/ifm:type!='Eth-Trunk') or ((/ifm:ifm/ifm:interfaces/ifm:interface[ifm:name=current()/../../l2vpn:interface-name]/ifm:type='Eth-Trunk') and (/ifm:ifm/ifm:interfaces/ifm:interface[ifm:name=current()/../../l2vpn:interface-name]/ifm-trunk:trunk/ifm-trunk:work-mode!='static')))) or (action!='discard')" {
          tailf:xpath-root 3;
        }
        must "mode!='untag' or (mode='untag' and /ifm:ifm/ifm:interfaces/ifm:interface[ifm:name=current()/../../l2vpn:interface-name]/ethernet:ethernet/ethernet:l3-sub-interface/ethernet:vlan-type-dot1q)" {
          tailf:xpath-root 3;
        }
        key "protocol-type action";
        description
          "Configure link-protocol action.";
        leaf protocol-type {
          type protocol-type;
          description
            "Protocol type.";
        }
        leaf action {
          type action-type;
          description
            "Protocol action.";
        }
        leaf mode {
          when "../action='transport'" {
            tailf:xpath-root 3;
          }
          type mode;
          mandatory true;
          description
            "Link-protocol transport mode.";
        }
      }
    }
  }
  augment "/ncs:devices/ncs:template/ncs:ned-id/ncs:config/l2vpn:l2vpn/l2vpn:instances/l2vpn:instance/l2vpn:vpws-ldp/l2vpn:acs/l2vpn:ac" {
    description
      "L2 protocol service for VPWS.";
    container protocol-actions {
      description
        "List of interface link protocol action.";
      list protocol-action {
        // NCS patched for predictable order
        ordered-by user;
        // NCS drop must statement
        // NCS drop must statement
        key "protocol-type action";
        description
          "Configure link-protocol action.";
        leaf protocol-type {
          type ncs_template_protocol-type;
          description
            "Protocol type.";
        }
        leaf action {
          type ncs_template_action-type;
          description
            "Protocol action.";
        }
        leaf mode {
          // NCS drop when statement
          type ncs_template_mode;
          // NCS drop mandatory statement
          description
            "Link-protocol transport mode.";
        }
      }
    }
  }
  augment "/ncs:devices/ncs:device/ncs:live-status/l2vpn:l2vpn/l2vpn:instances/l2vpn:instance/l2vpn:vpws-ldp/l2vpn:acs/l2vpn:ac" {
    description
      "L2 protocol service for VPWS.";
    container protocol-actions {
      tailf:ncs-device-type "netconf";
      tailf:display-when "not(../../../../../../../../ncs:module) or ../../../../../../../../ncs:module[ncs:name='huawei-l2protocol-fwd'] or (../../../../../../../../ncs:live-status-protocol[not(ncs:capability)]) or (../../../../../../../../ncs:live-status-protocol/ncs:capability/ncs:module[.='huawei-l2protocol-fwd'])";
      description
        "List of interface link protocol action.";
      list protocol-action {
        // NCS drop must statement
        // NCS drop must statement
        key "protocol-type action";
        description
          "Configure link-protocol action.";
        leaf protocol-type {
          type live_ncs_protocol-type;
          description
            "Protocol type.";
        }
        leaf action {
          type live_ncs_action-type;
          description
            "Protocol action.";
        }
        leaf mode {
          // NCS drop when statement
          type live_ncs_mode;
          // NCS drop mandatory statement
          description
            "Link-protocol transport mode.";
        }
      }
    }
  }
  augment "/ncs:devices/ncs:device/ncs:config/l2vpn:l2vpn/l2vpn:instances/l2vpn:instance/l2vpn:vpws-ldp/l2vpn:acs/l2vpn:ac" {
    description
      "L2 protocol service for VPWS.";
    container protocol-actions {
      tailf:ncs-device-type "netconf";
      tailf:display-when "not(../../../../../../../../ncs:module) or ../../../../../../../../ncs:module[ncs:name='huawei-l2protocol-fwd']";
      description
        "List of interface link protocol action.";
      list protocol-action {
        must "/ifm:ifm/ifm:interfaces/ifm:interface[ifm:name=current()/../../l2vpn:interface-name]/ifm:type='Ethernet' or
/ifm:ifm/ifm:interfaces/ifm:interface[ifm:name=current()/../../l2vpn:interface-name]/ifm:type='GigabitEthernet' or
/ifm:ifm/ifm:interfaces/ifm:interface[ifm:name=current()/../../l2vpn:interface-name]/ifm:type='Eth-Trunk' or
/ifm:ifm/ifm:interfaces/ifm:interface[ifm:name=current()/../../l2vpn:interface-name]/ifm:type='100GE' or
/ifm:ifm/ifm:interfaces/ifm:interface[ifm:name=current()/../../l2vpn:interface-name]/ifm:type='XGigabitEthernet' or
/ifm:ifm/ifm:interfaces/ifm:interface[ifm:name=current()/../../l2vpn:interface-name]/ifm:type='40GE' or
/ifm:ifm/ifm:interfaces/ifm:interface[ifm:name=current()/../../l2vpn:interface-name]/ifm:type='10GE' or
/ifm:ifm/ifm:interfaces/ifm:interface[ifm:name=current()/../../l2vpn:interface-name]/ifm:type='400GE' or
/ifm:ifm/ifm:interfaces/ifm:interface[ifm:name=current()/../../l2vpn:interface-name]/ifm:type='25GE' or
/ifm:ifm/ifm:interfaces/ifm:interface[ifm:name=current()/../../l2vpn:interface-name]/ifm:type='FlexE' or
/ifm:ifm/ifm:interfaces/ifm:interface[ifm:name=current()/../../l2vpn:interface-name]/ifm:type='50GE' or
/ifm:ifm/ifm:interfaces/ifm:interface[ifm:name=current()/../../l2vpn:interface-name]/ifm:type='50|100GE'" {
          tailf:xpath-root 3;
        }
        must "mode!='untag' or (mode='untag' and /ifm:ifm/ifm:interfaces/ifm:interface[ifm:name=current()/../../l2vpn:interface-name]/ethernet:ethernet/ethernet:l3-sub-interface/ethernet:vlan-type-dot1q)" {
          tailf:xpath-root 3;
        }
        key "protocol-type action";
        description
          "Configure link-protocol action.";
        leaf protocol-type {
          type protocol-type;
          description
            "Protocol type.";
        }
        leaf action {
          type action-type;
          description
            "Protocol action.";
        }
        leaf mode {
          when "../action='transport'" {
            tailf:xpath-root 3;
          }
          type mode;
          mandatory true;
          description
            "Link-protocol transport mode.";
        }
      }
    }
  }
  augment "/ncs:devices/ncs:template/ncs:ned-id/ncs:config/l2vpn:l2vpn/l2vpn:instances/l2vpn:instance/l2vpn:vpws-bgp/l2vpn:acs/l2vpn:ac" {
    description
      "L2 protocol service for VPWS BGP.";
    container protocol-actions {
      description
        "List of interface link protocol action.";
      list protocol-action {
        // NCS patched for predictable order
        ordered-by user;
        // NCS drop must statement
        // NCS drop must statement
        // NCS drop must statement
        key "protocol-type action";
        description
          "Configure link-protocol action.";
        leaf protocol-type {
          type ncs_template_protocol-type;
          description
            "Protocol type.";
        }
        leaf action {
          type ncs_template_action-type;
          description
            "Protocol action.";
        }
        leaf mode {
          // NCS drop when statement
          type ncs_template_mode;
          // NCS drop mandatory statement
          description
            "Link-protocol transport mode.";
        }
      }
    }
  }
  augment "/ncs:devices/ncs:device/ncs:live-status/l2vpn:l2vpn/l2vpn:instances/l2vpn:instance/l2vpn:vpws-bgp/l2vpn:acs/l2vpn:ac" {
    description
      "L2 protocol service for VPWS BGP.";
    container protocol-actions {
      tailf:ncs-device-type "netconf";
      tailf:display-when "not(../../../../../../../../ncs:module) or ../../../../../../../../ncs:module[ncs:name='huawei-l2protocol-fwd'] or (../../../../../../../../ncs:live-status-protocol[not(ncs:capability)]) or (../../../../../../../../ncs:live-status-protocol/ncs:capability/ncs:module[.='huawei-l2protocol-fwd'])";
      description
        "List of interface link protocol action.";
      list protocol-action {
        // NCS drop must statement
        // NCS drop must statement
        // NCS drop must statement
        key "protocol-type action";
        description
          "Configure link-protocol action.";
        leaf protocol-type {
          type live_ncs_protocol-type;
          description
            "Protocol type.";
        }
        leaf action {
          type live_ncs_action-type;
          description
            "Protocol action.";
        }
        leaf mode {
          // NCS drop when statement
          type live_ncs_mode;
          // NCS drop mandatory statement
          description
            "Link-protocol transport mode.";
        }
      }
    }
  }
  augment "/ncs:devices/ncs:device/ncs:config/l2vpn:l2vpn/l2vpn:instances/l2vpn:instance/l2vpn:vpws-bgp/l2vpn:acs/l2vpn:ac" {
    description
      "L2 protocol service for VPWS BGP.";
    container protocol-actions {
      tailf:ncs-device-type "netconf";
      tailf:display-when "not(../../../../../../../../ncs:module) or ../../../../../../../../ncs:module[ncs:name='huawei-l2protocol-fwd']";
      description
        "List of interface link protocol action.";
      list protocol-action {
        must "/ifm:ifm/ifm:interfaces/ifm:interface[ifm:name=current()/../../l2vpn:interface-name]/ifm:class='sub-interface' and /ifm:ifm/ifm:interfaces/ifm:interface[ifm:name=current()/../../l2vpn:interface-name]/ifm:l2-mode-enable='false'" {
          tailf:xpath-root 3;
        }
        must "/ifm:ifm/ifm:interfaces/ifm:interface[ifm:name=current()/../../l2vpn:interface-name]/ifm:type='Ethernet' or
/ifm:ifm/ifm:interfaces/ifm:interface[ifm:name=current()/../../l2vpn:interface-name]/ifm:type='GigabitEthernet' or
/ifm:ifm/ifm:interfaces/ifm:interface[ifm:name=current()/../../l2vpn:interface-name]/ifm:type='Eth-Trunk' or
/ifm:ifm/ifm:interfaces/ifm:interface[ifm:name=current()/../../l2vpn:interface-name]/ifm:type='100GE' or
/ifm:ifm/ifm:interfaces/ifm:interface[ifm:name=current()/../../l2vpn:interface-name]/ifm:type='XGigabitEthernet' or
/ifm:ifm/ifm:interfaces/ifm:interface[ifm:name=current()/../../l2vpn:interface-name]/ifm:type='40GE' or
/ifm:ifm/ifm:interfaces/ifm:interface[ifm:name=current()/../../l2vpn:interface-name]/ifm:type='10GE' or
/ifm:ifm/ifm:interfaces/ifm:interface[ifm:name=current()/../../l2vpn:interface-name]/ifm:type='400GE' or
/ifm:ifm/ifm:interfaces/ifm:interface[ifm:name=current()/../../l2vpn:interface-name]/ifm:type='25GE' or
/ifm:ifm/ifm:interfaces/ifm:interface[ifm:name=current()/../../l2vpn:interface-name]/ifm:type='FlexE' or
/ifm:ifm/ifm:interfaces/ifm:interface[ifm:name=current()/../../l2vpn:interface-name]/ifm:type='50GE' or
/ifm:ifm/ifm:interfaces/ifm:interface[ifm:name=current()/../../l2vpn:interface-name]/ifm:type='50|100GE'" {
          tailf:xpath-root 3;
        }
        must "mode!='untag' or (mode='untag' and /ifm:ifm/ifm:interfaces/ifm:interface[ifm:name=current()/../../l2vpn:interface-name]/ethernet:ethernet/ethernet:l3-sub-interface/ethernet:vlan-type-dot1q)" {
          tailf:xpath-root 3;
        }
        key "protocol-type action";
        description
          "Configure link-protocol action.";
        leaf protocol-type {
          type protocol-type;
          description
            "Protocol type.";
        }
        leaf action {
          type action-type;
          description
            "Protocol action.";
        }
        leaf mode {
          when "../action='transport'" {
            tailf:xpath-root 3;
          }
          type mode;
          mandatory true;
          description
            "Link-protocol transport mode.";
        }
      }
    }
  }
  augment "/ncs:devices/ncs:template/ncs:ned-id/ncs:config/l2vpn:l2vpn/l2vpn:instances/l2vpn:instance/l2vpn:vpls/l2vpn:acs/l2vpn:ac" {
    description
      "L2 protocol service for VSI.";
    container protocol-actions {
      description
        "List of interface link protocol action.";
      list protocol-action {
        // NCS patched for predictable order
        ordered-by user;
        // NCS drop must statement
        // NCS drop must statement
        key "protocol-type action";
        description
          "Configure link-protocol action.";
        leaf protocol-type {
          type ncs_template_protocol-type;
          description
            "Protocol type.";
        }
        leaf action {
          type ncs_template_action-type;
          description
            "Protocol action.";
        }
        leaf mode {
          // NCS drop when statement
          type ncs_template_mode;
          // NCS drop mandatory statement
          description
            "Link-protocol transport mode.";
        }
      }
    }
  }
  augment "/ncs:devices/ncs:device/ncs:live-status/l2vpn:l2vpn/l2vpn:instances/l2vpn:instance/l2vpn:vpls/l2vpn:acs/l2vpn:ac" {
    description
      "L2 protocol service for VSI.";
    container protocol-actions {
      tailf:ncs-device-type "netconf";
      tailf:display-when "not(../../../../../../../../ncs:module) or ../../../../../../../../ncs:module[ncs:name='huawei-l2protocol-fwd'] or (../../../../../../../../ncs:live-status-protocol[not(ncs:capability)]) or (../../../../../../../../ncs:live-status-protocol/ncs:capability/ncs:module[.='huawei-l2protocol-fwd'])";
      description
        "List of interface link protocol action.";
      list protocol-action {
        // NCS drop must statement
        // NCS drop must statement
        key "protocol-type action";
        description
          "Configure link-protocol action.";
        leaf protocol-type {
          type live_ncs_protocol-type;
          description
            "Protocol type.";
        }
        leaf action {
          type live_ncs_action-type;
          description
            "Protocol action.";
        }
        leaf mode {
          // NCS drop when statement
          type live_ncs_mode;
          // NCS drop mandatory statement
          description
            "Link-protocol transport mode.";
        }
      }
    }
  }
  augment "/ncs:devices/ncs:device/ncs:config/l2vpn:l2vpn/l2vpn:instances/l2vpn:instance/l2vpn:vpls/l2vpn:acs/l2vpn:ac" {
    description
      "L2 protocol service for VSI.";
    container protocol-actions {
      tailf:ncs-device-type "netconf";
      tailf:display-when "not(../../../../../../../../ncs:module) or ../../../../../../../../ncs:module[ncs:name='huawei-l2protocol-fwd']";
      description
        "List of interface link protocol action.";
      list protocol-action {
        must "/ifm:ifm/ifm:interfaces/ifm:interface[ifm:name=current()/../../l2vpn:interface-name]/ifm:type='Ethernet' or
/ifm:ifm/ifm:interfaces/ifm:interface[ifm:name=current()/../../l2vpn:interface-name]/ifm:type='GigabitEthernet' or
/ifm:ifm/ifm:interfaces/ifm:interface[ifm:name=current()/../../l2vpn:interface-name]/ifm:type='Eth-Trunk' or
/ifm:ifm/ifm:interfaces/ifm:interface[ifm:name=current()/../../l2vpn:interface-name]/ifm:type='100GE' or
/ifm:ifm/ifm:interfaces/ifm:interface[ifm:name=current()/../../l2vpn:interface-name]/ifm:type='XGigabitEthernet' or
/ifm:ifm/ifm:interfaces/ifm:interface[ifm:name=current()/../../l2vpn:interface-name]/ifm:type='40GE' or
/ifm:ifm/ifm:interfaces/ifm:interface[ifm:name=current()/../../l2vpn:interface-name]/ifm:type='10GE' or
/ifm:ifm/ifm:interfaces/ifm:interface[ifm:name=current()/../../l2vpn:interface-name]/ifm:type='400GE' or
/ifm:ifm/ifm:interfaces/ifm:interface[ifm:name=current()/../../l2vpn:interface-name]/ifm:type='25GE' or
/ifm:ifm/ifm:interfaces/ifm:interface[ifm:name=current()/../../l2vpn:interface-name]/ifm:type='FlexE' or
/ifm:ifm/ifm:interfaces/ifm:interface[ifm:name=current()/../../l2vpn:interface-name]/ifm:type='50GE' or
/ifm:ifm/ifm:interfaces/ifm:interface[ifm:name=current()/../../l2vpn:interface-name]/ifm:type='50|100GE'" {
          tailf:xpath-root 3;
        }
        must "mode!='untag' or (mode='untag' and /ifm:ifm/ifm:interfaces/ifm:interface[ifm:name=current()/../../l2vpn:interface-name]/ethernet:ethernet/ethernet:l3-sub-interface/ethernet:vlan-type-dot1q)" {
          tailf:xpath-root 3;
        }
        key "protocol-type action";
        description
          "Configure link-protocol action.";
        leaf protocol-type {
          type protocol-type;
          description
            "Protocol type.";
        }
        leaf action {
          type action-type;
          description
            "Protocol action.";
        }
        leaf mode {
          when "../action='transport'" {
            tailf:xpath-root 3;
          }
          type mode;
          mandatory true;
          description
            "Link-protocol transport mode.";
        }
      }
    }
  }
  augment "/ncs:devices/ncs:template/ncs:ned-id/ncs:config/bd:bd/bd:instances/bd:instance/bd:service-points/bd:service-point" {
    description
      "L2 protocol service for BD.";
    container protocol-actions {
      description
        "List of interface link protocol action.";
      list protocol-action {
        // NCS patched for predictable order
        ordered-by user;
        // NCS drop must statement
        key "protocol-type action";
        description
          "Configure link-protocol action.";
        leaf protocol-type {
          type ncs_template_protocol-type;
          description
            "Protocol type.";
        }
        leaf action {
          type ncs_template_action-type;
          description
            "Protocol action.";
        }
        leaf mode {
          // NCS drop when statement
          type ncs_template_mode-evpn;
          // NCS drop mandatory statement
          description
            "Link-protocol transport mode.";
        }
      }
    }
  }
  augment "/ncs:devices/ncs:device/ncs:live-status/bd:bd/bd:instances/bd:instance/bd:service-points/bd:service-point" {
    description
      "L2 protocol service for BD.";
    container protocol-actions {
      tailf:ncs-device-type "netconf";
      tailf:display-when "not(../../../../../../../ncs:module) or ../../../../../../../ncs:module[ncs:name='huawei-l2protocol-fwd'] or (../../../../../../../ncs:live-status-protocol[not(ncs:capability)]) or (../../../../../../../ncs:live-status-protocol/ncs:capability/ncs:module[.='huawei-l2protocol-fwd'])";
      description
        "List of interface link protocol action.";
      list protocol-action {
        // NCS drop must statement
        key "protocol-type action";
        description
          "Configure link-protocol action.";
        leaf protocol-type {
          type live_ncs_protocol-type;
          description
            "Protocol type.";
        }
        leaf action {
          type live_ncs_action-type;
          description
            "Protocol action.";
        }
        leaf mode {
          // NCS drop when statement
          type live_ncs_mode-evpn;
          // NCS drop mandatory statement
          description
            "Link-protocol transport mode.";
        }
      }
    }
  }
  augment "/ncs:devices/ncs:device/ncs:config/bd:bd/bd:instances/bd:instance/bd:service-points/bd:service-point" {
    description
      "L2 protocol service for BD.";
    container protocol-actions {
      tailf:ncs-device-type "netconf";
      tailf:display-when "not(../../../../../../../ncs:module) or ../../../../../../../ncs:module[ncs:name='huawei-l2protocol-fwd']";
      description
        "List of interface link protocol action.";
      list protocol-action {
        must "/ifm:ifm/ifm:interfaces/ifm:interface[ifm:name=current()/../../bd:interface-name]/ifm:type='Ethernet' or
/ifm:ifm/ifm:interfaces/ifm:interface[ifm:name=current()/../../bd:interface-name]/ifm:type='GigabitEthernet' or
/ifm:ifm/ifm:interfaces/ifm:interface[ifm:name=current()/../../bd:interface-name]/ifm:type='Eth-Trunk' or
/ifm:ifm/ifm:interfaces/ifm:interface[ifm:name=current()/../../bd:interface-name]/ifm:type='100GE' or
/ifm:ifm/ifm:interfaces/ifm:interface[ifm:name=current()/../../bd:interface-name]/ifm:type='XGigabitEthernet' or
/ifm:ifm/ifm:interfaces/ifm:interface[ifm:name=current()/../../bd:interface-name]/ifm:type='40GE' or
/ifm:ifm/ifm:interfaces/ifm:interface[ifm:name=current()/../../bd:interface-name]/ifm:type='10GE' or
/ifm:ifm/ifm:interfaces/ifm:interface[ifm:name=current()/../../bd:interface-name]/ifm:type='400GE' or
/ifm:ifm/ifm:interfaces/ifm:interface[ifm:name=current()/../../bd:interface-name]/ifm:type='25GE' or
/ifm:ifm/ifm:interfaces/ifm:interface[ifm:name=current()/../../bd:interface-name]/ifm:type='FlexE' or
/ifm:ifm/ifm:interfaces/ifm:interface[ifm:name=current()/../../bd:interface-name]/ifm:type='50GE' or
/ifm:ifm/ifm:interfaces/ifm:interface[ifm:name=current()/../../bd:interface-name]/ifm:type='50|100GE'" {
          tailf:xpath-root 3;
        }
        key "protocol-type action";
        description
          "Configure link-protocol action.";
        leaf protocol-type {
          type protocol-type;
          description
            "Protocol type.";
        }
        leaf action {
          type action-type;
          description
            "Protocol action.";
        }
        leaf mode {
          when "../action='transport'" {
            tailf:xpath-root 3;
          }
          type mode-evpn;
          mandatory true;
          description
            "Link-protocol transport mode.";
        }
      }
    }
  }
  augment "/ncs:devices/ncs:template/ncs:ned-id/ncs:config/evpl:evpl/evpl:instances/evpl:instance/evpl:interfaces/evpl:interface" {
    description
      "L2 protocol service for EVPL.";
    container protocol-actions {
      description
        "List of interface link protocol action.";
      list protocol-action {
        // NCS patched for predictable order
        ordered-by user;
        // NCS drop must statement
        // NCS drop must statement
        key "protocol-type action";
        description
          "Configure link-protocol action.";
        leaf protocol-type {
          type ncs_template_protocol-type;
          description
            "Protocol type.";
        }
        leaf action {
          type ncs_template_action-type;
          description
            "Protocol action.";
        }
        leaf mode {
          // NCS drop when statement
          type ncs_template_mode-evpn;
          // NCS drop mandatory statement
          description
            "Link-protocol transport mode.";
        }
      }
    }
  }
  augment "/ncs:devices/ncs:device/ncs:live-status/evpl:evpl/evpl:instances/evpl:instance/evpl:interfaces/evpl:interface" {
    description
      "L2 protocol service for EVPL.";
    container protocol-actions {
      tailf:ncs-device-type "netconf";
      tailf:display-when "not(../../../../../../../ncs:module) or ../../../../../../../ncs:module[ncs:name='huawei-l2protocol-fwd'] or (../../../../../../../ncs:live-status-protocol[not(ncs:capability)]) or (../../../../../../../ncs:live-status-protocol/ncs:capability/ncs:module[.='huawei-l2protocol-fwd'])";
      description
        "List of interface link protocol action.";
      list protocol-action {
        // NCS drop must statement
        // NCS drop must statement
        key "protocol-type action";
        description
          "Configure link-protocol action.";
        leaf protocol-type {
          type live_ncs_protocol-type;
          description
            "Protocol type.";
        }
        leaf action {
          type live_ncs_action-type;
          description
            "Protocol action.";
        }
        leaf mode {
          // NCS drop when statement
          type live_ncs_mode-evpn;
          // NCS drop mandatory statement
          description
            "Link-protocol transport mode.";
        }
      }
    }
  }
  augment "/ncs:devices/ncs:device/ncs:config/evpl:evpl/evpl:instances/evpl:instance/evpl:interfaces/evpl:interface" {
    description
      "L2 protocol service for EVPL.";
    container protocol-actions {
      tailf:ncs-device-type "netconf";
      tailf:display-when "not(../../../../../../../ncs:module) or ../../../../../../../ncs:module[ncs:name='huawei-l2protocol-fwd']";
      description
        "List of interface link protocol action.";
      list protocol-action {
        must "/ifm:ifm/ifm:interfaces/ifm:interface[ifm:name=current()/../../evpl:name]/ifm:type='Ethernet' or
/ifm:ifm/ifm:interfaces/ifm:interface[ifm:name=current()/../../evpl:name]/ifm:type='GigabitEthernet' or
/ifm:ifm/ifm:interfaces/ifm:interface[ifm:name=current()/../../evpl:name]/ifm:type='Eth-Trunk' or
/ifm:ifm/ifm:interfaces/ifm:interface[ifm:name=current()/../../evpl:name]/ifm:type='100GE' or
/ifm:ifm/ifm:interfaces/ifm:interface[ifm:name=current()/../../evpl:name]/ifm:type='XGigabitEthernet' or
/ifm:ifm/ifm:interfaces/ifm:interface[ifm:name=current()/../../evpl:name]/ifm:type='40GE' or
/ifm:ifm/ifm:interfaces/ifm:interface[ifm:name=current()/../../evpl:name]/ifm:type='10GE' or
/ifm:ifm/ifm:interfaces/ifm:interface[ifm:name=current()/../../evpl:name]/ifm:type='400GE' or
/ifm:ifm/ifm:interfaces/ifm:interface[ifm:name=current()/../../evpl:name]/ifm:type='25GE' or
/ifm:ifm/ifm:interfaces/ifm:interface[ifm:name=current()/../../evpl:name]/ifm:type='FlexE' or
/ifm:ifm/ifm:interfaces/ifm:interface[ifm:name=current()/../../evpl:name]/ifm:type='50GE' or
/ifm:ifm/ifm:interfaces/ifm:interface[ifm:name=current()/../../evpl:name]/ifm:type='50|100GE'" {
          tailf:xpath-root 3;
        }
        must "/ifm:ifm/ifm:interfaces/ifm:interface[ifm:name=current()/../../evpl:name]/ifm:parent-name and /ifm:ifm/ifm:interfaces/ifm:interface[ifm:name=current()/../../evpl:name]/ifm:l2-mode-enable='false'" {
          tailf:xpath-root 3;
        }
        key "protocol-type action";
        description
          "Configure link-protocol action.";
        leaf protocol-type {
          type protocol-type;
          description
            "Protocol type.";
        }
        leaf action {
          type action-type;
          description
            "Protocol action.";
        }
        leaf mode {
          when "../action='transport'" {
            tailf:xpath-root 3;
          }
          type mode-evpn;
          mandatory true;
          description
            "Link-protocol transport mode.";
        }
      }
    }
  }
  augment "/ncs:devices/ncs:template/ncs:ned-id/ncs:config/ifm:ifm/ifm:interfaces/ifm:interface/evpn:evpn" {
    description
      "L2 protocol service for EVPN.";
    container protocol-actions {
      // NCS drop when statement
      description
        "List of interface link protocol action.";
      list protocol-action {
        // NCS patched for predictable order
        ordered-by user;
        key "protocol-type action";
        description
          "Configure link-protocol action.";
        leaf protocol-type {
          type ncs_template_protocol-type;
          description
            "Protocol type.";
        }
        leaf action {
          type ncs_template_action-type;
          description
            "Protocol action.";
        }
        leaf mode {
          // NCS drop when statement
          type ncs_template_mode-evpn;
          // NCS drop mandatory statement
          description
            "Link-protocol transport mode.";
        }
      }
    }
  }
  augment "/ncs:devices/ncs:device/ncs:live-status/ifm:ifm/ifm:interfaces/ifm:interface/evpn:evpn" {
    description
      "L2 protocol service for EVPN.";
    container protocol-actions {
      tailf:ncs-device-type "netconf";
      tailf:display-when "not(../../../../../../ncs:module) or ../../../../../../ncs:module[ncs:name='huawei-l2protocol-fwd'] or (../../../../../../ncs:live-status-protocol[not(ncs:capability)]) or (../../../../../../ncs:live-status-protocol/ncs:capability/ncs:module[.='huawei-l2protocol-fwd'])";
      // NCS drop when statement
      description
        "List of interface link protocol action.";
      list protocol-action {
        key "protocol-type action";
        description
          "Configure link-protocol action.";
        leaf protocol-type {
          type live_ncs_protocol-type;
          description
            "Protocol type.";
        }
        leaf action {
          type live_ncs_action-type;
          description
            "Protocol action.";
        }
        leaf mode {
          // NCS drop when statement
          type live_ncs_mode-evpn;
          // NCS drop mandatory statement
          description
            "Link-protocol transport mode.";
        }
      }
    }
  }
  augment "/ncs:devices/ncs:device/ncs:config/ifm:ifm/ifm:interfaces/ifm:interface/evpn:evpn" {
    description
      "L2 protocol service for EVPN.";
    container protocol-actions {
      tailf:ncs-device-type "netconf";
      tailf:display-when "not(../../../../../../ncs:module) or ../../../../../../ncs:module[ncs:name='huawei-l2protocol-fwd']";
      when "(../../ifm:type='Ethernet' or ../../ifm:type='GigabitEthernet' or ../../ifm:type='Eth-Trunk' or ../../ifm:type='100GE' or ../../ifm:type='XGigabitEthernet' or ../../ifm:type='40GE' or ../../ifm:type='10GE' or ../../ifm:type='400GE' or ../../ifm:type='25GE' or ../../ifm:type='FlexE' or ../../ifm:type='50GE' or ../../ifm:type='50|100GE') and ../evpn:name" {
        tailf:xpath-root 3;
      }
      description
        "List of interface link protocol action.";
      list protocol-action {
        key "protocol-type action";
        description
          "Configure link-protocol action.";
        leaf protocol-type {
          type protocol-type;
          description
            "Protocol type.";
        }
        leaf action {
          type action-type;
          description
            "Protocol action.";
        }
        leaf mode {
          when "../action='transport'" {
            tailf:xpath-root 3;
          }
          type mode-evpn;
          mandatory true;
          description
            "Link-protocol transport mode.";
        }
      }
    }
  }
  augment "/ncs:devices/ncs:template/ncs:ned-id/ncs:config/devm:devm/devm:lpu-boards/devm:lpu-board" {
    description
      "L2 protocol transport configuration.";
    container link-protocol-transport {
      description
        "Configure transparent transmission of link-layer protocol information.";
      uses ncs_template_slot-linkprotocol-type;
    }
  }
  augment "/ncs:devices/ncs:device/ncs:live-status/devm:devm/devm:lpu-boards/devm:lpu-board" {
    description
      "L2 protocol transport configuration.";
    container link-protocol-transport {
      tailf:ncs-device-type "netconf";
      tailf:display-when "not(../../../../../ncs:module) or ../../../../../ncs:module[ncs:name='huawei-l2protocol-fwd'] or (../../../../../ncs:live-status-protocol[not(ncs:capability)]) or (../../../../../ncs:live-status-protocol/ncs:capability/ncs:module[.='huawei-l2protocol-fwd'])";
      description
        "Configure transparent transmission of link-layer protocol information.";
      uses live_ncs_slot-linkprotocol-type;
    }
  }
  augment "/ncs:devices/ncs:device/ncs:config/devm:devm/devm:lpu-boards/devm:lpu-board" {
    description
      "L2 protocol transport configuration.";
    container link-protocol-transport {
      tailf:ncs-device-type "netconf";
      tailf:display-when "not(../../../../../ncs:module) or ../../../../../ncs:module[ncs:name='huawei-l2protocol-fwd']";
      description
        "Configure transparent transmission of link-layer protocol information.";
      uses slot-linkprotocol-type;
    }
  }
  augment "/ncs:devices/ncs:template/ncs:ned-id/ncs:config/devm:devm/devm:mpu-boards/devm:mpu-board" {
    description
      "L2 protocol transport configuration.";
    container link-protocol-transport {
      description
        "Configure transparent transmission of link-layer protocol information.";
      uses ncs_template_slot-linkprotocol-type;
    }
  }
  augment "/ncs:devices/ncs:device/ncs:live-status/devm:devm/devm:mpu-boards/devm:mpu-board" {
    description
      "L2 protocol transport configuration.";
    container link-protocol-transport {
      tailf:ncs-device-type "netconf";
      tailf:display-when "not(../../../../../ncs:module) or ../../../../../ncs:module[ncs:name='huawei-l2protocol-fwd'] or (../../../../../ncs:live-status-protocol[not(ncs:capability)]) or (../../../../../ncs:live-status-protocol/ncs:capability/ncs:module[.='huawei-l2protocol-fwd'])";
      description
        "Configure transparent transmission of link-layer protocol information.";
      uses live_ncs_slot-linkprotocol-type;
    }
  }
  augment "/ncs:devices/ncs:device/ncs:config/devm:devm/devm:mpu-boards/devm:mpu-board" {
    description
      "L2 protocol transport configuration.";
    container link-protocol-transport {
      tailf:ncs-device-type "netconf";
      tailf:display-when "not(../../../../../ncs:module) or ../../../../../ncs:module[ncs:name='huawei-l2protocol-fwd']";
      description
        "Configure transparent transmission of link-layer protocol information.";
      uses slot-linkprotocol-type;
    }
  }
}
