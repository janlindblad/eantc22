module huawei-cfg-ext {
  // Generated by yanger -t ncs
  tailf:mount-id "huawei-nc-1.0:huawei-nc-1.0";
  tailf:ncs-device-type "netconf";

  yang-version 1.1;
  namespace "urn:huawei:yang:huawei-cfg-ext";
  prefix cfg-ext;

  import huawei-extension {
    prefix ext;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Display the changes information in the candidate datastore.";

  revision 2019-05-21 {
    description
      "Init revision.";
    reference "RFC 6241, Section 8.3.";
  }
  ext:task-name "config";

  augment "/ncs:devices/ncs:device/ncs:rpc" {
    container rpc-load-configuration-result {
      tailf:ncs-device-type "netconf";
      tailf:display-when "not(../../ncs:module) or ../../ncs:module[ncs:name='huawei-cfg-ext']";
      tailf:action load-configuration-result {
        tailf:actionpoint ncsproxy {
          tailf:internal;
        }
        description
          "The result of load configuration changes.";
        output {
          anydata result {
            description
              "Configuration loading result.";
          }
        }
      }
    }
  }
  augment "/ncs:devices/ncs:device-group/ncs:ned-id/ncs:rpc" {
    container rpc-load-configuration-result {
      tailf:ncs-device-type "netconf";
      tailf:display-when "/ncs:devices/ncs:device[ncs:name=current()/../../../ncs:member]/ncs:module[ncs:name='huawei-cfg-ext']";
      tailf:action load-configuration-result {
        tailf:actionpoint ncsproxy {
          tailf:internal;
        }
        description
          "The result of load configuration changes.";
        output {
          container "device" {
            leaf "name" {
              type string;
            }
            leaf "info" {
              type string;
            }
            container "result" {
              anydata result {
                description
                  "Configuration loading result.";
              }
            }
          }
        }
      }
    }
  }
  augment "/ncs:devices/ncs:device/ncs:rpc" {
    container rpc-load-configuration-change {
      tailf:ncs-device-type "netconf";
      tailf:display-when "not(../../ncs:module) or ../../ncs:module[ncs:name='huawei-cfg-ext']";
      tailf:action load-configuration-change {
        tailf:actionpoint ncsproxy {
          tailf:internal;
        }
        description
          "After configuration difference loading, users can get to know the result of configuration difference loading through load-configuration-result node.";
        input {
          anydata changes {
            description
              "Configuration change to be loaded.";
          }
        }
      }
    }
  }
  augment "/ncs:devices/ncs:device-group/ncs:ned-id/ncs:rpc" {
    container rpc-load-configuration-change {
      tailf:ncs-device-type "netconf";
      tailf:display-when "/ncs:devices/ncs:device[ncs:name=current()/../../../ncs:member]/ncs:module[ncs:name='huawei-cfg-ext']";
      tailf:action load-configuration-change {
        tailf:actionpoint ncsproxy {
          tailf:internal;
        }
        description
          "After configuration difference loading, users can get to know the result of configuration difference loading through load-configuration-result node.";
        input {
          anydata changes {
            description
              "Configuration change to be loaded.";
          }
        }
      }
    }
  }
  augment "/ncs:devices/ncs:device/ncs:rpc" {
    container rpc-get-configuration-change {
      tailf:ncs-device-type "netconf";
      tailf:display-when "not(../../ncs:module) or ../../ncs:module[ncs:name='huawei-cfg-ext']";
      tailf:action get-configuration-change {
        tailf:actionpoint ncsproxy {
          tailf:internal;
        }
        description
          "Get configuration change information.";
        input {
          container source {
            description
              "The source configuration.";
            choice config-source {
              description
                "Particular source configuration to compare from.";
              case checkpoint {
                description
                  "Configuration checkpoints.";
                leaf commit-id {
                  type string {
                    length "1..20";
                  }
                  description
                    "Uniquely identify a configuration checkpoint.";
                }
              }
              case running {
                description
                  "Running configuration.";
                leaf running {
                  type empty;
                  description
                    "Running configuration.";
                }
              }
              case url {
                description
                  "The URL-based configuration.";
                leaf url {
                  type string {
                    length "1..256";
                  }
                  description
                    "The URL-based configuration.";
                }
              }
            }
          }
          container target {
            description
              "The target configuration.";
            choice config-target {
              description
                "Particular target configuration to compare to.";
              case checkpoint {
                description
                  "Configuration checkpoints.";
                leaf commit-id {
                  type string {
                    length "1..20";
                  }
                  description
                    "Uniquely identify a configuration checkpoint.";
                }
              }
              case running {
                description
                  "Running configuration.";
                leaf running {
                  type empty;
                  description
                    "Running configuration.";
                }
              }
              case url {
                description
                  "The URL-based configuration.";
                leaf url {
                  type string {
                    length "1..256";
                  }
                  description
                    "The URL-based configuration.";
                }
              }
            }
          }
          leaf rollback-tag {
            type empty;
            description
              "With rollback tag.";
          }
        }
        output {
          anydata changes {
            description
              "Configuration changes.";
          }
        }
      }
    }
  }
  augment "/ncs:devices/ncs:device-group/ncs:ned-id/ncs:rpc" {
    container rpc-get-configuration-change {
      tailf:ncs-device-type "netconf";
      tailf:display-when "/ncs:devices/ncs:device[ncs:name=current()/../../../ncs:member]/ncs:module[ncs:name='huawei-cfg-ext']";
      tailf:action get-configuration-change {
        tailf:actionpoint ncsproxy {
          tailf:internal;
        }
        description
          "Get configuration change information.";
        input {
          container source {
            description
              "The source configuration.";
            choice config-source {
              description
                "Particular source configuration to compare from.";
              case checkpoint {
                description
                  "Configuration checkpoints.";
                leaf commit-id {
                  type string {
                    length "1..20";
                  }
                  description
                    "Uniquely identify a configuration checkpoint.";
                }
              }
              case running {
                description
                  "Running configuration.";
                leaf running {
                  type empty;
                  description
                    "Running configuration.";
                }
              }
              case url {
                description
                  "The URL-based configuration.";
                leaf url {
                  type string {
                    length "1..256";
                  }
                  description
                    "The URL-based configuration.";
                }
              }
            }
          }
          container target {
            description
              "The target configuration.";
            choice config-target {
              description
                "Particular target configuration to compare to.";
              case checkpoint {
                description
                  "Configuration checkpoints.";
                leaf commit-id {
                  type string {
                    length "1..20";
                  }
                  description
                    "Uniquely identify a configuration checkpoint.";
                }
              }
              case running {
                description
                  "Running configuration.";
                leaf running {
                  type empty;
                  description
                    "Running configuration.";
                }
              }
              case url {
                description
                  "The URL-based configuration.";
                leaf url {
                  type string {
                    length "1..256";
                  }
                  description
                    "The URL-based configuration.";
                }
              }
            }
          }
          leaf rollback-tag {
            type empty;
            description
              "With rollback tag.";
          }
        }
        output {
          container "device" {
            leaf "name" {
              type string;
            }
            leaf "info" {
              type string;
            }
            container "result" {
              anydata changes {
                description
                  "Configuration changes.";
              }
            }
          }
        }
      }
    }
  }
  augment "/ncs:devices/ncs:device/ncs:rpc" {
    container rpc-get-candidate-change {
      tailf:ncs-device-type "netconf";
      tailf:display-when "not(../../ncs:module) or ../../ncs:module[ncs:name='huawei-cfg-ext']";
      tailf:action get-candidate-change {
        tailf:actionpoint ncsproxy {
          tailf:internal;
        }
        description
          "Configuration change information.";
        output {
          anydata effective-changes {
            description
              "Configuration change information recorded in the candidate datastore.";
          }
          anydata ineffective-changes {
            description
              "Changes in configurations that have not taken effect in the candidate datastore.";
          }
        }
      }
    }
  }
  augment "/ncs:devices/ncs:device-group/ncs:ned-id/ncs:rpc" {
    container rpc-get-candidate-change {
      tailf:ncs-device-type "netconf";
      tailf:display-when "/ncs:devices/ncs:device[ncs:name=current()/../../../ncs:member]/ncs:module[ncs:name='huawei-cfg-ext']";
      tailf:action get-candidate-change {
        tailf:actionpoint ncsproxy {
          tailf:internal;
        }
        description
          "Configuration change information.";
        output {
          container "device" {
            leaf "name" {
              type string;
            }
            leaf "info" {
              type string;
            }
            container "result" {
              anydata effective-changes {
                description
                  "Configuration change information recorded in the candidate datastore.";
              }
              anydata ineffective-changes {
                description
                  "Changes in configurations that have not taken effect in the candidate datastore.";
              }
            }
          }
        }
      }
    }
  }
}
