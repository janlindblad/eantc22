submodule huawei-snmp-type {
  // Generated by yanger -t ncs
  tailf:mount-id "huawei-nc-1.0:huawei-nc-1.0";

  belongs-to huawei-snmp {
    prefix snmp;
  }

  import ietf-yang-types {
    prefix yang;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "SNMP type.";

  revision 2019-12-26 {
    description
      "Modify description syntax.";
    reference "Huawei private.";
  }
  revision 2019-11-29 {
    description
      "YANG refactoring extension.";
    reference "Huawei private.";
  }
  revision 2019-11-18 {
    description
      "YANG refactoring extension.";
    reference "Huawei private.";
  }
  revision 2019-04-23 {
    description
      "Init revision.";
    reference "Huawei private.";
  }

  typedef ncs_template_snmp-engine-id {
    type string;
    description
      "The engine ID specified as a list of colon-specified
       hexadecimal octets, e.g., '80:00:02:b8:04:61:62:63'.";
  }

  typedef ncs_template_snmp-privacy {
    type string;
    description
      "SNMP privacy enum.";
  }

  typedef ncs_template_snmp-local-privacy {
    type string;
    description
      "SNMP local-user privacy enum.";
  }

  typedef ncs_template_snmp-version {
    type string;
    description
      "SNMP version enum.";
  }

  typedef ncs_template_snmp-notify {
    type string;
    description
      "SNMP notify type enum.";
  }

  typedef ncs_template_snmp-security-level {
    type string;
    description
      "SNMP security level enum.";
  }

  typedef ncs_template_snmp-filter {
    type string;
    description
      "SNMP filter type enum.";
  }

  typedef ncs_template_snmp-access {
    type string;
    description
      "SNMP access enum.";
  }

  typedef ncs_template_snmp-authenmode {
    type string;
    description
      "SNMP authentication protocol enum.";
  }

  typedef ncs_template_snmp-local-authenmode {
    type string;
    description
      "SNMP local-user authentication protocol enum.";
  }

  typedef ncs_template_snmp-domain {
    type string;
    description
      "SNMP address domain enum.";
  }

  typedef ncs_template_snmp-security-model {
    type string;
    description
      "SNMP security model enum.";
  }

  typedef ncs_template_snmp-target-host-version {
    type string;
    description
      "SNMP target-host version enum.";
  }

  typedef ncs_template_snmp-proxy-type {
    type string;
    description
      "SNMP proxy type enum.";
  }

  typedef ncs_rpc_notif_snmp-engine-id {
    type yang:hex-string {
      pattern '([0-9a-fA-F]){2}(:([0-9a-fA-F]){2}){4,31}';
    }
    description
      "The engine ID specified as a list of colon-specified
       hexadecimal octets, e.g., '80:00:02:b8:04:61:62:63'.";
  }

  typedef ncs_rpc_notif_snmp-privacy {
    type enumeration {
      enum "noPriv" {
        value 0;
        description
          "Without any encryption algorithm.";
      }
      enum "des56" {
        value 1;
        description
          "DES56 encryption algorithm.";
      }
      enum "3des168" {
        value 5;
        description
          "3DES168 encryption algorithm.";
      }
      enum "aes128" {
        value 2;
        description
          "AES128 encryption algorithm.";
      }
      enum "aes192" {
        value 3;
        description
          "AES192 encryption algorithm.";
      }
      enum "aes256" {
        value 4;
        description
          "AES256 encryption algorithm.";
      }
    }
    description
      "SNMP privacy enum.";
  }

  typedef ncs_rpc_notif_snmp-local-privacy {
    type enumeration {
      enum "des56" {
        value 1;
        description
          "DES56 encryption algorithm.";
      }
      enum "3des168" {
        value 5;
        description
          "3DES168 encryption algorithm.";
      }
      enum "aes128" {
        value 2;
        description
          "AES128 encryption algorithm.";
      }
      enum "aes192" {
        value 3;
        description
          "AES192 encryption algorithm.";
      }
      enum "aes256" {
        value 4;
        description
          "AES256 encryption algorithm.";
      }
    }
    description
      "SNMP local-user privacy enum.";
  }

  typedef ncs_rpc_notif_snmp-version {
    type enumeration {
      enum "none" {
        value 0;
        description
          "None Version.";
      }
      enum "v1" {
        value 1;
        description
          "SNMP v1.";
      }
      enum "v2c" {
        value 2;
        description
          "SNMP v2c.";
      }
      enum "v1v2c" {
        value 3;
        description
          "SNMP v1v2c.";
      }
      enum "v3" {
        value 4;
        description
          "SNMP v3.";
      }
      enum "v1v3" {
        value 5;
        description
          "SNMP v1v3.";
      }
      enum "v2cv3" {
        value 6;
        description
          "SNMP v2cv3.";
      }
      enum "all" {
        value 7;
        description
          "All SNMP Versions.";
      }
    }
    description
      "SNMP version enum.";
  }

  typedef ncs_rpc_notif_snmp-notify {
    type enumeration {
      enum "trap" {
        value 1;
        description
          "Trap.";
      }
      enum "inform" {
        value 2;
        description
          "Inform.";
      }
    }
    description
      "SNMP notify type enum.";
  }

  typedef ncs_rpc_notif_snmp-security-level {
    type enumeration {
      enum "noAuthNoPriv" {
        value 1;
        description
          "No Authentication No Privacy.";
      }
      enum "authentication" {
        value 2;
        description
          "Authentication No Privacy.";
      }
      enum "privacy" {
        value 3;
        description
          "Authentication Privacy.";
      }
    }
    description
      "SNMP security level enum.";
  }

  typedef ncs_rpc_notif_snmp-filter {
    type enumeration {
      enum "included" {
        value 1;
        description
          "Included.";
      }
      enum "excluded" {
        value 2;
        description
          "Excluded.";
      }
    }
    description
      "SNMP filter type enum.";
  }

  typedef ncs_rpc_notif_snmp-access {
    type enumeration {
      enum "read" {
        value 0;
        description
          "Read access.";
      }
      enum "write" {
        value 1;
        description
          "Write access.";
      }
    }
    description
      "SNMP access enum.";
  }

  typedef ncs_rpc_notif_snmp-authenmode {
    type enumeration {
      enum "noAuth" {
        value 0;
        description
          "Without any authentication algorithm.";
      }
      enum "md5" {
        value 1;
        description
          "MD5 authentication algorithm.";
      }
      enum "sha" {
        value 2;
        description
          "SHA authentication algorithm.";
      }
      enum "sha2-224" {
        value 5;
        description
          "SHA2-224 authentication algorithm.";
      }
      enum "sha2-256" {
        value 6;
        description
          "SHA2-256 authentication algorithm.";
      }
      enum "sha2-384" {
        value 7;
        description
          "SHA2-384 authentication algorithm.";
      }
      enum "sha2-512" {
        value 8;
        description
          "SHA2-512 authentication algorithm.";
      }
    }
    description
      "SNMP authentication protocol enum.";
  }

  typedef ncs_rpc_notif_snmp-local-authenmode {
    type enumeration {
      enum "md5" {
        value 1;
        description
          "MD5 authentication algorithm.";
      }
      enum "sha" {
        value 2;
        description
          "SHA authentication algorithm.";
      }
      enum "sha2-224" {
        value 5;
        description
          "SHA2-224 authentication algorithm.";
      }
      enum "sha2-256" {
        value 6;
        description
          "SHA2-256 authentication algorithm.";
      }
      enum "sha2-384" {
        value 7;
        description
          "SHA2-384 authentication algorithm.";
      }
      enum "sha2-512" {
        value 8;
        description
          "SHA2-512 authentication algorithm.";
      }
    }
    description
      "SNMP local-user authentication protocol enum.";
  }

  typedef ncs_rpc_notif_snmp-domain {
    type enumeration {
      enum "snmpUDPDomain" {
        value 1;
        description
          "SNMP UDP Domain.";
      }
    }
    description
      "SNMP address domain enum.";
  }

  typedef ncs_rpc_notif_snmp-security-model {
    type enumeration {
      enum "v1" {
        value 1;
        description
          "SNMPv1: SNMPv1.";
      }
      enum "v2c" {
        value 2;
        description
          "SNMPv2c: SNMPv2c.";
      }
      enum "usm" {
        value 3;
        description
          "USM: USM.";
      }
    }
    description
      "SNMP security model enum.";
  }

  typedef ncs_rpc_notif_snmp-target-host-version {
    type enumeration {
      enum "v1" {
        value 0;
        description
          "V1.";
      }
      enum "v2c" {
        value 1;
        description
          "V2c.";
      }
      enum "v3" {
        value 2;
        description
          "V3.";
      }
    }
    description
      "SNMP target-host version enum.";
  }

  typedef ncs_rpc_notif_snmp-proxy-type {
    type enumeration {
      enum "read" {
        value 1;
        description
          "Read access.";
      }
      enum "write" {
        value 2;
        description
          "Write access.";
      }
      enum "trap" {
        value 3;
        description
          "Trap.";
      }
      enum "inform" {
        value 4;
        description
          "Inform.";
      }
    }
    description
      "SNMP proxy type enum.";
  }

  typedef live_ncs_snmp-engine-id {
    type yang:hex-string {
      pattern '([0-9a-fA-F]){2}(:([0-9a-fA-F]){2}){4,31}';
    }
    description
      "The engine ID specified as a list of colon-specified
       hexadecimal octets, e.g., '80:00:02:b8:04:61:62:63'.";
  }

  typedef live_ncs_snmp-privacy {
    type enumeration {
      enum "noPriv" {
        value 0;
        description
          "Without any encryption algorithm.";
      }
      enum "des56" {
        value 1;
        description
          "DES56 encryption algorithm.";
      }
      enum "3des168" {
        value 5;
        description
          "3DES168 encryption algorithm.";
      }
      enum "aes128" {
        value 2;
        description
          "AES128 encryption algorithm.";
      }
      enum "aes192" {
        value 3;
        description
          "AES192 encryption algorithm.";
      }
      enum "aes256" {
        value 4;
        description
          "AES256 encryption algorithm.";
      }
    }
    description
      "SNMP privacy enum.";
  }

  typedef live_ncs_snmp-local-privacy {
    type enumeration {
      enum "des56" {
        value 1;
        description
          "DES56 encryption algorithm.";
      }
      enum "3des168" {
        value 5;
        description
          "3DES168 encryption algorithm.";
      }
      enum "aes128" {
        value 2;
        description
          "AES128 encryption algorithm.";
      }
      enum "aes192" {
        value 3;
        description
          "AES192 encryption algorithm.";
      }
      enum "aes256" {
        value 4;
        description
          "AES256 encryption algorithm.";
      }
    }
    description
      "SNMP local-user privacy enum.";
  }

  typedef live_ncs_snmp-version {
    type enumeration {
      enum "none" {
        value 0;
        description
          "None Version.";
      }
      enum "v1" {
        value 1;
        description
          "SNMP v1.";
      }
      enum "v2c" {
        value 2;
        description
          "SNMP v2c.";
      }
      enum "v1v2c" {
        value 3;
        description
          "SNMP v1v2c.";
      }
      enum "v3" {
        value 4;
        description
          "SNMP v3.";
      }
      enum "v1v3" {
        value 5;
        description
          "SNMP v1v3.";
      }
      enum "v2cv3" {
        value 6;
        description
          "SNMP v2cv3.";
      }
      enum "all" {
        value 7;
        description
          "All SNMP Versions.";
      }
    }
    description
      "SNMP version enum.";
  }

  typedef live_ncs_snmp-notify {
    type enumeration {
      enum "trap" {
        value 1;
        description
          "Trap.";
      }
      enum "inform" {
        value 2;
        description
          "Inform.";
      }
    }
    description
      "SNMP notify type enum.";
  }

  typedef live_ncs_snmp-security-level {
    type enumeration {
      enum "noAuthNoPriv" {
        value 1;
        description
          "No Authentication No Privacy.";
      }
      enum "authentication" {
        value 2;
        description
          "Authentication No Privacy.";
      }
      enum "privacy" {
        value 3;
        description
          "Authentication Privacy.";
      }
    }
    description
      "SNMP security level enum.";
  }

  typedef live_ncs_snmp-filter {
    type enumeration {
      enum "included" {
        value 1;
        description
          "Included.";
      }
      enum "excluded" {
        value 2;
        description
          "Excluded.";
      }
    }
    description
      "SNMP filter type enum.";
  }

  typedef live_ncs_snmp-access {
    type enumeration {
      enum "read" {
        value 0;
        description
          "Read access.";
      }
      enum "write" {
        value 1;
        description
          "Write access.";
      }
    }
    description
      "SNMP access enum.";
  }

  typedef live_ncs_snmp-authenmode {
    type enumeration {
      enum "noAuth" {
        value 0;
        description
          "Without any authentication algorithm.";
      }
      enum "md5" {
        value 1;
        description
          "MD5 authentication algorithm.";
      }
      enum "sha" {
        value 2;
        description
          "SHA authentication algorithm.";
      }
      enum "sha2-224" {
        value 5;
        description
          "SHA2-224 authentication algorithm.";
      }
      enum "sha2-256" {
        value 6;
        description
          "SHA2-256 authentication algorithm.";
      }
      enum "sha2-384" {
        value 7;
        description
          "SHA2-384 authentication algorithm.";
      }
      enum "sha2-512" {
        value 8;
        description
          "SHA2-512 authentication algorithm.";
      }
    }
    description
      "SNMP authentication protocol enum.";
  }

  typedef live_ncs_snmp-local-authenmode {
    type enumeration {
      enum "md5" {
        value 1;
        description
          "MD5 authentication algorithm.";
      }
      enum "sha" {
        value 2;
        description
          "SHA authentication algorithm.";
      }
      enum "sha2-224" {
        value 5;
        description
          "SHA2-224 authentication algorithm.";
      }
      enum "sha2-256" {
        value 6;
        description
          "SHA2-256 authentication algorithm.";
      }
      enum "sha2-384" {
        value 7;
        description
          "SHA2-384 authentication algorithm.";
      }
      enum "sha2-512" {
        value 8;
        description
          "SHA2-512 authentication algorithm.";
      }
    }
    description
      "SNMP local-user authentication protocol enum.";
  }

  typedef live_ncs_snmp-domain {
    type enumeration {
      enum "snmpUDPDomain" {
        value 1;
        description
          "SNMP UDP Domain.";
      }
    }
    description
      "SNMP address domain enum.";
  }

  typedef live_ncs_snmp-security-model {
    type enumeration {
      enum "v1" {
        value 1;
        description
          "SNMPv1: SNMPv1.";
      }
      enum "v2c" {
        value 2;
        description
          "SNMPv2c: SNMPv2c.";
      }
      enum "usm" {
        value 3;
        description
          "USM: USM.";
      }
    }
    description
      "SNMP security model enum.";
  }

  typedef live_ncs_snmp-target-host-version {
    type enumeration {
      enum "v1" {
        value 0;
        description
          "V1.";
      }
      enum "v2c" {
        value 1;
        description
          "V2c.";
      }
      enum "v3" {
        value 2;
        description
          "V3.";
      }
    }
    description
      "SNMP target-host version enum.";
  }

  typedef live_ncs_snmp-proxy-type {
    type enumeration {
      enum "read" {
        value 1;
        description
          "Read access.";
      }
      enum "write" {
        value 2;
        description
          "Write access.";
      }
      enum "trap" {
        value 3;
        description
          "Trap.";
      }
      enum "inform" {
        value 4;
        description
          "Inform.";
      }
    }
    description
      "SNMP proxy type enum.";
  }

  typedef snmp-engine-id {
    type yang:hex-string {
      pattern '([0-9a-fA-F]){2}(:([0-9a-fA-F]){2}){4,31}';
    }
    description
      "The engine ID specified as a list of colon-specified
       hexadecimal octets, e.g., '80:00:02:b8:04:61:62:63'.";
  }

  typedef snmp-privacy {
    type enumeration {
      enum "noPriv" {
        value 0;
        description
          "Without any encryption algorithm.";
      }
      enum "des56" {
        value 1;
        description
          "DES56 encryption algorithm.";
      }
      enum "3des168" {
        value 5;
        description
          "3DES168 encryption algorithm.";
      }
      enum "aes128" {
        value 2;
        description
          "AES128 encryption algorithm.";
      }
      enum "aes192" {
        value 3;
        description
          "AES192 encryption algorithm.";
      }
      enum "aes256" {
        value 4;
        description
          "AES256 encryption algorithm.";
      }
    }
    description
      "SNMP privacy enum.";
  }

  typedef snmp-local-privacy {
    type enumeration {
      enum "des56" {
        value 1;
        description
          "DES56 encryption algorithm.";
      }
      enum "3des168" {
        value 5;
        description
          "3DES168 encryption algorithm.";
      }
      enum "aes128" {
        value 2;
        description
          "AES128 encryption algorithm.";
      }
      enum "aes192" {
        value 3;
        description
          "AES192 encryption algorithm.";
      }
      enum "aes256" {
        value 4;
        description
          "AES256 encryption algorithm.";
      }
    }
    description
      "SNMP local-user privacy enum.";
  }

  typedef snmp-version {
    type enumeration {
      enum "none" {
        value 0;
        description
          "None Version.";
      }
      enum "v1" {
        value 1;
        description
          "SNMP v1.";
      }
      enum "v2c" {
        value 2;
        description
          "SNMP v2c.";
      }
      enum "v1v2c" {
        value 3;
        description
          "SNMP v1v2c.";
      }
      enum "v3" {
        value 4;
        description
          "SNMP v3.";
      }
      enum "v1v3" {
        value 5;
        description
          "SNMP v1v3.";
      }
      enum "v2cv3" {
        value 6;
        description
          "SNMP v2cv3.";
      }
      enum "all" {
        value 7;
        description
          "All SNMP Versions.";
      }
    }
    description
      "SNMP version enum.";
  }

  typedef snmp-notify {
    type enumeration {
      enum "trap" {
        value 1;
        description
          "Trap.";
      }
      enum "inform" {
        value 2;
        description
          "Inform.";
      }
    }
    description
      "SNMP notify type enum.";
  }

  typedef snmp-security-level {
    type enumeration {
      enum "noAuthNoPriv" {
        value 1;
        description
          "No Authentication No Privacy.";
      }
      enum "authentication" {
        value 2;
        description
          "Authentication No Privacy.";
      }
      enum "privacy" {
        value 3;
        description
          "Authentication Privacy.";
      }
    }
    description
      "SNMP security level enum.";
  }

  typedef snmp-filter {
    type enumeration {
      enum "included" {
        value 1;
        description
          "Included.";
      }
      enum "excluded" {
        value 2;
        description
          "Excluded.";
      }
    }
    description
      "SNMP filter type enum.";
  }

  typedef snmp-access {
    type enumeration {
      enum "read" {
        value 0;
        description
          "Read access.";
      }
      enum "write" {
        value 1;
        description
          "Write access.";
      }
    }
    description
      "SNMP access enum.";
  }

  typedef snmp-authenmode {
    type enumeration {
      enum "noAuth" {
        value 0;
        description
          "Without any authentication algorithm.";
      }
      enum "md5" {
        value 1;
        description
          "MD5 authentication algorithm.";
      }
      enum "sha" {
        value 2;
        description
          "SHA authentication algorithm.";
      }
      enum "sha2-224" {
        value 5;
        description
          "SHA2-224 authentication algorithm.";
      }
      enum "sha2-256" {
        value 6;
        description
          "SHA2-256 authentication algorithm.";
      }
      enum "sha2-384" {
        value 7;
        description
          "SHA2-384 authentication algorithm.";
      }
      enum "sha2-512" {
        value 8;
        description
          "SHA2-512 authentication algorithm.";
      }
    }
    description
      "SNMP authentication protocol enum.";
  }

  typedef snmp-local-authenmode {
    type enumeration {
      enum "md5" {
        value 1;
        description
          "MD5 authentication algorithm.";
      }
      enum "sha" {
        value 2;
        description
          "SHA authentication algorithm.";
      }
      enum "sha2-224" {
        value 5;
        description
          "SHA2-224 authentication algorithm.";
      }
      enum "sha2-256" {
        value 6;
        description
          "SHA2-256 authentication algorithm.";
      }
      enum "sha2-384" {
        value 7;
        description
          "SHA2-384 authentication algorithm.";
      }
      enum "sha2-512" {
        value 8;
        description
          "SHA2-512 authentication algorithm.";
      }
    }
    description
      "SNMP local-user authentication protocol enum.";
  }

  typedef snmp-domain {
    type enumeration {
      enum "snmpUDPDomain" {
        value 1;
        description
          "SNMP UDP Domain.";
      }
    }
    description
      "SNMP address domain enum.";
  }

  typedef snmp-security-model {
    type enumeration {
      enum "v1" {
        value 1;
        description
          "SNMPv1: SNMPv1.";
      }
      enum "v2c" {
        value 2;
        description
          "SNMPv2c: SNMPv2c.";
      }
      enum "usm" {
        value 3;
        description
          "USM: USM.";
      }
    }
    description
      "SNMP security model enum.";
  }

  typedef snmp-target-host-version {
    type enumeration {
      enum "v1" {
        value 0;
        description
          "V1.";
      }
      enum "v2c" {
        value 1;
        description
          "V2c.";
      }
      enum "v3" {
        value 2;
        description
          "V3.";
      }
    }
    description
      "SNMP target-host version enum.";
  }

  typedef snmp-proxy-type {
    type enumeration {
      enum "read" {
        value 1;
        description
          "Read access.";
      }
      enum "write" {
        value 2;
        description
          "Write access.";
      }
      enum "trap" {
        value 3;
        description
          "Trap.";
      }
      enum "inform" {
        value 4;
        description
          "Inform.";
      }
    }
    description
      "SNMP proxy type enum.";
  }
}
