module huawei-vty {
  // Generated by yanger -t ncs
  tailf:mount-id "huawei-nc-1.0:huawei-nc-1.0";
  tailf:ncs-device-type "netconf";

  namespace "urn:huawei:yang:huawei-vty";
  prefix vty;

  import huawei-pub-type {
    prefix pub-type;
  }
  import huawei-acl {
    prefix acl;
  }
  import huawei-extension {
    prefix ext;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "VTY.";

  revision 2020-03-02 {
    description
      "Initial revision.";
    reference "Huawei private.";
  }
  ext:task-name "tty";

  typedef ncs_template_vty-authmode-type {
    type string;
    description
      "VTY and TTY authentication mode type.";
  }

  typedef ncs_template_vty-proto-inbnd-type {
    type string;
    description
      "VTY and TTY ProtoInbnd.";
  }

  typedef ncs_template_vty-bool-type {
    type string;
    description
      "VTY and TTY boolean type.";
  }

  typedef ncs_rpc_notif_vty-authmode-type {
    type enumeration {
      enum "none" {
        value 1;
        description
          "VTY authentication mode none.";
      }
      enum "password" {
        value 2;
        description
          "VTY authentication mode password.";
      }
      enum "aaa" {
        value 3;
        description
          "VTY authentication mode aaa.";
      }
      enum "init" {
        value 4;
        description
          "Undo authentication mode.";
      }
    }
    description
      "VTY and TTY authentication mode type.";
  }

  typedef ncs_rpc_notif_vty-proto-inbnd-type {
    type enumeration {
      enum "all" {
        value 0;
        description
          "Protocol inbound all.";
      }
      enum "ssh" {
        value 1;
        description
          "Protocol inbound ssh.";
      }
      enum "telnet" {
        value 2;
        description
          "Protocol inbound telnet.";
      }
    }
    description
      "VTY and TTY ProtoInbnd.";
  }

  typedef ncs_rpc_notif_vty-bool-type {
    type enumeration {
      enum "false" {
        value 0;
        description
          "VTY shell disable.";
      }
      enum "true" {
        value 1;
        description
          "VTY shell enable.";
      }
    }
    description
      "VTY and TTY boolean type.";
  }

  typedef live_ncs_vty-authmode-type {
    type enumeration {
      enum "none" {
        value 1;
        description
          "VTY authentication mode none.";
      }
      enum "password" {
        value 2;
        description
          "VTY authentication mode password.";
      }
      enum "aaa" {
        value 3;
        description
          "VTY authentication mode aaa.";
      }
      enum "init" {
        value 4;
        description
          "Undo authentication mode.";
      }
    }
    description
      "VTY and TTY authentication mode type.";
  }

  typedef live_ncs_vty-proto-inbnd-type {
    type enumeration {
      enum "all" {
        value 0;
        description
          "Protocol inbound all.";
      }
      enum "ssh" {
        value 1;
        description
          "Protocol inbound ssh.";
      }
      enum "telnet" {
        value 2;
        description
          "Protocol inbound telnet.";
      }
    }
    description
      "VTY and TTY ProtoInbnd.";
  }

  typedef live_ncs_vty-bool-type {
    type enumeration {
      enum "false" {
        value 0;
        description
          "VTY shell disable.";
      }
      enum "true" {
        value 1;
        description
          "VTY shell enable.";
      }
    }
    description
      "VTY and TTY boolean type.";
  }

  typedef vty-authmode-type {
    type enumeration {
      enum "none" {
        value 1;
        description
          "VTY authentication mode none.";
      }
      enum "password" {
        value 2;
        description
          "VTY authentication mode password.";
      }
      enum "aaa" {
        value 3;
        description
          "VTY authentication mode aaa.";
      }
      enum "init" {
        value 4;
        description
          "Undo authentication mode.";
      }
    }
    description
      "VTY and TTY authentication mode type.";
  }

  typedef vty-proto-inbnd-type {
    type enumeration {
      enum "all" {
        value 0;
        description
          "Protocol inbound all.";
      }
      enum "ssh" {
        value 1;
        description
          "Protocol inbound ssh.";
      }
      enum "telnet" {
        value 2;
        description
          "Protocol inbound telnet.";
      }
    }
    description
      "VTY and TTY ProtoInbnd.";
  }

  typedef vty-bool-type {
    type enumeration {
      enum "false" {
        value 0;
        description
          "VTY shell disable.";
      }
      enum "true" {
        value 1;
        description
          "VTY shell enable.";
      }
    }
    description
      "VTY and TTY boolean type.";
  }

  augment "/ncs:devices/ncs:device/ncs:config" {
    container vty {
      tailf:ncs-device-type "netconf";
      tailf:display-when "not(../../ncs:module) or ../../ncs:module[ncs:name='huawei-vty']";
      description
        "VTY.";
      container lines {
        description
          "List of VTY specific configuration list.";
        list line {
          key "index";
          max-elements 21;
          description
            "Configure VTY specific configuration policy.";
          ext:generated-by "system";
          leaf index {
            type uint8 {
              range "34..54";
            }
            description
              "Terminal line index.";
          }
          leaf idle-timeout-min {
            type uint16 {
              range "0..35791";
            }
            units "min";
            default "10";
            ext:support-filter "true";
            description
              "Idle timeout in minutes.";
          }
          leaf idle-timeout-sec {
            type uint16 {
              range "0..59";
            }
            units "s";
            default "0";
            ext:support-filter "true";
            description
              "Idle timeout in seconds.";
          }
          leaf auth-mode {
            type vty-authmode-type;
            must "(../auth-mode='aaa' and ../proto-inbound='ssh') or not(../proto-inbound='ssh')" {
              tailf:xpath-root 3;
            }
            default "init";
            ext:support-filter "true";
            description
              "Authentication Mode.";
          }
          leaf auth-password {
            type pub-type:password {
              length "8..128";
            }
            must "../auth-mode='password'" {
              tailf:xpath-root 3;
            }
            description
              "Authentication Password.";
          }
          leaf privilege-level {
            type uint8 {
              range "0..15";
            }
            default "0";
            ext:support-filter "true";
            description
              "User privilege level.";
          }
          leaf history-cmd-size {
            type uint16 {
              range "0..256";
            }
            default "10";
            ext:support-filter "true";
            description
              "History command buffer size. Describes the number of commands will be stored in history.";
          }
          leaf screen-length {
            type uint16 {
              range "0..512";
            }
            default "24";
            ext:support-filter "true";
            description
              "VTY screen length value.";
          }
          leaf shell-enable {
            type vty-bool-type;
            default "true";
            ext:support-filter "true";
            description
              "Shell (Enable/Disable).";
          }
          leaf acl4-inbound {
            type leafref {
              path "/ncs:devices/ncs:device/ncs:config/acl:acl/acl:groups/acl:group/acl:identity" {
                tailf:xpath-root 3;
              }
            }
            ext:support-filter "true";
            must "/acl:acl/acl:groups/acl:group[acl:identity=current()]/acl:type='basic' or /acl:acl/acl:groups/acl:group[acl:identity=current()]/acl:type='advance'" {
              tailf:xpath-root 3;
            }
            description
              "Acl inbound name or number for IPv4 protocol.";
          }
          leaf acl4-outbound {
            type leafref {
              path "/ncs:devices/ncs:device/ncs:config/acl:acl/acl:groups/acl:group/acl:identity" {
                tailf:xpath-root 3;
              }
            }
            ext:support-filter "true";
            must "/acl:acl/acl:groups/acl:group[acl:identity=current()]/acl:type='basic' or /acl:acl/acl:groups/acl:group[acl:identity=current()]/acl:type='advance'" {
              tailf:xpath-root 3;
            }
            description
              "Acl outbound name or number for IPv4 protocol.";
          }
          leaf acl6-inbound {
            type leafref {
              path "/ncs:devices/ncs:device/ncs:config/acl:acl/acl:group6s/acl:group6/acl:identity" {
                tailf:xpath-root 3;
              }
            }
            ext:support-filter "true";
            must "/acl:acl/acl:group6s/acl:group6[acl:identity=current()]/acl:type='basic' or /acl:acl/acl:group6s/acl:group6[acl:identity=current()]/acl:type='advance'" {
              tailf:xpath-root 3;
            }
            description
              "Acl inbound name or number for IPv6 protocol.";
          }
          leaf acl6-outbound {
            type leafref {
              path "/ncs:devices/ncs:device/ncs:config/acl:acl/acl:group6s/acl:group6/acl:identity" {
                tailf:xpath-root 3;
              }
            }
            ext:support-filter "true";
            must "/acl:acl/acl:group6s/acl:group6[acl:identity=current()]/acl:type='basic' or /acl:acl/acl:group6s/acl:group6[acl:identity=current()]/acl:type='advance'" {
              tailf:xpath-root 3;
            }
            description
              "Acl outbound name or number for IPv6 protocol.";
          }
          leaf acl4-inbound-num {
            type leafref {
              path "/ncs:devices/ncs:device/ncs:config/acl:acl/acl:groups/acl:group/acl:identity" {
                tailf:xpath-root 3;
              }
            }
            ext:support-filter "true";
            must "/acl:acl/acl:groups/acl:group[acl:identity=current()]/acl:type='basic' or /acl:acl/acl:groups/acl:group[acl:identity=current()]/acl:type='advance'" {
              tailf:xpath-root 3;
            }
            status deprecated;
            description
              "Acl inbound number for IPv4 protocol.";
          }
          leaf acl4-outbound-num {
            type leafref {
              path "/ncs:devices/ncs:device/ncs:config/acl:acl/acl:groups/acl:group/acl:identity" {
                tailf:xpath-root 3;
              }
            }
            ext:support-filter "true";
            must "/acl:acl/acl:groups/acl:group[acl:identity=current()]/acl:type='basic' or /acl:acl/acl:groups/acl:group[acl:identity=current()]/acl:type='advance'" {
              tailf:xpath-root 3;
            }
            status deprecated;
            description
              "Acl outbound number for IPv4 protocol.";
          }
          leaf acl6-inbound-num {
            type leafref {
              path "/ncs:devices/ncs:device/ncs:config/acl:acl/acl:group6s/acl:group6/acl:identity" {
                tailf:xpath-root 3;
              }
            }
            ext:support-filter "true";
            must "/acl:acl/acl:group6s/acl:group6[acl:identity=current()]/acl:type='basic' or /acl:acl/acl:group6s/acl:group6[acl:identity=current()]/acl:type='advance'" {
              tailf:xpath-root 3;
            }
            status deprecated;
            description
              "Acl inbound number for IPv6 protocol.";
          }
          leaf acl6-outbound-num {
            type leafref {
              path "/ncs:devices/ncs:device/ncs:config/acl:acl/acl:group6s/acl:group6/acl:identity" {
                tailf:xpath-root 3;
              }
            }
            ext:support-filter "true";
            must "/acl:acl/acl:group6s/acl:group6[acl:identity=current()]/acl:type='basic' or /acl:acl/acl:group6s/acl:group6[acl:identity=current()]/acl:type='advance'" {
              tailf:xpath-root 3;
            }
            status deprecated;
            description
              "Acl outbound number for IPv6 protocol.";
          }
          leaf proto-inbound {
            type vty-proto-inbnd-type;
            must "(../auth-mode='aaa' and ../proto-inbound='ssh') or not(../proto-inbound='ssh')" {
              tailf:xpath-root 3;
            }
            default "all";
            ext:support-filter "true";
            description
              "VTY protocol inbound name.";
          }
        }
      }
      container line-global {
        description
          "Configure VTY global configuration.";
        // NCS drop config false leaf 'max-users'
        leaf password-lock {
          type boolean;
          default "true";
          description
            "Enable/disable VTY IP block.";
        }
        leaf security-policy {
          type boolean;
          default "true";
          description
            "Enable/disable VTY security policy. Disabling this may reduce the degree of VTY security. It is strongly recommended to keep this enabled.";
        }
      }
    }
  }
  augment "/ncs:devices/ncs:device/ncs:live-status" {
    container vty {
      tailf:ncs-device-type "netconf";
      tailf:display-when "not(../../ncs:module) or ../../ncs:module[ncs:name='huawei-vty'] or (../../ncs:live-status-protocol[not(ncs:capability)]) or (../../ncs:live-status-protocol/ncs:capability/ncs:module[.='huawei-vty'])";
      description
        "VTY.";
      container lines {
        description
          "List of VTY specific configuration list.";
        list line {
          key "index";
          // NCS drop max-elements statement
          description
            "Configure VTY specific configuration policy.";
          ext:generated-by "system";
          leaf index {
            type uint8 {
              range "34..54";
            }
            description
              "Terminal line index.";
          }
          leaf idle-timeout-min {
            type uint16 {
              range "0..35791";
            }
            units "min";
            // NCS drop default statement
            ext:support-filter "true";
            description
              "Idle timeout in minutes.";
          }
          leaf idle-timeout-sec {
            type uint16 {
              range "0..59";
            }
            units "s";
            // NCS drop default statement
            ext:support-filter "true";
            description
              "Idle timeout in seconds.";
          }
          leaf auth-mode {
            type live_ncs_vty-authmode-type;
            // NCS drop must statement
            // NCS drop default statement
            ext:support-filter "true";
            description
              "Authentication Mode.";
          }
          leaf auth-password {
            type pub-type:live_ncs_password;
            // NCS drop must statement
            description
              "Authentication Password.";
          }
          leaf privilege-level {
            type uint8 {
              range "0..15";
            }
            // NCS drop default statement
            ext:support-filter "true";
            description
              "User privilege level.";
          }
          leaf history-cmd-size {
            type uint16 {
              range "0..256";
            }
            // NCS drop default statement
            ext:support-filter "true";
            description
              "History command buffer size. Describes the number of commands will be stored in history.";
          }
          leaf screen-length {
            type uint16 {
              range "0..512";
            }
            // NCS drop default statement
            ext:support-filter "true";
            description
              "VTY screen length value.";
          }
          leaf shell-enable {
            type live_ncs_vty-bool-type;
            // NCS drop default statement
            ext:support-filter "true";
            description
              "Shell (Enable/Disable).";
          }
          leaf acl4-inbound {
            type leafref {
              path "/ncs:devices/ncs:device/ncs:live-status/acl:acl/acl:groups/acl:group/acl:identity" {
                tailf:xpath-root 3;
              }
            }
            ext:support-filter "true";
            // NCS drop must statement
            description
              "Acl inbound name or number for IPv4 protocol.";
          }
          leaf acl4-outbound {
            type leafref {
              path "/ncs:devices/ncs:device/ncs:live-status/acl:acl/acl:groups/acl:group/acl:identity" {
                tailf:xpath-root 3;
              }
            }
            ext:support-filter "true";
            // NCS drop must statement
            description
              "Acl outbound name or number for IPv4 protocol.";
          }
          leaf acl6-inbound {
            type leafref {
              path "/ncs:devices/ncs:device/ncs:live-status/acl:acl/acl:group6s/acl:group6/acl:identity" {
                tailf:xpath-root 3;
              }
            }
            ext:support-filter "true";
            // NCS drop must statement
            description
              "Acl inbound name or number for IPv6 protocol.";
          }
          leaf acl6-outbound {
            type leafref {
              path "/ncs:devices/ncs:device/ncs:live-status/acl:acl/acl:group6s/acl:group6/acl:identity" {
                tailf:xpath-root 3;
              }
            }
            ext:support-filter "true";
            // NCS drop must statement
            description
              "Acl outbound name or number for IPv6 protocol.";
          }
          leaf acl4-inbound-num {
            type leafref {
              path "/ncs:devices/ncs:device/ncs:live-status/acl:acl/acl:groups/acl:group/acl:identity" {
                tailf:xpath-root 3;
              }
            }
            ext:support-filter "true";
            // NCS drop must statement
            status deprecated;
            description
              "Acl inbound number for IPv4 protocol.";
          }
          leaf acl4-outbound-num {
            type leafref {
              path "/ncs:devices/ncs:device/ncs:live-status/acl:acl/acl:groups/acl:group/acl:identity" {
                tailf:xpath-root 3;
              }
            }
            ext:support-filter "true";
            // NCS drop must statement
            status deprecated;
            description
              "Acl outbound number for IPv4 protocol.";
          }
          leaf acl6-inbound-num {
            type leafref {
              path "/ncs:devices/ncs:device/ncs:live-status/acl:acl/acl:group6s/acl:group6/acl:identity" {
                tailf:xpath-root 3;
              }
            }
            ext:support-filter "true";
            // NCS drop must statement
            status deprecated;
            description
              "Acl inbound number for IPv6 protocol.";
          }
          leaf acl6-outbound-num {
            type leafref {
              path "/ncs:devices/ncs:device/ncs:live-status/acl:acl/acl:group6s/acl:group6/acl:identity" {
                tailf:xpath-root 3;
              }
            }
            ext:support-filter "true";
            // NCS drop must statement
            status deprecated;
            description
              "Acl outbound number for IPv6 protocol.";
          }
          leaf proto-inbound {
            type live_ncs_vty-proto-inbnd-type;
            // NCS drop must statement
            // NCS drop default statement
            ext:support-filter "true";
            description
              "VTY protocol inbound name.";
          }
        }
      }
      container line-global {
        description
          "Configure VTY global configuration.";
        leaf max-users {
          type uint32 {
            range "0..21";
          }
          description
            "Maximum users can connect to VTY.";
        }
        leaf password-lock {
          type boolean;
          // NCS drop default statement
          description
            "Enable/disable VTY IP block.";
        }
        leaf security-policy {
          type boolean;
          // NCS drop default statement
          description
            "Enable/disable VTY security policy. Disabling this may reduce the degree of VTY security. It is strongly recommended to keep this enabled.";
        }
      }
    }
  }
  augment "/ncs:devices/ncs:template/ncs:ned-id/ncs:config" {
    container vty {
      description
        "VTY.";
      container lines {
        description
          "List of VTY specific configuration list.";
        list line {
          // NCS patched for predictable order
          ordered-by user;
          key "index";
          // NCS drop max-elements statement
          description
            "Configure VTY specific configuration policy.";
          ext:generated-by "system";
          leaf index {
            type string;
            description
              "Terminal line index.";
          }
          leaf idle-timeout-min {
            type string;
            units "min";
            // NCS drop default statement
            ext:support-filter "true";
            description
              "Idle timeout in minutes.";
          }
          leaf idle-timeout-sec {
            type string;
            units "s";
            // NCS drop default statement
            ext:support-filter "true";
            description
              "Idle timeout in seconds.";
          }
          leaf auth-mode {
            type ncs_template_vty-authmode-type;
            // NCS drop must statement
            // NCS drop default statement
            ext:support-filter "true";
            description
              "Authentication Mode.";
          }
          leaf auth-password {
            type pub-type:ncs_template_password;
            // NCS drop must statement
            description
              "Authentication Password.";
          }
          leaf privilege-level {
            type string;
            // NCS drop default statement
            ext:support-filter "true";
            description
              "User privilege level.";
          }
          leaf history-cmd-size {
            type string;
            // NCS drop default statement
            ext:support-filter "true";
            description
              "History command buffer size. Describes the number of commands will be stored in history.";
          }
          leaf screen-length {
            type string;
            // NCS drop default statement
            ext:support-filter "true";
            description
              "VTY screen length value.";
          }
          leaf shell-enable {
            type ncs_template_vty-bool-type;
            // NCS drop default statement
            ext:support-filter "true";
            description
              "Shell (Enable/Disable).";
          }
          leaf acl4-inbound {
            type string;
            ext:support-filter "true";
            // NCS drop must statement
            description
              "Acl inbound name or number for IPv4 protocol.";
          }
          leaf acl4-outbound {
            type string;
            ext:support-filter "true";
            // NCS drop must statement
            description
              "Acl outbound name or number for IPv4 protocol.";
          }
          leaf acl6-inbound {
            type string;
            ext:support-filter "true";
            // NCS drop must statement
            description
              "Acl inbound name or number for IPv6 protocol.";
          }
          leaf acl6-outbound {
            type string;
            ext:support-filter "true";
            // NCS drop must statement
            description
              "Acl outbound name or number for IPv6 protocol.";
          }
          leaf acl4-inbound-num {
            type string;
            ext:support-filter "true";
            // NCS drop must statement
            status deprecated;
            description
              "Acl inbound number for IPv4 protocol.";
          }
          leaf acl4-outbound-num {
            type string;
            ext:support-filter "true";
            // NCS drop must statement
            status deprecated;
            description
              "Acl outbound number for IPv4 protocol.";
          }
          leaf acl6-inbound-num {
            type string;
            ext:support-filter "true";
            // NCS drop must statement
            status deprecated;
            description
              "Acl inbound number for IPv6 protocol.";
          }
          leaf acl6-outbound-num {
            type string;
            ext:support-filter "true";
            // NCS drop must statement
            status deprecated;
            description
              "Acl outbound number for IPv6 protocol.";
          }
          leaf proto-inbound {
            type ncs_template_vty-proto-inbnd-type;
            // NCS drop must statement
            // NCS drop default statement
            ext:support-filter "true";
            description
              "VTY protocol inbound name.";
          }
        }
      }
      container line-global {
        description
          "Configure VTY global configuration.";
        // NCS drop config false leaf 'max-users'
        leaf password-lock {
          type string;
          // NCS drop default statement
          description
            "Enable/disable VTY IP block.";
        }
        leaf security-policy {
          type string;
          // NCS drop default statement
          description
            "Enable/disable VTY security policy. Disabling this may reduce the degree of VTY security. It is strongly recommended to keep this enabled.";
        }
      }
    }
  }
}
