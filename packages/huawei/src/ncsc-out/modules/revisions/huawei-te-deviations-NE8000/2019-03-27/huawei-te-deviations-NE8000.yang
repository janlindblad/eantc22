module huawei-te-deviations-NE8000 {
  // Generated by yanger -t ncs
  tailf:mount-id "huawei-nc-1.0:huawei-nc-1.0";
  tailf:ncs-device-type "netconf";

  namespace "urn:huawei:yang:huawei-te-deviations-NE8000";
  prefix te-devs-NE8000;

  import huawei-te {
    prefix te;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Specifies the multi-protocol label switching protocol.";

  revision 2019-03-27 {
    description
      "Init revision.";
    reference "Huawei private.";
  }

  typedef ncs_template_er-hop-mode-deviations {
    type string;
    description
      "ERHop Mode.";
  }

  typedef ncs_rpc_notif_er-hop-mode-deviations {
    type enumeration {
      enum "ipv4-ipv6-address" {
        value 1;
        description
          "IPv4 or IPv6 address.";
      }
      enum "sid-label" {
        value 2;
        description
          "SID label.";
      }
    }
    description
      "ERHop Mode.";
  }

  typedef live_ncs_er-hop-mode-deviations {
    type enumeration {
      enum "ipv4-ipv6-address" {
        value 1;
        description
          "IPv4 or IPv6 address.";
      }
      enum "sid-label" {
        value 2;
        description
          "SID label.";
      }
    }
    description
      "ERHop Mode.";
  }

  typedef er-hop-mode-deviations {
    type enumeration {
      enum "ipv4-ipv6-address" {
        value 1;
        description
          "IPv4 or IPv6 address.";
      }
      enum "sid-label" {
        value 2;
        description
          "SID label.";
      }
    }
    description
      "ERHop Mode.";
  }

  deviation "/ncs:devices/ncs:template/ncs:ned-id/ncs:config/te:te/te:explicit-paths/te:explicit-path/te:hops/te:hop/te:mode" {
    deviate replace {
      type te-devs-NE8000:ncs_template_er-hop-mode-deviations;
    }
  }
  deviation "/ncs:devices/ncs:device/ncs:live-status/te:te/te:explicit-paths/te:explicit-path/te:hops/te:hop/te:mode" {
    deviate replace {
      type te-devs-NE8000:live_ncs_er-hop-mode-deviations;
    }
  }
  deviation "/ncs:devices/ncs:device/ncs:config/te:te/te:explicit-paths/te:explicit-path/te:hops/te:hop/te:mode" {
    deviate replace {
      type te-devs-NE8000:er-hop-mode-deviations;
    }
  }
  deviation "/ncs:devices/ncs:template/ncs:ned-id/ncs:config/te:te/te:explicit-paths/te:explicit-path/te:hops/te:hop/te:sid-ipv6" {
    deviate not-supported;
  }
  deviation "/ncs:devices/ncs:device/ncs:live-status/te:te/te:explicit-paths/te:explicit-path/te:hops/te:hop/te:sid-ipv6" {
    deviate not-supported;
  }
  deviation "/ncs:devices/ncs:device/ncs:config/te:te/te:explicit-paths/te:explicit-path/te:hops/te:hop/te:sid-ipv6" {
    deviate not-supported;
  }
  deviation "/ncs:devices/ncs:template/ncs:ned-id/ncs:config/te:te/te:explicit-paths/te:explicit-path/te:hops/te:hop/te:sid-ipv6-label-type" {
    deviate not-supported;
  }
  deviation "/ncs:devices/ncs:device/ncs:live-status/te:te/te:explicit-paths/te:explicit-path/te:hops/te:hop/te:sid-ipv6-label-type" {
    deviate not-supported;
  }
  deviation "/ncs:devices/ncs:device/ncs:config/te:te/te:explicit-paths/te:explicit-path/te:hops/te:hop/te:sid-ipv6-label-type" {
    deviate not-supported;
  }
}
