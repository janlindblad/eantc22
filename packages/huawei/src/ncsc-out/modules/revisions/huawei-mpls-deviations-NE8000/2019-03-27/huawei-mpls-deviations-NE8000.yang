module huawei-mpls-deviations-NE8000 {
  // Generated by yanger -t ncs
  tailf:mount-id "huawei-nc-1.0:huawei-nc-1.0";
  tailf:ncs-device-type "netconf";

  namespace "urn:huawei:yang:huawei-mpls-deviations-NE8000";
  prefix mpls-devs-NE8000;

  import huawei-mpls {
    prefix mpls;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Specifies the multi-protocol label switching protocol.";

  revision 2019-03-27 {
    description
      "Initial revision.";
    reference "Huawei private.";
  }

  deviation "/ncs:devices/ncs:template/ncs:ned-id/ncs:config/mpls:mpls/mpls:common/mpls:global/mpls:sr-exp-mode" {
    deviate not-supported;
  }
  deviation "/ncs:devices/ncs:device/ncs:live-status/mpls:mpls/mpls:common/mpls:global/mpls:sr-exp-mode" {
    deviate not-supported;
  }
  deviation "/ncs:devices/ncs:device/ncs:config/mpls:mpls/mpls:common/mpls:global/mpls:sr-exp-mode" {
    deviate not-supported;
  }
}
