submodule huawei-qos-type {
  // Generated by yanger -t ncs
  tailf:mount-id "huawei-nc-1.0:huawei-nc-1.0";

  belongs-to huawei-qos {
    prefix qos;
  }

  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "The type definition of quality of service.";

  revision 2020-05-27 {
    description
      "Add new nodes.";
    reference "Huawei private.";
  }
  revision 2020-04-10 {
    description
      "Add new nodes.";
    reference "Huawei private.";
  }
  revision 2020-04-01 {
    description
      "Add new nodes.";
    reference "Huawei private.";
  }
  revision 2020-03-11 {
    description
      "Add new nodes.";
    reference "Huawei private.";
  }
  revision 2020-02-03 {
    description
      "Add new nodes.";
    reference "Huawei private.";
  }
  revision 2020-01-20 {
    description
      "Add new nodes.";
    reference "Huawei private.";
  }
  revision 2019-12-02 {
    description
      "Add new nodes.";
    reference "Huawei private.";
  }
  revision 2019-11-04 {
    description
      "Initial revision.";
    reference "Huawei private.";
  }

  typedef ncs_template_qos-ba-type {
    type string;
    description
      "Behavior aggregations type.";
  }

  typedef ncs_template_qos-phb-type {
    type string;
    description
      "Priority type.";
  }

  typedef ncs_template_qos-service-class {
    type string;
    description
      "QoS service class.";
  }

  typedef ncs_template_qos-service-class-total {
    type string;
    description
      "QoS service class.";
  }

  typedef ncs_template_qos-color {
    type string;
    description
      "Color type.";
  }

  typedef ncs_template_qos-direction-type {
    type string;
    description
      "Direction type.";
  }

  typedef ncs_template_qos-gq-direction-type {
    type string;
    description
      "Direction type.";
  }

  typedef ncs_template_qos-traffic-type {
    type string;
    description
      "Traffic policy type.";
  }

  typedef ncs_template_qos-acl-log-type {
    type string;
    description
      "Acl log.";
  }

  typedef ncs_template_template-name {
    type string;
    description
      "Template name is like string.";
  }

  typedef ncs_template_queue-schedule-mode {
    type string;
    description
      "Queue schedule mode.";
  }

  typedef ncs_template_queue-low-latency {
    type string;
    description
      "Enable low latency.";
  }

  typedef ncs_template_queue-low-jitter {
    type string;
    description
      "Enable low jitter.";
  }

  typedef ncs_template_queue-cir-schedule-mode {
    type string;
    description
      "Scheduling strategy of cir.";
  }

  typedef ncs_template_flow-queue-template-type {
    type string;
    description
      "Flow queue template mode type.";
  }

  typedef ncs_template_profile-template-type {
    type string;
    description
      "Profile template mode type.";
  }

  typedef ncs_template_all-direction-type {
    type string;
    description
      "Direction type include all.";
  }

  typedef ncs_template_priority-level-type {
    type string;
    description
      "Priority level type.";
  }

  typedef ncs_template_adjust-on-card-type {
    type string;
    description
      "Adjust on card flag.";
  }

  typedef ncs_template_gq-template-type {
    type string;
    description
      "User group queue mode.";
  }

  typedef ncs_template_class-operator {
    type string;
    description
      "Logical operator of a rule.";
  }

  typedef ncs_template_ip-family {
    type string;
    description
      "Ip family type.";
  }

  typedef ncs_template_priority-type {
    type string;
    description
      "Priority type.";
  }

  typedef ncs_template_action-car {
    type string;
    description
      "Type of a car action.";
  }

  typedef ncs_template_color-action-type {
    type string;
    description
      "Color action type.";
  }

  typedef ncs_template_service-class-notconfig {
    type string;
    description
      "Service class type.";
  }

  typedef ncs_template_filter-flag {
    type string;
    description
      "Filter type.";
  }

  typedef ncs_template_action-remark {
    type string;
    description
      "Action remark type.";
  }

  typedef ncs_template_service-class-action {
    type string;
    description
      "Type of a service class action.";
  }

  typedef ncs_template_remark-type {
    type string;
    description
      "Remark type.";
  }

  typedef ncs_template_trust-type {
    type string;
    description
      "Trust type.";
  }

  typedef ncs_template_trust-direction-type {
    type string;
    description
      "Trust direction type.";
  }

  typedef ncs_template_identifier-type {
    type string;
    description
      "Identifier type.";
  }

  typedef ncs_template_link-adjustment-type {
    type string;
    description
      "Link adjustment type.";
  }

  typedef ncs_template_policy-apply-layer-type {
    type string;
    description
      "Policy layer type.";
  }

  typedef ncs_template_policy-apply-vxlan-layer-type {
    type string;
    description
      "Policy layer type.";
  }

  typedef ncs_template_profile-apply-type {
    type string;
    description
      "Profile apply type.";
  }

  typedef ncs_template_linkage-bandwidth-type {
    type string;
    description
      "Linkage bandwidth type.";
  }

  typedef ncs_template_identify-type {
    type string;
    description
      "Identify type.";
  }

  typedef ncs_template_hqos-service-class {
    type string;
    description
      "Service class type.";
  }

  typedef ncs_template_qos-res-type {
    type string;
    description
      "Resource type.";
  }

  typedef ncs_template_switch-flag {
    type string;
    description
      "Switch flag.";
  }

  typedef ncs_template_low-latency {
    type string;
    description
      "Enable or disable low latency.";
  }

  typedef ncs_template_share-shape-mode {
    type string;
    description
      "Share shape mode.";
  }

  typedef ncs_template_be-type {
    type string;
    description
      "BE type.";
  }

  typedef ncs_template_af1-type {
    type string;
    description
      "AF1 type.";
  }

  typedef ncs_template_af2-type {
    type string;
    description
      "AF2 type.";
  }

  typedef ncs_template_af3-type {
    type string;
    description
      "AF3 type.";
  }

  typedef ncs_template_af4-type {
    type string;
    description
      "AF4 type.";
  }

  typedef ncs_template_ef-type {
    type string;
    description
      "EF type.";
  }

  typedef ncs_template_cs6-type {
    type string;
    description
      "CS6 type.";
  }

  typedef ncs_template_cs7-type {
    type string;
    description
      "CS7 type.";
  }

  typedef ncs_template_shapid-upritype {
    type string;
    description
      "Shap Id.";
  }

  typedef ncs_template_qos-cos-value {
    type string;
    description
      "Cos value.";
  }

  typedef ncs_template_shap-id-type {
    type string;
    description
      "Shap id type.";
  }

  typedef ncs_template_queue-select-be-type {
    type string;
    description
      "Queue BE.";
  }

  typedef ncs_template_queue-select-af1-type {
    type string;
    description
      "Queue AF1.";
  }

  typedef ncs_template_queue-select-af2-type {
    type string;
    description
      "Queue AF2.";
  }

  typedef ncs_template_queue-select-af3-type {
    type string;
    description
      "Queue AF3.";
  }

  typedef ncs_template_queue-select-af4-type {
    type string;
    description
      "Queue AF4.";
  }

  typedef ncs_template_queue-select-ef-type {
    type string;
    description
      "Queue EF.";
  }

  typedef ncs_template_queue-select-cs6-type {
    type string;
    description
      "Queue CS6.";
  }

  typedef ncs_template_queue-select-cs7-type {
    type string;
    description
      "Queue CS7.";
  }

  typedef ncs_template_priority-flow-queue-schedule-mode {
    type string;
    description
      "Priority mode.";
  }

  typedef ncs_template_slot-id {
    type string;
    description
      "Slot id is like 3, clc1/3 or ccc1/3.";
  }

  typedef ncs_template_group-name {
    type string;
    description
      "Group name is like string.";
  }

  typedef ncs_template_qos-service-class-filter {
    type string;
    description
      "Service class.";
  }

  typedef ncs_template_qos-service-class-8cos {
    type string;
    description
      "Service class.";
  }

  typedef ncs_template_qos-car-type {
    type string;
    description
      "CAR.";
  }

  typedef ncs_template_car-direction-type {
    type string;
    description
      "Direction type.";
  }

  typedef ncs_template_profile-car-type {
    type string;
    description
      "CAR.";
  }

  typedef ncs_template_profile-car-direction-type {
    type string;
    description
      "All.";
  }

  typedef ncs_template_qos-suppression-type {
    type string;
    description
      "Suppression type.";
  }

  typedef ncs_template_suppression-direction-type {
    type string;
    description
      "Suppression direction type.";
  }

  typedef ncs_template_color-aware-type {
    type string;
    description
      "Enable color aware.";
  }

  typedef ncs_template_priority-aware-type {
    type string;
    description
      "Enable priority aware.";
  }

  typedef ncs_template_mode-template-status {
    type string;
    description
      "Enable.";
  }

  typedef ncs_template_policy-match-type {
    type string;
    description
      "Traffic policy match type.";
  }

  typedef ncs_template_statistics-switch-status {
    type string;
    description
      "Statistics switch type.";
  }

  typedef ncs_template_stream-direction-type {
    type string;
    description
      "Stream direction type.";
  }

  typedef ncs_template_group-type {
    type string;
    description
      "Group type.";
  }

  typedef ncs_template_switch-type {
    type string;
    description
      "Enable.";
  }

  typedef ncs_template_out-direction-type {
    type string;
    description
      "Outbound direction.";
  }

  typedef ncs_template_priority-shaping-type {
    type string;
    description
      "Priority shaping type.";
  }

  typedef ncs_template_interval-value {
    type string;
    description
      "Interval value.";
  }

  typedef ncs_template_buffer-mode-type {
    type string;
    description
      "Buffer mode type.";
  }

  typedef ncs_template_speed-type {
    type string;
    description
      "Speed type.";
  }

  typedef ncs_template_qos-rule-service-type {
    type string;
    description
      "Rule service type.";
  }

  typedef ncs_template_qos-address-type {
    type string;
    description
      "Source or destination address.";
  }

  typedef ncs_template_qos-mac-type {
    type string;
    description
      "Source or destination address.";
  }

  typedef ncs_template_qos-ipv6-family {
    type string;
    description
      "IPv6 protocol family.";
  }

  typedef ncs_template_qos-tcp-bit-match {
    type string;
    description
      "TCP bit match type.";
  }

  typedef ncs_template_qos-tcp-bit-match-ipv6 {
    type string;
    description
      "IPv6 TCP bit match type.";
  }

  typedef ncs_template_car-limit-type {
    type string;
    description
      "Car limit type.";
  }

  typedef ncs_template_acl-log-action-type {
    type string;
    description
      "Type of the log action.";
  }

  typedef ncs_template_low-latency-enable-type {
    type string;
    description
      "Business type of low latency.";
  }

  typedef ncs_template_low-latency-enable-value {
    type string;
    description
      "Enable.";
  }

  typedef ncs_template_shaping-value-type {
    type string;
    description
      "Shaping value type.";
  }

  typedef ncs_template_port-shaping-weight-mode-type {
    type string;
    description
      "Weight mode enable.";
  }

  typedef ncs_template_scheduling-mode-type {
    type string;
    description
      "Scheduling mode type.";
  }

  typedef ncs_template_map-type {
    type string;
    description
      "Map type for phb.";
  }

  typedef ncs_template_convergence-schedule-mode {
    type string;
    description
      "Disable.";
  }

  typedef ncs_template_port-convergence-schedule-mode {
    type string;
    description
      "Enable.";
  }

  typedef ncs_template_traffic-policy-untag-type {
    type string;
    description
      "Disable.";
  }

  typedef ncs_template_qos-direction-inbound {
    type string;
    description
      "Direction.";
  }

  typedef ncs_template_in-direction-type {
    type string;
    description
      "Inbound.";
  }

  typedef ncs_template_discard-type {
    type string;
    description
      "Discard mode type.";
  }

  typedef ncs_template_lcs-active-status-type {
    type string;
    description
      "Liscense active status type.";
  }

  typedef ncs_template_statistics-car-type {
    type string;
    description
      "Car statistics type.";
  }

  typedef ncs_template_qos-priority-num-type {
    type string;
    description
      "The priority num.";
  }

  typedef ncs_template_qos-flow-type {
    type string;
    description
      "Flow CAR IP type.";
  }

  typedef ncs_template_increase-priority {
    type string;
    description
      "Increase priority.";
  }

  typedef ncs_template_forward-type {
    type string;
    description
      "VLL forward type.";
  }

  typedef ncs_template_ability-type {
    type string;
    description
      "Ability type.";
  }

  typedef ncs_template_qos-policy-layer {
    type string;
    description
      "IP layer.";
  }

  typedef ncs_template_enable-type {
    type string;
    description
      "Enable.";
  }

  typedef ncs_template_priority-convergent-type {
    type string;
    description
      "High priority.";
  }

  typedef ncs_template_untag-enable-type {
    type string;
    description
      "Untag enable type.";
  }

  typedef ncs_template_suppress-type {
    type string;
    description
      "Suppression type.";
  }

  typedef ncs_template_load-balance-type {
    type string;
    description
      "Load balance type.";
  }

  typedef ncs_template_sample-type {
    type string;
    description
      "Sampling type.";
  }

  typedef ncs_template_action-urpf {
    type string;
    description
      "URPF action.";
  }

  typedef ncs_template_check-type {
    type string;
    description
      "Type of the URPF check.";
  }

  typedef ncs_template_statistics-type {
    type string;
    description
      "Statistics type.";
  }

  typedef ncs_template_ip-type {
    type string;
    description
      "Type of an address.";
  }

  typedef ncs_template_pool-type {
    type string;
    description
      "Pool ID.";
  }

  typedef ncs_template_member-link-scheduler-type {
    type string;
    description
      "Business type.";
  }

  typedef ncs_template_traffic-type {
    type string;
    description
      "LDP traffic.";
  }

  typedef ncs_template_any-other-type {
    type string;
    description
      "BAS QoS profile apply type.";
  }

  typedef ncs_template_bas-profile-identifier-type {
    type string;
    description
      "BAS QoS profile apply identifier type.";
  }

  typedef ncs_template_vlan-user-group-queue-identifier-type {
    type string;
    description
      "VLAN user group queue apply identifier type.";
  }

  typedef ncs_template_user-access-type {
    type string;
    description
      "User access type.";
  }

  typedef ncs_template_hard-pipe-mode {
    type string;
    description
      "Hard pipe mode.";
  }

  typedef ncs_template_ac-mode-layer-type {
    type string;
    description
      "Layer type.";
  }

  typedef ncs_template_vxlan-trust-type {
    type string;
    description
      "VXLAN trust type.";
  }

  typedef ncs_template_exclude-type {
    type string;
    description
      "Exclude type.";
  }

  typedef ncs_template_qos-profile-template-name {
    type string;
    description
      "Qos profile template name is like string.";
  }

  typedef ncs_template_trust-remote-direction-type {
    type string;
    description
      "Trust remote direction type.";
  }

  typedef ncs_template_action-load-balance {
    type string;
    description
      "Load balancing.";
  }

  typedef ncs_template_user-type {
    type string;
    description
      "User type.";
  }

  typedef ncs_template_access-type {
    type string;
    description
      "User access type.";
  }

  typedef ncs_template_l2tp-user {
    type string;
    description
      "L2TP user.";
  }

  typedef ncs_template_cos-value-type {
    type string;
    description
      "Service class type.";
  }

  typedef ncs_template_rule-type {
    type string;
    description
      "Qos resource rule type.";
  }

  typedef ncs_template_yes-or-no {
    type string;
    description
      "Choose yes or no.";
  }

  typedef ncs_template_remote-trust-type {
    type string;
    description
      "Trust type.";
  }

  typedef ncs_template_type-8021p {
    type string;
    description
      "Trust 8021p type.";
  }

  typedef ncs_template_deficit-unit-type {
    type string;
    description
      "Deficit unit type.";
  }

  typedef ncs_template_user-queue-template-type {
    type string;
    description
      "User queue template mode type.";
  }

  typedef ncs_template_priority-schedule-mode {
    type string;
    description
      "Priority mode.";
  }

  typedef ncs_template_ignore-default-type {
    type string;
    description
      "Indicates a mode in which the default route is excluded.";
  }

  typedef ncs_template_protocol-family {
    type string;
    description
      "Protocol family type.";
  }

  typedef ncs_rpc_notif_qos-ba-type {
    type enumeration {
      enum "8021p" {
        value 0;
        description
          "802.1p priority.";
      }
      enum "ip-dscp" {
        value 1;
        description
          "DSCP priority.";
      }
      enum "mpls-exp" {
        value 2;
        description
          "MPLS-EXP priority.";
      }
      enum "user-priority" {
        value 3;
        description
          "User priority.";
      }
      enum "ip-precedence" {
        value 11;
        description
          "IP-Precedence priority.";
      }
    }
    description
      "Behavior aggregations type.";
  }

  typedef ncs_rpc_notif_qos-phb-type {
    type enumeration {
      enum "8021p" {
        value 0;
        description
          "802.1p priority.";
      }
      enum "ip-dscp" {
        value 1;
        description
          "DSCP priority.";
      }
      enum "mpls-exp" {
        value 2;
        description
          "MPLS-EXP priority.";
      }
      enum "ip-precedence" {
        value 11;
        description
          "IP Precedence priority.";
      }
    }
    description
      "Priority type.";
  }

  typedef ncs_rpc_notif_qos-service-class {
    type enumeration {
      enum "be" {
        value 0;
        description
          "BE service class.";
      }
      enum "af1" {
        value 1;
        description
          "AF1 service-class.";
      }
      enum "af2" {
        value 2;
        description
          "AF2 service-class.";
      }
      enum "af3" {
        value 3;
        description
          "AF3 service-class.";
      }
      enum "af4" {
        value 4;
        description
          "AF4 service-class.";
      }
      enum "ef" {
        value 5;
        description
          "EF service-class.";
      }
      enum "cs6" {
        value 6;
        description
          "CS6 service-class.";
      }
      enum "cs7" {
        value 7;
        description
          "CS7 service-class.";
      }
    }
    description
      "QoS service class.";
  }

  typedef ncs_rpc_notif_qos-service-class-total {
    type enumeration {
      enum "be" {
        value 0;
        description
          "BE service class.";
      }
      enum "af1" {
        value 1;
        description
          "AF1 service class.";
      }
      enum "af2" {
        value 2;
        description
          "AF2 service class.";
      }
      enum "af3" {
        value 3;
        description
          "AF3 service class.";
      }
      enum "af4" {
        value 4;
        description
          "AF4 service class.";
      }
      enum "ef" {
        value 5;
        description
          "EF service class.";
      }
      enum "cs6" {
        value 6;
        description
          "CS6 service class.";
      }
      enum "cs7" {
        value 7;
        description
          "CS7 service class.";
      }
      enum "total" {
        value 8;
        description
          "Total service class.";
      }
    }
    description
      "QoS service class.";
  }

  typedef ncs_rpc_notif_qos-color {
    type enumeration {
      enum "green" {
        value 0;
        description
          "Green.";
      }
      enum "yellow" {
        value 1;
        description
          "Yellow.";
      }
      enum "red" {
        value 2;
        description
          "Red.";
      }
    }
    description
      "Color type.";
  }

  typedef ncs_rpc_notif_qos-direction-type {
    type enumeration {
      enum "inbound" {
        value 0;
        description
          "Inbound.";
      }
      enum "outbound" {
        value 1;
        description
          "Outbound.";
      }
    }
    description
      "Direction type.";
  }

  typedef ncs_rpc_notif_qos-gq-direction-type {
    type enumeration {
      enum "inbound" {
        value 0;
        description
          "Inbound.";
      }
      enum "outbound" {
        value 1;
        description
          "Outbound.";
      }
    }
    description
      "Direction type.";
  }

  typedef ncs_rpc_notif_qos-traffic-type {
    type enumeration {
      enum "ucl" {
        value 0;
        description
          "Ucl.";
      }
      enum "acl" {
        value 1;
        description
          "Acl.";
      }
    }
    description
      "Traffic policy type.";
  }

  typedef ncs_rpc_notif_qos-acl-log-type {
    type enumeration {
      enum "acl-log" {
        value 1;
        description
          "Log first-packet parameter.";
      }
    }
    description
      "Acl log.";
  }

  typedef ncs_rpc_notif_template-name {
    type string {
      length "1..31";
    }
    description
      "Template name is like string.";
  }

  typedef ncs_rpc_notif_queue-schedule-mode {
    type enumeration {
      enum "pq" {
        value 0;
        description
          "Priority queue.";
      }
      enum "wfq" {
        value 1;
        description
          "Weighted fair queuing.";
      }
      enum "lpq" {
        value 2;
        description
          "Low priority queuing.";
      }
    }
    description
      "Queue schedule mode.";
  }

  typedef ncs_rpc_notif_queue-low-latency {
    type enumeration {
      enum "enable" {
        value 1;
        description
          "Enable.";
      }
    }
    description
      "Enable low latency.";
  }

  typedef ncs_rpc_notif_queue-low-jitter {
    type enumeration {
      enum "enable" {
        value 1;
        description
          "Enable.";
      }
    }
    description
      "Enable low jitter.";
  }

  typedef ncs_rpc_notif_queue-cir-schedule-mode {
    type enumeration {
      enum "pq" {
        value 0;
        description
          "PQ.";
      }
    }
    description
      "Scheduling strategy of cir.";
  }

  typedef ncs_rpc_notif_flow-queue-template-type {
    type enumeration {
      enum "normal" {
        value 0;
        description
          "Normal mode.";
      }
      enum "priority" {
        value 1;
        description
          "Priority mode.";
      }
      enum "4cos" {
        value 2;
        description
          "Four cos mode.";
      }
      enum "8cos-enhance" {
        value 5;
        description
          "Eight cos enhance.";
      }
    }
    description
      "Flow queue template mode type.";
  }

  typedef ncs_rpc_notif_profile-template-type {
    type enumeration {
      enum "normal" {
        value 0;
        description
          "Normal.";
      }
      enum "time-range" {
        value 1;
        description
          "Time range.";
      }
      enum "8cos-enhance" {
        value 5;
        description
          "Eight cos enhance.";
      }
    }
    description
      "Profile template mode type.";
  }

  typedef ncs_rpc_notif_all-direction-type {
    type enumeration {
      enum "inbound" {
        value 0;
        description
          "Inbound.";
      }
      enum "outbound" {
        value 1;
        description
          "Outbound.";
      }
      enum "all" {
        value 2;
        description
          "All.";
      }
    }
    description
      "Direction type include all.";
  }

  typedef ncs_rpc_notif_priority-level-type {
    type enumeration {
      enum "low" {
        value 255;
        description
          "Low.";
      }
      enum "high" {
        value 1;
        description
          "High.";
      }
    }
    description
      "Priority level type.";
  }

  typedef ncs_rpc_notif_adjust-on-card-type {
    type enumeration {
      enum "disable" {
        value 0;
        description
          "Disable.";
      }
      enum "enable" {
        value 1;
        description
          "Enable.";
      }
    }
    description
      "Adjust on card flag.";
  }

  typedef ncs_rpc_notif_gq-template-type {
    type enumeration {
      enum "normal" {
        value 0;
        description
          "Normal mode.";
      }
      enum "priority" {
        value 1;
        description
          "Priority mode.";
      }
    }
    description
      "User group queue mode.";
  }

  typedef ncs_rpc_notif_class-operator {
    type enumeration {
      enum "or" {
        value 0;
        description
          "Or.";
      }
      enum "and" {
        value 1;
        description
          "And.";
      }
    }
    description
      "Logical operator of a rule.";
  }

  typedef ncs_rpc_notif_ip-family {
    type enumeration {
      enum "ipv4" {
        value 1;
        description
          "IPv4.";
      }
      enum "ipv6" {
        value 2;
        description
          "IPv6.";
      }
    }
    description
      "Ip family type.";
  }

  typedef ncs_rpc_notif_priority-type {
    type enumeration {
      enum "8021p" {
        value 0;
        description
          "802.1p priority.";
      }
      enum "ip-precedence" {
        value 1;
        description
          "IP precedence.";
      }
      enum "dscp" {
        value 2;
        description
          "DSCP priority.";
      }
      enum "mpls-exp" {
        value 4;
        description
          "MPLS-EXP priority.";
      }
      enum "ipv6-dscp" {
        value 5;
        description
          "IPv6 DSCP priority.";
      }
      enum "ipv6-ip-precedence" {
        value 6;
        description
          "IPv6 IP precedence.";
      }
    }
    description
      "Priority type.";
  }

  typedef ncs_rpc_notif_action-car {
    type enumeration {
      enum "car" {
        value 0;
        description
          "CAR action.";
      }
    }
    description
      "Type of a car action.";
  }

  typedef ncs_rpc_notif_color-action-type {
    type enumeration {
      enum "pass" {
        value 0;
        description
          "Pass.";
      }
      enum "discard" {
        value 2;
        description
          "Discard.";
      }
    }
    description
      "Color action type.";
  }

  typedef ncs_rpc_notif_service-class-notconfig {
    type enumeration {
      enum "be" {
        value 0;
        description
          "BE service class.";
      }
      enum "af1" {
        value 1;
        description
          "AF1 service class.";
      }
      enum "af2" {
        value 2;
        description
          "AF2 service class.";
      }
      enum "af3" {
        value 3;
        description
          "AF3 service class.";
      }
      enum "af4" {
        value 4;
        description
          "AF4 service class.";
      }
      enum "ef" {
        value 5;
        description
          "EF service class.";
      }
      enum "cs6" {
        value 6;
        description
          "CS6 service class.";
      }
      enum "cs7" {
        value 7;
        description
          "CS7 service class.";
      }
      enum "not-config" {
        value 8;
        description
          "Not config service class.";
      }
    }
    description
      "Service class type.";
  }

  typedef ncs_rpc_notif_filter-flag {
    type enumeration {
      enum "permit" {
        value 0;
        description
          "Permit.";
      }
      enum "deny" {
        value 1;
        description
          "Deny.";
      }
    }
    description
      "Filter type.";
  }

  typedef ncs_rpc_notif_action-remark {
    type enumeration {
      enum "8021p" {
        value 12;
        description
          "Remark 802.1p priority action.";
      }
      enum "ipv4-dscp" {
        value 13;
        description
          "Remark DSCP action.";
      }
      enum "tos" {
        value 19;
        description
          "Remark tos priority action.";
      }
      enum "ipv6-dscp" {
        value 14;
        description
          "Remark IPv6 DSCP action.";
      }
      enum "ip-precedence" {
        value 15;
        description
          "Remark IP precedence action.";
      }
      enum "mpls-exp" {
        value 16;
        description
          "Remark MPLS-EXP action.";
      }
      enum "ip-df" {
        value 21;
        description
          "Remark IP-DF action.";
      }
      enum "ttl" {
        value 26;
        description
          "Remark TTL action.";
      }
      enum "inner-8021p" {
        value 34;
        description
          "Remark inner 802.1p priority action.";
      }
      enum "outer-8021p" {
        value 35;
        description
          "Remark outer 802.1p priority action.";
      }
      enum "remark-local-id" {
        value 60;
        description
          "Remark qos-local-id action.";
      }
    }
    description
      "Action remark type.";
  }

  typedef ncs_rpc_notif_service-class-action {
    type enumeration {
      enum "service-class" {
        value 0;
        description
          "Service class.";
      }
      enum "service-class-master-bfd" {
        value 1;
        description
          "Service class link master BFD.";
      }
      enum "service-class-slave-bfd" {
        value 2;
        description
          "Service class link slave BFD.";
      }
    }
    description
      "Type of a service class action.";
  }

  typedef ncs_rpc_notif_remark-type {
    type enumeration {
      enum "enable" {
        value 0;
        description
          "Remark enable.";
      }
      enum "disable" {
        value 1;
        description
          "Remark disable.";
      }
    }
    description
      "Remark type.";
  }

  typedef ncs_rpc_notif_trust-type {
    type enumeration {
      enum "ip-dscp" {
        value 0;
        description
          "Trust ip-dscp.";
      }
      enum "8021p" {
        value 1;
        description
          "Trust 8021p.";
      }
      enum "inner-8021p" {
        value 3;
        description
          "Trust inner-8021p.";
      }
      enum "outer-8021p" {
        value 2;
        description
          "Trust outer-8021p.";
      }
    }
    description
      "Trust type.";
  }

  typedef ncs_rpc_notif_trust-direction-type {
    type enumeration {
      enum "inbound" {
        value 1;
        description
          "Inbound.";
      }
      enum "outbound" {
        value 2;
        description
          "Outbound.";
      }
      enum "in-outbound" {
        value 0;
        description
          "Not config.";
      }
    }
    description
      "Trust direction type.";
  }

  typedef ncs_rpc_notif_identifier-type {
    type enumeration {
      enum "no" {
        value 0;
        description
          "Not config.";
      }
      enum "none" {
        value 1;
        description
          "Not config VLAN.";
      }
      enum "vid" {
        value 2;
        description
          "Vid.";
      }
      enum "ce-vid" {
        value 3;
        description
          "CE VLAN ID.";
      }
      enum "vid-ce-vid" {
        value 4;
        description
          "Vid CE vid.";
      }
    }
    description
      "Identifier type.";
  }

  typedef ncs_rpc_notif_link-adjustment-type {
    type enumeration {
      enum "cell" {
        value 1;
        description
          "Cell.";
      }
    }
    description
      "Link adjustment type.";
  }

  typedef ncs_rpc_notif_policy-apply-layer-type {
    type enumeration {
      enum "none" {
        value 0;
        description
          "Default classification.";
      }
      enum "link" {
        value 1;
        description
          "Classification based on Layer 2 information.";
      }
      enum "mpls" {
        value 3;
        description
          "Classification based on MPLS information.";
      }
      enum "all" {
        value 2;
        description
          "Classification based on ALL information.";
      }
      enum "vxlan" {
        value 4;
        description
          "Classification based on VXLAN information.";
      }
    }
    description
      "Policy layer type.";
  }

  typedef ncs_rpc_notif_policy-apply-vxlan-layer-type {
    type enumeration {
      enum "link" {
        value 1;
        description
          "Classification based on Layer 2 information.";
      }
    }
    description
      "Policy layer type.";
  }

  typedef ncs_rpc_notif_profile-apply-type {
    type enumeration {
      enum "interface" {
        value 0;
        description
          "Interface.";
      }
      enum "vlan" {
        value 1;
        description
          "VLAN.";
      }
      enum "pe" {
        value 2;
        description
          "Pe.";
      }
    }
    description
      "Profile apply type.";
  }

  typedef ncs_rpc_notif_linkage-bandwidth-type {
    type enumeration {
      enum "disable" {
        value 0;
        description
          "Disable.";
      }
      enum "enable" {
        value 1;
        description
          "Enable.";
      }
    }
    description
      "Linkage bandwidth type.";
  }

  typedef ncs_rpc_notif_identify-type {
    type enumeration {
      enum "none" {
        value 0;
        description
          "None.";
      }
      enum "vlan" {
        value 1;
        description
          "VLAN.";
      }
      enum "pe-vid" {
        value 2;
        description
          "Pe VLAN Id.";
      }
      enum "ce-vid" {
        value 3;
        description
          "Ce VLAN Id.";
      }
      enum "pe-ce-vid" {
        value 4;
        description
          "Pe-Ce VLAN Id.";
      }
      enum "vid" {
        value 5;
        description
          "Vid.";
      }
      enum "evc-ce-vid" {
        value 6;
        description
          "Ce-vid.";
      }
      enum "vid-ce-vid" {
        value 7;
        description
          "Vid-ce-vid.";
      }
    }
    description
      "Identify type.";
  }

  typedef ncs_rpc_notif_hqos-service-class {
    type enumeration {
      enum "be" {
        value 0;
        description
          "BE service class.";
      }
      enum "af1" {
        value 1;
        description
          "AF1 service class.";
      }
      enum "af2" {
        value 2;
        description
          "AF2 service class.";
      }
      enum "af3" {
        value 3;
        description
          "AF3 service class.";
      }
      enum "af4" {
        value 4;
        description
          "AF4 service class.";
      }
      enum "ef" {
        value 5;
        description
          "EF service class.";
      }
      enum "cs6" {
        value 6;
        description
          "CS6 service class.";
      }
      enum "cs7" {
        value 7;
        description
          "CS7 service class.";
      }
      enum "total" {
        value 8;
        description
          "Total.";
      }
      enum "cos0" {
        value 9;
        description
          "Cos0 service class.";
      }
      enum "cos1" {
        value 10;
        description
          "Cos1 service class.";
      }
      enum "cos2" {
        value 11;
        description
          "Cos2 service class.";
      }
      enum "cos3" {
        value 12;
        description
          "Cos3 service class.";
      }
    }
    description
      "Service class type.";
  }

  typedef ncs_rpc_notif_qos-res-type {
    type enumeration {
      enum "null" {
        value 0;
        description
          "Null.";
      }
      enum "sq" {
        value 1;
        description
          "SQ.";
      }
      enum "car" {
        value 2;
        description
          "CAR.";
      }
      enum "sq-car" {
        value 3;
        description
          "SQCAR.";
      }
      enum "l2-car" {
        value 4;
        description
          "L2CAR.";
      }
      enum "l2-l3-car" {
        value 5;
        description
          "L2L3CAR.";
      }
      enum "l3-car" {
        value 6;
        description
          "L3CAR.";
      }
    }
    description
      "Resource type.";
  }

  typedef ncs_rpc_notif_switch-flag {
    type enumeration {
      enum "enable" {
        value 1;
        description
          "Enable.";
      }
      enum "disable" {
        value 0;
        description
          "Disable.";
      }
    }
    description
      "Switch flag.";
  }

  typedef ncs_rpc_notif_low-latency {
    type enumeration {
      enum "enable" {
        value 1;
        description
          "Enable.";
      }
      enum "disable" {
        value 0;
        description
          "Disable.";
      }
    }
    description
      "Enable or disable low latency.";
  }

  typedef ncs_rpc_notif_share-shape-mode {
    type enumeration {
      enum "pq" {
        value 0;
        description
          "Priority queue.";
      }
      enum "wfq" {
        value 1;
        description
          "Weighted fair queuing.";
      }
      enum "lpq" {
        value 2;
        description
          "Low priority queuing.";
      }
      enum "not-config" {
        value 3;
        description
          "Not config.";
      }
    }
    description
      "Share shape mode.";
  }

  typedef ncs_rpc_notif_be-type {
    type enumeration {
      enum "true" {
        value 0;
        description
          "True.";
      }
      enum "false" {
        value 8;
        description
          "False.";
      }
    }
    description
      "BE type.";
  }

  typedef ncs_rpc_notif_af1-type {
    type enumeration {
      enum "true" {
        value 1;
        description
          "True.";
      }
      enum "false" {
        value 8;
        description
          "False.";
      }
    }
    description
      "AF1 type.";
  }

  typedef ncs_rpc_notif_af2-type {
    type enumeration {
      enum "true" {
        value 2;
        description
          "True.";
      }
      enum "false" {
        value 8;
        description
          "False.";
      }
    }
    description
      "AF2 type.";
  }

  typedef ncs_rpc_notif_af3-type {
    type enumeration {
      enum "true" {
        value 3;
        description
          "True.";
      }
      enum "false" {
        value 8;
        description
          "False.";
      }
    }
    description
      "AF3 type.";
  }

  typedef ncs_rpc_notif_af4-type {
    type enumeration {
      enum "true" {
        value 4;
        description
          "True.";
      }
      enum "false" {
        value 8;
        description
          "False.";
      }
    }
    description
      "AF4 type.";
  }

  typedef ncs_rpc_notif_ef-type {
    type enumeration {
      enum "true" {
        value 5;
        description
          "True.";
      }
      enum "false" {
        value 8;
        description
          "False.";
      }
    }
    description
      "EF type.";
  }

  typedef ncs_rpc_notif_cs6-type {
    type enumeration {
      enum "true" {
        value 6;
        description
          "True.";
      }
      enum "false" {
        value 8;
        description
          "False.";
      }
    }
    description
      "CS6 type.";
  }

  typedef ncs_rpc_notif_cs7-type {
    type enumeration {
      enum "true" {
        value 7;
        description
          "True.";
      }
      enum "false" {
        value 8;
        description
          "False.";
      }
    }
    description
      "CS7 type.";
  }

  typedef ncs_rpc_notif_shapid-upritype {
    type enumeration {
      enum "1" {
        value 1;
        description
          "1.";
      }
    }
    description
      "Shap Id.";
  }

  typedef ncs_rpc_notif_qos-cos-value {
    type enumeration {
      enum "cos0" {
        value 0;
        description
          "Cos0.";
      }
      enum "cos1" {
        value 1;
        description
          "Cos1.";
      }
      enum "cos2" {
        value 2;
        description
          "Cos2.";
      }
      enum "cos3" {
        value 3;
        description
          "Cos3.";
      }
    }
    description
      "Cos value.";
  }

  typedef ncs_rpc_notif_shap-id-type {
    type enumeration {
      enum "1" {
        value 1;
        description
          "Shap-id 1.";
      }
      enum "not-config" {
        value 2;
        description
          "Not config.";
      }
    }
    description
      "Shap id type.";
  }

  typedef ncs_rpc_notif_queue-select-be-type {
    type enumeration {
      enum "true" {
        value 0;
        description
          "True.";
      }
    }
    description
      "Queue BE.";
  }

  typedef ncs_rpc_notif_queue-select-af1-type {
    type enumeration {
      enum "true" {
        value 1;
        description
          "True.";
      }
    }
    description
      "Queue AF1.";
  }

  typedef ncs_rpc_notif_queue-select-af2-type {
    type enumeration {
      enum "true" {
        value 2;
        description
          "True.";
      }
    }
    description
      "Queue AF2.";
  }

  typedef ncs_rpc_notif_queue-select-af3-type {
    type enumeration {
      enum "true" {
        value 3;
        description
          "True.";
      }
    }
    description
      "Queue AF3.";
  }

  typedef ncs_rpc_notif_queue-select-af4-type {
    type enumeration {
      enum "true" {
        value 4;
        description
          "True.";
      }
    }
    description
      "Queue AF4.";
  }

  typedef ncs_rpc_notif_queue-select-ef-type {
    type enumeration {
      enum "true" {
        value 5;
        description
          "True.";
      }
    }
    description
      "Queue EF.";
  }

  typedef ncs_rpc_notif_queue-select-cs6-type {
    type enumeration {
      enum "true" {
        value 6;
        description
          "True.";
      }
    }
    description
      "Queue CS6.";
  }

  typedef ncs_rpc_notif_queue-select-cs7-type {
    type enumeration {
      enum "true" {
        value 7;
        description
          "True.";
      }
    }
    description
      "Queue CS7.";
  }

  typedef ncs_rpc_notif_priority-flow-queue-schedule-mode {
    type enumeration {
      enum "pq" {
        value 0;
        description
          "Priority queue.";
      }
      enum "wfq" {
        value 1;
        description
          "Weighted fair queue.";
      }
    }
    description
      "Priority mode.";
  }

  typedef ncs_rpc_notif_slot-id {
    type string {
      length "1..31";
      pattern '((c[cl]c\d+/)|(\d+/))?\d+';
    }
    description
      "Slot id is like 3, clc1/3 or ccc1/3.";
  }

  typedef ncs_rpc_notif_group-name {
    type string {
      length "1..32";
    }
    description
      "Group name is like string.";
  }

  typedef ncs_rpc_notif_qos-service-class-filter {
    type enumeration {
      enum "be" {
        value 0;
        description
          "BE service class.";
      }
      enum "af1" {
        value 1;
        description
          "AF1 service class.";
      }
      enum "af2" {
        value 2;
        description
          "AF2 service class.";
      }
      enum "af3" {
        value 3;
        description
          "AF3 service class.";
      }
      enum "af4" {
        value 4;
        description
          "AF4 service class.";
      }
      enum "ef" {
        value 5;
        description
          "Ef service class.";
      }
      enum "cs6" {
        value 6;
        description
          "CS6 service class.";
      }
      enum "cs7" {
        value 7;
        description
          "CS7 service class.";
      }
      enum "total" {
        value 8;
        description
          "Total.";
      }
    }
    description
      "Service class.";
  }

  typedef ncs_rpc_notif_qos-service-class-8cos {
    type enumeration {
      enum "be" {
        value 0;
        description
          "BE service class.";
      }
      enum "af1" {
        value 1;
        description
          "AF1 service class.";
      }
      enum "af2" {
        value 2;
        description
          "AF2 service class.";
      }
      enum "af3" {
        value 3;
        description
          "AF3 service class.";
      }
      enum "af4" {
        value 4;
        description
          "AF4 service class.";
      }
      enum "ef" {
        value 5;
        description
          "Ef service class.";
      }
      enum "cs6" {
        value 6;
        description
          "CS6 service class.";
      }
      enum "cs7" {
        value 7;
        description
          "CS7 service class.";
      }
      enum "total" {
        value 8;
        description
          "Total.";
      }
      enum "cos0" {
        value 9;
        description
          "Cos0 service class.";
      }
      enum "cos1" {
        value 10;
        description
          "Cos1 service class.";
      }
      enum "cos2" {
        value 11;
        description
          "Cos2 service class.";
      }
      enum "cos3" {
        value 12;
        description
          "Cos3 service class.";
      }
      enum "cos4" {
        value 13;
        description
          "Cos4 service class.";
      }
      enum "cos5" {
        value 14;
        description
          "Cos5 service class.";
      }
      enum "cos6" {
        value 15;
        description
          "Cos6 service class.";
      }
      enum "cos7" {
        value 16;
        description
          "Cos7 service class.";
      }
    }
    description
      "Service class.";
  }

  typedef ncs_rpc_notif_qos-car-type {
    type enumeration {
      enum "car" {
        value 1;
        description
          "CAR action.";
      }
    }
    description
      "CAR.";
  }

  typedef ncs_rpc_notif_car-direction-type {
    type enumeration {
      enum "inbound" {
        value 0;
        description
          "Inbound.";
      }
      enum "outbound" {
        value 1;
        description
          "Outbound.";
      }
      enum "all" {
        value 2;
        description
          "All.";
      }
    }
    description
      "Direction type.";
  }

  typedef ncs_rpc_notif_profile-car-type {
    type enumeration {
      enum "car" {
        value 1;
        description
          "CAR action.";
      }
    }
    description
      "CAR.";
  }

  typedef ncs_rpc_notif_profile-car-direction-type {
    type enumeration {
      enum "all" {
        value 2;
        description
          "All.";
      }
    }
    description
      "All.";
  }

  typedef ncs_rpc_notif_qos-suppression-type {
    type enumeration {
      enum "broadcast" {
        value 2;
        description
          "Broadcast suppression.";
      }
      enum "multicast" {
        value 3;
        description
          "Multicast suppression.";
      }
      enum "unknow-unicast" {
        value 4;
        description
          "Unknown unicast suppression.";
      }
      enum "bum" {
        value 7;
        description
          "BUM suppression.";
      }
      enum "bu" {
        value 8;
        description
          "BU suppression.";
      }
      enum "unknow-multicast" {
        value 9;
        description
          "Unknown multicast suppression.";
      }
    }
    description
      "Suppression type.";
  }

  typedef ncs_rpc_notif_suppression-direction-type {
    type enumeration {
      enum "inbound" {
        value 0;
        description
          "Inbound.";
      }
      enum "outbound" {
        value 1;
        description
          "Outbound.";
      }
      enum "all" {
        value 2;
        description
          "All.";
      }
    }
    description
      "Suppression direction type.";
  }

  typedef ncs_rpc_notif_color-aware-type {
    type enumeration {
      enum "enable" {
        value 1;
        description
          "Enable.";
      }
    }
    description
      "Enable color aware.";
  }

  typedef ncs_rpc_notif_priority-aware-type {
    type enumeration {
      enum "enable" {
        value 1;
        description
          "Enable.";
      }
    }
    description
      "Enable priority aware.";
  }

  typedef ncs_rpc_notif_mode-template-status {
    type enumeration {
      enum "enable" {
        value 1;
        description
          "Enable.";
      }
    }
    description
      "Enable.";
  }

  typedef ncs_rpc_notif_policy-match-type {
    type enumeration {
      enum "ip-layer-push" {
        value 0;
        description
          "MF traffic classification based only on IP Layer (Layer 3) information for incoming traffic on the public network.";
      }
      enum "ip-layer-pop" {
        value 7;
        description
          "MF traffic classification based only on IP Layer (Layer 3) information for outgoing traffic on the public network.";
      }
      enum "mpls-layer-push" {
        value 3;
        description
          "MF classification based on both IP and MPLS information for incoming traffic on the public network.";
      }
      enum "mpls-layer-pop" {
        value 6;
        description
          "MF classification based on both IP and MPLS information for outgoing traffic on the public network.";
      }
      enum "mpls-layer-l2-inbound" {
        value 4;
        description
          "MF traffic classification based on MPLS information for outgoing traffic on the public network in Layer 2 forwarding scenarios.";
      }
      enum "protocol-mc-reserved" {
        value 2;
        description
          "Match Layer 3 protocol packets with reserved multicast addresses against ACLs.";
      }
      enum "rule-packet" {
        value 5;
        description
          "Enable packet type-based filtering for MF classification.";
      }
    }
    description
      "Traffic policy match type.";
  }

  typedef ncs_rpc_notif_statistics-switch-status {
    type enumeration {
      enum "disable" {
        value 0;
        description
          "Disable.";
      }
      enum "enable" {
        value 1;
        description
          "Enable.";
      }
    }
    description
      "Statistics switch type.";
  }

  typedef ncs_rpc_notif_stream-direction-type {
    type enumeration {
      enum "source" {
        value 1;
        description
          "Source.";
      }
      enum "destination" {
        value 2;
        description
          "Destination.";
      }
    }
    description
      "Stream direction type.";
  }

  typedef ncs_rpc_notif_group-type {
    type enumeration {
      enum "service-group" {
        value 1;
        description
          "Service group.";
      }
      enum "user-group" {
        value 2;
        description
          "User group.";
      }
    }
    description
      "Group type.";
  }

  typedef ncs_rpc_notif_switch-type {
    type enumeration {
      enum "enable" {
        value 1;
        description
          "Enable.";
      }
    }
    description
      "Enable.";
  }

  typedef ncs_rpc_notif_out-direction-type {
    type enumeration {
      enum "outbound" {
        value 1;
        description
          "Outbound.";
      }
    }
    description
      "Outbound direction.";
  }

  typedef ncs_rpc_notif_priority-shaping-type {
    type enumeration {
      enum "priority0" {
        value 0;
        description
          "Priority mode 0.";
      }
      enum "priority1" {
        value 1;
        description
          "Priority mode 1.";
      }
      enum "priority2" {
        value 2;
        description
          "Priority mode 2.";
      }
      enum "nopriority" {
        value 255;
        description
          "No priority.";
      }
    }
    description
      "Priority shaping type.";
  }

  typedef ncs_rpc_notif_interval-value {
    type enumeration {
      enum "5s" {
        value 5;
        description
          "5s.";
      }
      enum "30s" {
        value 30;
        description
          "30s.";
      }
      enum "300s" {
        value 300;
        description
          "300s.";
      }
    }
    description
      "Interval value.";
  }

  typedef ncs_rpc_notif_buffer-mode-type {
    type enumeration {
      enum "normal" {
        value 0;
        description
          "Normal.";
      }
      enum "large" {
        value 1;
        description
          "Large.";
      }
    }
    description
      "Buffer mode type.";
  }

  typedef ncs_rpc_notif_speed-type {
    type enumeration {
      enum "both-speed" {
        value 0;
        description
          "High speed and low speed.";
      }
      enum "low-speed" {
        value 1;
        description
          "Low speed.";
      }
      enum "high-speed" {
        value 2;
        description
          "High speed.";
      }
    }
    description
      "Speed type.";
  }

  typedef ncs_rpc_notif_qos-rule-service-type {
    type enumeration {
      enum "normal" {
        value 0;
        description
          "Normal interface.";
      }
      enum "vbd-if" {
        value 1;
        description
          "Vbd interface.";
      }
      enum "multi-type" {
        value 2;
        description
          "Multi type interface.";
      }
      enum "vlan-if" {
        value 3;
        description
          "VLAN interface.";
      }
    }
    description
      "Rule service type.";
  }

  typedef ncs_rpc_notif_qos-address-type {
    type enumeration {
      enum "source" {
        value 0;
        description
          "Source address.";
      }
      enum "destination" {
        value 1;
        description
          "Destination address.";
      }
    }
    description
      "Source or destination address.";
  }

  typedef ncs_rpc_notif_qos-mac-type {
    type enumeration {
      enum "source" {
        value 0;
        description
          "Source MAC address.";
      }
      enum "destination" {
        value 1;
        description
          "Destination MAC address.";
      }
    }
    description
      "Source or destination address.";
  }

  typedef ncs_rpc_notif_qos-ipv6-family {
    type enumeration {
      enum "ipv6" {
        value 2;
        description
          "IPv6 protocol family.";
      }
    }
    description
      "IPv6 protocol family.";
  }

  typedef ncs_rpc_notif_qos-tcp-bit-match {
    type enumeration {
      enum "not-config" {
        value 0;
        description
          "Not config.";
      }
      enum "established" {
        value 1;
        description
          "Established.";
      }
      enum "fin" {
        value 2;
        description
          "Fin.";
      }
      enum "syn" {
        value 3;
        description
          "Syn.";
      }
      enum "rst" {
        value 4;
        description
          "Rst.";
      }
      enum "psh" {
        value 5;
        description
          "Psh.";
      }
      enum "ack" {
        value 6;
        description
          "Ack.";
      }
      enum "urg" {
        value 7;
        description
          "Urg.";
      }
      enum "ece" {
        value 8;
        description
          "Ece.";
      }
      enum "cwr" {
        value 9;
        description
          "Cwr.";
      }
      enum "ns" {
        value 10;
        description
          "Ns.";
      }
    }
    description
      "TCP bit match type.";
  }

  typedef ncs_rpc_notif_qos-tcp-bit-match-ipv6 {
    type enumeration {
      enum "not-config" {
        value 0;
        description
          "NotConfig.";
      }
      enum "established" {
        value 1;
        description
          "Established.";
      }
      enum "fin" {
        value 2;
        description
          "Fin.";
      }
      enum "syn" {
        value 3;
        description
          "Syn.";
      }
      enum "rst" {
        value 4;
        description
          "Rst.";
      }
      enum "psh" {
        value 5;
        description
          "Psh.";
      }
      enum "ack" {
        value 6;
        description
          "Ack.";
      }
      enum "urg" {
        value 7;
        description
          "Urg.";
      }
    }
    description
      "IPv6 TCP bit match type.";
  }

  typedef ncs_rpc_notif_car-limit-type {
    type enumeration {
      enum "pps" {
        value 1;
        description
          "Car limit type pps.";
      }
    }
    description
      "Car limit type.";
  }

  typedef ncs_rpc_notif_acl-log-action-type {
    type enumeration {
      enum "first-packet" {
        value 39;
        description
          "Log first packet action.";
      }
    }
    description
      "Type of the log action.";
  }

  typedef ncs_rpc_notif_low-latency-enable-type {
    type enumeration {
      enum "flow-queue" {
        value 1;
        description
          "Flow queue.";
      }
    }
    description
      "Business type of low latency.";
  }

  typedef ncs_rpc_notif_low-latency-enable-value {
    type enumeration {
      enum "enable" {
        value 1;
        description
          "Enable.";
      }
    }
    description
      "Enable.";
  }

  typedef ncs_rpc_notif_shaping-value-type {
    type enumeration {
      enum "256K" {
        value 0;
        description
          "256K.";
      }
      enum "512K" {
        value 1;
        description
          "512K.";
      }
    }
    description
      "Shaping value type.";
  }

  typedef ncs_rpc_notif_port-shaping-weight-mode-type {
    type enumeration {
      enum "enable" {
        value 1;
        description
          "Weight mode enable.";
      }
    }
    description
      "Weight mode enable.";
  }

  typedef ncs_rpc_notif_scheduling-mode-type {
    type enumeration {
      enum "mode2" {
        value 0;
        description
          "Mode 2.";
      }
      enum "mode3" {
        value 1;
        description
          "Mode 3.";
      }
    }
    description
      "Scheduling mode type.";
  }

  typedef ncs_rpc_notif_map-type {
    type enumeration {
      enum "none" {
        value 1;
        description
          "Notconfig map type.";
      }
      enum "inner-8021p" {
        value 2;
        description
          "Inner 802.1p priority.";
      }
      enum "outer-8021p" {
        value 4;
        description
          "Outer 802.1p priority.";
      }
      enum "dscp" {
        value 8;
        description
          "Dscp type.";
      }
      enum "mpls-exp" {
        value 16;
        description
          "MPLS-EXP type.";
      }
    }
    description
      "Map type for phb.";
  }

  typedef ncs_rpc_notif_convergence-schedule-mode {
    type enumeration {
      enum "disable" {
        value 4;
        description
          "Disable.";
      }
    }
    description
      "Disable.";
  }

  typedef ncs_rpc_notif_port-convergence-schedule-mode {
    type enumeration {
      enum "enable" {
        value 1;
        description
          "Enable.";
      }
    }
    description
      "Enable.";
  }

  typedef ncs_rpc_notif_traffic-policy-untag-type {
    type enumeration {
      enum "disable" {
        value 0;
        description
          "Disable.";
      }
    }
    description
      "Disable.";
  }

  typedef ncs_rpc_notif_qos-direction-inbound {
    type enumeration {
      enum "inbound" {
        value 0;
        description
          "Inbound.";
      }
    }
    description
      "Direction.";
  }

  typedef ncs_rpc_notif_in-direction-type {
    type enumeration {
      enum "inbound" {
        value 0;
        description
          "Inbound.";
      }
    }
    description
      "Inbound.";
  }

  typedef ncs_rpc_notif_discard-type {
    type enumeration {
      enum "discard-packet" {
        value 1;
        description
          "Discard Packets.";
      }
      enum "discard-byte" {
        value 2;
        description
          "Discard Bytes.";
      }
      enum "discard-packet-ratio" {
        value 3;
        description
          "Discard Ratio.";
      }
    }
    description
      "Discard mode type.";
  }

  typedef ncs_rpc_notif_lcs-active-status-type {
    type enumeration {
      enum "allocated" {
        value 1;
        description
          "Allocated.";
      }
      enum "activated" {
        value 2;
        description
          "Activated.";
      }
    }
    description
      "Liscense active status type.";
  }

  typedef ncs_rpc_notif_statistics-car-type {
    type enumeration {
      enum "car" {
        value 1;
        description
          "CAR action.";
      }
      enum "broadcast" {
        value 2;
        description
          "Broadcast suppression.";
      }
      enum "multicast" {
        value 3;
        description
          "Multicast suppression.";
      }
      enum "unknow-unicast" {
        value 4;
        description
          "Unknown unicast suppression.";
      }
      enum "l2-forward" {
        value 5;
        description
          "CAR L2 forward parameter.";
      }
      enum "l3-forward" {
        value 6;
        description
          "CAR L3 forward parameter.";
      }
      enum "bum" {
        value 7;
        description
          "BUM suppression.";
      }
      enum "bu" {
        value 8;
        description
          "BU suppression.";
      }
      enum "unknow-multicast" {
        value 9;
        description
          "Unknown multicast suppression.";
      }
    }
    description
      "Car statistics type.";
  }

  typedef ncs_rpc_notif_qos-priority-num-type {
    type enumeration {
      enum "p0" {
        value 0;
        description
          "P0.";
      }
      enum "p1" {
        value 1;
        description
          "P1.";
      }
      enum "p2" {
        value 2;
        description
          "P2.";
      }
      enum "p3" {
        value 3;
        description
          "P3.";
      }
      enum "p4" {
        value 4;
        description
          "P4.";
      }
      enum "p5" {
        value 5;
        description
          "P5.";
      }
      enum "p6" {
        value 6;
        description
          "P6.";
      }
      enum "p7" {
        value 7;
        description
          "P7.";
      }
      enum "total" {
        value 8;
        description
          "Total.";
      }
    }
    description
      "The priority num.";
  }

  typedef ncs_rpc_notif_qos-flow-type {
    type enumeration {
      enum "source-ip" {
        value 1;
        description
          "Source address.";
      }
      enum "destination-ip" {
        value 2;
        description
          "Destination address.";
      }
    }
    description
      "Flow CAR IP type.";
  }

  typedef ncs_rpc_notif_increase-priority {
    type enumeration {
      enum "increase-priority" {
        value 1;
        description
          "Increase priority.";
      }
    }
    description
      "Increase priority.";
  }

  typedef ncs_rpc_notif_forward-type {
    type enumeration {
      enum "vll" {
        value 1;
        description
          "VLL forward type.";
      }
    }
    description
      "VLL forward type.";
  }

  typedef ncs_rpc_notif_ability-type {
    type enumeration {
      enum "S" {
        value 1;
        description
          "The port support share-mode hard pipe.";
      }
      enum "N" {
        value 2;
        description
          "None hard-pipe ability.";
      }
      enum "U" {
        value 3;
        description
          "Unknown hard-pipe ability.";
      }
      enum "M" {
        value 4;
        description
          "The port need split member interface.";
      }
      enum "E" {
        value 5;
        description
          "The port support exclusive-mode hard pipe.";
      }
    }
    description
      "Ability type.";
  }

  typedef ncs_rpc_notif_qos-policy-layer {
    type enumeration {
      enum "ip-layer" {
        value 1;
        description
          "IP layer.";
      }
    }
    description
      "IP layer.";
  }

  typedef ncs_rpc_notif_enable-type {
    type enumeration {
      enum "enable" {
        value 1;
        description
          "Enable.";
      }
    }
    description
      "Enable.";
  }

  typedef ncs_rpc_notif_priority-convergent-type {
    type enumeration {
      enum "high" {
        value 1;
        description
          "High.";
      }
    }
    description
      "High priority.";
  }

  typedef ncs_rpc_notif_untag-enable-type {
    type enumeration {
      enum "enable" {
        value 2;
        description
          "Enable.";
      }
    }
    description
      "Untag enable type.";
  }

  typedef ncs_rpc_notif_suppress-type {
    type enumeration {
      enum "unknown-unicast-suppression" {
        value 2;
        description
          "Unknown unicast suppression.";
      }
      enum "multicast-suppression" {
        value 3;
        description
          "Multicast suppression.";
      }
      enum "broadcast-suppression" {
        value 4;
        description
          "Broadcast suppression.";
      }
    }
    description
      "Suppression type.";
  }

  typedef ncs_rpc_notif_load-balance-type {
    type enumeration {
      enum "flow" {
        value 0;
        description
          "Flow by flow.";
      }
      enum "packet" {
        value 1;
        description
          "Packet by packet.";
      }
      enum "flow-l2" {
        value 2;
        description
          "Flow by flow with L2.";
      }
      enum "flow-l3" {
        value 3;
        description
          "Flow by flow with L3.";
      }
    }
    description
      "Load balance type.";
  }

  typedef ncs_rpc_notif_sample-type {
    type enumeration {
      enum "fix-packets" {
        value 0;
        description
          "Sampling based on the fixed number of packets.";
      }
      enum "fix-time" {
        value 1;
        description
          "Fixed sampling interval.";
      }
      enum "random-packets" {
        value 2;
        description
          "Sampling based on the random number of packets.";
      }
    }
    description
      "Sampling type.";
  }

  typedef ncs_rpc_notif_action-urpf {
    type enumeration {
      enum "urpf" {
        value 3;
        description
          "URPF action.";
      }
    }
    description
      "URPF action.";
  }

  typedef ncs_rpc_notif_check-type {
    type enumeration {
      enum "strict" {
        value 0;
        description
          "Strict.";
      }
      enum "loose" {
        value 1;
        description
          "Loose.";
      }
    }
    description
      "Type of the URPF check.";
  }

  typedef ncs_rpc_notif_statistics-type {
    type enumeration {
      enum "BPS" {
        value 1;
        description
          "Byte/s.";
      }
      enum "PPS" {
        value 2;
        description
          "Packet/s.";
      }
    }
    description
      "Statistics type.";
  }

  typedef ncs_rpc_notif_ip-type {
    type enumeration {
      enum "ipv4" {
        value 0;
        description
          "IPv4.";
      }
      enum "ipv6" {
        value 1;
        description
          "IPv6.";
      }
    }
    description
      "Type of an address.";
  }

  typedef ncs_rpc_notif_pool-type {
    type enumeration {
      enum "pool-0" {
        value 0;
        description
          "Pool 0.";
      }
      enum "pool-1" {
        value 1;
        description
          "Pool 0.";
      }
    }
    description
      "Pool ID.";
  }

  typedef ncs_rpc_notif_member-link-scheduler-type {
    type enumeration {
      enum "traffic-car" {
        value 1;
        description
          "Traffic CAR.";
      }
      enum "qos-car" {
        value 2;
        description
          "QoS CAR.";
      }
      enum "port-shaping" {
        value 3;
        description
          "Port shaping.";
      }
      enum "hard-pipe" {
        value 4;
        description
          "Hard pipe.";
      }
      enum "user-queue" {
        value 5;
        description
          "User queue.";
      }
      enum "profile-car" {
        value 7;
        description
          "Profile CAR.";
      }
      enum "hqos-outbound" {
        value 8;
        description
          "HQoS outbound.";
      }
      enum "mpls-te" {
        value 9;
        description
          "MPLS TE.";
      }
    }
    description
      "Business type.";
  }

  typedef ncs_rpc_notif_traffic-type {
    type enumeration {
      enum "ldp-traffic" {
        value 1;
        description
          "LDP traffic.";
      }
    }
    description
      "LDP traffic.";
  }

  typedef ncs_rpc_notif_any-other-type {
    type enumeration {
      enum "not-config" {
        value 0;
        description
          "Not config.";
      }
      enum "user-vlan" {
        value 1;
        description
          "User VLAN.";
      }
      enum "qinq" {
        value 2;
        description
          "QinQ.";
      }
    }
    description
      "BAS QoS profile apply type.";
  }

  typedef ncs_rpc_notif_bas-profile-identifier-type {
    type enumeration {
      enum "pe-vid" {
        value 1;
        description
          "PE VLAN ID.";
      }
      enum "ce-vid" {
        value 2;
        description
          "CE VLAN ID.";
      }
      enum "pe-ce-vid" {
        value 3;
        description
          "PE CE VLAN ID.";
      }
      enum "vlan-id" {
        value 4;
        description
          "VLAN ID.";
      }
      enum "none" {
        value 5;
        description
          "None.";
      }
      enum "option82" {
        value 7;
        description
          "Option82.";
      }
      enum "access-line-id" {
        value 11;
        description
          "Access line ID.";
      }
    }
    description
      "BAS QoS profile apply identifier type.";
  }

  typedef ncs_rpc_notif_vlan-user-group-queue-identifier-type {
    type enumeration {
      enum "none" {
        value 0;
        description
          "None.";
      }
      enum "vlan-id" {
        value 1;
        description
          "VLAN ID.";
      }
      enum "pe-vid" {
        value 2;
        description
          "PE VLAN ID.";
      }
      enum "ce-vid" {
        value 3;
        description
          "CE VLAN ID.";
      }
      enum "pe-ce-vid" {
        value 4;
        description
          "PE CE VLAN ID.";
      }
    }
    description
      "VLAN user group queue apply identifier type.";
  }

  typedef ncs_rpc_notif_user-access-type {
    type enumeration {
      enum "leased-line-access" {
        value 10;
        description
          "Leased line access.";
      }
      enum "subscriber-access" {
        value 13;
        description
          "Subscriber access.";
      }
    }
    description
      "User access type.";
  }

  typedef ncs_rpc_notif_hard-pipe-mode {
    type enumeration {
      enum "share-mode" {
        value 0;
        description
          "Share mode.";
      }
      enum "exclusive-mode" {
        value 1;
        description
          "Exclusive mode.";
      }
    }
    description
      "Hard pipe mode.";
  }

  typedef ncs_rpc_notif_ac-mode-layer-type {
    type enumeration {
      enum "link-layer" {
        value 1;
        description
          "Link layer:";
      }
      enum "all-layer" {
        value 2;
        description
          "All layer:";
      }
    }
    description
      "Layer type.";
  }

  typedef ncs_rpc_notif_vxlan-trust-type {
    type enumeration {
      enum "8021p" {
        value 1;
        description
          "Trust 8021p.";
      }
      enum "upstream" {
        value 0;
        description
          "Trust upstream.";
      }
    }
    description
      "VXLAN trust type.";
  }

  typedef ncs_rpc_notif_exclude-type {
    type enumeration {
      enum "no-exclude" {
        value 0;
        description
          "Non-exclude mode.";
      }
      enum "exclude" {
        value 1;
        description
          "Exclude mode.";
      }
    }
    description
      "Exclude type.";
  }

  typedef ncs_rpc_notif_qos-profile-template-name {
    type string {
      length "1..63";
    }
    description
      "Qos profile template name is like string.";
  }

  typedef ncs_rpc_notif_trust-remote-direction-type {
    type enumeration {
      enum "inbound" {
        value 1;
        description
          "Inbound.";
      }
    }
    description
      "Trust remote direction type.";
  }

  typedef ncs_rpc_notif_action-load-balance {
    type enumeration {
      enum "load-balance" {
        value 4;
        description
          "Load balancing action.";
      }
    }
    description
      "Load balancing.";
  }

  typedef ncs_rpc_notif_user-type {
    type enumeration {
      enum "lac" {
        value 1;
        description
          "Specifies the user type as lac.";
      }
      enum "lns" {
        value 2;
        description
          "Specifies the user type as lns.";
      }
      enum "lac-and-lns" {
        value 3;
        description
          "Specifies the user type as lac and lns.";
      }
    }
    description
      "User type.";
  }

  typedef ncs_rpc_notif_access-type {
    type enumeration {
      enum "leased-line-access" {
        value 1;
        description
          "Leased line access.";
      }
      enum "none" {
        value 0;
        description
          "Not config.";
      }
    }
    description
      "User access type.";
  }

  typedef ncs_rpc_notif_l2tp-user {
    type enumeration {
      enum "l2tp-user" {
        value 12;
        description
          "L2TP user.";
      }
    }
    description
      "L2TP user.";
  }

  typedef ncs_rpc_notif_cos-value-type {
    type enumeration {
      enum "be" {
        value 0;
        description
          "Specifies the service class to be BE.";
      }
      enum "af1-af2" {
        value 1;
        description
          "Specifies the service class to be AF1 and AF2.";
      }
      enum "af3-af4" {
        value 2;
        description
          "Specifies the service class to be Af3 and af4.";
      }
      enum "ef-cs6-cs7" {
        value 3;
        description
          "Specifies the service class to be EF and CS6 and CS7.";
      }
    }
    description
      "Service class type.";
  }

  typedef ncs_rpc_notif_rule-type {
    type enumeration {
      enum "aclv4" {
        value 1;
        description
          "Aclv4.";
      }
      enum "aclv6" {
        value 2;
        description
          "Aclv6.";
      }
      enum "l2acl" {
        value 3;
        description
          "L2acl.";
      }
      enum "mpls" {
        value 4;
        description
          "MPLS.";
      }
      enum "uclv4" {
        value 5;
        description
          "Uclv4.";
      }
      enum "uclv6" {
        value 6;
        description
          "Uclv6.";
      }
    }
    description
      "Qos resource rule type.";
  }

  typedef ncs_rpc_notif_yes-or-no {
    type enumeration {
      enum "no" {
        value 0;
        description
          "No.";
      }
      enum "yes" {
        value 1;
        description
          "Yes.";
      }
    }
    description
      "Choose yes or no.";
  }

  typedef ncs_rpc_notif_remote-trust-type {
    type enumeration {
      enum "ip-dscp" {
        value 0;
        description
          "Trust ip-dscp.";
      }
      enum "8021p" {
        value 1;
        description
          "Trust 8021p.";
      }
    }
    description
      "Trust type.";
  }

  typedef ncs_rpc_notif_type-8021p {
    type enumeration {
      enum "8021p" {
        value 1;
        description
          "Trust 8021p.";
      }
      enum "inner-8021p" {
        value 3;
        description
          "Trust inner 8021p.";
      }
      enum "outer-8021p" {
        value 2;
        description
          "Trust outer 8021p.";
      }
    }
    description
      "Trust 8021p type.";
  }

  typedef ncs_rpc_notif_deficit-unit-type {
    type enumeration {
      enum "1K" {
        value 4;
        description
          "1K (byte).";
      }
      enum "2K" {
        value 5;
        description
          "2K (byte).";
      }
    }
    description
      "Deficit unit type.";
  }

  typedef ncs_rpc_notif_user-queue-template-type {
    type enumeration {
      enum "4-priority" {
        value 0;
        description
          "Four priority mode.";
      }
    }
    description
      "User queue template mode type.";
  }

  typedef ncs_rpc_notif_priority-schedule-mode {
    type enumeration {
      enum "pq" {
        value 0;
        description
          "Priority queue.";
      }
      enum "wfq" {
        value 1;
        description
          "Weighted fair queue.";
      }
    }
    description
      "Priority mode.";
  }

  typedef ncs_rpc_notif_ignore-default-type {
    type enumeration {
      enum "disable" {
        value 0;
        description
          "The default route is excluded.";
      }
    }
    description
      "Indicates a mode in which the default route is excluded.";
  }

  typedef ncs_rpc_notif_protocol-family {
    type enumeration {
      enum "ipv4" {
        value 1;
        description
          "IPv4.";
      }
      enum "ipv6" {
        value 2;
        description
          "IPv6.";
      }
      enum "l2" {
        value 3;
        description
          "L2.";
      }
      enum "mpls" {
        value 4;
        description
          "MPLS.";
      }
    }
    description
      "Protocol family type.";
  }

  typedef live_ncs_qos-ba-type {
    type enumeration {
      enum "8021p" {
        value 0;
        description
          "802.1p priority.";
      }
      enum "ip-dscp" {
        value 1;
        description
          "DSCP priority.";
      }
      enum "mpls-exp" {
        value 2;
        description
          "MPLS-EXP priority.";
      }
      enum "user-priority" {
        value 3;
        description
          "User priority.";
      }
      enum "ip-precedence" {
        value 11;
        description
          "IP-Precedence priority.";
      }
    }
    description
      "Behavior aggregations type.";
  }

  typedef live_ncs_qos-phb-type {
    type enumeration {
      enum "8021p" {
        value 0;
        description
          "802.1p priority.";
      }
      enum "ip-dscp" {
        value 1;
        description
          "DSCP priority.";
      }
      enum "mpls-exp" {
        value 2;
        description
          "MPLS-EXP priority.";
      }
      enum "ip-precedence" {
        value 11;
        description
          "IP Precedence priority.";
      }
    }
    description
      "Priority type.";
  }

  typedef live_ncs_qos-service-class {
    type enumeration {
      enum "be" {
        value 0;
        description
          "BE service class.";
      }
      enum "af1" {
        value 1;
        description
          "AF1 service-class.";
      }
      enum "af2" {
        value 2;
        description
          "AF2 service-class.";
      }
      enum "af3" {
        value 3;
        description
          "AF3 service-class.";
      }
      enum "af4" {
        value 4;
        description
          "AF4 service-class.";
      }
      enum "ef" {
        value 5;
        description
          "EF service-class.";
      }
      enum "cs6" {
        value 6;
        description
          "CS6 service-class.";
      }
      enum "cs7" {
        value 7;
        description
          "CS7 service-class.";
      }
    }
    description
      "QoS service class.";
  }

  typedef live_ncs_qos-service-class-total {
    type enumeration {
      enum "be" {
        value 0;
        description
          "BE service class.";
      }
      enum "af1" {
        value 1;
        description
          "AF1 service class.";
      }
      enum "af2" {
        value 2;
        description
          "AF2 service class.";
      }
      enum "af3" {
        value 3;
        description
          "AF3 service class.";
      }
      enum "af4" {
        value 4;
        description
          "AF4 service class.";
      }
      enum "ef" {
        value 5;
        description
          "EF service class.";
      }
      enum "cs6" {
        value 6;
        description
          "CS6 service class.";
      }
      enum "cs7" {
        value 7;
        description
          "CS7 service class.";
      }
      enum "total" {
        value 8;
        description
          "Total service class.";
      }
    }
    description
      "QoS service class.";
  }

  typedef live_ncs_qos-color {
    type enumeration {
      enum "green" {
        value 0;
        description
          "Green.";
      }
      enum "yellow" {
        value 1;
        description
          "Yellow.";
      }
      enum "red" {
        value 2;
        description
          "Red.";
      }
    }
    description
      "Color type.";
  }

  typedef live_ncs_qos-direction-type {
    type enumeration {
      enum "inbound" {
        value 0;
        description
          "Inbound.";
      }
      enum "outbound" {
        value 1;
        description
          "Outbound.";
      }
    }
    description
      "Direction type.";
  }

  typedef live_ncs_qos-gq-direction-type {
    type enumeration {
      enum "inbound" {
        value 0;
        description
          "Inbound.";
      }
      enum "outbound" {
        value 1;
        description
          "Outbound.";
      }
    }
    description
      "Direction type.";
  }

  typedef live_ncs_qos-traffic-type {
    type enumeration {
      enum "ucl" {
        value 0;
        description
          "Ucl.";
      }
      enum "acl" {
        value 1;
        description
          "Acl.";
      }
    }
    description
      "Traffic policy type.";
  }

  typedef live_ncs_qos-acl-log-type {
    type enumeration {
      enum "acl-log" {
        value 1;
        description
          "Log first-packet parameter.";
      }
    }
    description
      "Acl log.";
  }

  typedef live_ncs_template-name {
    type string {
      length "1..31";
    }
    description
      "Template name is like string.";
  }

  typedef live_ncs_queue-schedule-mode {
    type enumeration {
      enum "pq" {
        value 0;
        description
          "Priority queue.";
      }
      enum "wfq" {
        value 1;
        description
          "Weighted fair queuing.";
      }
      enum "lpq" {
        value 2;
        description
          "Low priority queuing.";
      }
    }
    description
      "Queue schedule mode.";
  }

  typedef live_ncs_queue-low-latency {
    type enumeration {
      enum "enable" {
        value 1;
        description
          "Enable.";
      }
    }
    description
      "Enable low latency.";
  }

  typedef live_ncs_queue-low-jitter {
    type enumeration {
      enum "enable" {
        value 1;
        description
          "Enable.";
      }
    }
    description
      "Enable low jitter.";
  }

  typedef live_ncs_queue-cir-schedule-mode {
    type enumeration {
      enum "pq" {
        value 0;
        description
          "PQ.";
      }
    }
    description
      "Scheduling strategy of cir.";
  }

  typedef live_ncs_flow-queue-template-type {
    type enumeration {
      enum "normal" {
        value 0;
        description
          "Normal mode.";
      }
      enum "priority" {
        value 1;
        description
          "Priority mode.";
      }
      enum "4cos" {
        value 2;
        description
          "Four cos mode.";
      }
      enum "8cos-enhance" {
        value 5;
        description
          "Eight cos enhance.";
      }
    }
    description
      "Flow queue template mode type.";
  }

  typedef live_ncs_profile-template-type {
    type enumeration {
      enum "normal" {
        value 0;
        description
          "Normal.";
      }
      enum "time-range" {
        value 1;
        description
          "Time range.";
      }
      enum "8cos-enhance" {
        value 5;
        description
          "Eight cos enhance.";
      }
    }
    description
      "Profile template mode type.";
  }

  typedef live_ncs_all-direction-type {
    type enumeration {
      enum "inbound" {
        value 0;
        description
          "Inbound.";
      }
      enum "outbound" {
        value 1;
        description
          "Outbound.";
      }
      enum "all" {
        value 2;
        description
          "All.";
      }
    }
    description
      "Direction type include all.";
  }

  typedef live_ncs_priority-level-type {
    type enumeration {
      enum "low" {
        value 255;
        description
          "Low.";
      }
      enum "high" {
        value 1;
        description
          "High.";
      }
    }
    description
      "Priority level type.";
  }

  typedef live_ncs_adjust-on-card-type {
    type enumeration {
      enum "disable" {
        value 0;
        description
          "Disable.";
      }
      enum "enable" {
        value 1;
        description
          "Enable.";
      }
    }
    description
      "Adjust on card flag.";
  }

  typedef live_ncs_gq-template-type {
    type enumeration {
      enum "normal" {
        value 0;
        description
          "Normal mode.";
      }
      enum "priority" {
        value 1;
        description
          "Priority mode.";
      }
    }
    description
      "User group queue mode.";
  }

  typedef live_ncs_class-operator {
    type enumeration {
      enum "or" {
        value 0;
        description
          "Or.";
      }
      enum "and" {
        value 1;
        description
          "And.";
      }
    }
    description
      "Logical operator of a rule.";
  }

  typedef live_ncs_ip-family {
    type enumeration {
      enum "ipv4" {
        value 1;
        description
          "IPv4.";
      }
      enum "ipv6" {
        value 2;
        description
          "IPv6.";
      }
    }
    description
      "Ip family type.";
  }

  typedef live_ncs_priority-type {
    type enumeration {
      enum "8021p" {
        value 0;
        description
          "802.1p priority.";
      }
      enum "ip-precedence" {
        value 1;
        description
          "IP precedence.";
      }
      enum "dscp" {
        value 2;
        description
          "DSCP priority.";
      }
      enum "mpls-exp" {
        value 4;
        description
          "MPLS-EXP priority.";
      }
      enum "ipv6-dscp" {
        value 5;
        description
          "IPv6 DSCP priority.";
      }
      enum "ipv6-ip-precedence" {
        value 6;
        description
          "IPv6 IP precedence.";
      }
    }
    description
      "Priority type.";
  }

  typedef live_ncs_action-car {
    type enumeration {
      enum "car" {
        value 0;
        description
          "CAR action.";
      }
    }
    description
      "Type of a car action.";
  }

  typedef live_ncs_color-action-type {
    type enumeration {
      enum "pass" {
        value 0;
        description
          "Pass.";
      }
      enum "discard" {
        value 2;
        description
          "Discard.";
      }
    }
    description
      "Color action type.";
  }

  typedef live_ncs_service-class-notconfig {
    type enumeration {
      enum "be" {
        value 0;
        description
          "BE service class.";
      }
      enum "af1" {
        value 1;
        description
          "AF1 service class.";
      }
      enum "af2" {
        value 2;
        description
          "AF2 service class.";
      }
      enum "af3" {
        value 3;
        description
          "AF3 service class.";
      }
      enum "af4" {
        value 4;
        description
          "AF4 service class.";
      }
      enum "ef" {
        value 5;
        description
          "EF service class.";
      }
      enum "cs6" {
        value 6;
        description
          "CS6 service class.";
      }
      enum "cs7" {
        value 7;
        description
          "CS7 service class.";
      }
      enum "not-config" {
        value 8;
        description
          "Not config service class.";
      }
    }
    description
      "Service class type.";
  }

  typedef live_ncs_filter-flag {
    type enumeration {
      enum "permit" {
        value 0;
        description
          "Permit.";
      }
      enum "deny" {
        value 1;
        description
          "Deny.";
      }
    }
    description
      "Filter type.";
  }

  typedef live_ncs_action-remark {
    type enumeration {
      enum "8021p" {
        value 12;
        description
          "Remark 802.1p priority action.";
      }
      enum "ipv4-dscp" {
        value 13;
        description
          "Remark DSCP action.";
      }
      enum "tos" {
        value 19;
        description
          "Remark tos priority action.";
      }
      enum "ipv6-dscp" {
        value 14;
        description
          "Remark IPv6 DSCP action.";
      }
      enum "ip-precedence" {
        value 15;
        description
          "Remark IP precedence action.";
      }
      enum "mpls-exp" {
        value 16;
        description
          "Remark MPLS-EXP action.";
      }
      enum "ip-df" {
        value 21;
        description
          "Remark IP-DF action.";
      }
      enum "ttl" {
        value 26;
        description
          "Remark TTL action.";
      }
      enum "inner-8021p" {
        value 34;
        description
          "Remark inner 802.1p priority action.";
      }
      enum "outer-8021p" {
        value 35;
        description
          "Remark outer 802.1p priority action.";
      }
      enum "remark-local-id" {
        value 60;
        description
          "Remark qos-local-id action.";
      }
    }
    description
      "Action remark type.";
  }

  typedef live_ncs_service-class-action {
    type enumeration {
      enum "service-class" {
        value 0;
        description
          "Service class.";
      }
      enum "service-class-master-bfd" {
        value 1;
        description
          "Service class link master BFD.";
      }
      enum "service-class-slave-bfd" {
        value 2;
        description
          "Service class link slave BFD.";
      }
    }
    description
      "Type of a service class action.";
  }

  typedef live_ncs_remark-type {
    type enumeration {
      enum "enable" {
        value 0;
        description
          "Remark enable.";
      }
      enum "disable" {
        value 1;
        description
          "Remark disable.";
      }
    }
    description
      "Remark type.";
  }

  typedef live_ncs_trust-type {
    type enumeration {
      enum "ip-dscp" {
        value 0;
        description
          "Trust ip-dscp.";
      }
      enum "8021p" {
        value 1;
        description
          "Trust 8021p.";
      }
      enum "inner-8021p" {
        value 3;
        description
          "Trust inner-8021p.";
      }
      enum "outer-8021p" {
        value 2;
        description
          "Trust outer-8021p.";
      }
    }
    description
      "Trust type.";
  }

  typedef live_ncs_trust-direction-type {
    type enumeration {
      enum "inbound" {
        value 1;
        description
          "Inbound.";
      }
      enum "outbound" {
        value 2;
        description
          "Outbound.";
      }
      enum "in-outbound" {
        value 0;
        description
          "Not config.";
      }
    }
    description
      "Trust direction type.";
  }

  typedef live_ncs_identifier-type {
    type enumeration {
      enum "no" {
        value 0;
        description
          "Not config.";
      }
      enum "none" {
        value 1;
        description
          "Not config VLAN.";
      }
      enum "vid" {
        value 2;
        description
          "Vid.";
      }
      enum "ce-vid" {
        value 3;
        description
          "CE VLAN ID.";
      }
      enum "vid-ce-vid" {
        value 4;
        description
          "Vid CE vid.";
      }
    }
    description
      "Identifier type.";
  }

  typedef live_ncs_link-adjustment-type {
    type enumeration {
      enum "cell" {
        value 1;
        description
          "Cell.";
      }
    }
    description
      "Link adjustment type.";
  }

  typedef live_ncs_policy-apply-layer-type {
    type enumeration {
      enum "none" {
        value 0;
        description
          "Default classification.";
      }
      enum "link" {
        value 1;
        description
          "Classification based on Layer 2 information.";
      }
      enum "mpls" {
        value 3;
        description
          "Classification based on MPLS information.";
      }
      enum "all" {
        value 2;
        description
          "Classification based on ALL information.";
      }
      enum "vxlan" {
        value 4;
        description
          "Classification based on VXLAN information.";
      }
    }
    description
      "Policy layer type.";
  }

  typedef live_ncs_policy-apply-vxlan-layer-type {
    type enumeration {
      enum "link" {
        value 1;
        description
          "Classification based on Layer 2 information.";
      }
    }
    description
      "Policy layer type.";
  }

  typedef live_ncs_profile-apply-type {
    type enumeration {
      enum "interface" {
        value 0;
        description
          "Interface.";
      }
      enum "vlan" {
        value 1;
        description
          "VLAN.";
      }
      enum "pe" {
        value 2;
        description
          "Pe.";
      }
    }
    description
      "Profile apply type.";
  }

  typedef live_ncs_linkage-bandwidth-type {
    type enumeration {
      enum "disable" {
        value 0;
        description
          "Disable.";
      }
      enum "enable" {
        value 1;
        description
          "Enable.";
      }
    }
    description
      "Linkage bandwidth type.";
  }

  typedef live_ncs_identify-type {
    type enumeration {
      enum "none" {
        value 0;
        description
          "None.";
      }
      enum "vlan" {
        value 1;
        description
          "VLAN.";
      }
      enum "pe-vid" {
        value 2;
        description
          "Pe VLAN Id.";
      }
      enum "ce-vid" {
        value 3;
        description
          "Ce VLAN Id.";
      }
      enum "pe-ce-vid" {
        value 4;
        description
          "Pe-Ce VLAN Id.";
      }
      enum "vid" {
        value 5;
        description
          "Vid.";
      }
      enum "evc-ce-vid" {
        value 6;
        description
          "Ce-vid.";
      }
      enum "vid-ce-vid" {
        value 7;
        description
          "Vid-ce-vid.";
      }
    }
    description
      "Identify type.";
  }

  typedef live_ncs_hqos-service-class {
    type enumeration {
      enum "be" {
        value 0;
        description
          "BE service class.";
      }
      enum "af1" {
        value 1;
        description
          "AF1 service class.";
      }
      enum "af2" {
        value 2;
        description
          "AF2 service class.";
      }
      enum "af3" {
        value 3;
        description
          "AF3 service class.";
      }
      enum "af4" {
        value 4;
        description
          "AF4 service class.";
      }
      enum "ef" {
        value 5;
        description
          "EF service class.";
      }
      enum "cs6" {
        value 6;
        description
          "CS6 service class.";
      }
      enum "cs7" {
        value 7;
        description
          "CS7 service class.";
      }
      enum "total" {
        value 8;
        description
          "Total.";
      }
      enum "cos0" {
        value 9;
        description
          "Cos0 service class.";
      }
      enum "cos1" {
        value 10;
        description
          "Cos1 service class.";
      }
      enum "cos2" {
        value 11;
        description
          "Cos2 service class.";
      }
      enum "cos3" {
        value 12;
        description
          "Cos3 service class.";
      }
    }
    description
      "Service class type.";
  }

  typedef live_ncs_qos-res-type {
    type enumeration {
      enum "null" {
        value 0;
        description
          "Null.";
      }
      enum "sq" {
        value 1;
        description
          "SQ.";
      }
      enum "car" {
        value 2;
        description
          "CAR.";
      }
      enum "sq-car" {
        value 3;
        description
          "SQCAR.";
      }
      enum "l2-car" {
        value 4;
        description
          "L2CAR.";
      }
      enum "l2-l3-car" {
        value 5;
        description
          "L2L3CAR.";
      }
      enum "l3-car" {
        value 6;
        description
          "L3CAR.";
      }
    }
    description
      "Resource type.";
  }

  typedef live_ncs_switch-flag {
    type enumeration {
      enum "enable" {
        value 1;
        description
          "Enable.";
      }
      enum "disable" {
        value 0;
        description
          "Disable.";
      }
    }
    description
      "Switch flag.";
  }

  typedef live_ncs_low-latency {
    type enumeration {
      enum "enable" {
        value 1;
        description
          "Enable.";
      }
      enum "disable" {
        value 0;
        description
          "Disable.";
      }
    }
    description
      "Enable or disable low latency.";
  }

  typedef live_ncs_share-shape-mode {
    type enumeration {
      enum "pq" {
        value 0;
        description
          "Priority queue.";
      }
      enum "wfq" {
        value 1;
        description
          "Weighted fair queuing.";
      }
      enum "lpq" {
        value 2;
        description
          "Low priority queuing.";
      }
      enum "not-config" {
        value 3;
        description
          "Not config.";
      }
    }
    description
      "Share shape mode.";
  }

  typedef live_ncs_be-type {
    type enumeration {
      enum "true" {
        value 0;
        description
          "True.";
      }
      enum "false" {
        value 8;
        description
          "False.";
      }
    }
    description
      "BE type.";
  }

  typedef live_ncs_af1-type {
    type enumeration {
      enum "true" {
        value 1;
        description
          "True.";
      }
      enum "false" {
        value 8;
        description
          "False.";
      }
    }
    description
      "AF1 type.";
  }

  typedef live_ncs_af2-type {
    type enumeration {
      enum "true" {
        value 2;
        description
          "True.";
      }
      enum "false" {
        value 8;
        description
          "False.";
      }
    }
    description
      "AF2 type.";
  }

  typedef live_ncs_af3-type {
    type enumeration {
      enum "true" {
        value 3;
        description
          "True.";
      }
      enum "false" {
        value 8;
        description
          "False.";
      }
    }
    description
      "AF3 type.";
  }

  typedef live_ncs_af4-type {
    type enumeration {
      enum "true" {
        value 4;
        description
          "True.";
      }
      enum "false" {
        value 8;
        description
          "False.";
      }
    }
    description
      "AF4 type.";
  }

  typedef live_ncs_ef-type {
    type enumeration {
      enum "true" {
        value 5;
        description
          "True.";
      }
      enum "false" {
        value 8;
        description
          "False.";
      }
    }
    description
      "EF type.";
  }

  typedef live_ncs_cs6-type {
    type enumeration {
      enum "true" {
        value 6;
        description
          "True.";
      }
      enum "false" {
        value 8;
        description
          "False.";
      }
    }
    description
      "CS6 type.";
  }

  typedef live_ncs_cs7-type {
    type enumeration {
      enum "true" {
        value 7;
        description
          "True.";
      }
      enum "false" {
        value 8;
        description
          "False.";
      }
    }
    description
      "CS7 type.";
  }

  typedef live_ncs_shapid-upritype {
    type enumeration {
      enum "1" {
        value 1;
        description
          "1.";
      }
    }
    description
      "Shap Id.";
  }

  typedef live_ncs_qos-cos-value {
    type enumeration {
      enum "cos0" {
        value 0;
        description
          "Cos0.";
      }
      enum "cos1" {
        value 1;
        description
          "Cos1.";
      }
      enum "cos2" {
        value 2;
        description
          "Cos2.";
      }
      enum "cos3" {
        value 3;
        description
          "Cos3.";
      }
    }
    description
      "Cos value.";
  }

  typedef live_ncs_shap-id-type {
    type enumeration {
      enum "1" {
        value 1;
        description
          "Shap-id 1.";
      }
      enum "not-config" {
        value 2;
        description
          "Not config.";
      }
    }
    description
      "Shap id type.";
  }

  typedef live_ncs_queue-select-be-type {
    type enumeration {
      enum "true" {
        value 0;
        description
          "True.";
      }
    }
    description
      "Queue BE.";
  }

  typedef live_ncs_queue-select-af1-type {
    type enumeration {
      enum "true" {
        value 1;
        description
          "True.";
      }
    }
    description
      "Queue AF1.";
  }

  typedef live_ncs_queue-select-af2-type {
    type enumeration {
      enum "true" {
        value 2;
        description
          "True.";
      }
    }
    description
      "Queue AF2.";
  }

  typedef live_ncs_queue-select-af3-type {
    type enumeration {
      enum "true" {
        value 3;
        description
          "True.";
      }
    }
    description
      "Queue AF3.";
  }

  typedef live_ncs_queue-select-af4-type {
    type enumeration {
      enum "true" {
        value 4;
        description
          "True.";
      }
    }
    description
      "Queue AF4.";
  }

  typedef live_ncs_queue-select-ef-type {
    type enumeration {
      enum "true" {
        value 5;
        description
          "True.";
      }
    }
    description
      "Queue EF.";
  }

  typedef live_ncs_queue-select-cs6-type {
    type enumeration {
      enum "true" {
        value 6;
        description
          "True.";
      }
    }
    description
      "Queue CS6.";
  }

  typedef live_ncs_queue-select-cs7-type {
    type enumeration {
      enum "true" {
        value 7;
        description
          "True.";
      }
    }
    description
      "Queue CS7.";
  }

  typedef live_ncs_priority-flow-queue-schedule-mode {
    type enumeration {
      enum "pq" {
        value 0;
        description
          "Priority queue.";
      }
      enum "wfq" {
        value 1;
        description
          "Weighted fair queue.";
      }
    }
    description
      "Priority mode.";
  }

  typedef live_ncs_slot-id {
    type string {
      length "1..31";
      pattern '((c[cl]c\d+/)|(\d+/))?\d+';
    }
    description
      "Slot id is like 3, clc1/3 or ccc1/3.";
  }

  typedef live_ncs_group-name {
    type string {
      length "1..32";
    }
    description
      "Group name is like string.";
  }

  typedef live_ncs_qos-service-class-filter {
    type enumeration {
      enum "be" {
        value 0;
        description
          "BE service class.";
      }
      enum "af1" {
        value 1;
        description
          "AF1 service class.";
      }
      enum "af2" {
        value 2;
        description
          "AF2 service class.";
      }
      enum "af3" {
        value 3;
        description
          "AF3 service class.";
      }
      enum "af4" {
        value 4;
        description
          "AF4 service class.";
      }
      enum "ef" {
        value 5;
        description
          "Ef service class.";
      }
      enum "cs6" {
        value 6;
        description
          "CS6 service class.";
      }
      enum "cs7" {
        value 7;
        description
          "CS7 service class.";
      }
      enum "total" {
        value 8;
        description
          "Total.";
      }
    }
    description
      "Service class.";
  }

  typedef live_ncs_qos-service-class-8cos {
    type enumeration {
      enum "be" {
        value 0;
        description
          "BE service class.";
      }
      enum "af1" {
        value 1;
        description
          "AF1 service class.";
      }
      enum "af2" {
        value 2;
        description
          "AF2 service class.";
      }
      enum "af3" {
        value 3;
        description
          "AF3 service class.";
      }
      enum "af4" {
        value 4;
        description
          "AF4 service class.";
      }
      enum "ef" {
        value 5;
        description
          "Ef service class.";
      }
      enum "cs6" {
        value 6;
        description
          "CS6 service class.";
      }
      enum "cs7" {
        value 7;
        description
          "CS7 service class.";
      }
      enum "total" {
        value 8;
        description
          "Total.";
      }
      enum "cos0" {
        value 9;
        description
          "Cos0 service class.";
      }
      enum "cos1" {
        value 10;
        description
          "Cos1 service class.";
      }
      enum "cos2" {
        value 11;
        description
          "Cos2 service class.";
      }
      enum "cos3" {
        value 12;
        description
          "Cos3 service class.";
      }
      enum "cos4" {
        value 13;
        description
          "Cos4 service class.";
      }
      enum "cos5" {
        value 14;
        description
          "Cos5 service class.";
      }
      enum "cos6" {
        value 15;
        description
          "Cos6 service class.";
      }
      enum "cos7" {
        value 16;
        description
          "Cos7 service class.";
      }
    }
    description
      "Service class.";
  }

  typedef live_ncs_qos-car-type {
    type enumeration {
      enum "car" {
        value 1;
        description
          "CAR action.";
      }
    }
    description
      "CAR.";
  }

  typedef live_ncs_car-direction-type {
    type enumeration {
      enum "inbound" {
        value 0;
        description
          "Inbound.";
      }
      enum "outbound" {
        value 1;
        description
          "Outbound.";
      }
      enum "all" {
        value 2;
        description
          "All.";
      }
    }
    description
      "Direction type.";
  }

  typedef live_ncs_profile-car-type {
    type enumeration {
      enum "car" {
        value 1;
        description
          "CAR action.";
      }
    }
    description
      "CAR.";
  }

  typedef live_ncs_profile-car-direction-type {
    type enumeration {
      enum "all" {
        value 2;
        description
          "All.";
      }
    }
    description
      "All.";
  }

  typedef live_ncs_qos-suppression-type {
    type enumeration {
      enum "broadcast" {
        value 2;
        description
          "Broadcast suppression.";
      }
      enum "multicast" {
        value 3;
        description
          "Multicast suppression.";
      }
      enum "unknow-unicast" {
        value 4;
        description
          "Unknown unicast suppression.";
      }
      enum "bum" {
        value 7;
        description
          "BUM suppression.";
      }
      enum "bu" {
        value 8;
        description
          "BU suppression.";
      }
      enum "unknow-multicast" {
        value 9;
        description
          "Unknown multicast suppression.";
      }
    }
    description
      "Suppression type.";
  }

  typedef live_ncs_suppression-direction-type {
    type enumeration {
      enum "inbound" {
        value 0;
        description
          "Inbound.";
      }
      enum "outbound" {
        value 1;
        description
          "Outbound.";
      }
      enum "all" {
        value 2;
        description
          "All.";
      }
    }
    description
      "Suppression direction type.";
  }

  typedef live_ncs_color-aware-type {
    type enumeration {
      enum "enable" {
        value 1;
        description
          "Enable.";
      }
    }
    description
      "Enable color aware.";
  }

  typedef live_ncs_priority-aware-type {
    type enumeration {
      enum "enable" {
        value 1;
        description
          "Enable.";
      }
    }
    description
      "Enable priority aware.";
  }

  typedef live_ncs_mode-template-status {
    type enumeration {
      enum "enable" {
        value 1;
        description
          "Enable.";
      }
    }
    description
      "Enable.";
  }

  typedef live_ncs_policy-match-type {
    type enumeration {
      enum "ip-layer-push" {
        value 0;
        description
          "MF traffic classification based only on IP Layer (Layer 3) information for incoming traffic on the public network.";
      }
      enum "ip-layer-pop" {
        value 7;
        description
          "MF traffic classification based only on IP Layer (Layer 3) information for outgoing traffic on the public network.";
      }
      enum "mpls-layer-push" {
        value 3;
        description
          "MF classification based on both IP and MPLS information for incoming traffic on the public network.";
      }
      enum "mpls-layer-pop" {
        value 6;
        description
          "MF classification based on both IP and MPLS information for outgoing traffic on the public network.";
      }
      enum "mpls-layer-l2-inbound" {
        value 4;
        description
          "MF traffic classification based on MPLS information for outgoing traffic on the public network in Layer 2 forwarding scenarios.";
      }
      enum "protocol-mc-reserved" {
        value 2;
        description
          "Match Layer 3 protocol packets with reserved multicast addresses against ACLs.";
      }
      enum "rule-packet" {
        value 5;
        description
          "Enable packet type-based filtering for MF classification.";
      }
    }
    description
      "Traffic policy match type.";
  }

  typedef live_ncs_statistics-switch-status {
    type enumeration {
      enum "disable" {
        value 0;
        description
          "Disable.";
      }
      enum "enable" {
        value 1;
        description
          "Enable.";
      }
    }
    description
      "Statistics switch type.";
  }

  typedef live_ncs_stream-direction-type {
    type enumeration {
      enum "source" {
        value 1;
        description
          "Source.";
      }
      enum "destination" {
        value 2;
        description
          "Destination.";
      }
    }
    description
      "Stream direction type.";
  }

  typedef live_ncs_group-type {
    type enumeration {
      enum "service-group" {
        value 1;
        description
          "Service group.";
      }
      enum "user-group" {
        value 2;
        description
          "User group.";
      }
    }
    description
      "Group type.";
  }

  typedef live_ncs_switch-type {
    type enumeration {
      enum "enable" {
        value 1;
        description
          "Enable.";
      }
    }
    description
      "Enable.";
  }

  typedef live_ncs_out-direction-type {
    type enumeration {
      enum "outbound" {
        value 1;
        description
          "Outbound.";
      }
    }
    description
      "Outbound direction.";
  }

  typedef live_ncs_priority-shaping-type {
    type enumeration {
      enum "priority0" {
        value 0;
        description
          "Priority mode 0.";
      }
      enum "priority1" {
        value 1;
        description
          "Priority mode 1.";
      }
      enum "priority2" {
        value 2;
        description
          "Priority mode 2.";
      }
      enum "nopriority" {
        value 255;
        description
          "No priority.";
      }
    }
    description
      "Priority shaping type.";
  }

  typedef live_ncs_interval-value {
    type enumeration {
      enum "5s" {
        value 5;
        description
          "5s.";
      }
      enum "30s" {
        value 30;
        description
          "30s.";
      }
      enum "300s" {
        value 300;
        description
          "300s.";
      }
    }
    description
      "Interval value.";
  }

  typedef live_ncs_buffer-mode-type {
    type enumeration {
      enum "normal" {
        value 0;
        description
          "Normal.";
      }
      enum "large" {
        value 1;
        description
          "Large.";
      }
    }
    description
      "Buffer mode type.";
  }

  typedef live_ncs_speed-type {
    type enumeration {
      enum "both-speed" {
        value 0;
        description
          "High speed and low speed.";
      }
      enum "low-speed" {
        value 1;
        description
          "Low speed.";
      }
      enum "high-speed" {
        value 2;
        description
          "High speed.";
      }
    }
    description
      "Speed type.";
  }

  typedef live_ncs_qos-rule-service-type {
    type enumeration {
      enum "normal" {
        value 0;
        description
          "Normal interface.";
      }
      enum "vbd-if" {
        value 1;
        description
          "Vbd interface.";
      }
      enum "multi-type" {
        value 2;
        description
          "Multi type interface.";
      }
      enum "vlan-if" {
        value 3;
        description
          "VLAN interface.";
      }
    }
    description
      "Rule service type.";
  }

  typedef live_ncs_qos-address-type {
    type enumeration {
      enum "source" {
        value 0;
        description
          "Source address.";
      }
      enum "destination" {
        value 1;
        description
          "Destination address.";
      }
    }
    description
      "Source or destination address.";
  }

  typedef live_ncs_qos-mac-type {
    type enumeration {
      enum "source" {
        value 0;
        description
          "Source MAC address.";
      }
      enum "destination" {
        value 1;
        description
          "Destination MAC address.";
      }
    }
    description
      "Source or destination address.";
  }

  typedef live_ncs_qos-ipv6-family {
    type enumeration {
      enum "ipv6" {
        value 2;
        description
          "IPv6 protocol family.";
      }
    }
    description
      "IPv6 protocol family.";
  }

  typedef live_ncs_qos-tcp-bit-match {
    type enumeration {
      enum "not-config" {
        value 0;
        description
          "Not config.";
      }
      enum "established" {
        value 1;
        description
          "Established.";
      }
      enum "fin" {
        value 2;
        description
          "Fin.";
      }
      enum "syn" {
        value 3;
        description
          "Syn.";
      }
      enum "rst" {
        value 4;
        description
          "Rst.";
      }
      enum "psh" {
        value 5;
        description
          "Psh.";
      }
      enum "ack" {
        value 6;
        description
          "Ack.";
      }
      enum "urg" {
        value 7;
        description
          "Urg.";
      }
      enum "ece" {
        value 8;
        description
          "Ece.";
      }
      enum "cwr" {
        value 9;
        description
          "Cwr.";
      }
      enum "ns" {
        value 10;
        description
          "Ns.";
      }
    }
    description
      "TCP bit match type.";
  }

  typedef live_ncs_qos-tcp-bit-match-ipv6 {
    type enumeration {
      enum "not-config" {
        value 0;
        description
          "NotConfig.";
      }
      enum "established" {
        value 1;
        description
          "Established.";
      }
      enum "fin" {
        value 2;
        description
          "Fin.";
      }
      enum "syn" {
        value 3;
        description
          "Syn.";
      }
      enum "rst" {
        value 4;
        description
          "Rst.";
      }
      enum "psh" {
        value 5;
        description
          "Psh.";
      }
      enum "ack" {
        value 6;
        description
          "Ack.";
      }
      enum "urg" {
        value 7;
        description
          "Urg.";
      }
    }
    description
      "IPv6 TCP bit match type.";
  }

  typedef live_ncs_car-limit-type {
    type enumeration {
      enum "pps" {
        value 1;
        description
          "Car limit type pps.";
      }
    }
    description
      "Car limit type.";
  }

  typedef live_ncs_acl-log-action-type {
    type enumeration {
      enum "first-packet" {
        value 39;
        description
          "Log first packet action.";
      }
    }
    description
      "Type of the log action.";
  }

  typedef live_ncs_low-latency-enable-type {
    type enumeration {
      enum "flow-queue" {
        value 1;
        description
          "Flow queue.";
      }
    }
    description
      "Business type of low latency.";
  }

  typedef live_ncs_low-latency-enable-value {
    type enumeration {
      enum "enable" {
        value 1;
        description
          "Enable.";
      }
    }
    description
      "Enable.";
  }

  typedef live_ncs_shaping-value-type {
    type enumeration {
      enum "256K" {
        value 0;
        description
          "256K.";
      }
      enum "512K" {
        value 1;
        description
          "512K.";
      }
    }
    description
      "Shaping value type.";
  }

  typedef live_ncs_port-shaping-weight-mode-type {
    type enumeration {
      enum "enable" {
        value 1;
        description
          "Weight mode enable.";
      }
    }
    description
      "Weight mode enable.";
  }

  typedef live_ncs_scheduling-mode-type {
    type enumeration {
      enum "mode2" {
        value 0;
        description
          "Mode 2.";
      }
      enum "mode3" {
        value 1;
        description
          "Mode 3.";
      }
    }
    description
      "Scheduling mode type.";
  }

  typedef live_ncs_map-type {
    type enumeration {
      enum "none" {
        value 1;
        description
          "Notconfig map type.";
      }
      enum "inner-8021p" {
        value 2;
        description
          "Inner 802.1p priority.";
      }
      enum "outer-8021p" {
        value 4;
        description
          "Outer 802.1p priority.";
      }
      enum "dscp" {
        value 8;
        description
          "Dscp type.";
      }
      enum "mpls-exp" {
        value 16;
        description
          "MPLS-EXP type.";
      }
    }
    description
      "Map type for phb.";
  }

  typedef live_ncs_convergence-schedule-mode {
    type enumeration {
      enum "disable" {
        value 4;
        description
          "Disable.";
      }
    }
    description
      "Disable.";
  }

  typedef live_ncs_port-convergence-schedule-mode {
    type enumeration {
      enum "enable" {
        value 1;
        description
          "Enable.";
      }
    }
    description
      "Enable.";
  }

  typedef live_ncs_traffic-policy-untag-type {
    type enumeration {
      enum "disable" {
        value 0;
        description
          "Disable.";
      }
    }
    description
      "Disable.";
  }

  typedef live_ncs_qos-direction-inbound {
    type enumeration {
      enum "inbound" {
        value 0;
        description
          "Inbound.";
      }
    }
    description
      "Direction.";
  }

  typedef live_ncs_in-direction-type {
    type enumeration {
      enum "inbound" {
        value 0;
        description
          "Inbound.";
      }
    }
    description
      "Inbound.";
  }

  typedef live_ncs_discard-type {
    type enumeration {
      enum "discard-packet" {
        value 1;
        description
          "Discard Packets.";
      }
      enum "discard-byte" {
        value 2;
        description
          "Discard Bytes.";
      }
      enum "discard-packet-ratio" {
        value 3;
        description
          "Discard Ratio.";
      }
    }
    description
      "Discard mode type.";
  }

  typedef live_ncs_lcs-active-status-type {
    type enumeration {
      enum "allocated" {
        value 1;
        description
          "Allocated.";
      }
      enum "activated" {
        value 2;
        description
          "Activated.";
      }
    }
    description
      "Liscense active status type.";
  }

  typedef live_ncs_statistics-car-type {
    type enumeration {
      enum "car" {
        value 1;
        description
          "CAR action.";
      }
      enum "broadcast" {
        value 2;
        description
          "Broadcast suppression.";
      }
      enum "multicast" {
        value 3;
        description
          "Multicast suppression.";
      }
      enum "unknow-unicast" {
        value 4;
        description
          "Unknown unicast suppression.";
      }
      enum "l2-forward" {
        value 5;
        description
          "CAR L2 forward parameter.";
      }
      enum "l3-forward" {
        value 6;
        description
          "CAR L3 forward parameter.";
      }
      enum "bum" {
        value 7;
        description
          "BUM suppression.";
      }
      enum "bu" {
        value 8;
        description
          "BU suppression.";
      }
      enum "unknow-multicast" {
        value 9;
        description
          "Unknown multicast suppression.";
      }
    }
    description
      "Car statistics type.";
  }

  typedef live_ncs_qos-priority-num-type {
    type enumeration {
      enum "p0" {
        value 0;
        description
          "P0.";
      }
      enum "p1" {
        value 1;
        description
          "P1.";
      }
      enum "p2" {
        value 2;
        description
          "P2.";
      }
      enum "p3" {
        value 3;
        description
          "P3.";
      }
      enum "p4" {
        value 4;
        description
          "P4.";
      }
      enum "p5" {
        value 5;
        description
          "P5.";
      }
      enum "p6" {
        value 6;
        description
          "P6.";
      }
      enum "p7" {
        value 7;
        description
          "P7.";
      }
      enum "total" {
        value 8;
        description
          "Total.";
      }
    }
    description
      "The priority num.";
  }

  typedef live_ncs_qos-flow-type {
    type enumeration {
      enum "source-ip" {
        value 1;
        description
          "Source address.";
      }
      enum "destination-ip" {
        value 2;
        description
          "Destination address.";
      }
    }
    description
      "Flow CAR IP type.";
  }

  typedef live_ncs_increase-priority {
    type enumeration {
      enum "increase-priority" {
        value 1;
        description
          "Increase priority.";
      }
    }
    description
      "Increase priority.";
  }

  typedef live_ncs_forward-type {
    type enumeration {
      enum "vll" {
        value 1;
        description
          "VLL forward type.";
      }
    }
    description
      "VLL forward type.";
  }

  typedef live_ncs_ability-type {
    type enumeration {
      enum "S" {
        value 1;
        description
          "The port support share-mode hard pipe.";
      }
      enum "N" {
        value 2;
        description
          "None hard-pipe ability.";
      }
      enum "U" {
        value 3;
        description
          "Unknown hard-pipe ability.";
      }
      enum "M" {
        value 4;
        description
          "The port need split member interface.";
      }
      enum "E" {
        value 5;
        description
          "The port support exclusive-mode hard pipe.";
      }
    }
    description
      "Ability type.";
  }

  typedef live_ncs_qos-policy-layer {
    type enumeration {
      enum "ip-layer" {
        value 1;
        description
          "IP layer.";
      }
    }
    description
      "IP layer.";
  }

  typedef live_ncs_enable-type {
    type enumeration {
      enum "enable" {
        value 1;
        description
          "Enable.";
      }
    }
    description
      "Enable.";
  }

  typedef live_ncs_priority-convergent-type {
    type enumeration {
      enum "high" {
        value 1;
        description
          "High.";
      }
    }
    description
      "High priority.";
  }

  typedef live_ncs_untag-enable-type {
    type enumeration {
      enum "enable" {
        value 2;
        description
          "Enable.";
      }
    }
    description
      "Untag enable type.";
  }

  typedef live_ncs_suppress-type {
    type enumeration {
      enum "unknown-unicast-suppression" {
        value 2;
        description
          "Unknown unicast suppression.";
      }
      enum "multicast-suppression" {
        value 3;
        description
          "Multicast suppression.";
      }
      enum "broadcast-suppression" {
        value 4;
        description
          "Broadcast suppression.";
      }
    }
    description
      "Suppression type.";
  }

  typedef live_ncs_load-balance-type {
    type enumeration {
      enum "flow" {
        value 0;
        description
          "Flow by flow.";
      }
      enum "packet" {
        value 1;
        description
          "Packet by packet.";
      }
      enum "flow-l2" {
        value 2;
        description
          "Flow by flow with L2.";
      }
      enum "flow-l3" {
        value 3;
        description
          "Flow by flow with L3.";
      }
    }
    description
      "Load balance type.";
  }

  typedef live_ncs_sample-type {
    type enumeration {
      enum "fix-packets" {
        value 0;
        description
          "Sampling based on the fixed number of packets.";
      }
      enum "fix-time" {
        value 1;
        description
          "Fixed sampling interval.";
      }
      enum "random-packets" {
        value 2;
        description
          "Sampling based on the random number of packets.";
      }
    }
    description
      "Sampling type.";
  }

  typedef live_ncs_action-urpf {
    type enumeration {
      enum "urpf" {
        value 3;
        description
          "URPF action.";
      }
    }
    description
      "URPF action.";
  }

  typedef live_ncs_check-type {
    type enumeration {
      enum "strict" {
        value 0;
        description
          "Strict.";
      }
      enum "loose" {
        value 1;
        description
          "Loose.";
      }
    }
    description
      "Type of the URPF check.";
  }

  typedef live_ncs_statistics-type {
    type enumeration {
      enum "BPS" {
        value 1;
        description
          "Byte/s.";
      }
      enum "PPS" {
        value 2;
        description
          "Packet/s.";
      }
    }
    description
      "Statistics type.";
  }

  typedef live_ncs_ip-type {
    type enumeration {
      enum "ipv4" {
        value 0;
        description
          "IPv4.";
      }
      enum "ipv6" {
        value 1;
        description
          "IPv6.";
      }
    }
    description
      "Type of an address.";
  }

  typedef live_ncs_pool-type {
    type enumeration {
      enum "pool-0" {
        value 0;
        description
          "Pool 0.";
      }
      enum "pool-1" {
        value 1;
        description
          "Pool 0.";
      }
    }
    description
      "Pool ID.";
  }

  typedef live_ncs_member-link-scheduler-type {
    type enumeration {
      enum "traffic-car" {
        value 1;
        description
          "Traffic CAR.";
      }
      enum "qos-car" {
        value 2;
        description
          "QoS CAR.";
      }
      enum "port-shaping" {
        value 3;
        description
          "Port shaping.";
      }
      enum "hard-pipe" {
        value 4;
        description
          "Hard pipe.";
      }
      enum "user-queue" {
        value 5;
        description
          "User queue.";
      }
      enum "profile-car" {
        value 7;
        description
          "Profile CAR.";
      }
      enum "hqos-outbound" {
        value 8;
        description
          "HQoS outbound.";
      }
      enum "mpls-te" {
        value 9;
        description
          "MPLS TE.";
      }
    }
    description
      "Business type.";
  }

  typedef live_ncs_traffic-type {
    type enumeration {
      enum "ldp-traffic" {
        value 1;
        description
          "LDP traffic.";
      }
    }
    description
      "LDP traffic.";
  }

  typedef live_ncs_any-other-type {
    type enumeration {
      enum "not-config" {
        value 0;
        description
          "Not config.";
      }
      enum "user-vlan" {
        value 1;
        description
          "User VLAN.";
      }
      enum "qinq" {
        value 2;
        description
          "QinQ.";
      }
    }
    description
      "BAS QoS profile apply type.";
  }

  typedef live_ncs_bas-profile-identifier-type {
    type enumeration {
      enum "pe-vid" {
        value 1;
        description
          "PE VLAN ID.";
      }
      enum "ce-vid" {
        value 2;
        description
          "CE VLAN ID.";
      }
      enum "pe-ce-vid" {
        value 3;
        description
          "PE CE VLAN ID.";
      }
      enum "vlan-id" {
        value 4;
        description
          "VLAN ID.";
      }
      enum "none" {
        value 5;
        description
          "None.";
      }
      enum "option82" {
        value 7;
        description
          "Option82.";
      }
      enum "access-line-id" {
        value 11;
        description
          "Access line ID.";
      }
    }
    description
      "BAS QoS profile apply identifier type.";
  }

  typedef live_ncs_vlan-user-group-queue-identifier-type {
    type enumeration {
      enum "none" {
        value 0;
        description
          "None.";
      }
      enum "vlan-id" {
        value 1;
        description
          "VLAN ID.";
      }
      enum "pe-vid" {
        value 2;
        description
          "PE VLAN ID.";
      }
      enum "ce-vid" {
        value 3;
        description
          "CE VLAN ID.";
      }
      enum "pe-ce-vid" {
        value 4;
        description
          "PE CE VLAN ID.";
      }
    }
    description
      "VLAN user group queue apply identifier type.";
  }

  typedef live_ncs_user-access-type {
    type enumeration {
      enum "leased-line-access" {
        value 10;
        description
          "Leased line access.";
      }
      enum "subscriber-access" {
        value 13;
        description
          "Subscriber access.";
      }
    }
    description
      "User access type.";
  }

  typedef live_ncs_hard-pipe-mode {
    type enumeration {
      enum "share-mode" {
        value 0;
        description
          "Share mode.";
      }
      enum "exclusive-mode" {
        value 1;
        description
          "Exclusive mode.";
      }
    }
    description
      "Hard pipe mode.";
  }

  typedef live_ncs_ac-mode-layer-type {
    type enumeration {
      enum "link-layer" {
        value 1;
        description
          "Link layer:";
      }
      enum "all-layer" {
        value 2;
        description
          "All layer:";
      }
    }
    description
      "Layer type.";
  }

  typedef live_ncs_vxlan-trust-type {
    type enumeration {
      enum "8021p" {
        value 1;
        description
          "Trust 8021p.";
      }
      enum "upstream" {
        value 0;
        description
          "Trust upstream.";
      }
    }
    description
      "VXLAN trust type.";
  }

  typedef live_ncs_exclude-type {
    type enumeration {
      enum "no-exclude" {
        value 0;
        description
          "Non-exclude mode.";
      }
      enum "exclude" {
        value 1;
        description
          "Exclude mode.";
      }
    }
    description
      "Exclude type.";
  }

  typedef live_ncs_qos-profile-template-name {
    type string {
      length "1..63";
    }
    description
      "Qos profile template name is like string.";
  }

  typedef live_ncs_trust-remote-direction-type {
    type enumeration {
      enum "inbound" {
        value 1;
        description
          "Inbound.";
      }
    }
    description
      "Trust remote direction type.";
  }

  typedef live_ncs_action-load-balance {
    type enumeration {
      enum "load-balance" {
        value 4;
        description
          "Load balancing action.";
      }
    }
    description
      "Load balancing.";
  }

  typedef live_ncs_user-type {
    type enumeration {
      enum "lac" {
        value 1;
        description
          "Specifies the user type as lac.";
      }
      enum "lns" {
        value 2;
        description
          "Specifies the user type as lns.";
      }
      enum "lac-and-lns" {
        value 3;
        description
          "Specifies the user type as lac and lns.";
      }
    }
    description
      "User type.";
  }

  typedef live_ncs_access-type {
    type enumeration {
      enum "leased-line-access" {
        value 1;
        description
          "Leased line access.";
      }
      enum "none" {
        value 0;
        description
          "Not config.";
      }
    }
    description
      "User access type.";
  }

  typedef live_ncs_l2tp-user {
    type enumeration {
      enum "l2tp-user" {
        value 12;
        description
          "L2TP user.";
      }
    }
    description
      "L2TP user.";
  }

  typedef live_ncs_cos-value-type {
    type enumeration {
      enum "be" {
        value 0;
        description
          "Specifies the service class to be BE.";
      }
      enum "af1-af2" {
        value 1;
        description
          "Specifies the service class to be AF1 and AF2.";
      }
      enum "af3-af4" {
        value 2;
        description
          "Specifies the service class to be Af3 and af4.";
      }
      enum "ef-cs6-cs7" {
        value 3;
        description
          "Specifies the service class to be EF and CS6 and CS7.";
      }
    }
    description
      "Service class type.";
  }

  typedef live_ncs_rule-type {
    type enumeration {
      enum "aclv4" {
        value 1;
        description
          "Aclv4.";
      }
      enum "aclv6" {
        value 2;
        description
          "Aclv6.";
      }
      enum "l2acl" {
        value 3;
        description
          "L2acl.";
      }
      enum "mpls" {
        value 4;
        description
          "MPLS.";
      }
      enum "uclv4" {
        value 5;
        description
          "Uclv4.";
      }
      enum "uclv6" {
        value 6;
        description
          "Uclv6.";
      }
    }
    description
      "Qos resource rule type.";
  }

  typedef live_ncs_yes-or-no {
    type enumeration {
      enum "no" {
        value 0;
        description
          "No.";
      }
      enum "yes" {
        value 1;
        description
          "Yes.";
      }
    }
    description
      "Choose yes or no.";
  }

  typedef live_ncs_remote-trust-type {
    type enumeration {
      enum "ip-dscp" {
        value 0;
        description
          "Trust ip-dscp.";
      }
      enum "8021p" {
        value 1;
        description
          "Trust 8021p.";
      }
    }
    description
      "Trust type.";
  }

  typedef live_ncs_type-8021p {
    type enumeration {
      enum "8021p" {
        value 1;
        description
          "Trust 8021p.";
      }
      enum "inner-8021p" {
        value 3;
        description
          "Trust inner 8021p.";
      }
      enum "outer-8021p" {
        value 2;
        description
          "Trust outer 8021p.";
      }
    }
    description
      "Trust 8021p type.";
  }

  typedef live_ncs_deficit-unit-type {
    type enumeration {
      enum "1K" {
        value 4;
        description
          "1K (byte).";
      }
      enum "2K" {
        value 5;
        description
          "2K (byte).";
      }
    }
    description
      "Deficit unit type.";
  }

  typedef live_ncs_user-queue-template-type {
    type enumeration {
      enum "4-priority" {
        value 0;
        description
          "Four priority mode.";
      }
    }
    description
      "User queue template mode type.";
  }

  typedef live_ncs_priority-schedule-mode {
    type enumeration {
      enum "pq" {
        value 0;
        description
          "Priority queue.";
      }
      enum "wfq" {
        value 1;
        description
          "Weighted fair queue.";
      }
    }
    description
      "Priority mode.";
  }

  typedef live_ncs_ignore-default-type {
    type enumeration {
      enum "disable" {
        value 0;
        description
          "The default route is excluded.";
      }
    }
    description
      "Indicates a mode in which the default route is excluded.";
  }

  typedef live_ncs_protocol-family {
    type enumeration {
      enum "ipv4" {
        value 1;
        description
          "IPv4.";
      }
      enum "ipv6" {
        value 2;
        description
          "IPv6.";
      }
      enum "l2" {
        value 3;
        description
          "L2.";
      }
      enum "mpls" {
        value 4;
        description
          "MPLS.";
      }
    }
    description
      "Protocol family type.";
  }

  typedef qos-ba-type {
    type enumeration {
      enum "8021p" {
        value 0;
        description
          "802.1p priority.";
      }
      enum "ip-dscp" {
        value 1;
        description
          "DSCP priority.";
      }
      enum "mpls-exp" {
        value 2;
        description
          "MPLS-EXP priority.";
      }
      enum "user-priority" {
        value 3;
        description
          "User priority.";
      }
      enum "ip-precedence" {
        value 11;
        description
          "IP-Precedence priority.";
      }
    }
    description
      "Behavior aggregations type.";
  }

  typedef qos-phb-type {
    type enumeration {
      enum "8021p" {
        value 0;
        description
          "802.1p priority.";
      }
      enum "ip-dscp" {
        value 1;
        description
          "DSCP priority.";
      }
      enum "mpls-exp" {
        value 2;
        description
          "MPLS-EXP priority.";
      }
      enum "ip-precedence" {
        value 11;
        description
          "IP Precedence priority.";
      }
    }
    description
      "Priority type.";
  }

  typedef qos-service-class {
    type enumeration {
      enum "be" {
        value 0;
        description
          "BE service class.";
      }
      enum "af1" {
        value 1;
        description
          "AF1 service-class.";
      }
      enum "af2" {
        value 2;
        description
          "AF2 service-class.";
      }
      enum "af3" {
        value 3;
        description
          "AF3 service-class.";
      }
      enum "af4" {
        value 4;
        description
          "AF4 service-class.";
      }
      enum "ef" {
        value 5;
        description
          "EF service-class.";
      }
      enum "cs6" {
        value 6;
        description
          "CS6 service-class.";
      }
      enum "cs7" {
        value 7;
        description
          "CS7 service-class.";
      }
    }
    description
      "QoS service class.";
  }

  typedef qos-service-class-total {
    type enumeration {
      enum "be" {
        value 0;
        description
          "BE service class.";
      }
      enum "af1" {
        value 1;
        description
          "AF1 service class.";
      }
      enum "af2" {
        value 2;
        description
          "AF2 service class.";
      }
      enum "af3" {
        value 3;
        description
          "AF3 service class.";
      }
      enum "af4" {
        value 4;
        description
          "AF4 service class.";
      }
      enum "ef" {
        value 5;
        description
          "EF service class.";
      }
      enum "cs6" {
        value 6;
        description
          "CS6 service class.";
      }
      enum "cs7" {
        value 7;
        description
          "CS7 service class.";
      }
      enum "total" {
        value 8;
        description
          "Total service class.";
      }
    }
    description
      "QoS service class.";
  }

  typedef qos-color {
    type enumeration {
      enum "green" {
        value 0;
        description
          "Green.";
      }
      enum "yellow" {
        value 1;
        description
          "Yellow.";
      }
      enum "red" {
        value 2;
        description
          "Red.";
      }
    }
    description
      "Color type.";
  }

  typedef qos-direction-type {
    type enumeration {
      enum "inbound" {
        value 0;
        description
          "Inbound.";
      }
      enum "outbound" {
        value 1;
        description
          "Outbound.";
      }
    }
    description
      "Direction type.";
  }

  typedef qos-gq-direction-type {
    type enumeration {
      enum "inbound" {
        value 0;
        description
          "Inbound.";
      }
      enum "outbound" {
        value 1;
        description
          "Outbound.";
      }
    }
    description
      "Direction type.";
  }

  typedef qos-traffic-type {
    type enumeration {
      enum "ucl" {
        value 0;
        description
          "Ucl.";
      }
      enum "acl" {
        value 1;
        description
          "Acl.";
      }
    }
    description
      "Traffic policy type.";
  }

  typedef qos-acl-log-type {
    type enumeration {
      enum "acl-log" {
        value 1;
        description
          "Log first-packet parameter.";
      }
    }
    description
      "Acl log.";
  }

  typedef template-name {
    type string {
      length "1..31";
    }
    description
      "Template name is like string.";
  }

  typedef queue-schedule-mode {
    type enumeration {
      enum "pq" {
        value 0;
        description
          "Priority queue.";
      }
      enum "wfq" {
        value 1;
        description
          "Weighted fair queuing.";
      }
      enum "lpq" {
        value 2;
        description
          "Low priority queuing.";
      }
    }
    description
      "Queue schedule mode.";
  }

  typedef queue-low-latency {
    type enumeration {
      enum "enable" {
        value 1;
        description
          "Enable.";
      }
    }
    description
      "Enable low latency.";
  }

  typedef queue-low-jitter {
    type enumeration {
      enum "enable" {
        value 1;
        description
          "Enable.";
      }
    }
    description
      "Enable low jitter.";
  }

  typedef queue-cir-schedule-mode {
    type enumeration {
      enum "pq" {
        value 0;
        description
          "PQ.";
      }
    }
    description
      "Scheduling strategy of cir.";
  }

  typedef flow-queue-template-type {
    type enumeration {
      enum "normal" {
        value 0;
        description
          "Normal mode.";
      }
      enum "priority" {
        value 1;
        description
          "Priority mode.";
      }
      enum "4cos" {
        value 2;
        description
          "Four cos mode.";
      }
      enum "8cos-enhance" {
        value 5;
        description
          "Eight cos enhance.";
      }
    }
    description
      "Flow queue template mode type.";
  }

  typedef profile-template-type {
    type enumeration {
      enum "normal" {
        value 0;
        description
          "Normal.";
      }
      enum "time-range" {
        value 1;
        description
          "Time range.";
      }
      enum "8cos-enhance" {
        value 5;
        description
          "Eight cos enhance.";
      }
    }
    description
      "Profile template mode type.";
  }

  typedef all-direction-type {
    type enumeration {
      enum "inbound" {
        value 0;
        description
          "Inbound.";
      }
      enum "outbound" {
        value 1;
        description
          "Outbound.";
      }
      enum "all" {
        value 2;
        description
          "All.";
      }
    }
    description
      "Direction type include all.";
  }

  typedef priority-level-type {
    type enumeration {
      enum "low" {
        value 255;
        description
          "Low.";
      }
      enum "high" {
        value 1;
        description
          "High.";
      }
    }
    description
      "Priority level type.";
  }

  typedef adjust-on-card-type {
    type enumeration {
      enum "disable" {
        value 0;
        description
          "Disable.";
      }
      enum "enable" {
        value 1;
        description
          "Enable.";
      }
    }
    description
      "Adjust on card flag.";
  }

  typedef gq-template-type {
    type enumeration {
      enum "normal" {
        value 0;
        description
          "Normal mode.";
      }
      enum "priority" {
        value 1;
        description
          "Priority mode.";
      }
    }
    description
      "User group queue mode.";
  }

  typedef class-operator {
    type enumeration {
      enum "or" {
        value 0;
        description
          "Or.";
      }
      enum "and" {
        value 1;
        description
          "And.";
      }
    }
    description
      "Logical operator of a rule.";
  }

  typedef ip-family {
    type enumeration {
      enum "ipv4" {
        value 1;
        description
          "IPv4.";
      }
      enum "ipv6" {
        value 2;
        description
          "IPv6.";
      }
    }
    description
      "Ip family type.";
  }

  typedef priority-type {
    type enumeration {
      enum "8021p" {
        value 0;
        description
          "802.1p priority.";
      }
      enum "ip-precedence" {
        value 1;
        description
          "IP precedence.";
      }
      enum "dscp" {
        value 2;
        description
          "DSCP priority.";
      }
      enum "mpls-exp" {
        value 4;
        description
          "MPLS-EXP priority.";
      }
      enum "ipv6-dscp" {
        value 5;
        description
          "IPv6 DSCP priority.";
      }
      enum "ipv6-ip-precedence" {
        value 6;
        description
          "IPv6 IP precedence.";
      }
    }
    description
      "Priority type.";
  }

  typedef action-car {
    type enumeration {
      enum "car" {
        value 0;
        description
          "CAR action.";
      }
    }
    description
      "Type of a car action.";
  }

  typedef color-action-type {
    type enumeration {
      enum "pass" {
        value 0;
        description
          "Pass.";
      }
      enum "discard" {
        value 2;
        description
          "Discard.";
      }
    }
    description
      "Color action type.";
  }

  typedef service-class-notconfig {
    type enumeration {
      enum "be" {
        value 0;
        description
          "BE service class.";
      }
      enum "af1" {
        value 1;
        description
          "AF1 service class.";
      }
      enum "af2" {
        value 2;
        description
          "AF2 service class.";
      }
      enum "af3" {
        value 3;
        description
          "AF3 service class.";
      }
      enum "af4" {
        value 4;
        description
          "AF4 service class.";
      }
      enum "ef" {
        value 5;
        description
          "EF service class.";
      }
      enum "cs6" {
        value 6;
        description
          "CS6 service class.";
      }
      enum "cs7" {
        value 7;
        description
          "CS7 service class.";
      }
      enum "not-config" {
        value 8;
        description
          "Not config service class.";
      }
    }
    description
      "Service class type.";
  }

  typedef filter-flag {
    type enumeration {
      enum "permit" {
        value 0;
        description
          "Permit.";
      }
      enum "deny" {
        value 1;
        description
          "Deny.";
      }
    }
    description
      "Filter type.";
  }

  typedef action-remark {
    type enumeration {
      enum "8021p" {
        value 12;
        description
          "Remark 802.1p priority action.";
      }
      enum "ipv4-dscp" {
        value 13;
        description
          "Remark DSCP action.";
      }
      enum "tos" {
        value 19;
        description
          "Remark tos priority action.";
      }
      enum "ipv6-dscp" {
        value 14;
        description
          "Remark IPv6 DSCP action.";
      }
      enum "ip-precedence" {
        value 15;
        description
          "Remark IP precedence action.";
      }
      enum "mpls-exp" {
        value 16;
        description
          "Remark MPLS-EXP action.";
      }
      enum "ip-df" {
        value 21;
        description
          "Remark IP-DF action.";
      }
      enum "ttl" {
        value 26;
        description
          "Remark TTL action.";
      }
      enum "inner-8021p" {
        value 34;
        description
          "Remark inner 802.1p priority action.";
      }
      enum "outer-8021p" {
        value 35;
        description
          "Remark outer 802.1p priority action.";
      }
      enum "remark-local-id" {
        value 60;
        description
          "Remark qos-local-id action.";
      }
    }
    description
      "Action remark type.";
  }

  typedef service-class-action {
    type enumeration {
      enum "service-class" {
        value 0;
        description
          "Service class.";
      }
      enum "service-class-master-bfd" {
        value 1;
        description
          "Service class link master BFD.";
      }
      enum "service-class-slave-bfd" {
        value 2;
        description
          "Service class link slave BFD.";
      }
    }
    description
      "Type of a service class action.";
  }

  typedef remark-type {
    type enumeration {
      enum "enable" {
        value 0;
        description
          "Remark enable.";
      }
      enum "disable" {
        value 1;
        description
          "Remark disable.";
      }
    }
    description
      "Remark type.";
  }

  typedef trust-type {
    type enumeration {
      enum "ip-dscp" {
        value 0;
        description
          "Trust ip-dscp.";
      }
      enum "8021p" {
        value 1;
        description
          "Trust 8021p.";
      }
      enum "inner-8021p" {
        value 3;
        description
          "Trust inner-8021p.";
      }
      enum "outer-8021p" {
        value 2;
        description
          "Trust outer-8021p.";
      }
    }
    description
      "Trust type.";
  }

  typedef trust-direction-type {
    type enumeration {
      enum "inbound" {
        value 1;
        description
          "Inbound.";
      }
      enum "outbound" {
        value 2;
        description
          "Outbound.";
      }
      enum "in-outbound" {
        value 0;
        description
          "Not config.";
      }
    }
    description
      "Trust direction type.";
  }

  typedef identifier-type {
    type enumeration {
      enum "no" {
        value 0;
        description
          "Not config.";
      }
      enum "none" {
        value 1;
        description
          "Not config VLAN.";
      }
      enum "vid" {
        value 2;
        description
          "Vid.";
      }
      enum "ce-vid" {
        value 3;
        description
          "CE VLAN ID.";
      }
      enum "vid-ce-vid" {
        value 4;
        description
          "Vid CE vid.";
      }
    }
    description
      "Identifier type.";
  }

  typedef link-adjustment-type {
    type enumeration {
      enum "cell" {
        value 1;
        description
          "Cell.";
      }
    }
    description
      "Link adjustment type.";
  }

  typedef policy-apply-layer-type {
    type enumeration {
      enum "none" {
        value 0;
        description
          "Default classification.";
      }
      enum "link" {
        value 1;
        description
          "Classification based on Layer 2 information.";
      }
      enum "mpls" {
        value 3;
        description
          "Classification based on MPLS information.";
      }
      enum "all" {
        value 2;
        description
          "Classification based on ALL information.";
      }
      enum "vxlan" {
        value 4;
        description
          "Classification based on VXLAN information.";
      }
    }
    description
      "Policy layer type.";
  }

  typedef policy-apply-vxlan-layer-type {
    type enumeration {
      enum "link" {
        value 1;
        description
          "Classification based on Layer 2 information.";
      }
    }
    description
      "Policy layer type.";
  }

  typedef profile-apply-type {
    type enumeration {
      enum "interface" {
        value 0;
        description
          "Interface.";
      }
      enum "vlan" {
        value 1;
        description
          "VLAN.";
      }
      enum "pe" {
        value 2;
        description
          "Pe.";
      }
    }
    description
      "Profile apply type.";
  }

  typedef linkage-bandwidth-type {
    type enumeration {
      enum "disable" {
        value 0;
        description
          "Disable.";
      }
      enum "enable" {
        value 1;
        description
          "Enable.";
      }
    }
    description
      "Linkage bandwidth type.";
  }

  typedef identify-type {
    type enumeration {
      enum "none" {
        value 0;
        description
          "None.";
      }
      enum "vlan" {
        value 1;
        description
          "VLAN.";
      }
      enum "pe-vid" {
        value 2;
        description
          "Pe VLAN Id.";
      }
      enum "ce-vid" {
        value 3;
        description
          "Ce VLAN Id.";
      }
      enum "pe-ce-vid" {
        value 4;
        description
          "Pe-Ce VLAN Id.";
      }
      enum "vid" {
        value 5;
        description
          "Vid.";
      }
      enum "evc-ce-vid" {
        value 6;
        description
          "Ce-vid.";
      }
      enum "vid-ce-vid" {
        value 7;
        description
          "Vid-ce-vid.";
      }
    }
    description
      "Identify type.";
  }

  typedef hqos-service-class {
    type enumeration {
      enum "be" {
        value 0;
        description
          "BE service class.";
      }
      enum "af1" {
        value 1;
        description
          "AF1 service class.";
      }
      enum "af2" {
        value 2;
        description
          "AF2 service class.";
      }
      enum "af3" {
        value 3;
        description
          "AF3 service class.";
      }
      enum "af4" {
        value 4;
        description
          "AF4 service class.";
      }
      enum "ef" {
        value 5;
        description
          "EF service class.";
      }
      enum "cs6" {
        value 6;
        description
          "CS6 service class.";
      }
      enum "cs7" {
        value 7;
        description
          "CS7 service class.";
      }
      enum "total" {
        value 8;
        description
          "Total.";
      }
      enum "cos0" {
        value 9;
        description
          "Cos0 service class.";
      }
      enum "cos1" {
        value 10;
        description
          "Cos1 service class.";
      }
      enum "cos2" {
        value 11;
        description
          "Cos2 service class.";
      }
      enum "cos3" {
        value 12;
        description
          "Cos3 service class.";
      }
    }
    description
      "Service class type.";
  }

  typedef qos-res-type {
    type enumeration {
      enum "null" {
        value 0;
        description
          "Null.";
      }
      enum "sq" {
        value 1;
        description
          "SQ.";
      }
      enum "car" {
        value 2;
        description
          "CAR.";
      }
      enum "sq-car" {
        value 3;
        description
          "SQCAR.";
      }
      enum "l2-car" {
        value 4;
        description
          "L2CAR.";
      }
      enum "l2-l3-car" {
        value 5;
        description
          "L2L3CAR.";
      }
      enum "l3-car" {
        value 6;
        description
          "L3CAR.";
      }
    }
    description
      "Resource type.";
  }

  typedef switch-flag {
    type enumeration {
      enum "enable" {
        value 1;
        description
          "Enable.";
      }
      enum "disable" {
        value 0;
        description
          "Disable.";
      }
    }
    description
      "Switch flag.";
  }

  typedef low-latency {
    type enumeration {
      enum "enable" {
        value 1;
        description
          "Enable.";
      }
      enum "disable" {
        value 0;
        description
          "Disable.";
      }
    }
    description
      "Enable or disable low latency.";
  }

  typedef share-shape-mode {
    type enumeration {
      enum "pq" {
        value 0;
        description
          "Priority queue.";
      }
      enum "wfq" {
        value 1;
        description
          "Weighted fair queuing.";
      }
      enum "lpq" {
        value 2;
        description
          "Low priority queuing.";
      }
      enum "not-config" {
        value 3;
        description
          "Not config.";
      }
    }
    description
      "Share shape mode.";
  }

  typedef be-type {
    type enumeration {
      enum "true" {
        value 0;
        description
          "True.";
      }
      enum "false" {
        value 8;
        description
          "False.";
      }
    }
    description
      "BE type.";
  }

  typedef af1-type {
    type enumeration {
      enum "true" {
        value 1;
        description
          "True.";
      }
      enum "false" {
        value 8;
        description
          "False.";
      }
    }
    description
      "AF1 type.";
  }

  typedef af2-type {
    type enumeration {
      enum "true" {
        value 2;
        description
          "True.";
      }
      enum "false" {
        value 8;
        description
          "False.";
      }
    }
    description
      "AF2 type.";
  }

  typedef af3-type {
    type enumeration {
      enum "true" {
        value 3;
        description
          "True.";
      }
      enum "false" {
        value 8;
        description
          "False.";
      }
    }
    description
      "AF3 type.";
  }

  typedef af4-type {
    type enumeration {
      enum "true" {
        value 4;
        description
          "True.";
      }
      enum "false" {
        value 8;
        description
          "False.";
      }
    }
    description
      "AF4 type.";
  }

  typedef ef-type {
    type enumeration {
      enum "true" {
        value 5;
        description
          "True.";
      }
      enum "false" {
        value 8;
        description
          "False.";
      }
    }
    description
      "EF type.";
  }

  typedef cs6-type {
    type enumeration {
      enum "true" {
        value 6;
        description
          "True.";
      }
      enum "false" {
        value 8;
        description
          "False.";
      }
    }
    description
      "CS6 type.";
  }

  typedef cs7-type {
    type enumeration {
      enum "true" {
        value 7;
        description
          "True.";
      }
      enum "false" {
        value 8;
        description
          "False.";
      }
    }
    description
      "CS7 type.";
  }

  typedef shapid-upritype {
    type enumeration {
      enum "1" {
        value 1;
        description
          "1.";
      }
    }
    description
      "Shap Id.";
  }

  typedef qos-cos-value {
    type enumeration {
      enum "cos0" {
        value 0;
        description
          "Cos0.";
      }
      enum "cos1" {
        value 1;
        description
          "Cos1.";
      }
      enum "cos2" {
        value 2;
        description
          "Cos2.";
      }
      enum "cos3" {
        value 3;
        description
          "Cos3.";
      }
    }
    description
      "Cos value.";
  }

  typedef shap-id-type {
    type enumeration {
      enum "1" {
        value 1;
        description
          "Shap-id 1.";
      }
      enum "not-config" {
        value 2;
        description
          "Not config.";
      }
    }
    description
      "Shap id type.";
  }

  typedef queue-select-be-type {
    type enumeration {
      enum "true" {
        value 0;
        description
          "True.";
      }
    }
    description
      "Queue BE.";
  }

  typedef queue-select-af1-type {
    type enumeration {
      enum "true" {
        value 1;
        description
          "True.";
      }
    }
    description
      "Queue AF1.";
  }

  typedef queue-select-af2-type {
    type enumeration {
      enum "true" {
        value 2;
        description
          "True.";
      }
    }
    description
      "Queue AF2.";
  }

  typedef queue-select-af3-type {
    type enumeration {
      enum "true" {
        value 3;
        description
          "True.";
      }
    }
    description
      "Queue AF3.";
  }

  typedef queue-select-af4-type {
    type enumeration {
      enum "true" {
        value 4;
        description
          "True.";
      }
    }
    description
      "Queue AF4.";
  }

  typedef queue-select-ef-type {
    type enumeration {
      enum "true" {
        value 5;
        description
          "True.";
      }
    }
    description
      "Queue EF.";
  }

  typedef queue-select-cs6-type {
    type enumeration {
      enum "true" {
        value 6;
        description
          "True.";
      }
    }
    description
      "Queue CS6.";
  }

  typedef queue-select-cs7-type {
    type enumeration {
      enum "true" {
        value 7;
        description
          "True.";
      }
    }
    description
      "Queue CS7.";
  }

  typedef priority-flow-queue-schedule-mode {
    type enumeration {
      enum "pq" {
        value 0;
        description
          "Priority queue.";
      }
      enum "wfq" {
        value 1;
        description
          "Weighted fair queue.";
      }
    }
    description
      "Priority mode.";
  }

  typedef slot-id {
    type string {
      length "1..31";
      pattern '((c[cl]c\d+/)|(\d+/))?\d+';
    }
    description
      "Slot id is like 3, clc1/3 or ccc1/3.";
  }

  typedef group-name {
    type string {
      length "1..32";
    }
    description
      "Group name is like string.";
  }

  typedef qos-service-class-filter {
    type enumeration {
      enum "be" {
        value 0;
        description
          "BE service class.";
      }
      enum "af1" {
        value 1;
        description
          "AF1 service class.";
      }
      enum "af2" {
        value 2;
        description
          "AF2 service class.";
      }
      enum "af3" {
        value 3;
        description
          "AF3 service class.";
      }
      enum "af4" {
        value 4;
        description
          "AF4 service class.";
      }
      enum "ef" {
        value 5;
        description
          "Ef service class.";
      }
      enum "cs6" {
        value 6;
        description
          "CS6 service class.";
      }
      enum "cs7" {
        value 7;
        description
          "CS7 service class.";
      }
      enum "total" {
        value 8;
        description
          "Total.";
      }
    }
    description
      "Service class.";
  }

  typedef qos-service-class-8cos {
    type enumeration {
      enum "be" {
        value 0;
        description
          "BE service class.";
      }
      enum "af1" {
        value 1;
        description
          "AF1 service class.";
      }
      enum "af2" {
        value 2;
        description
          "AF2 service class.";
      }
      enum "af3" {
        value 3;
        description
          "AF3 service class.";
      }
      enum "af4" {
        value 4;
        description
          "AF4 service class.";
      }
      enum "ef" {
        value 5;
        description
          "Ef service class.";
      }
      enum "cs6" {
        value 6;
        description
          "CS6 service class.";
      }
      enum "cs7" {
        value 7;
        description
          "CS7 service class.";
      }
      enum "total" {
        value 8;
        description
          "Total.";
      }
      enum "cos0" {
        value 9;
        description
          "Cos0 service class.";
      }
      enum "cos1" {
        value 10;
        description
          "Cos1 service class.";
      }
      enum "cos2" {
        value 11;
        description
          "Cos2 service class.";
      }
      enum "cos3" {
        value 12;
        description
          "Cos3 service class.";
      }
      enum "cos4" {
        value 13;
        description
          "Cos4 service class.";
      }
      enum "cos5" {
        value 14;
        description
          "Cos5 service class.";
      }
      enum "cos6" {
        value 15;
        description
          "Cos6 service class.";
      }
      enum "cos7" {
        value 16;
        description
          "Cos7 service class.";
      }
    }
    description
      "Service class.";
  }

  typedef qos-car-type {
    type enumeration {
      enum "car" {
        value 1;
        description
          "CAR action.";
      }
    }
    description
      "CAR.";
  }

  typedef car-direction-type {
    type enumeration {
      enum "inbound" {
        value 0;
        description
          "Inbound.";
      }
      enum "outbound" {
        value 1;
        description
          "Outbound.";
      }
      enum "all" {
        value 2;
        description
          "All.";
      }
    }
    description
      "Direction type.";
  }

  typedef profile-car-type {
    type enumeration {
      enum "car" {
        value 1;
        description
          "CAR action.";
      }
    }
    description
      "CAR.";
  }

  typedef profile-car-direction-type {
    type enumeration {
      enum "all" {
        value 2;
        description
          "All.";
      }
    }
    description
      "All.";
  }

  typedef qos-suppression-type {
    type enumeration {
      enum "broadcast" {
        value 2;
        description
          "Broadcast suppression.";
      }
      enum "multicast" {
        value 3;
        description
          "Multicast suppression.";
      }
      enum "unknow-unicast" {
        value 4;
        description
          "Unknown unicast suppression.";
      }
      enum "bum" {
        value 7;
        description
          "BUM suppression.";
      }
      enum "bu" {
        value 8;
        description
          "BU suppression.";
      }
      enum "unknow-multicast" {
        value 9;
        description
          "Unknown multicast suppression.";
      }
    }
    description
      "Suppression type.";
  }

  typedef suppression-direction-type {
    type enumeration {
      enum "inbound" {
        value 0;
        description
          "Inbound.";
      }
      enum "outbound" {
        value 1;
        description
          "Outbound.";
      }
      enum "all" {
        value 2;
        description
          "All.";
      }
    }
    description
      "Suppression direction type.";
  }

  typedef color-aware-type {
    type enumeration {
      enum "enable" {
        value 1;
        description
          "Enable.";
      }
    }
    description
      "Enable color aware.";
  }

  typedef priority-aware-type {
    type enumeration {
      enum "enable" {
        value 1;
        description
          "Enable.";
      }
    }
    description
      "Enable priority aware.";
  }

  typedef mode-template-status {
    type enumeration {
      enum "enable" {
        value 1;
        description
          "Enable.";
      }
    }
    description
      "Enable.";
  }

  typedef policy-match-type {
    type enumeration {
      enum "ip-layer-push" {
        value 0;
        description
          "MF traffic classification based only on IP Layer (Layer 3) information for incoming traffic on the public network.";
      }
      enum "ip-layer-pop" {
        value 7;
        description
          "MF traffic classification based only on IP Layer (Layer 3) information for outgoing traffic on the public network.";
      }
      enum "mpls-layer-push" {
        value 3;
        description
          "MF classification based on both IP and MPLS information for incoming traffic on the public network.";
      }
      enum "mpls-layer-pop" {
        value 6;
        description
          "MF classification based on both IP and MPLS information for outgoing traffic on the public network.";
      }
      enum "mpls-layer-l2-inbound" {
        value 4;
        description
          "MF traffic classification based on MPLS information for outgoing traffic on the public network in Layer 2 forwarding scenarios.";
      }
      enum "protocol-mc-reserved" {
        value 2;
        description
          "Match Layer 3 protocol packets with reserved multicast addresses against ACLs.";
      }
      enum "rule-packet" {
        value 5;
        description
          "Enable packet type-based filtering for MF classification.";
      }
    }
    description
      "Traffic policy match type.";
  }

  typedef statistics-switch-status {
    type enumeration {
      enum "disable" {
        value 0;
        description
          "Disable.";
      }
      enum "enable" {
        value 1;
        description
          "Enable.";
      }
    }
    description
      "Statistics switch type.";
  }

  typedef stream-direction-type {
    type enumeration {
      enum "source" {
        value 1;
        description
          "Source.";
      }
      enum "destination" {
        value 2;
        description
          "Destination.";
      }
    }
    description
      "Stream direction type.";
  }

  typedef group-type {
    type enumeration {
      enum "service-group" {
        value 1;
        description
          "Service group.";
      }
      enum "user-group" {
        value 2;
        description
          "User group.";
      }
    }
    description
      "Group type.";
  }

  typedef switch-type {
    type enumeration {
      enum "enable" {
        value 1;
        description
          "Enable.";
      }
    }
    description
      "Enable.";
  }

  typedef out-direction-type {
    type enumeration {
      enum "outbound" {
        value 1;
        description
          "Outbound.";
      }
    }
    description
      "Outbound direction.";
  }

  typedef priority-shaping-type {
    type enumeration {
      enum "priority0" {
        value 0;
        description
          "Priority mode 0.";
      }
      enum "priority1" {
        value 1;
        description
          "Priority mode 1.";
      }
      enum "priority2" {
        value 2;
        description
          "Priority mode 2.";
      }
      enum "nopriority" {
        value 255;
        description
          "No priority.";
      }
    }
    description
      "Priority shaping type.";
  }

  typedef interval-value {
    type enumeration {
      enum "5s" {
        value 5;
        description
          "5s.";
      }
      enum "30s" {
        value 30;
        description
          "30s.";
      }
      enum "300s" {
        value 300;
        description
          "300s.";
      }
    }
    description
      "Interval value.";
  }

  typedef buffer-mode-type {
    type enumeration {
      enum "normal" {
        value 0;
        description
          "Normal.";
      }
      enum "large" {
        value 1;
        description
          "Large.";
      }
    }
    description
      "Buffer mode type.";
  }

  typedef speed-type {
    type enumeration {
      enum "both-speed" {
        value 0;
        description
          "High speed and low speed.";
      }
      enum "low-speed" {
        value 1;
        description
          "Low speed.";
      }
      enum "high-speed" {
        value 2;
        description
          "High speed.";
      }
    }
    description
      "Speed type.";
  }

  typedef qos-rule-service-type {
    type enumeration {
      enum "normal" {
        value 0;
        description
          "Normal interface.";
      }
      enum "vbd-if" {
        value 1;
        description
          "Vbd interface.";
      }
      enum "multi-type" {
        value 2;
        description
          "Multi type interface.";
      }
      enum "vlan-if" {
        value 3;
        description
          "VLAN interface.";
      }
    }
    description
      "Rule service type.";
  }

  typedef qos-address-type {
    type enumeration {
      enum "source" {
        value 0;
        description
          "Source address.";
      }
      enum "destination" {
        value 1;
        description
          "Destination address.";
      }
    }
    description
      "Source or destination address.";
  }

  typedef qos-mac-type {
    type enumeration {
      enum "source" {
        value 0;
        description
          "Source MAC address.";
      }
      enum "destination" {
        value 1;
        description
          "Destination MAC address.";
      }
    }
    description
      "Source or destination address.";
  }

  typedef qos-ipv6-family {
    type enumeration {
      enum "ipv6" {
        value 2;
        description
          "IPv6 protocol family.";
      }
    }
    description
      "IPv6 protocol family.";
  }

  typedef qos-tcp-bit-match {
    type enumeration {
      enum "not-config" {
        value 0;
        description
          "Not config.";
      }
      enum "established" {
        value 1;
        description
          "Established.";
      }
      enum "fin" {
        value 2;
        description
          "Fin.";
      }
      enum "syn" {
        value 3;
        description
          "Syn.";
      }
      enum "rst" {
        value 4;
        description
          "Rst.";
      }
      enum "psh" {
        value 5;
        description
          "Psh.";
      }
      enum "ack" {
        value 6;
        description
          "Ack.";
      }
      enum "urg" {
        value 7;
        description
          "Urg.";
      }
      enum "ece" {
        value 8;
        description
          "Ece.";
      }
      enum "cwr" {
        value 9;
        description
          "Cwr.";
      }
      enum "ns" {
        value 10;
        description
          "Ns.";
      }
    }
    description
      "TCP bit match type.";
  }

  typedef qos-tcp-bit-match-ipv6 {
    type enumeration {
      enum "not-config" {
        value 0;
        description
          "NotConfig.";
      }
      enum "established" {
        value 1;
        description
          "Established.";
      }
      enum "fin" {
        value 2;
        description
          "Fin.";
      }
      enum "syn" {
        value 3;
        description
          "Syn.";
      }
      enum "rst" {
        value 4;
        description
          "Rst.";
      }
      enum "psh" {
        value 5;
        description
          "Psh.";
      }
      enum "ack" {
        value 6;
        description
          "Ack.";
      }
      enum "urg" {
        value 7;
        description
          "Urg.";
      }
    }
    description
      "IPv6 TCP bit match type.";
  }

  typedef car-limit-type {
    type enumeration {
      enum "pps" {
        value 1;
        description
          "Car limit type pps.";
      }
    }
    description
      "Car limit type.";
  }

  typedef acl-log-action-type {
    type enumeration {
      enum "first-packet" {
        value 39;
        description
          "Log first packet action.";
      }
    }
    description
      "Type of the log action.";
  }

  typedef low-latency-enable-type {
    type enumeration {
      enum "flow-queue" {
        value 1;
        description
          "Flow queue.";
      }
    }
    description
      "Business type of low latency.";
  }

  typedef low-latency-enable-value {
    type enumeration {
      enum "enable" {
        value 1;
        description
          "Enable.";
      }
    }
    description
      "Enable.";
  }

  typedef shaping-value-type {
    type enumeration {
      enum "256K" {
        value 0;
        description
          "256K.";
      }
      enum "512K" {
        value 1;
        description
          "512K.";
      }
    }
    description
      "Shaping value type.";
  }

  typedef port-shaping-weight-mode-type {
    type enumeration {
      enum "enable" {
        value 1;
        description
          "Weight mode enable.";
      }
    }
    description
      "Weight mode enable.";
  }

  typedef scheduling-mode-type {
    type enumeration {
      enum "mode2" {
        value 0;
        description
          "Mode 2.";
      }
      enum "mode3" {
        value 1;
        description
          "Mode 3.";
      }
    }
    description
      "Scheduling mode type.";
  }

  typedef map-type {
    type enumeration {
      enum "none" {
        value 1;
        description
          "Notconfig map type.";
      }
      enum "inner-8021p" {
        value 2;
        description
          "Inner 802.1p priority.";
      }
      enum "outer-8021p" {
        value 4;
        description
          "Outer 802.1p priority.";
      }
      enum "dscp" {
        value 8;
        description
          "Dscp type.";
      }
      enum "mpls-exp" {
        value 16;
        description
          "MPLS-EXP type.";
      }
    }
    description
      "Map type for phb.";
  }

  typedef convergence-schedule-mode {
    type enumeration {
      enum "disable" {
        value 4;
        description
          "Disable.";
      }
    }
    description
      "Disable.";
  }

  typedef port-convergence-schedule-mode {
    type enumeration {
      enum "enable" {
        value 1;
        description
          "Enable.";
      }
    }
    description
      "Enable.";
  }

  typedef traffic-policy-untag-type {
    type enumeration {
      enum "disable" {
        value 0;
        description
          "Disable.";
      }
    }
    description
      "Disable.";
  }

  typedef qos-direction-inbound {
    type enumeration {
      enum "inbound" {
        value 0;
        description
          "Inbound.";
      }
    }
    description
      "Direction.";
  }

  typedef in-direction-type {
    type enumeration {
      enum "inbound" {
        value 0;
        description
          "Inbound.";
      }
    }
    description
      "Inbound.";
  }

  typedef discard-type {
    type enumeration {
      enum "discard-packet" {
        value 1;
        description
          "Discard Packets.";
      }
      enum "discard-byte" {
        value 2;
        description
          "Discard Bytes.";
      }
      enum "discard-packet-ratio" {
        value 3;
        description
          "Discard Ratio.";
      }
    }
    description
      "Discard mode type.";
  }

  typedef lcs-active-status-type {
    type enumeration {
      enum "allocated" {
        value 1;
        description
          "Allocated.";
      }
      enum "activated" {
        value 2;
        description
          "Activated.";
      }
    }
    description
      "Liscense active status type.";
  }

  typedef statistics-car-type {
    type enumeration {
      enum "car" {
        value 1;
        description
          "CAR action.";
      }
      enum "broadcast" {
        value 2;
        description
          "Broadcast suppression.";
      }
      enum "multicast" {
        value 3;
        description
          "Multicast suppression.";
      }
      enum "unknow-unicast" {
        value 4;
        description
          "Unknown unicast suppression.";
      }
      enum "l2-forward" {
        value 5;
        description
          "CAR L2 forward parameter.";
      }
      enum "l3-forward" {
        value 6;
        description
          "CAR L3 forward parameter.";
      }
      enum "bum" {
        value 7;
        description
          "BUM suppression.";
      }
      enum "bu" {
        value 8;
        description
          "BU suppression.";
      }
      enum "unknow-multicast" {
        value 9;
        description
          "Unknown multicast suppression.";
      }
    }
    description
      "Car statistics type.";
  }

  typedef qos-priority-num-type {
    type enumeration {
      enum "p0" {
        value 0;
        description
          "P0.";
      }
      enum "p1" {
        value 1;
        description
          "P1.";
      }
      enum "p2" {
        value 2;
        description
          "P2.";
      }
      enum "p3" {
        value 3;
        description
          "P3.";
      }
      enum "p4" {
        value 4;
        description
          "P4.";
      }
      enum "p5" {
        value 5;
        description
          "P5.";
      }
      enum "p6" {
        value 6;
        description
          "P6.";
      }
      enum "p7" {
        value 7;
        description
          "P7.";
      }
      enum "total" {
        value 8;
        description
          "Total.";
      }
    }
    description
      "The priority num.";
  }

  typedef qos-flow-type {
    type enumeration {
      enum "source-ip" {
        value 1;
        description
          "Source address.";
      }
      enum "destination-ip" {
        value 2;
        description
          "Destination address.";
      }
    }
    description
      "Flow CAR IP type.";
  }

  typedef increase-priority {
    type enumeration {
      enum "increase-priority" {
        value 1;
        description
          "Increase priority.";
      }
    }
    description
      "Increase priority.";
  }

  typedef forward-type {
    type enumeration {
      enum "vll" {
        value 1;
        description
          "VLL forward type.";
      }
    }
    description
      "VLL forward type.";
  }

  typedef ability-type {
    type enumeration {
      enum "S" {
        value 1;
        description
          "The port support share-mode hard pipe.";
      }
      enum "N" {
        value 2;
        description
          "None hard-pipe ability.";
      }
      enum "U" {
        value 3;
        description
          "Unknown hard-pipe ability.";
      }
      enum "M" {
        value 4;
        description
          "The port need split member interface.";
      }
      enum "E" {
        value 5;
        description
          "The port support exclusive-mode hard pipe.";
      }
    }
    description
      "Ability type.";
  }

  typedef qos-policy-layer {
    type enumeration {
      enum "ip-layer" {
        value 1;
        description
          "IP layer.";
      }
    }
    description
      "IP layer.";
  }

  typedef enable-type {
    type enumeration {
      enum "enable" {
        value 1;
        description
          "Enable.";
      }
    }
    description
      "Enable.";
  }

  typedef priority-convergent-type {
    type enumeration {
      enum "high" {
        value 1;
        description
          "High.";
      }
    }
    description
      "High priority.";
  }

  typedef untag-enable-type {
    type enumeration {
      enum "enable" {
        value 2;
        description
          "Enable.";
      }
    }
    description
      "Untag enable type.";
  }

  typedef suppress-type {
    type enumeration {
      enum "unknown-unicast-suppression" {
        value 2;
        description
          "Unknown unicast suppression.";
      }
      enum "multicast-suppression" {
        value 3;
        description
          "Multicast suppression.";
      }
      enum "broadcast-suppression" {
        value 4;
        description
          "Broadcast suppression.";
      }
    }
    description
      "Suppression type.";
  }

  typedef load-balance-type {
    type enumeration {
      enum "flow" {
        value 0;
        description
          "Flow by flow.";
      }
      enum "packet" {
        value 1;
        description
          "Packet by packet.";
      }
      enum "flow-l2" {
        value 2;
        description
          "Flow by flow with L2.";
      }
      enum "flow-l3" {
        value 3;
        description
          "Flow by flow with L3.";
      }
    }
    description
      "Load balance type.";
  }

  typedef sample-type {
    type enumeration {
      enum "fix-packets" {
        value 0;
        description
          "Sampling based on the fixed number of packets.";
      }
      enum "fix-time" {
        value 1;
        description
          "Fixed sampling interval.";
      }
      enum "random-packets" {
        value 2;
        description
          "Sampling based on the random number of packets.";
      }
    }
    description
      "Sampling type.";
  }

  typedef action-urpf {
    type enumeration {
      enum "urpf" {
        value 3;
        description
          "URPF action.";
      }
    }
    description
      "URPF action.";
  }

  typedef check-type {
    type enumeration {
      enum "strict" {
        value 0;
        description
          "Strict.";
      }
      enum "loose" {
        value 1;
        description
          "Loose.";
      }
    }
    description
      "Type of the URPF check.";
  }

  typedef statistics-type {
    type enumeration {
      enum "BPS" {
        value 1;
        description
          "Byte/s.";
      }
      enum "PPS" {
        value 2;
        description
          "Packet/s.";
      }
    }
    description
      "Statistics type.";
  }

  typedef ip-type {
    type enumeration {
      enum "ipv4" {
        value 0;
        description
          "IPv4.";
      }
      enum "ipv6" {
        value 1;
        description
          "IPv6.";
      }
    }
    description
      "Type of an address.";
  }

  typedef pool-type {
    type enumeration {
      enum "pool-0" {
        value 0;
        description
          "Pool 0.";
      }
      enum "pool-1" {
        value 1;
        description
          "Pool 0.";
      }
    }
    description
      "Pool ID.";
  }

  typedef member-link-scheduler-type {
    type enumeration {
      enum "traffic-car" {
        value 1;
        description
          "Traffic CAR.";
      }
      enum "qos-car" {
        value 2;
        description
          "QoS CAR.";
      }
      enum "port-shaping" {
        value 3;
        description
          "Port shaping.";
      }
      enum "hard-pipe" {
        value 4;
        description
          "Hard pipe.";
      }
      enum "user-queue" {
        value 5;
        description
          "User queue.";
      }
      enum "profile-car" {
        value 7;
        description
          "Profile CAR.";
      }
      enum "hqos-outbound" {
        value 8;
        description
          "HQoS outbound.";
      }
      enum "mpls-te" {
        value 9;
        description
          "MPLS TE.";
      }
    }
    description
      "Business type.";
  }

  typedef traffic-type {
    type enumeration {
      enum "ldp-traffic" {
        value 1;
        description
          "LDP traffic.";
      }
    }
    description
      "LDP traffic.";
  }

  typedef any-other-type {
    type enumeration {
      enum "not-config" {
        value 0;
        description
          "Not config.";
      }
      enum "user-vlan" {
        value 1;
        description
          "User VLAN.";
      }
      enum "qinq" {
        value 2;
        description
          "QinQ.";
      }
    }
    description
      "BAS QoS profile apply type.";
  }

  typedef bas-profile-identifier-type {
    type enumeration {
      enum "pe-vid" {
        value 1;
        description
          "PE VLAN ID.";
      }
      enum "ce-vid" {
        value 2;
        description
          "CE VLAN ID.";
      }
      enum "pe-ce-vid" {
        value 3;
        description
          "PE CE VLAN ID.";
      }
      enum "vlan-id" {
        value 4;
        description
          "VLAN ID.";
      }
      enum "none" {
        value 5;
        description
          "None.";
      }
      enum "option82" {
        value 7;
        description
          "Option82.";
      }
      enum "access-line-id" {
        value 11;
        description
          "Access line ID.";
      }
    }
    description
      "BAS QoS profile apply identifier type.";
  }

  typedef vlan-user-group-queue-identifier-type {
    type enumeration {
      enum "none" {
        value 0;
        description
          "None.";
      }
      enum "vlan-id" {
        value 1;
        description
          "VLAN ID.";
      }
      enum "pe-vid" {
        value 2;
        description
          "PE VLAN ID.";
      }
      enum "ce-vid" {
        value 3;
        description
          "CE VLAN ID.";
      }
      enum "pe-ce-vid" {
        value 4;
        description
          "PE CE VLAN ID.";
      }
    }
    description
      "VLAN user group queue apply identifier type.";
  }

  typedef user-access-type {
    type enumeration {
      enum "leased-line-access" {
        value 10;
        description
          "Leased line access.";
      }
      enum "subscriber-access" {
        value 13;
        description
          "Subscriber access.";
      }
    }
    description
      "User access type.";
  }

  typedef hard-pipe-mode {
    type enumeration {
      enum "share-mode" {
        value 0;
        description
          "Share mode.";
      }
      enum "exclusive-mode" {
        value 1;
        description
          "Exclusive mode.";
      }
    }
    description
      "Hard pipe mode.";
  }

  typedef ac-mode-layer-type {
    type enumeration {
      enum "link-layer" {
        value 1;
        description
          "Link layer:";
      }
      enum "all-layer" {
        value 2;
        description
          "All layer:";
      }
    }
    description
      "Layer type.";
  }

  typedef vxlan-trust-type {
    type enumeration {
      enum "8021p" {
        value 1;
        description
          "Trust 8021p.";
      }
      enum "upstream" {
        value 0;
        description
          "Trust upstream.";
      }
    }
    description
      "VXLAN trust type.";
  }

  typedef exclude-type {
    type enumeration {
      enum "no-exclude" {
        value 0;
        description
          "Non-exclude mode.";
      }
      enum "exclude" {
        value 1;
        description
          "Exclude mode.";
      }
    }
    description
      "Exclude type.";
  }

  typedef qos-profile-template-name {
    type string {
      length "1..63";
    }
    description
      "Qos profile template name is like string.";
  }

  typedef trust-remote-direction-type {
    type enumeration {
      enum "inbound" {
        value 1;
        description
          "Inbound.";
      }
    }
    description
      "Trust remote direction type.";
  }

  typedef action-load-balance {
    type enumeration {
      enum "load-balance" {
        value 4;
        description
          "Load balancing action.";
      }
    }
    description
      "Load balancing.";
  }

  typedef user-type {
    type enumeration {
      enum "lac" {
        value 1;
        description
          "Specifies the user type as lac.";
      }
      enum "lns" {
        value 2;
        description
          "Specifies the user type as lns.";
      }
      enum "lac-and-lns" {
        value 3;
        description
          "Specifies the user type as lac and lns.";
      }
    }
    description
      "User type.";
  }

  typedef access-type {
    type enumeration {
      enum "leased-line-access" {
        value 1;
        description
          "Leased line access.";
      }
      enum "none" {
        value 0;
        description
          "Not config.";
      }
    }
    description
      "User access type.";
  }

  typedef l2tp-user {
    type enumeration {
      enum "l2tp-user" {
        value 12;
        description
          "L2TP user.";
      }
    }
    description
      "L2TP user.";
  }

  typedef cos-value-type {
    type enumeration {
      enum "be" {
        value 0;
        description
          "Specifies the service class to be BE.";
      }
      enum "af1-af2" {
        value 1;
        description
          "Specifies the service class to be AF1 and AF2.";
      }
      enum "af3-af4" {
        value 2;
        description
          "Specifies the service class to be Af3 and af4.";
      }
      enum "ef-cs6-cs7" {
        value 3;
        description
          "Specifies the service class to be EF and CS6 and CS7.";
      }
    }
    description
      "Service class type.";
  }

  typedef rule-type {
    type enumeration {
      enum "aclv4" {
        value 1;
        description
          "Aclv4.";
      }
      enum "aclv6" {
        value 2;
        description
          "Aclv6.";
      }
      enum "l2acl" {
        value 3;
        description
          "L2acl.";
      }
      enum "mpls" {
        value 4;
        description
          "MPLS.";
      }
      enum "uclv4" {
        value 5;
        description
          "Uclv4.";
      }
      enum "uclv6" {
        value 6;
        description
          "Uclv6.";
      }
    }
    description
      "Qos resource rule type.";
  }

  typedef yes-or-no {
    type enumeration {
      enum "no" {
        value 0;
        description
          "No.";
      }
      enum "yes" {
        value 1;
        description
          "Yes.";
      }
    }
    description
      "Choose yes or no.";
  }

  typedef remote-trust-type {
    type enumeration {
      enum "ip-dscp" {
        value 0;
        description
          "Trust ip-dscp.";
      }
      enum "8021p" {
        value 1;
        description
          "Trust 8021p.";
      }
    }
    description
      "Trust type.";
  }

  typedef type-8021p {
    type enumeration {
      enum "8021p" {
        value 1;
        description
          "Trust 8021p.";
      }
      enum "inner-8021p" {
        value 3;
        description
          "Trust inner 8021p.";
      }
      enum "outer-8021p" {
        value 2;
        description
          "Trust outer 8021p.";
      }
    }
    description
      "Trust 8021p type.";
  }

  typedef deficit-unit-type {
    type enumeration {
      enum "1K" {
        value 4;
        description
          "1K (byte).";
      }
      enum "2K" {
        value 5;
        description
          "2K (byte).";
      }
    }
    description
      "Deficit unit type.";
  }

  typedef user-queue-template-type {
    type enumeration {
      enum "4-priority" {
        value 0;
        description
          "Four priority mode.";
      }
    }
    description
      "User queue template mode type.";
  }

  typedef priority-schedule-mode {
    type enumeration {
      enum "pq" {
        value 0;
        description
          "Priority queue.";
      }
      enum "wfq" {
        value 1;
        description
          "Weighted fair queue.";
      }
    }
    description
      "Priority mode.";
  }

  typedef ignore-default-type {
    type enumeration {
      enum "disable" {
        value 0;
        description
          "The default route is excluded.";
      }
    }
    description
      "Indicates a mode in which the default route is excluded.";
  }

  typedef protocol-family {
    type enumeration {
      enum "ipv4" {
        value 1;
        description
          "IPv4.";
      }
      enum "ipv6" {
        value 2;
        description
          "IPv6.";
      }
      enum "l2" {
        value 3;
        description
          "L2.";
      }
      enum "mpls" {
        value 4;
        description
          "MPLS.";
      }
    }
    description
      "Protocol family type.";
  }
}
