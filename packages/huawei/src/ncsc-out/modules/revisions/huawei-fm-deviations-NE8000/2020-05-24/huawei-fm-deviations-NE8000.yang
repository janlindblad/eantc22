module huawei-fm-deviations-NE8000 {
  // Generated by yanger -t ncs
  tailf:mount-id "huawei-nc-1.0:huawei-nc-1.0";
  tailf:ncs-device-type "netconf";

  namespace "urn:huawei:yang:huawei-fm-deviations-NE8000";
  prefix fm-devs-NE8000;

  import huawei-fm {
    prefix fm;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Deviation of Fault management module.";

  revision 2020-05-24 {
    description
      "Initial revision.";
    reference "Huawei private.";
  }

  typedef ncs_template_inverse-mode-type-deviations {
    type string;
    description
      "The type of inverse mode.";
  }

  typedef ncs_rpc_notif_inverse-mode-type-deviations {
    type enumeration {
      enum "forbid-reverse" {
        value 0;
        description
          "Forbid reversion.";
      }
      enum "auto-resume" {
        value 1;
        description
          "Automatic reversion resumption.";
      }
    }
    description
      "The type of inverse mode.";
  }

  typedef live_ncs_inverse-mode-type-deviations {
    type enumeration {
      enum "forbid-reverse" {
        value 0;
        description
          "Forbid reversion.";
      }
      enum "auto-resume" {
        value 1;
        description
          "Automatic reversion resumption.";
      }
    }
    description
      "The type of inverse mode.";
  }

  typedef inverse-mode-type-deviations {
    type enumeration {
      enum "forbid-reverse" {
        value 0;
        description
          "Forbid reversion.";
      }
      enum "auto-resume" {
        value 1;
        description
          "Automatic reversion resumption.";
      }
    }
    description
      "The type of inverse mode.";
  }

  deviation "/ncs:devices/ncs:device/ncs:rpc/fm:rpc-clear-all-history-alarm/fm:clear-all-history-alarm" {
    deviate not-supported;
  }
  deviation "/ncs:devices/ncs:device/ncs:rpc/fm:rpc-clear-history-alarm/fm:clear-history-alarm" {
    deviate not-supported;
  }
  deviation "/ncs:devices/ncs:device/ncs:rpc/fm:rpc-clear-active-alarm/fm:clear-active-alarm" {
    deviate not-supported;
  }
  deviation "/ncs:devices/ncs:device/ncs:rpc/fm:rpc-clear-all-active-alarm/fm:clear-all-active-alarm" {
    deviate not-supported;
  }
  deviation "/ncs:devices/ncs:device/ncs:rpc/fm:rpc-reset-all-alarm-statistic/fm:reset-all-alarm-statistic" {
    deviate not-supported;
  }
  deviation "/ncs:devices/ncs:template/ncs:ned-id/ncs:config/fm:fm/fm:global/fm:inverse-mode" {
    deviate replace {
      type fm-devs-NE8000:ncs_template_inverse-mode-type-deviations;
    }
  }
  deviation "/ncs:devices/ncs:device/ncs:live-status/fm:fm/fm:global/fm:inverse-mode" {
    deviate replace {
      type fm-devs-NE8000:live_ncs_inverse-mode-type-deviations;
    }
  }
  deviation "/ncs:devices/ncs:device/ncs:config/fm:fm/fm:global/fm:inverse-mode" {
    deviate replace {
      type fm-devs-NE8000:inverse-mode-type-deviations;
    }
  }
}
