module huawei-unicast-fwd-srv6 {
  // Generated by yanger -t ncs
  tailf:mount-id "huawei-nc-1.0:huawei-nc-1.0";
  tailf:ncs-device-type "netconf";

  yang-version 1;
  namespace "urn:huawei:yang:huawei-unicast-fwd-srv6";
  prefix unicast-fwd-srv6;

  import huawei-network-instance {
    prefix ni;
  }
  import huawei-extension {
    prefix ext;
  }
  import huawei-srv6 {
    prefix srv6;
  }
  import huawei-license {
    prefix lcs;
  }
  import huawei-devm {
    prefix devm;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Unicast forward SRv6 configuration.";

  revision 2021-04-17 {
    description
      "Add network slice license nodes.";
    reference "Huawei private.";
  }
  revision 2020-03-19 {
    description
      "Initial revision.";
    reference "Huawei private.";
  }
  ext:task-name "forwarding";

  typedef ncs_template_srv6-ttl-mode-type {
    type string;
    description
      "SRv6 TTL mode type.";
  }

  typedef ncs_template_lcs-slice-rtu-type {
    type string;
    description
      "Network-slice license type.";
  }

  typedef ncs_rpc_notif_srv6-ttl-mode-type {
    type enumeration {
      enum "pipe" {
        value 1;
        description
          "Pipe mode.";
      }
      enum "uniform" {
        value 3;
        description
          "Uniform mode.";
      }
    }
    description
      "SRv6 TTL mode type.";
  }

  typedef ncs_rpc_notif_lcs-slice-rtu-type {
    type enumeration {
      enum "data-plane" {
        value 1;
        description
          "License type for data-plane.";
      }
      enum "flex-channel" {
        value 2;
        description
          "License type for flex-channel.";
      }
    }
    description
      "Network-slice license type.";
  }

  typedef live_ncs_srv6-ttl-mode-type {
    type enumeration {
      enum "pipe" {
        value 1;
        description
          "Pipe mode.";
      }
      enum "uniform" {
        value 3;
        description
          "Uniform mode.";
      }
    }
    description
      "SRv6 TTL mode type.";
  }

  typedef live_ncs_lcs-slice-rtu-type {
    type enumeration {
      enum "data-plane" {
        value 1;
        description
          "License type for data-plane.";
      }
      enum "flex-channel" {
        value 2;
        description
          "License type for flex-channel.";
      }
    }
    description
      "Network-slice license type.";
  }

  typedef srv6-ttl-mode-type {
    type enumeration {
      enum "pipe" {
        value 1;
        description
          "Pipe mode.";
      }
      enum "uniform" {
        value 3;
        description
          "Uniform mode.";
      }
    }
    description
      "SRv6 TTL mode type.";
  }

  typedef lcs-slice-rtu-type {
    type enumeration {
      enum "data-plane" {
        value 1;
        description
          "License type for data-plane.";
      }
      enum "flex-channel" {
        value 2;
        description
          "License type for flex-channel.";
      }
    }
    description
      "Network-slice license type.";
  }

  augment "/ncs:devices/ncs:template/ncs:ned-id/ncs:config/ni:network-instance/ni:instances/ni:instance/srv6:srv6" {
    description
      "Unicast forward configuration to the SRv6 module.";
    container global-ipv6uc-attribute {
      // NCS drop when statement
      description
        "Configure global IPv6 unicast attributes.";
      leaf forward-mode-through {
        type string;
        // NCS drop default statement
        description
          "Enable/disable the forwarding mode of an SRv6 Tunnel to software loopback.";
      }
      leaf srv6-ttl-mode {
        type ncs_template_srv6-ttl-mode-type;
        // NCS drop default statement
        description
          "Set SRv6 tunnel-encapsulated mode.";
      }
    }
  }
  augment "/ncs:devices/ncs:device/ncs:live-status/ni:network-instance/ni:instances/ni:instance/srv6:srv6" {
    description
      "Unicast forward configuration to the SRv6 module.";
    container global-ipv6uc-attribute {
      tailf:ncs-device-type "netconf";
      tailf:display-when "not(../../../../../../ncs:module) or ../../../../../../ncs:module[ncs:name='huawei-unicast-fwd-srv6'] or (../../../../../../ncs:live-status-protocol[not(ncs:capability)]) or (../../../../../../ncs:live-status-protocol/ncs:capability/ncs:module[.='huawei-unicast-fwd-srv6'])";
      // NCS drop when statement
      description
        "Configure global IPv6 unicast attributes.";
      leaf forward-mode-through {
        type boolean;
        // NCS drop default statement
        description
          "Enable/disable the forwarding mode of an SRv6 Tunnel to software loopback.";
      }
      leaf srv6-ttl-mode {
        type live_ncs_srv6-ttl-mode-type;
        // NCS drop default statement
        description
          "Set SRv6 tunnel-encapsulated mode.";
      }
    }
  }
  augment "/ncs:devices/ncs:device/ncs:config/ni:network-instance/ni:instances/ni:instance/srv6:srv6" {
    description
      "Unicast forward configuration to the SRv6 module.";
    container global-ipv6uc-attribute {
      tailf:ncs-device-type "netconf";
      tailf:display-when "not(../../../../../../ncs:module) or ../../../../../../ncs:module[ncs:name='huawei-unicast-fwd-srv6']";
      when "../srv6:enable = 'true'" {
        tailf:xpath-root 3;
      }
      description
        "Configure global IPv6 unicast attributes.";
      leaf forward-mode-through {
        type boolean;
        default "false";
        description
          "Enable/disable the forwarding mode of an SRv6 Tunnel to software loopback.";
      }
      leaf srv6-ttl-mode {
        type srv6-ttl-mode-type;
        default "pipe";
        description
          "Set SRv6 tunnel-encapsulated mode.";
      }
    }
  }
  augment "/ncs:devices/ncs:template/ncs:ned-id/ncs:config/lcs:license" {
    description
      "Network slice license.";
    container lcs-network-slices {
      description
        "List of license information about all boards network-slice resources.";
      list lcs-network-slice {
        // NCS patched for predictable order
        ordered-by user;
        key "slot-id license-type";
        description
          "Configure license information about a board to active network-slice resources.";
        leaf slot-id {
          type string;
          description
            "Indicates the slot ID of a board.";
        }
        leaf license-type {
          type ncs_template_lcs-slice-rtu-type;
          description
            "Network slice license type.";
        }
        leaf resource-size {
          type string;
          // NCS drop mandatory statement
          description
            "The number of network-slice resources is related to a specific board.";
        }
      }
    }
    // NCS drop config false container 'lcs-usage-slice-items'
  }
  augment "/ncs:devices/ncs:device/ncs:live-status/lcs:license" {
    description
      "Network slice license.";
    container lcs-network-slices {
      tailf:ncs-device-type "netconf";
      tailf:display-when "not(../../../ncs:module) or ../../../ncs:module[ncs:name='huawei-unicast-fwd-srv6'] or (../../../ncs:live-status-protocol[not(ncs:capability)]) or (../../../ncs:live-status-protocol/ncs:capability/ncs:module[.='huawei-unicast-fwd-srv6'])";
      description
        "List of license information about all boards network-slice resources.";
      list lcs-network-slice {
        key "slot-id license-type";
        description
          "Configure license information about a board to active network-slice resources.";
        leaf slot-id {
          type leafref {
            path "/ncs:devices/ncs:device/ncs:live-status/devm:devm/devm:lpu-boards/devm:lpu-board/devm:position" {
              tailf:xpath-root 3;
            }
          }
          description
            "Indicates the slot ID of a board.";
        }
        leaf license-type {
          type live_ncs_lcs-slice-rtu-type;
          description
            "Network slice license type.";
        }
        leaf resource-size {
          type uint32 {
            range "1..65535";
          }
          // NCS drop mandatory statement
          description
            "The number of network-slice resources is related to a specific board.";
        }
      }
    }
    container lcs-usage-slice-items {
      tailf:ncs-device-type "netconf";
      tailf:display-when "not(../../../ncs:module) or ../../../ncs:module[ncs:name='huawei-unicast-fwd-srv6'] or (../../../ncs:live-status-protocol[not(ncs:capability)]) or (../../../ncs:live-status-protocol/ncs:capability/ncs:module[.='huawei-unicast-fwd-srv6'])";
      description
        "List of network slice license resource usage information.";
      list lcs-usage-slice-item {
        key "feature-name";
        description
          "Statistics of network slice license resource usage information.";
        leaf feature-name {
          type string {
            length "1..31";
          }
          description
            "Name of the control item corresponding to the network license.";
        }
        leaf feature-description {
          type string {
            length "1..255";
          }
          description
            "Description of the control item corresponding to the network license.";
        }
        leaf activated-total {
          type uint32;
          description
            "Number of activated resources.";
        }
        leaf available-total {
          type uint32;
          description
            "Number of remaining available resources.";
        }
        leaf total {
          type uint32;
          description
            "Total number of resources.";
        }
        container lcs-info-boards {
          description
            "List of board network slice license information.";
          list lcs-info-board {
            key "position";
            description
              "Statistics of network slice license usage information on a board.";
            leaf position {
              type string {
                length "1..32";
              }
              description
                "Board position.";
            }
            leaf barcode {
              type string {
                length "1..128";
              }
              description
                "Bar code in the electronic label of a board.";
            }
            leaf usage-on-board {
              type uint32;
              description
                "Number of used resources on a board.";
            }
            leaf available-on-board {
              type uint32;
              description
                "Number of remaining available resources on a board.";
            }
            leaf activated-on-board {
              type uint32;
              description
                "Total number of resources on a board.";
            }
          }
        }
      }
    }
  }
  augment "/ncs:devices/ncs:device/ncs:config/lcs:license" {
    description
      "Network slice license.";
    container lcs-network-slices {
      tailf:ncs-device-type "netconf";
      tailf:display-when "not(../../../ncs:module) or ../../../ncs:module[ncs:name='huawei-unicast-fwd-srv6']";
      description
        "List of license information about all boards network-slice resources.";
      list lcs-network-slice {
        key "slot-id license-type";
        description
          "Configure license information about a board to active network-slice resources.";
        leaf slot-id {
          type leafref {
            path "/ncs:devices/ncs:device/ncs:config/devm:devm/devm:lpu-boards/devm:lpu-board/devm:position" {
              tailf:xpath-root 3;
            }
          }
          description
            "Indicates the slot ID of a board.";
        }
        leaf license-type {
          type lcs-slice-rtu-type;
          description
            "Network slice license type.";
        }
        leaf resource-size {
          type uint32 {
            range "1..65535";
          }
          mandatory true;
          description
            "The number of network-slice resources is related to a specific board.";
        }
      }
    }
    // NCS drop config false container 'lcs-usage-slice-items'
  }
}
