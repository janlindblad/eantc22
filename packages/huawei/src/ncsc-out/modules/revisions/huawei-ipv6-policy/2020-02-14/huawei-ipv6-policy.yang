module huawei-ipv6-policy {
  // Generated by yanger -t ncs
  tailf:mount-id "huawei-nc-1.0:huawei-nc-1.0";
  tailf:ncs-device-type "netconf";

  namespace "urn:huawei:yang:huawei-ipv6-policy";
  prefix ipv6-policy;

  import ietf-inet-types {
    prefix inet;
  }
  import huawei-network-instance {
    prefix ni;
  }
  import huawei-extension {
    prefix ext;
  }
  import huawei-l3vpn {
    prefix l3vpn;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "This module contains a collection of YANG definitions for
     configuring IP implementations.
     Copyright (C) 2019 Huawei Technologies Co., Ltd. All rights reserved.";

  revision 2020-02-14 {
    description
      "Modify the description of nodes.";
    reference "Huawei private.";
  }
  revision 2019-04-15 {
    description
      "Reinitialize revision.";
    reference "Huawei private.";
  }
  revision 2019-04-10 {
    description
      "Initial revision.";
    reference "Huawei private.";
  }
  ext:task-name "interface-mgr";

  augment "/ncs:devices/ncs:template/ncs:ned-id/ncs:config/ni:network-instance/ni:instances/ni:instance" {
    // NCS drop when statement
    description
      "Policies for selecting source and destination IPv6 addresses and parameters for configuring IP on interfaces.";
    container ipv6-policys {
      description
        "List of policies for selecting source and destination IPv6 addresses.";
      list ipv6-policy {
        // NCS patched for predictable order
        ordered-by user;
        key "ipv6-prefix ipv6-prefix-length";
        // NCS drop max-elements statement
        description
          "Configure policy for selecting source and destination IPv6 addresses.";
        leaf ipv6-prefix {
          type string;
          description
            "Specifies the prefix of an IPv6 address.";
        }
        leaf ipv6-prefix-length {
          type string;
          description
            "Specifies the prefix length of an IPv6 address.";
        }
        leaf prefix-precedence {
          type string;
          // NCS drop mandatory statement
          description
            "Specifies the priority of an IPv6 address when the address is the destination address.";
        }
        leaf prefix-label {
          type string;
          // NCS drop mandatory statement
          description
            "Specifies the priority of an IPv6 address when the address is the source address.";
        }
        // NCS drop config false leaf 'default-flag'
      }
    }
  }
  augment "/ncs:devices/ncs:device/ncs:live-status/ni:network-instance/ni:instances/ni:instance" {
    // NCS drop when statement
    description
      "Policies for selecting source and destination IPv6 addresses and parameters for configuring IP on interfaces.";
    container ipv6-policys {
      tailf:ncs-device-type "netconf";
      tailf:display-when "not(../../../../../ncs:module) or ../../../../../ncs:module[ncs:name='huawei-ipv6-policy'] or (../../../../../ncs:live-status-protocol[not(ncs:capability)]) or (../../../../../ncs:live-status-protocol/ncs:capability/ncs:module[.='huawei-ipv6-policy'])";
      description
        "List of policies for selecting source and destination IPv6 addresses.";
      list ipv6-policy {
        key "ipv6-prefix ipv6-prefix-length";
        // NCS drop max-elements statement
        description
          "Configure policy for selecting source and destination IPv6 addresses.";
        leaf ipv6-prefix {
          type inet:ipv6-address-no-zone;
          description
            "Specifies the prefix of an IPv6 address.";
        }
        leaf ipv6-prefix-length {
          type uint32 {
            range "0..128";
          }
          description
            "Specifies the prefix length of an IPv6 address.";
        }
        leaf prefix-precedence {
          type uint32 {
            range "0..4294967295";
          }
          // NCS drop mandatory statement
          description
            "Specifies the priority of an IPv6 address when the address is the destination address.";
        }
        leaf prefix-label {
          type uint32 {
            range "0..4294967295";
          }
          // NCS drop mandatory statement
          description
            "Specifies the priority of an IPv6 address when the address is the source address.";
        }
        leaf default-flag {
          type boolean;
          // NCS drop default statement
          description
            "Specifies whether the configuration is an default configuration.";
        }
      }
    }
  }
  augment "/ncs:devices/ncs:device/ncs:config/ni:network-instance/ni:instances/ni:instance" {
    when "./l3vpn:afs/l3vpn:af[l3vpn:type='ipv6-unicast']" {
      tailf:xpath-root 3;
    }
    description
      "Policies for selecting source and destination IPv6 addresses and parameters for configuring IP on interfaces.";
    container ipv6-policys {
      tailf:ncs-device-type "netconf";
      tailf:display-when "not(../../../../../ncs:module) or ../../../../../ncs:module[ncs:name='huawei-ipv6-policy']";
      description
        "List of policies for selecting source and destination IPv6 addresses.";
      list ipv6-policy {
        key "ipv6-prefix ipv6-prefix-length";
        max-elements 50;
        description
          "Configure policy for selecting source and destination IPv6 addresses.";
        leaf ipv6-prefix {
          type inet:ipv6-address-no-zone;
          description
            "Specifies the prefix of an IPv6 address.";
        }
        leaf ipv6-prefix-length {
          type uint32 {
            range "0..128";
          }
          description
            "Specifies the prefix length of an IPv6 address.";
        }
        leaf prefix-precedence {
          type uint32 {
            range "0..4294967295";
          }
          mandatory true;
          description
            "Specifies the priority of an IPv6 address when the address is the destination address.";
        }
        leaf prefix-label {
          type uint32 {
            range "0..4294967295";
          }
          mandatory true;
          description
            "Specifies the priority of an IPv6 address when the address is the source address.";
        }
        // NCS drop config false leaf 'default-flag'
      }
    }
  }
}
