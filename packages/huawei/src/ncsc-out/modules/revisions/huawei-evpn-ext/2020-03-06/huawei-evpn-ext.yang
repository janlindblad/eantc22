module huawei-evpn-ext {
  // Generated by yanger -t ncs
  tailf:mount-id "huawei-nc-1.0:huawei-nc-1.0";
  tailf:ncs-device-type "netconf";

  namespace "urn:huawei:yang:huawei-evpn-ext";
  prefix evpn-ext;

  import huawei-evpn {
    prefix evpn;
  }
  import huawei-license {
    prefix lcs;
  }
  import huawei-extension {
    prefix ext;
  }
  import huawei-qos {
    prefix qos;
  }
  import huawei-pic {
    prefix pic;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Evpn ext configuration.";

  revision 2020-03-06 {
    description
      "Add pipe type.";
    reference "Huawei private.";
  }
  revision 2020-01-13 {
    description
      "Modify description.";
    reference "Huawei private.";
  }
  revision 2019-10-26 {
    description
      "Add container.";
    reference "Huawei private.";
  }
  revision 2019-04-23 {
    description
      "Initial revision.";
    reference "Huawei private.";
  }
  ext:task-name "forwarding";

  typedef ncs_template_lcs-active-type {
    type string;
    description
      "License active type.";
  }

  typedef ncs_template_lcs-active-status-type {
    type string;
    description
      "License active status type.";
  }

  typedef ncs_template_evpn-pipe-mode {
    type string;
    description
      "Evpn pipe mode.";
  }

  typedef ncs_template_evpn-service-class {
    type string;
    description
      "Description of CoS.";
  }

  typedef ncs_template_evpn-color {
    type string;
    description
      "Description of packet color.";
  }

  typedef ncs_template_evpn-trust-type {
    type string;
    description
      "Description of trust type.";
  }

  typedef ncs_rpc_notif_lcs-active-type {
    type enumeration {
      enum "deactive" {
        value 0;
        description
          "Specify the license active type as deactivate.";
      }
      enum "active" {
        value 1;
        description
          "Specify the license active type as activate.";
      }
    }
    description
      "License active type.";
  }

  typedef ncs_rpc_notif_lcs-active-status-type {
    type enumeration {
      enum "unallocated" {
        value 0;
        description
          "Specify the license active status as unallocated.";
      }
      enum "allocated" {
        value 1;
        description
          "Specify the license active status as allocated.";
      }
      enum "activated" {
        value 2;
        description
          "Specify the license active status as ctivated.";
      }
    }
    description
      "License active status type.";
  }

  typedef ncs_rpc_notif_evpn-pipe-mode {
    type enumeration {
      enum "pipe" {
        value 1;
        description
          "Evpn pipe mode.";
      }
      enum "shortpipe" {
        value 2;
        description
          "Evpn Short Pipe mode.";
      }
      enum "uniform" {
        value 3;
        description
          "Evpn uniform mode.";
      }
    }
    description
      "Evpn pipe mode.";
  }

  typedef ncs_rpc_notif_evpn-service-class {
    type enumeration {
      enum "be" {
        value 0;
        description
          "Specify the CoS as BE.";
      }
      enum "af1" {
        value 1;
        description
          "Specify the CoS as AF1.";
      }
      enum "af2" {
        value 2;
        description
          "Specify the CoS as AF2.";
      }
      enum "af3" {
        value 3;
        description
          "Specify the CoS as AF3.";
      }
      enum "af4" {
        value 4;
        description
          "Specify the CoS as AF4.";
      }
      enum "ef" {
        value 5;
        description
          "Specify the CoS as EF.";
      }
      enum "cs6" {
        value 6;
        description
          "Specify the CoS as CS6.";
      }
      enum "cs7" {
        value 7;
        description
          "Specify the CoS as CS7.";
      }
    }
    description
      "Description of CoS.";
  }

  typedef ncs_rpc_notif_evpn-color {
    type enumeration {
      enum "green" {
        value 0;
        description
          "Specify the packet color as green.";
      }
      enum "yellow" {
        value 1;
        description
          "Specify the packet color as yellow.";
      }
      enum "red" {
        value 2;
        description
          "Specify the packet color as red.";
      }
    }
    description
      "Description of packet color.";
  }

  typedef ncs_rpc_notif_evpn-trust-type {
    type enumeration {
      enum "outpri" {
        value 0;
        description
          "Specify the trust type as OUTTER-VLAN-8021P.";
      }
      enum "inpri" {
        value 1;
        description
          "Specify the trust type as INNER-VLAN-8021P.";
      }
      enum "ipdscp" {
        value 2;
        description
          "Specify the trust type as IP-DSCP.";
      }
    }
    description
      "Description of trust type.";
  }

  typedef live_ncs_lcs-active-type {
    type enumeration {
      enum "deactive" {
        value 0;
        description
          "Specify the license active type as deactivate.";
      }
      enum "active" {
        value 1;
        description
          "Specify the license active type as activate.";
      }
    }
    description
      "License active type.";
  }

  typedef live_ncs_lcs-active-status-type {
    type enumeration {
      enum "unallocated" {
        value 0;
        description
          "Specify the license active status as unallocated.";
      }
      enum "allocated" {
        value 1;
        description
          "Specify the license active status as allocated.";
      }
      enum "activated" {
        value 2;
        description
          "Specify the license active status as ctivated.";
      }
    }
    description
      "License active status type.";
  }

  typedef live_ncs_evpn-pipe-mode {
    type enumeration {
      enum "pipe" {
        value 1;
        description
          "Evpn pipe mode.";
      }
      enum "shortpipe" {
        value 2;
        description
          "Evpn Short Pipe mode.";
      }
      enum "uniform" {
        value 3;
        description
          "Evpn uniform mode.";
      }
    }
    description
      "Evpn pipe mode.";
  }

  typedef live_ncs_evpn-service-class {
    type enumeration {
      enum "be" {
        value 0;
        description
          "Specify the CoS as BE.";
      }
      enum "af1" {
        value 1;
        description
          "Specify the CoS as AF1.";
      }
      enum "af2" {
        value 2;
        description
          "Specify the CoS as AF2.";
      }
      enum "af3" {
        value 3;
        description
          "Specify the CoS as AF3.";
      }
      enum "af4" {
        value 4;
        description
          "Specify the CoS as AF4.";
      }
      enum "ef" {
        value 5;
        description
          "Specify the CoS as EF.";
      }
      enum "cs6" {
        value 6;
        description
          "Specify the CoS as CS6.";
      }
      enum "cs7" {
        value 7;
        description
          "Specify the CoS as CS7.";
      }
    }
    description
      "Description of CoS.";
  }

  typedef live_ncs_evpn-color {
    type enumeration {
      enum "green" {
        value 0;
        description
          "Specify the packet color as green.";
      }
      enum "yellow" {
        value 1;
        description
          "Specify the packet color as yellow.";
      }
      enum "red" {
        value 2;
        description
          "Specify the packet color as red.";
      }
    }
    description
      "Description of packet color.";
  }

  typedef live_ncs_evpn-trust-type {
    type enumeration {
      enum "outpri" {
        value 0;
        description
          "Specify the trust type as OUTTER-VLAN-8021P.";
      }
      enum "inpri" {
        value 1;
        description
          "Specify the trust type as INNER-VLAN-8021P.";
      }
      enum "ipdscp" {
        value 2;
        description
          "Specify the trust type as IP-DSCP.";
      }
    }
    description
      "Description of trust type.";
  }

  typedef lcs-active-type {
    type enumeration {
      enum "deactive" {
        value 0;
        description
          "Specify the license active type as deactivate.";
      }
      enum "active" {
        value 1;
        description
          "Specify the license active type as activate.";
      }
    }
    description
      "License active type.";
  }

  typedef lcs-active-status-type {
    type enumeration {
      enum "unallocated" {
        value 0;
        description
          "Specify the license active status as unallocated.";
      }
      enum "allocated" {
        value 1;
        description
          "Specify the license active status as allocated.";
      }
      enum "activated" {
        value 2;
        description
          "Specify the license active status as ctivated.";
      }
    }
    description
      "License active status type.";
  }

  typedef evpn-pipe-mode {
    type enumeration {
      enum "pipe" {
        value 1;
        description
          "Evpn pipe mode.";
      }
      enum "shortpipe" {
        value 2;
        description
          "Evpn Short Pipe mode.";
      }
      enum "uniform" {
        value 3;
        description
          "Evpn uniform mode.";
      }
    }
    description
      "Evpn pipe mode.";
  }

  typedef evpn-service-class {
    type enumeration {
      enum "be" {
        value 0;
        description
          "Specify the CoS as BE.";
      }
      enum "af1" {
        value 1;
        description
          "Specify the CoS as AF1.";
      }
      enum "af2" {
        value 2;
        description
          "Specify the CoS as AF2.";
      }
      enum "af3" {
        value 3;
        description
          "Specify the CoS as AF3.";
      }
      enum "af4" {
        value 4;
        description
          "Specify the CoS as AF4.";
      }
      enum "ef" {
        value 5;
        description
          "Specify the CoS as EF.";
      }
      enum "cs6" {
        value 6;
        description
          "Specify the CoS as CS6.";
      }
      enum "cs7" {
        value 7;
        description
          "Specify the CoS as CS7.";
      }
    }
    description
      "Description of CoS.";
  }

  typedef evpn-color {
    type enumeration {
      enum "green" {
        value 0;
        description
          "Specify the packet color as green.";
      }
      enum "yellow" {
        value 1;
        description
          "Specify the packet color as yellow.";
      }
      enum "red" {
        value 2;
        description
          "Specify the packet color as red.";
      }
    }
    description
      "Description of packet color.";
  }

  typedef evpn-trust-type {
    type enumeration {
      enum "outpri" {
        value 0;
        description
          "Specify the trust type as OUTTER-VLAN-8021P.";
      }
      enum "inpri" {
        value 1;
        description
          "Specify the trust type as INNER-VLAN-8021P.";
      }
      enum "ipdscp" {
        value 2;
        description
          "Specify the trust type as IP-DSCP.";
      }
    }
    description
      "Description of trust type.";
  }

  augment "/ncs:devices/ncs:template/ncs:ned-id/ncs:config/evpn:evpn" {
    description
      "EVPN configuration.";
    container system {
      description
        "Configure the system configuration of evpn.";
      container port-select {
        description
          "Configure the port selection abort EVPN accessing VLL.";
        leaf flag {
          type string;
          // NCS drop default statement
          description
            "Enable/disable the coupling flag in the EVPN-accessing-VLL direction.";
        }
      }
      container self-board {
        description
          "Configure evpn reserve-interface enhancement.";
        leaf flag {
          type string;
          // NCS drop default statement
          description
            "Enable/disable the flag to use the internal GRE reserved interfaces to implement public-network-and-private-network decoupling in the BUM forwarding process.";
        }
      }
      container evpn-udp-port {
        description
          "Configure the UDP port.";
        leaf port-id {
          type string;
          description
            "Specifies a port number for a UDP interface.";
        }
      }
    }
  }
  augment "/ncs:devices/ncs:device/ncs:live-status/evpn:evpn" {
    description
      "EVPN configuration.";
    container system {
      tailf:ncs-device-type "netconf";
      tailf:display-when "not(../../../ncs:module) or ../../../ncs:module[ncs:name='huawei-evpn-ext'] or (../../../ncs:live-status-protocol[not(ncs:capability)]) or (../../../ncs:live-status-protocol/ncs:capability/ncs:module[.='huawei-evpn-ext'])";
      description
        "Configure the system configuration of evpn.";
      container port-select {
        description
          "Configure the port selection abort EVPN accessing VLL.";
        leaf flag {
          type boolean;
          // NCS drop default statement
          description
            "Enable/disable the coupling flag in the EVPN-accessing-VLL direction.";
        }
      }
      container self-board {
        description
          "Configure evpn reserve-interface enhancement.";
        leaf flag {
          type boolean;
          // NCS drop default statement
          description
            "Enable/disable the flag to use the internal GRE reserved interfaces to implement public-network-and-private-network decoupling in the BUM forwarding process.";
        }
      }
      container evpn-udp-port {
        description
          "Configure the UDP port.";
        leaf port-id {
          type uint32 {
            range "1025..65535";
          }
          description
            "Specifies a port number for a UDP interface.";
        }
      }
    }
  }
  augment "/ncs:devices/ncs:device/ncs:config/evpn:evpn" {
    description
      "EVPN configuration.";
    container system {
      tailf:ncs-device-type "netconf";
      tailf:display-when "not(../../../ncs:module) or ../../../ncs:module[ncs:name='huawei-evpn-ext']";
      description
        "Configure the system configuration of evpn.";
      container port-select {
        description
          "Configure the port selection abort EVPN accessing VLL.";
        leaf flag {
          type boolean;
          default "true";
          description
            "Enable/disable the coupling flag in the EVPN-accessing-VLL direction.";
        }
      }
      container self-board {
        description
          "Configure evpn reserve-interface enhancement.";
        leaf flag {
          type boolean;
          default "false";
          description
            "Enable/disable the flag to use the internal GRE reserved interfaces to implement public-network-and-private-network decoupling in the BUM forwarding process.";
        }
      }
      container evpn-udp-port {
        description
          "Configure the UDP port.";
        leaf port-id {
          type uint32 {
            range "1025..65535";
          }
          description
            "Specifies a port number for a UDP interface.";
        }
      }
    }
  }
  augment "/ncs:devices/ncs:template/ncs:ned-id/ncs:config/evpn:evpn/evpn:instances/evpn:instance/evpn:normal-evpn" {
    description
      "Normal evpn pipe configuration.";
    container pipe {
      description
        "Configure the diffserv mode of evpn.";
      leaf split-mode {
        type string;
        // NCS drop must statement
        // NCS drop default statement
        description
          "Enable/disable split mode.";
      }
      leaf pipe-mode {
        // NCS drop when statement
        type ncs_template_evpn-pipe-mode;
        // NCS drop must statement
        // NCS drop default statement
        description
          "Specify the pipe mode.";
      }
      leaf ingress-pipe-mode {
        // NCS drop when statement
        type ncs_template_evpn-pipe-mode;
        // NCS drop must statement
        // NCS drop default statement
        description
          "Specify the ingress pipe mode.";
      }
      leaf egress-pipe-mode {
        // NCS drop when statement
        type ncs_template_evpn-pipe-mode;
        // NCS drop must statement
        // NCS drop default statement
        description
          "Specify the egress pipe mode.";
      }
      leaf service-class {
        // NCS drop when statement
        type ncs_template_evpn-service-class;
        // NCS drop must statement
        // NCS drop default statement
        description
          "Specify the CoS.";
      }
      leaf color {
        // NCS drop when statement
        type ncs_template_evpn-color;
        // NCS drop must statement
        // NCS drop default statement
        description
          "Specify the color of packets.";
      }
      leaf domain-name {
        // NCS drop when statement
        type string;
        // NCS drop must statement
        // NCS drop default statement
        description
          "DS domain name.";
      }
      leaf trust-type {
        // NCS drop when statement
        type ncs_template_evpn-trust-type;
        // NCS drop must statement
        // NCS drop default statement
        description
          "Specify the trust type.";
      }
    }
    container reserve-if-switch {
      description
        "Configure EVPN broadcast fast switching.";
      leaf enable {
        type string;
        // NCS drop default statement
        description
          "Enable/disable the flag of EVPN broadcast fast switching.";
      }
    }
  }
  augment "/ncs:devices/ncs:device/ncs:live-status/evpn:evpn/evpn:instances/evpn:instance/evpn:normal-evpn" {
    description
      "Normal evpn pipe configuration.";
    container pipe {
      tailf:ncs-device-type "netconf";
      tailf:display-when "not(../../../../../../ncs:module) or ../../../../../../ncs:module[ncs:name='huawei-evpn-ext'] or (../../../../../../ncs:live-status-protocol[not(ncs:capability)]) or (../../../../../../ncs:live-status-protocol/ncs:capability/ncs:module[.='huawei-evpn-ext'])";
      description
        "Configure the diffserv mode of evpn.";
      leaf split-mode {
        type boolean;
        // NCS drop must statement
        // NCS drop default statement
        description
          "Enable/disable split mode.";
      }
      leaf pipe-mode {
        // NCS drop when statement
        type live_ncs_evpn-pipe-mode;
        // NCS drop must statement
        // NCS drop default statement
        description
          "Specify the pipe mode.";
      }
      leaf ingress-pipe-mode {
        // NCS drop when statement
        type live_ncs_evpn-pipe-mode;
        // NCS drop must statement
        // NCS drop default statement
        description
          "Specify the ingress pipe mode.";
      }
      leaf egress-pipe-mode {
        // NCS drop when statement
        type live_ncs_evpn-pipe-mode;
        // NCS drop must statement
        // NCS drop default statement
        description
          "Specify the egress pipe mode.";
      }
      leaf service-class {
        // NCS drop when statement
        type live_ncs_evpn-service-class;
        // NCS drop must statement
        // NCS drop default statement
        description
          "Specify the CoS.";
      }
      leaf color {
        // NCS drop when statement
        type live_ncs_evpn-color;
        // NCS drop must statement
        // NCS drop default statement
        description
          "Specify the color of packets.";
      }
      leaf domain-name {
        // NCS drop when statement
        type leafref {
          path "/ncs:devices/ncs:device/ncs:live-status/qos:qos/qos:classifier-template/qos:diffserv-domains/qos:diffserv-domain/qos:name" {
            tailf:xpath-root 3;
          }
        }
        // NCS drop must statement
        // NCS drop default statement
        description
          "DS domain name.";
      }
      leaf trust-type {
        // NCS drop when statement
        type live_ncs_evpn-trust-type;
        // NCS drop must statement
        // NCS drop default statement
        description
          "Specify the trust type.";
      }
    }
    container reserve-if-switch {
      tailf:ncs-device-type "netconf";
      tailf:display-when "not(../../../../../../ncs:module) or ../../../../../../ncs:module[ncs:name='huawei-evpn-ext'] or (../../../../../../ncs:live-status-protocol[not(ncs:capability)]) or (../../../../../../ncs:live-status-protocol/ncs:capability/ncs:module[.='huawei-evpn-ext'])";
      description
        "Configure EVPN broadcast fast switching.";
      leaf enable {
        type boolean;
        // NCS drop default statement
        description
          "Enable/disable the flag of EVPN broadcast fast switching.";
      }
    }
  }
  augment "/ncs:devices/ncs:device/ncs:config/evpn:evpn/evpn:instances/evpn:instance/evpn:normal-evpn" {
    description
      "Normal evpn pipe configuration.";
    container pipe {
      tailf:ncs-device-type "netconf";
      tailf:display-when "not(../../../../../../ncs:module) or ../../../../../../ncs:module[ncs:name='huawei-evpn-ext']";
      description
        "Configure the diffserv mode of evpn.";
      leaf split-mode {
        type boolean;
        must "((../split-mode='false' and not(../ingress-pipe-mode) and not(../egress-pipe-mode) and ../pipe-mode) or (../split-mode='true' and not(../pipe-mode) and ../ingress-pipe-mode and ../egress-pipe-mode and not(../ingress-pipe-mode='uniform' and ../egress-pipe-mode='uniform')))" {
          tailf:xpath-root 3;
        }
        default "false";
        description
          "Enable/disable split mode.";
      }
      leaf pipe-mode {
        when "../split-mode='false'" {
          tailf:xpath-root 3;
        }
        type evpn-pipe-mode;
        must "(../split-mode='false') and ((../pipe-mode='pipe' and (../service-class) and (../color)) or (../pipe-mode='shortpipe' and (../service-class) and (../color) and (../domain-name)) or (../pipe-mode='uniform'))" {
          tailf:xpath-root 3;
        }
        default "uniform";
        description
          "Specify the pipe mode.";
      }
      leaf ingress-pipe-mode {
        when "../split-mode='true'" {
          tailf:xpath-root 3;
        }
        type evpn-pipe-mode;
        must "((../split-mode='true') and (((../service-class) and (../color) and (../ingress-pipe-mode='shortpipe' or ../ingress-pipe-mode='pipe')) or (../ingress-pipe-mode='uniform' and ../egress-pipe-mode!='uniform')))" {
          tailf:xpath-root 3;
        }
        default "uniform";
        description
          "Specify the ingress pipe mode.";
      }
      leaf egress-pipe-mode {
        when "../split-mode='true'" {
          tailf:xpath-root 3;
        }
        type evpn-pipe-mode;
        must "((../split-mode='true') and (((../domain-name) and (../trust-type) and (../egress-pipe-mode='shortpipe')) or (../egress-pipe-mode='pipe') or (../egress-pipe-mode='uniform' and ../ingress-pipe-mode!='uniform')))" {
          tailf:xpath-root 3;
        }
        default "uniform";
        description
          "Specify the egress pipe mode.";
      }
      leaf service-class {
        when "(../pipe-mode='pipe' or ../pipe-mode='shortpipe' or ../ingress-pipe-mode='pipe' or ../ingress-pipe-mode='shortpipe')" {
          tailf:xpath-root 3;
        }
        type evpn-service-class;
        must "(../pipe-mode='pipe' or ../pipe-mode='shortpipe' or ../ingress-pipe-mode='pipe' or ../ingress-pipe-mode='shortpipe')" {
          tailf:xpath-root 3;
        }
        default "be";
        description
          "Specify the CoS.";
      }
      leaf color {
        when "(../pipe-mode='pipe' or ../pipe-mode='shortpipe' or ../ingress-pipe-mode='pipe' or ../ingress-pipe-mode='shortpipe')" {
          tailf:xpath-root 3;
        }
        type evpn-color;
        must "(../pipe-mode='pipe' or ../pipe-mode='shortpipe' or ../ingress-pipe-mode='pipe' or ../ingress-pipe-mode='shortpipe')" {
          tailf:xpath-root 3;
        }
        default "green";
        description
          "Specify the color of packets.";
      }
      leaf domain-name {
        when "(../pipe-mode='shortpipe' or ../egress-pipe-mode='shortpipe')" {
          tailf:xpath-root 3;
        }
        type leafref {
          path "/ncs:devices/ncs:device/ncs:config/qos:qos/qos:classifier-template/qos:diffserv-domains/qos:diffserv-domain/qos:name" {
            tailf:xpath-root 3;
          }
        }
        must "(../pipe-mode='shortpipe' or ../egress-pipe-mode='shortpipe')" {
          tailf:xpath-root 3;
        }
        default "default";
        description
          "DS domain name.";
      }
      leaf trust-type {
        when "../egress-pipe-mode='shortpipe'" {
          tailf:xpath-root 3;
        }
        type evpn-trust-type;
        must "../egress-pipe-mode='shortpipe'" {
          tailf:xpath-root 3;
        }
        default "outpri";
        description
          "Specify the trust type.";
      }
    }
    container reserve-if-switch {
      tailf:ncs-device-type "netconf";
      tailf:display-when "not(../../../../../../ncs:module) or ../../../../../../ncs:module[ncs:name='huawei-evpn-ext']";
      description
        "Configure EVPN broadcast fast switching.";
      leaf enable {
        type boolean;
        default "false";
        description
          "Enable/disable the flag of EVPN broadcast fast switching.";
      }
    }
  }
  augment "/ncs:devices/ncs:template/ncs:ned-id/ncs:config/evpn:evpn/evpn:instances/evpn:instance/evpn:bd-evpn" {
    description
      "BD evpn pipe configuration.";
    container pipe {
      description
        "Configure the diffserv mode of evpn.";
      leaf split-mode {
        type string;
        // NCS drop must statement
        // NCS drop default statement
        description
          "Enable/disable split mode.";
      }
      leaf pipe-mode {
        // NCS drop when statement
        type ncs_template_evpn-pipe-mode;
        // NCS drop must statement
        // NCS drop default statement
        description
          "Specify the pipe mode.";
      }
      leaf ingress-pipe-mode {
        // NCS drop when statement
        type ncs_template_evpn-pipe-mode;
        // NCS drop must statement
        // NCS drop default statement
        description
          "Specify the ingress pipe mode.";
      }
      leaf egress-pipe-mode {
        // NCS drop when statement
        type ncs_template_evpn-pipe-mode;
        // NCS drop must statement
        // NCS drop default statement
        description
          "Specify the egress pipe mode.";
      }
      leaf service-class {
        // NCS drop when statement
        type ncs_template_evpn-service-class;
        // NCS drop must statement
        // NCS drop default statement
        description
          "Specify the CoS.";
      }
      leaf color {
        // NCS drop when statement
        type ncs_template_evpn-color;
        // NCS drop must statement
        // NCS drop default statement
        description
          "Specify the color of packets.";
      }
      leaf domain-name {
        // NCS drop when statement
        type string;
        // NCS drop must statement
        // NCS drop default statement
        description
          "DS domain name.";
      }
      leaf trust-type {
        // NCS drop when statement
        type ncs_template_evpn-trust-type;
        // NCS drop must statement
        // NCS drop default statement
        description
          "Specify the trust type.";
      }
    }
  }
  augment "/ncs:devices/ncs:device/ncs:live-status/evpn:evpn/evpn:instances/evpn:instance/evpn:bd-evpn" {
    description
      "BD evpn pipe configuration.";
    container pipe {
      tailf:ncs-device-type "netconf";
      tailf:display-when "not(../../../../../../ncs:module) or ../../../../../../ncs:module[ncs:name='huawei-evpn-ext'] or (../../../../../../ncs:live-status-protocol[not(ncs:capability)]) or (../../../../../../ncs:live-status-protocol/ncs:capability/ncs:module[.='huawei-evpn-ext'])";
      description
        "Configure the diffserv mode of evpn.";
      leaf split-mode {
        type boolean;
        // NCS drop must statement
        // NCS drop default statement
        description
          "Enable/disable split mode.";
      }
      leaf pipe-mode {
        // NCS drop when statement
        type live_ncs_evpn-pipe-mode;
        // NCS drop must statement
        // NCS drop default statement
        description
          "Specify the pipe mode.";
      }
      leaf ingress-pipe-mode {
        // NCS drop when statement
        type live_ncs_evpn-pipe-mode;
        // NCS drop must statement
        // NCS drop default statement
        description
          "Specify the ingress pipe mode.";
      }
      leaf egress-pipe-mode {
        // NCS drop when statement
        type live_ncs_evpn-pipe-mode;
        // NCS drop must statement
        // NCS drop default statement
        description
          "Specify the egress pipe mode.";
      }
      leaf service-class {
        // NCS drop when statement
        type live_ncs_evpn-service-class;
        // NCS drop must statement
        // NCS drop default statement
        description
          "Specify the CoS.";
      }
      leaf color {
        // NCS drop when statement
        type live_ncs_evpn-color;
        // NCS drop must statement
        // NCS drop default statement
        description
          "Specify the color of packets.";
      }
      leaf domain-name {
        // NCS drop when statement
        type leafref {
          path "/ncs:devices/ncs:device/ncs:live-status/qos:qos/qos:classifier-template/qos:diffserv-domains/qos:diffserv-domain/qos:name" {
            tailf:xpath-root 3;
          }
        }
        // NCS drop must statement
        // NCS drop default statement
        description
          "DS domain name.";
      }
      leaf trust-type {
        // NCS drop when statement
        type live_ncs_evpn-trust-type;
        // NCS drop must statement
        // NCS drop default statement
        description
          "Specify the trust type.";
      }
    }
  }
  augment "/ncs:devices/ncs:device/ncs:config/evpn:evpn/evpn:instances/evpn:instance/evpn:bd-evpn" {
    description
      "BD evpn pipe configuration.";
    container pipe {
      tailf:ncs-device-type "netconf";
      tailf:display-when "not(../../../../../../ncs:module) or ../../../../../../ncs:module[ncs:name='huawei-evpn-ext']";
      description
        "Configure the diffserv mode of evpn.";
      leaf split-mode {
        type boolean;
        must "((../split-mode='false' and not(../ingress-pipe-mode) and not(../egress-pipe-mode) and ../pipe-mode) or (../split-mode='true' and not(../pipe-mode) and ../ingress-pipe-mode and ../egress-pipe-mode and not(../ingress-pipe-mode='uniform' and ../egress-pipe-mode='uniform')))" {
          tailf:xpath-root 3;
        }
        default "false";
        description
          "Enable/disable split mode.";
      }
      leaf pipe-mode {
        when "../split-mode='false'" {
          tailf:xpath-root 3;
        }
        type evpn-pipe-mode;
        must "(../split-mode='false') and ((../pipe-mode='pipe' and (../service-class) and (../color)) or (../pipe-mode='shortpipe' and (../service-class) and (../color) and (../domain-name)) or (../pipe-mode='uniform'))" {
          tailf:xpath-root 3;
        }
        default "uniform";
        description
          "Specify the pipe mode.";
      }
      leaf ingress-pipe-mode {
        when "../split-mode='true'" {
          tailf:xpath-root 3;
        }
        type evpn-pipe-mode;
        must "((../split-mode='true') and (((../service-class) and (../color) and (../ingress-pipe-mode='shortpipe' or ../ingress-pipe-mode='pipe')) or (../ingress-pipe-mode='uniform' and ../egress-pipe-mode!='uniform')))" {
          tailf:xpath-root 3;
        }
        default "uniform";
        description
          "Specify the ingress pipe mode.";
      }
      leaf egress-pipe-mode {
        when "../split-mode='true'" {
          tailf:xpath-root 3;
        }
        type evpn-pipe-mode;
        must "((../split-mode='true') and (((../domain-name) and (../trust-type) and (../egress-pipe-mode='shortpipe')) or (../egress-pipe-mode='pipe') or (../egress-pipe-mode='uniform' and ../ingress-pipe-mode!='uniform')))" {
          tailf:xpath-root 3;
        }
        default "uniform";
        description
          "Specify the egress pipe mode.";
      }
      leaf service-class {
        when "(../pipe-mode='pipe' or ../pipe-mode='shortpipe' or ../ingress-pipe-mode='pipe' or ../ingress-pipe-mode='shortpipe')" {
          tailf:xpath-root 3;
        }
        type evpn-service-class;
        must "(../pipe-mode='pipe' or ../pipe-mode='shortpipe' or ../ingress-pipe-mode='pipe' or ../ingress-pipe-mode='shortpipe')" {
          tailf:xpath-root 3;
        }
        default "be";
        description
          "Specify the CoS.";
      }
      leaf color {
        when "(../pipe-mode='pipe' or ../pipe-mode='shortpipe' or ../ingress-pipe-mode='pipe' or ../ingress-pipe-mode='shortpipe')" {
          tailf:xpath-root 3;
        }
        type evpn-color;
        must "(../pipe-mode='pipe' or ../pipe-mode='shortpipe' or ../ingress-pipe-mode='pipe' or ../ingress-pipe-mode='shortpipe')" {
          tailf:xpath-root 3;
        }
        default "green";
        description
          "Specify the color of packets.";
      }
      leaf domain-name {
        when "(../pipe-mode='shortpipe' or ../egress-pipe-mode='shortpipe')" {
          tailf:xpath-root 3;
        }
        type leafref {
          path "/ncs:devices/ncs:device/ncs:config/qos:qos/qos:classifier-template/qos:diffserv-domains/qos:diffserv-domain/qos:name" {
            tailf:xpath-root 3;
          }
        }
        must "(../pipe-mode='shortpipe' or ../egress-pipe-mode='shortpipe')" {
          tailf:xpath-root 3;
        }
        default "default";
        description
          "DS domain name.";
      }
      leaf trust-type {
        when "../egress-pipe-mode='shortpipe'" {
          tailf:xpath-root 3;
        }
        type evpn-trust-type;
        must "../egress-pipe-mode='shortpipe'" {
          tailf:xpath-root 3;
        }
        default "outpri";
        description
          "Specify the trust type.";
      }
    }
  }
  augment "/ncs:devices/ncs:template/ncs:ned-id/ncs:config/lcs:license/lcs:license-items/lcs:license-item" {
    status deprecated;
    description
      "License resource usage.";
    container lcs-port-evpns {
      // NCS drop when statement
      status deprecated;
      description
        "List of evpn port license information.";
      list lcs-port-evpn {
        // NCS patched for predictable order
        ordered-by user;
        key "position";
        status deprecated;
        description
          "Configure evpn port license.";
        leaf position {
          type string;
          status deprecated;
          description
            "Port position.";
        }
      }
    }
    container lcs-port-vxlans {
      // NCS drop when statement
      status deprecated;
      description
        "List of vxlan port license information.";
      list lcs-port-vxlan {
        // NCS patched for predictable order
        ordered-by user;
        key "position";
        status deprecated;
        description
          "Configure vxlan port license.";
        leaf position {
          type string;
          status deprecated;
          description
            "VXLAN port license interface position, the format is slotid/cardid/portid.";
        }
      }
    }
  }
  augment "/ncs:devices/ncs:device/ncs:live-status/lcs:license/lcs:license-items/lcs:license-item" {
    status deprecated;
    description
      "License resource usage.";
    container lcs-port-evpns {
      tailf:ncs-device-type "netconf";
      tailf:display-when "not(../../../../../ncs:module) or ../../../../../ncs:module[ncs:name='huawei-evpn-ext'] or (../../../../../ncs:live-status-protocol[not(ncs:capability)]) or (../../../../../ncs:live-status-protocol/ncs:capability/ncs:module[.='huawei-evpn-ext'])";
      // NCS drop when statement
      status deprecated;
      description
        "List of evpn port license information.";
      list lcs-port-evpn {
        key "position";
        status deprecated;
        description
          "Configure evpn port license.";
        leaf position {
          type leafref {
            path "/ncs:devices/ncs:device/ncs:live-status/lcs:license/pic:lcs-ports/pic:port-basic/pic:position" {
              tailf:xpath-root 3;
            }
          }
          status deprecated;
          description
            "Port position.";
        }
      }
    }
    container lcs-port-vxlans {
      tailf:ncs-device-type "netconf";
      tailf:display-when "not(../../../../../ncs:module) or ../../../../../ncs:module[ncs:name='huawei-evpn-ext'] or (../../../../../ncs:live-status-protocol[not(ncs:capability)]) or (../../../../../ncs:live-status-protocol/ncs:capability/ncs:module[.='huawei-evpn-ext'])";
      // NCS drop when statement
      status deprecated;
      description
        "List of vxlan port license information.";
      list lcs-port-vxlan {
        key "position";
        status deprecated;
        description
          "Configure vxlan port license.";
        leaf position {
          type leafref {
            path "/ncs:devices/ncs:device/ncs:live-status/lcs:license/pic:lcs-ports/pic:port-basic/pic:position" {
              tailf:xpath-root 3;
            }
          }
          status deprecated;
          description
            "VXLAN port license interface position, the format is slotid/cardid/portid.";
        }
      }
    }
  }
  augment "/ncs:devices/ncs:device/ncs:config/lcs:license/lcs:license-items/lcs:license-item" {
    status deprecated;
    description
      "License resource usage.";
    container lcs-port-evpns {
      tailf:ncs-device-type "netconf";
      tailf:display-when "not(../../../../../ncs:module) or ../../../../../ncs:module[ncs:name='huawei-evpn-ext']";
      when "../lcs:name='LCR5S40NEVN0P' or ../lcs:name='LCR9S9KNEVN0L' or ../lcs:name='LCR9S9KXEVN0L' or ../lcs:name='LCR5S40XEVN0P' or ../lcs:name='LCR9S9KNEVN0P' or ../lcs:name='LCR9S9KXEVN0P' or ../lcs:name='LCR5S5KNEVN0P' or ../lcs:name='LCR5S5KKEVN0P' or ../lcs:name='LCR5S5KXEVN0P' or ../lcs:name='LCX6S60NEVPAP' or ../lcs:name='LCX6S60XEVPAP' or ../lcs:name='LCR9S9KNEVN0Q' or ../lcs:name='LCR6S00NEVNAQ' or ../lcs:name='LCR5S40VEVN0P' or ../lcs:name='LCR5S40YEVN0P' or ../lcs:name='LCX6S00NEVN0P' or ../lcs:name='LCX6S00VEVN0P' or ../lcs:name='LCX6S00YEVN0P' or ../lcs:name='LTNRS69NEVN0P' or ../lcs:name='LTNRS69VEVN0P' or ../lcs:name='LTNRS69YEVN0P' or ../lcs:name='LCR8S00EVPNC2' or ../lcs:name='LCR8S00EVPNC4' or ../lcs:name='LCR8SF0EVPNC1' or ../lcs:name='LCR8SF0EVPNC4' or ../lcs:name='LCR5S00EVPNC2' or ../lcs:name='LCR5S00EVPNC4' or ../lcs:name='LTNRS00EVPNC2' or ../lcs:name='LTNRS00EVPNC4'" {
        tailf:xpath-root 3;
      }
      status deprecated;
      description
        "List of evpn port license information.";
      list lcs-port-evpn {
        key "position";
        status deprecated;
        description
          "Configure evpn port license.";
        leaf position {
          type leafref {
            path "/ncs:devices/ncs:device/ncs:config/lcs:license/pic:lcs-ports/pic:port-basic/pic:position" {
              tailf:xpath-root 3;
            }
          }
          status deprecated;
          description
            "Port position.";
        }
      }
    }
    container lcs-port-vxlans {
      tailf:ncs-device-type "netconf";
      tailf:display-when "not(../../../../../ncs:module) or ../../../../../ncs:module[ncs:name='huawei-evpn-ext']";
      when "../lcs:name='LCR5S40NXLA0P' or ../lcs:name='LCR5S40XLAN0P' or ../lcs:name='LCR5S40XLAV0P' or ../lcs:name='LCR5S40XLAY0P' or ../lcs:name='LCR5S40YXLA0P' or ../lcs:name='LCR5S40XLAX0P' or ../lcs:name='LCR5S40XXLA0P' or ../lcs:name='LCX6S00XLAN0P' or ../lcs:name='LCX6S00NXLA0P' or ../lcs:name='LCX6S00VXLA0P' or ../lcs:name='LCX6S00XLAY0P' or ../lcs:name='LCX6S00YXLA0P' or ../lcs:name='LCX6S00XLAX0P' or ../lcs:name='LCX6S00XXLA0P' or ../lcs:name='LTNRS69NXLA0P' or ../lcs:name='LTNRS69VXLA0P' or ../lcs:name='LTNRS69YXLA0P' or ../lcs:name='LTNRS69XXLA0P' or ../lcs:name='LCR9S9KNXLA0S' or ../lcs:name='LCR9S9KNXLA0Q' or ../lcs:name='LCR9S9KNXLA0R' or ../lcs:name='LCR9S9KNXLA0P' or ../lcs:name='LCR9S9KXXLAQ' or ../lcs:name='LCR9S9KXXLA0P'" {
        tailf:xpath-root 3;
      }
      status deprecated;
      description
        "List of vxlan port license information.";
      list lcs-port-vxlan {
        key "position";
        status deprecated;
        description
          "Configure vxlan port license.";
        leaf position {
          type leafref {
            path "/ncs:devices/ncs:device/ncs:config/lcs:license/pic:lcs-ports/pic:port-basic/pic:position" {
              tailf:xpath-root 3;
            }
          }
          status deprecated;
          description
            "VXLAN port license interface position, the format is slotid/cardid/portid.";
        }
      }
    }
  }
  augment "/ncs:devices/ncs:template/ncs:ned-id/ncs:config/lcs:license" {
    description
      "License resource usage.";
    container lcs-port-evpns {
      description
        "List of evpn port license information.";
      list lcs-port-evpn {
        // NCS patched for predictable order
        ordered-by user;
        key "position";
        description
          "Configure evpn port license.";
        leaf position {
          type string;
          description
            "Port position.";
        }
        // NCS drop config false leaf 'active-status'
      }
    }
    container lcs-port-vxlans {
      description
        "List of vxlan port license information.";
      list lcs-port-vxlan {
        // NCS patched for predictable order
        ordered-by user;
        key "position";
        description
          "Configure vxlan port license.";
        leaf position {
          type string;
          description
            "VXLAN port license interface position, the format is slotid/cardid/portid.";
        }
        // NCS drop config false leaf 'active-status'
      }
    }
  }
  augment "/ncs:devices/ncs:device/ncs:live-status/lcs:license" {
    description
      "License resource usage.";
    container lcs-port-evpns {
      tailf:ncs-device-type "netconf";
      tailf:display-when "not(../../../ncs:module) or ../../../ncs:module[ncs:name='huawei-evpn-ext'] or (../../../ncs:live-status-protocol[not(ncs:capability)]) or (../../../ncs:live-status-protocol/ncs:capability/ncs:module[.='huawei-evpn-ext'])";
      description
        "List of evpn port license information.";
      list lcs-port-evpn {
        key "position";
        description
          "Configure evpn port license.";
        leaf position {
          type leafref {
            path "/ncs:devices/ncs:device/ncs:live-status/lcs:license/pic:lcs-ports/pic:port-basic/pic:position" {
              tailf:xpath-root 3;
            }
          }
          description
            "Port position.";
        }
        leaf active-status {
          type live_ncs_lcs-active-status-type;
          description
            "Activated state.";
        }
      }
    }
    container lcs-port-vxlans {
      tailf:ncs-device-type "netconf";
      tailf:display-when "not(../../../ncs:module) or ../../../ncs:module[ncs:name='huawei-evpn-ext'] or (../../../ncs:live-status-protocol[not(ncs:capability)]) or (../../../ncs:live-status-protocol/ncs:capability/ncs:module[.='huawei-evpn-ext'])";
      description
        "List of vxlan port license information.";
      list lcs-port-vxlan {
        key "position";
        description
          "Configure vxlan port license.";
        leaf position {
          type leafref {
            path "/ncs:devices/ncs:device/ncs:live-status/lcs:license/pic:lcs-ports/pic:port-basic/pic:position" {
              tailf:xpath-root 3;
            }
          }
          description
            "VXLAN port license interface position, the format is slotid/cardid/portid.";
        }
        leaf active-status {
          type live_ncs_lcs-active-status-type;
          description
            "Activated state.";
        }
      }
    }
  }
  augment "/ncs:devices/ncs:device/ncs:config/lcs:license" {
    description
      "License resource usage.";
    container lcs-port-evpns {
      tailf:ncs-device-type "netconf";
      tailf:display-when "not(../../../ncs:module) or ../../../ncs:module[ncs:name='huawei-evpn-ext']";
      description
        "List of evpn port license information.";
      list lcs-port-evpn {
        key "position";
        description
          "Configure evpn port license.";
        leaf position {
          type leafref {
            path "/ncs:devices/ncs:device/ncs:config/lcs:license/pic:lcs-ports/pic:port-basic/pic:position" {
              tailf:xpath-root 3;
            }
          }
          description
            "Port position.";
        }
        // NCS drop config false leaf 'active-status'
      }
    }
    container lcs-port-vxlans {
      tailf:ncs-device-type "netconf";
      tailf:display-when "not(../../../ncs:module) or ../../../ncs:module[ncs:name='huawei-evpn-ext']";
      description
        "List of vxlan port license information.";
      list lcs-port-vxlan {
        key "position";
        description
          "Configure vxlan port license.";
        leaf position {
          type leafref {
            path "/ncs:devices/ncs:device/ncs:config/lcs:license/pic:lcs-ports/pic:port-basic/pic:position" {
              tailf:xpath-root 3;
            }
          }
          description
            "VXLAN port license interface position, the format is slotid/cardid/portid.";
        }
        // NCS drop config false leaf 'active-status'
      }
    }
  }
}
