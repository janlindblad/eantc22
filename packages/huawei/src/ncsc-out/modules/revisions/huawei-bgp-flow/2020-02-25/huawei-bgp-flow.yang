module huawei-bgp-flow {
  // Generated by yanger -t ncs
  tailf:mount-id "huawei-nc-1.0:huawei-nc-1.0";
  tailf:ncs-device-type "netconf";

  yang-version 1;
  namespace "urn:huawei:yang:huawei-bgp-flow";
  prefix bgp-flow;

  import huawei-extension {
    prefix ext;
  }
  import huawei-network-instance {
    prefix ni;
  }
  import huawei-bgp {
    prefix bgp;
  }
  import huawei-routing-policy {
    prefix rtp;
  }
  import huawei-xpl {
    prefix xpl;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Inter-AS routing protocol that exchanges Network Layer Reachability Information (NLRI) with other BGP systems.";

  revision 2020-02-25 {
    description
      "The YANG descriptions are modified according to new standards.";
    reference "Huawei private.";
  }
  revision 2019-03-22 {
    description
      "Initial revision.";
    reference "Huawei private.";
  }
  ext:task-name "bgp";

  typedef ncs_template_rpd-cap-type {
    type string;
    description
      "The type of FlowSpec Route Policy Distribute.";
  }

  typedef ncs_rpc_notif_rpd-cap-type {
    type enumeration {
      enum "receive" {
        value 1;
        description
          "Converts received BGP FlowSpec routes to common IP routes if these BGP FlowSpec routes carry the RPD attribute.";
      }
    }
    description
      "The type of FlowSpec Route Policy Distribute.";
  }

  typedef live_ncs_rpd-cap-type {
    type enumeration {
      enum "receive" {
        value 1;
        description
          "Converts received BGP FlowSpec routes to common IP routes if these BGP FlowSpec routes carry the RPD attribute.";
      }
    }
    description
      "The type of FlowSpec Route Policy Distribute.";
  }

  typedef rpd-cap-type {
    type enumeration {
      enum "receive" {
        value 1;
        description
          "Converts received BGP FlowSpec routes to common IP routes if these BGP FlowSpec routes carry the RPD attribute.";
      }
    }
    description
      "The type of FlowSpec Route Policy Distribute.";
  }

  grouping ncs_template_bgp-peer-ipv4flow-cap-type {
    description
      "BGP IPv4-flow peer redirect tunnelv6.";
    leaf redirect-tunnelv6 {
      type string;
      // NCS drop default statement
      description
        "Enable/disable the function to handle the extended community attribute redirect-tunnelv6.";
    }
  }

  grouping ncs_rpc_notif_bgp-peer-ipv4flow-cap-type {
    description
      "BGP IPv4-flow peer redirect tunnelv6.";
    leaf redirect-tunnelv6 {
      type boolean;
      default "false";
      description
        "Enable/disable the function to handle the extended community attribute redirect-tunnelv6.";
    }
  }

  grouping live_ncs_bgp-peer-ipv4flow-cap-type {
    description
      "BGP IPv4-flow peer redirect tunnelv6.";
    leaf redirect-tunnelv6 {
      type boolean;
      // NCS drop default statement
      description
        "Enable/disable the function to handle the extended community attribute redirect-tunnelv6.";
    }
  }

  grouping bgp-peer-ipv4flow-cap-type {
    description
      "BGP IPv4-flow peer redirect tunnelv6.";
    leaf redirect-tunnelv6 {
      type boolean;
      default "false";
      description
        "Enable/disable the function to handle the extended community attribute redirect-tunnelv6.";
    }
  }

  augment "/ncs:devices/ncs:template/ncs:ned-id/ncs:config/ni:network-instance/ni:instances/ni:instance/bgp:bgp/bgp:base-process/bgp:afs/bgp:af" {
    description
      "BGP flow address family configuration.";
    container ipv4-flow {
      // NCS drop when statement
      description
        "Configure IPv4-family flow options.";
      container common {
        description
          "Configure BGP IPv4-family flow common options.";
        leaf route-match-destination {
          type string;
          // NCS drop default statement
          description
            "Enable/disable matching the route destination.";
        }
        leaf validation-mode-as {
          type string;
          // NCS drop default statement
          description
            "Enable/disable using the route validation-mode include-as command, you can configure flow-route validation mode include as.";
        }
        leaf redirect-ip-relay-tnl-enable {
          // NCS drop when statement
          type string;
          // NCS drop default statement
          description
            "Enable/disable flow-route recursive-lookup tunnel.";
        }
        leaf redirect-ipv6-relay-tnl-sel-name {
          // NCS drop when statement
          type string;
          description
            "Flow-route Tunnel Selector Name.";
        }
        leaf redirect-ip-relay-tunnel-selector-name {
          // NCS drop when statement
          type string;
          description
            "Specifies the name of a tunnel selector.";
        }
        uses bgp:ncs_template_reflector-cluster-type;
        leaf reflect-between-client {
          type string;
          // NCS drop default statement
          description
            "Enable/disable route reflection between clients. If clients of a route reflector (RR) are fully meshed, you can disable route reflection among clients to reduce the cost.";
        }
        leaf check-origin-as-enable {
          // NCS drop when statement
          type string;
          // NCS drop default statement
          description
            "Enable/disable the received BGP Flow Specification routes carrying a filtering rule that is based on the origin AS number of the destination IP address to be valid.";
        }
      }
      uses bgp:ncs_template_routing-table-rib-only-type;
    }
    container ipv6-flow {
      // NCS drop when statement
      description
        "Configure IPv6-family flow options.";
      container common {
        description
          "Configure BGP IPv6-family flow common options.";
        leaf route-match-destination {
          type string;
          // NCS drop default statement
          description
            "Enable/disable matchingatch the route destination.";
        }
        leaf validation-mode-as {
          type string;
          // NCS drop default statement
          description
            "Enable/disable using the route validation-mode include-as command, you can configure flow-route validation mode include as.";
        }
        leaf reflect-between-client {
          type string;
          // NCS drop default statement
          description
            "Enable/disable route reflection between clients. If clients of a route reflector (RR) are fully meshed, you can disable route reflection among clients to reduce the cost.";
        }
        uses bgp:ncs_template_reflector-cluster-type;
      }
      uses bgp:ncs_template_routing-table-rib-only-type;
    }
    container vpnv4-flow {
      // NCS drop when statement
      description
        "Configure IPv4 VPN flow options.";
      container common {
        description
          "Configure IPv4 VPN flow common options.";
        uses bgp:ncs_template_vpn-target-type;
        uses bgp:ncs_template_reflector-cluster-type;
        leaf reflect-between-client {
          type string;
          // NCS drop default statement
          description
            "Enable/disable route reflection between clients.";
        }
      }
    }
    container vpnv6-flow {
      // NCS drop when statement
      description
        "Configure IPv6 VPN flow options.";
      container common {
        description
          "Configure IPv6 VPN flow common options.";
        uses bgp:ncs_template_vpn-target-type;
        uses bgp:ncs_template_reflector-cluster-type;
        leaf reflect-between-client {
          type string;
          // NCS drop default statement
          description
            "Enable/disable route reflection between clients.";
        }
      }
    }
  }
  augment "/ncs:devices/ncs:device/ncs:live-status/ni:network-instance/ni:instances/ni:instance/bgp:bgp/bgp:base-process/bgp:afs/bgp:af" {
    description
      "BGP flow address family configuration.";
    container ipv4-flow {
      tailf:ncs-device-type "netconf";
      tailf:display-when "not(../../../../../../../../../ncs:module) or ../../../../../../../../../ncs:module[ncs:name='huawei-bgp-flow'] or (../../../../../../../../../ncs:live-status-protocol[not(ncs:capability)]) or (../../../../../../../../../ncs:live-status-protocol/ncs:capability/ncs:module[.='huawei-bgp-flow'])";
      // NCS drop when statement
      description
        "Configure IPv4-family flow options.";
      container common {
        description
          "Configure BGP IPv4-family flow common options.";
        leaf route-match-destination {
          type boolean;
          // NCS drop default statement
          description
            "Enable/disable matching the route destination.";
        }
        leaf validation-mode-as {
          type boolean;
          // NCS drop default statement
          description
            "Enable/disable using the route validation-mode include-as command, you can configure flow-route validation mode include as.";
        }
        leaf redirect-ip-relay-tnl-enable {
          // NCS drop when statement
          type boolean;
          // NCS drop default statement
          description
            "Enable/disable flow-route recursive-lookup tunnel.";
        }
        leaf redirect-ipv6-relay-tnl-sel-name {
          // NCS drop when statement
          type leafref {
            path "/ncs:devices/ncs:device/ncs:live-status/rtp:routing-policy/rtp:tunnel-selectors/rtp:tunnel-selector/rtp:name" {
              tailf:xpath-root 3;
            }
          }
          description
            "Flow-route Tunnel Selector Name.";
        }
        leaf redirect-ip-relay-tunnel-selector-name {
          // NCS drop when statement
          type leafref {
            path "/ncs:devices/ncs:device/ncs:live-status/rtp:routing-policy/rtp:tunnel-selectors/rtp:tunnel-selector/rtp:name" {
              tailf:xpath-root 3;
            }
          }
          description
            "Specifies the name of a tunnel selector.";
        }
        uses bgp:live_ncs_reflector-cluster-type;
        leaf reflect-between-client {
          type boolean;
          // NCS drop default statement
          description
            "Enable/disable route reflection between clients. If clients of a route reflector (RR) are fully meshed, you can disable route reflection among clients to reduce the cost.";
        }
        leaf check-origin-as-enable {
          // NCS drop when statement
          type boolean;
          // NCS drop default statement
          description
            "Enable/disable the received BGP Flow Specification routes carrying a filtering rule that is based on the origin AS number of the destination IP address to be valid.";
        }
      }
      uses bgp:live_ncs_routing-table-rib-only-type;
    }
    container ipv6-flow {
      tailf:ncs-device-type "netconf";
      tailf:display-when "not(../../../../../../../../../ncs:module) or ../../../../../../../../../ncs:module[ncs:name='huawei-bgp-flow'] or (../../../../../../../../../ncs:live-status-protocol[not(ncs:capability)]) or (../../../../../../../../../ncs:live-status-protocol/ncs:capability/ncs:module[.='huawei-bgp-flow'])";
      // NCS drop when statement
      description
        "Configure IPv6-family flow options.";
      container common {
        description
          "Configure BGP IPv6-family flow common options.";
        leaf route-match-destination {
          type boolean;
          // NCS drop default statement
          description
            "Enable/disable matchingatch the route destination.";
        }
        leaf validation-mode-as {
          type boolean;
          // NCS drop default statement
          description
            "Enable/disable using the route validation-mode include-as command, you can configure flow-route validation mode include as.";
        }
        leaf reflect-between-client {
          type boolean;
          // NCS drop default statement
          description
            "Enable/disable route reflection between clients. If clients of a route reflector (RR) are fully meshed, you can disable route reflection among clients to reduce the cost.";
        }
        uses bgp:live_ncs_reflector-cluster-type;
      }
      uses bgp:live_ncs_routing-table-rib-only-type;
    }
    container vpnv4-flow {
      tailf:ncs-device-type "netconf";
      tailf:display-when "not(../../../../../../../../../ncs:module) or ../../../../../../../../../ncs:module[ncs:name='huawei-bgp-flow'] or (../../../../../../../../../ncs:live-status-protocol[not(ncs:capability)]) or (../../../../../../../../../ncs:live-status-protocol/ncs:capability/ncs:module[.='huawei-bgp-flow'])";
      // NCS drop when statement
      description
        "Configure IPv4 VPN flow options.";
      container common {
        description
          "Configure IPv4 VPN flow common options.";
        uses bgp:live_ncs_vpn-target-type;
        uses bgp:live_ncs_reflector-cluster-type;
        leaf reflect-between-client {
          type boolean;
          // NCS drop default statement
          description
            "Enable/disable route reflection between clients.";
        }
      }
    }
    container vpnv6-flow {
      tailf:ncs-device-type "netconf";
      tailf:display-when "not(../../../../../../../../../ncs:module) or ../../../../../../../../../ncs:module[ncs:name='huawei-bgp-flow'] or (../../../../../../../../../ncs:live-status-protocol[not(ncs:capability)]) or (../../../../../../../../../ncs:live-status-protocol/ncs:capability/ncs:module[.='huawei-bgp-flow'])";
      // NCS drop when statement
      description
        "Configure IPv6 VPN flow options.";
      container common {
        description
          "Configure IPv6 VPN flow common options.";
        uses bgp:live_ncs_vpn-target-type;
        uses bgp:live_ncs_reflector-cluster-type;
        leaf reflect-between-client {
          type boolean;
          // NCS drop default statement
          description
            "Enable/disable route reflection between clients.";
        }
      }
    }
  }
  augment "/ncs:devices/ncs:device/ncs:config/ni:network-instance/ni:instances/ni:instance/bgp:bgp/bgp:base-process/bgp:afs/bgp:af" {
    description
      "BGP flow address family configuration.";
    container ipv4-flow {
      tailf:ncs-device-type "netconf";
      tailf:display-when "not(../../../../../../../../../ncs:module) or ../../../../../../../../../ncs:module[ncs:name='huawei-bgp-flow']";
      when "../bgp:type='ipv4flow'" {
        tailf:xpath-root 3;
      }
      description
        "Configure IPv4-family flow options.";
      container common {
        description
          "Configure BGP IPv4-family flow common options.";
        leaf route-match-destination {
          type boolean;
          default "false";
          description
            "Enable/disable matching the route destination.";
        }
        leaf validation-mode-as {
          type boolean;
          default "false";
          description
            "Enable/disable using the route validation-mode include-as command, you can configure flow-route validation mode include as.";
        }
        leaf redirect-ip-relay-tnl-enable {
          when "../../../../../../../ni:name='_public_'" {
            tailf:xpath-root 3;
          }
          type boolean;
          default "false";
          description
            "Enable/disable flow-route recursive-lookup tunnel.";
        }
        leaf redirect-ipv6-relay-tnl-sel-name {
          when "../../../../../../../ni:name='_public_'" {
            tailf:xpath-root 3;
          }
          type leafref {
            path "/ncs:devices/ncs:device/ncs:config/rtp:routing-policy/rtp:tunnel-selectors/rtp:tunnel-selector/rtp:name" {
              tailf:xpath-root 3;
            }
          }
          description
            "Flow-route Tunnel Selector Name.";
        }
        leaf redirect-ip-relay-tunnel-selector-name {
          when "../redirect-ip-relay-tnl-enable = 'true'" {
            tailf:xpath-root 3;
          }
          type leafref {
            path "/ncs:devices/ncs:device/ncs:config/rtp:routing-policy/rtp:tunnel-selectors/rtp:tunnel-selector/rtp:name" {
              tailf:xpath-root 3;
            }
          }
          description
            "Specifies the name of a tunnel selector.";
        }
        uses bgp:reflector-cluster-type;
        leaf reflect-between-client {
          type boolean;
          default "true";
          description
            "Enable/disable route reflection between clients. If clients of a route reflector (RR) are fully meshed, you can disable route reflection among clients to reduce the cost.";
        }
        leaf check-origin-as-enable {
          when "../../../../../../../ni:name='_public_'" {
            tailf:xpath-root 3;
          }
          type boolean;
          default "false";
          description
            "Enable/disable the received BGP Flow Specification routes carrying a filtering rule that is based on the origin AS number of the destination IP address to be valid.";
        }
      }
      uses bgp:routing-table-rib-only-type;
    }
    container ipv6-flow {
      tailf:ncs-device-type "netconf";
      tailf:display-when "not(../../../../../../../../../ncs:module) or ../../../../../../../../../ncs:module[ncs:name='huawei-bgp-flow']";
      when "../bgp:type='ipv6flow'" {
        tailf:xpath-root 3;
      }
      description
        "Configure IPv6-family flow options.";
      container common {
        description
          "Configure BGP IPv6-family flow common options.";
        leaf route-match-destination {
          type boolean;
          default "false";
          description
            "Enable/disable matchingatch the route destination.";
        }
        leaf validation-mode-as {
          type boolean;
          default "false";
          description
            "Enable/disable using the route validation-mode include-as command, you can configure flow-route validation mode include as.";
        }
        leaf reflect-between-client {
          type boolean;
          default "true";
          description
            "Enable/disable route reflection between clients. If clients of a route reflector (RR) are fully meshed, you can disable route reflection among clients to reduce the cost.";
        }
        uses bgp:reflector-cluster-type;
      }
      uses bgp:routing-table-rib-only-type;
    }
    container vpnv4-flow {
      tailf:ncs-device-type "netconf";
      tailf:display-when "not(../../../../../../../../../ncs:module) or ../../../../../../../../../ncs:module[ncs:name='huawei-bgp-flow']";
      when "../bgp:type='vpnv4flow'" {
        tailf:xpath-root 3;
      }
      description
        "Configure IPv4 VPN flow options.";
      container common {
        description
          "Configure IPv4 VPN flow common options.";
        uses bgp:vpn-target-type;
        uses bgp:reflector-cluster-type;
        leaf reflect-between-client {
          type boolean;
          default "true";
          description
            "Enable/disable route reflection between clients.";
        }
      }
    }
    container vpnv6-flow {
      tailf:ncs-device-type "netconf";
      tailf:display-when "not(../../../../../../../../../ncs:module) or ../../../../../../../../../ncs:module[ncs:name='huawei-bgp-flow']";
      when "../bgp:type='vpnv6flow'" {
        tailf:xpath-root 3;
      }
      description
        "Configure IPv6 VPN flow options.";
      container common {
        description
          "Configure IPv6 VPN flow common options.";
        uses bgp:vpn-target-type;
        uses bgp:reflector-cluster-type;
        leaf reflect-between-client {
          type boolean;
          default "true";
          description
            "Enable/disable route reflection between clients.";
        }
      }
    }
  }
  augment "/ncs:devices/ncs:template/ncs:ned-id/ncs:config/ni:network-instance/ni:instances/ni:instance/bgp:bgp/bgp:base-process/bgp:peers/bgp:peer/bgp:afs/bgp:af" {
    description
      "BGP flow address family configuration.";
    container ipv4-flow {
      // NCS drop when statement
      description
        "Configure IPv4-family flow options.";
      leaf advertise-community {
        type string;
        // NCS drop default statement
        description
          "Enable/disable advertise the community attribute to a peer or a peer group.";
      }
      leaf reflect-client {
        type string;
        // NCS drop default statement
        description
          "Enable/disable the local device as a route reflector (RR) and a peer or peer group as its client. This configuration is applicable between IBGP peers only. The configurations of RRs and its clients in an address family are valid only in this address family. Therefore, it is recommended to configure RRs and its clients in the specified address family that is required.";
      }
      leaf validation-disable {
        type string;
        // NCS drop default statement
        description
          "Enable/disable route validation.";
      }
      leaf redirect-ip {
        type string;
        // NCS drop default statement
        description
          "Enable/disable peer handle the extended community attribute redirect-ip.";
      }
      leaf redirect-ip-vaildation {
        type string;
        // NCS drop default statement
        description
          "Enable/disable the function to indicate whether validation redirect ip, and this command only support IPv4-family flow address family.";
      }
      leaf redirect-ip-rfc-compatible {
        type string;
        // NCS drop must statement
        // NCS drop default statement
        description
          "Enable/disable sending both number for the apply redirect IPv4 action.";
      }
      leaf redirect-ip-draft-compatible {
        type string;
        // NCS drop default statement
        description
          "Enable/disable sending both number for the apply redirect IPv4 action.";
      }
      uses ncs_template_bgp-peer-ipv4flow-cap-type;
      leaf graceful-restart-static-timer {
        type string;
        units "s";
        description
          "Specifies the maximum time during which a peer waits for a BGP session reestablishment.";
      }
      leaf destination-origin-as {
        type string;
        // NCS drop default statement
        description
          "Enable/disable the BGP peer origin validation.";
      }
      choice import-policy-type {
        description
          "Set route policy or filter.";
        case rtp-ref {
          description
            "Route policy.";
          leaf import-policy {
            type string;
            description
              "Specify the filtering policy applied to the routes learned from a peer. By default, no such policy is specified.";
          }
        }
        case xpl-ref {
          description
            "Route filter.";
          container import-filter {
            description
              "Configure an import route-filter to filter the routes received from peers. By default, no route-filter is specified to filter the routes imported from peers.";
            leaf name {
              type string;
              description
                "Specify an import route-filter name.";
            }
            leaf parameter {
              // NCS drop when statement
              type xpl:ncs_template_filter-parameter-type;
              description
                "Specify an import route-filter parameter.";
            }
          }
        }
      }
      choice export-policy-type {
        description
          "Set route policy or filter.";
        case rtp-ref {
          description
            "Route policy.";
          leaf export-policy {
            type string;
            description
              "Specify the filtering policy applied to the routes to be advertised to a peer. By default, no such policy is specified.";
          }
        }
        case xpl-ref {
          description
            "Route filter.";
          container export-filter {
            description
              "Configure an export route-filter to filter the routes to be advertised to peers. By default, no route-filter is specified to filter the routes to be advertised to peers.";
            leaf name {
              type string;
              description
                "Specify an export route-filter name.";
            }
            leaf parameter {
              // NCS drop when statement
              type xpl:ncs_template_filter-parameter-type;
              description
                "Specify an export route-filter parameter.";
            }
          }
        }
      }
      leaf advertise-large-community {
        type bgp:ncs_template_peer-enable-config-type;
        // NCS drop default statement
        description
          "Enable large-community attribute advertisement. The Link-state address family and the RPD address family do not support this element.";
      }
      leaf route-update-interval {
        type string;
        units "s";
        description
          "Specify the minimum interval at which Update packets are sent. By default, the interval at which Update packets are sent to IBGP peers is 15s,
           and the interval at which Update packets are sent to EBGP peers is 30s. When routes change, a router will send Update packets to notify its peers.
           If a route changes frequently, you can set an interval at which Update packets are sent to prevent the router from sending Update packets each time the route changes.
           This configuration is valid only to the routes learned from peers.";
        ext:dynamic-default;
      }
      leaf update-group-independent {
        type bgp:ncs_template_peer-comm-config-type;
        // NCS drop default statement
        description
          "Enable/disable the peer which can reside in an independent peer group.";
      }
      leaf route-policy-distribute {
        // NCS drop when statement
        type ncs_template_rpd-cap-type;
        description
          "Enable/disable route policy distribution (RPD) on a BGP device.";
      }
      uses bgp:ncs_template_route-limit-type;
      uses bgp:ncs_template_path-attr-map-type;
    }
    container ipv6-flow {
      // NCS drop when statement
      description
        "Configure IPv6-family flow options.";
      leaf advertise-community {
        type string;
        // NCS drop default statement
        description
          "Enable/disable advertise the community attribute to a peer or a peer group.";
      }
      leaf reflect-client {
        type string;
        // NCS drop default statement
        description
          "Enable/disable the local device as a route reflector (RR) and a peer or peer group as its client. This configuration is applicable between IBGP peers only. The configurations of RRs and its clients in an address family are valid only in this address family. Therefore, it is recommended to configure RRs and its clients in the specified address family that is required.";
      }
      leaf validation-disable {
        type string;
        // NCS drop default statement
        description
          "Enable/disable route validation.";
      }
      leaf graceful-restart-static-timer {
        type string;
        units "s";
        description
          "Specifies the maximum time during which a peer waits for a BGP session reestablishment.";
      }
      choice import-policy-type {
        description
          "Set route policy or filter.";
        case rtp-ref {
          description
            "Route policy.";
          leaf import-policy {
            type string;
            description
              "Specify the filtering policy applied to the routes learned from a peer. By default, no such policy is specified.";
          }
        }
        case xpl-ref {
          description
            "Route filter.";
          container import-filter {
            description
              "Configure an import route-filter to filter the routes received from peers. By default, no route-filter is specified to filter the routes imported from peers.";
            leaf name {
              type string;
              description
                "Specify an import route-filter name.";
            }
            leaf parameter {
              // NCS drop when statement
              type xpl:ncs_template_filter-parameter-type;
              description
                "Specify an import route-filter parameter.";
            }
          }
        }
      }
      choice export-policy-type {
        description
          "Set route policy or filter.";
        case rtp-ref {
          description
            "Route policy.";
          leaf export-policy {
            type string;
            description
              "Specify the filtering policy applied to the routes to be advertised to a peer. By default, no such policy is specified.";
          }
        }
        case xpl-ref {
          description
            "Route filter.";
          container export-filter {
            description
              "Configure an export route-filter to filter the routes to be advertised to peers. By default, no route-filter is specified to filter the routes to be advertised to peers.";
            leaf name {
              type string;
              description
                "Specify an export route-filter name.";
            }
            leaf parameter {
              // NCS drop when statement
              type xpl:ncs_template_filter-parameter-type;
              description
                "Specify an export route-filter parameter.";
            }
          }
        }
      }
      leaf advertise-large-community {
        type bgp:ncs_template_peer-enable-config-type;
        // NCS drop default statement
        description
          "Enable large-community attribute advertisement. The Link-state address family and the RPD address family do not support this element.";
      }
      uses bgp:ncs_template_rt-update-interval-type;
      leaf update-group-independent {
        type bgp:ncs_template_peer-comm-config-type;
        // NCS drop default statement
        description
          "Enable/disable the peer which can reside in an independent peer group.";
      }
      uses bgp:ncs_template_route-limit-type;
      uses bgp:ncs_template_path-attr-map-type;
    }
    container vpnv4-flow {
      // NCS drop when statement
      description
        "Configure IPv4 VPN flow options.";
      leaf advertise-large-community {
        type bgp:ncs_template_peer-enable-config-type;
        // NCS drop default statement
        description
          "Enable large-community attribute advertisement.";
      }
      uses bgp:ncs_template_reflect-client-type;
      leaf graceful-restart-static-timer {
        type string;
        units "s";
        description
          "Specifies the maximum time during which a peer waits for a BGP session reestablishment.";
      }
      leaf update-group-independent {
        type bgp:ncs_template_peer-comm-config-type;
        // NCS drop default statement
        description
          "Enable/disable the peer which can reside in an independent peer group.";
      }
      choice import-policy-type {
        description
          "Set route policy or filter.";
        case rtp-ref {
          description
            "Route policy.";
          leaf import-policy {
            type string;
            description
              "Specify the filtering policy applied to the routes learned from a peer. By default, no such policy is specified.";
          }
        }
        case xpl-ref {
          description
            "Route filter.";
          container import-filter {
            description
              "Configure an import route-filter to filter the routes received from peers. By default, no route-filter is specified to filter the routes imported from peers.";
            leaf name {
              type string;
              description
                "Specify an import route-filter name.";
            }
            leaf parameter {
              // NCS drop when statement
              type xpl:ncs_template_filter-parameter-type;
              description
                "Specify an import route-filter parameter.";
            }
          }
        }
      }
      choice export-policy-type {
        description
          "Set route policy or filter.";
        case rtp-ref {
          description
            "Route policy.";
          leaf export-policy {
            type string;
            description
              "Specify the filtering policy applied to the routes to be advertised to a peer. By default, no such policy is specified.";
          }
        }
        case xpl-ref {
          description
            "Route filter.";
          container export-filter {
            description
              "Configure an export route-filter to filter the routes to be advertised to peers. By default, no route-filter is specified to filter the routes to be advertised to peers.";
            leaf name {
              type string;
              description
                "Specify an export route-filter name.";
            }
            leaf parameter {
              // NCS drop when statement
              type xpl:ncs_template_filter-parameter-type;
              description
                "Specify an export route-filter parameter.";
            }
          }
        }
      }
      leaf advertise-community {
        type string;
        // NCS drop default statement
        description
          "Enable/disable advertise the community attribute to a peer or a peer group.";
      }
      leaf redirect-ip-rfc-compatible {
        type string;
        // NCS drop must statement
        // NCS drop default statement
        description
          "Enable/disable sending both number for the apply redirect IPv4 action.";
      }
      leaf redirect-ip-draft-compatible {
        type string;
        // NCS drop default statement
        description
          "Enable/disable sending both number for the apply redirect IPv4 action.";
      }
      uses bgp:ncs_template_route-limit-type;
      uses bgp:ncs_template_path-attr-map-type;
    }
    container vpnv6-flow {
      // NCS drop when statement
      description
        "Configure IPv6 VPN flow options.";
      leaf advertise-large-community {
        type bgp:ncs_template_peer-enable-config-type;
        // NCS drop default statement
        description
          "Enable large-community attribute advertisement.";
      }
      uses bgp:ncs_template_reflect-client-type;
      leaf graceful-restart-static-timer {
        type string;
        units "s";
        description
          "Specifies the maximum time during which a peer waits for a BGP session reestablishment.";
      }
      choice import-policy-type {
        description
          "Set route policy or filter.";
        case rtp-ref {
          description
            "Route policy.";
          leaf import-policy {
            type string;
            description
              "Specify the filtering policy applied to the routes learned from a peer. By default, no such policy is specified.";
          }
        }
        case xpl-ref {
          description
            "Route filter.";
          container import-filter {
            description
              "Configure an import route-filter to filter the routes received from peers. By default, no route-filter is specified to filter the routes imported from peers.";
            leaf name {
              type string;
              description
                "Specify an import route-filter name.";
            }
            leaf parameter {
              // NCS drop when statement
              type xpl:ncs_template_filter-parameter-type;
              description
                "Specify an import route-filter parameter.";
            }
          }
        }
      }
      choice export-policy-type {
        description
          "Set route policy or filter.";
        case rtp-ref {
          description
            "Route policy.";
          leaf export-policy {
            type string;
            description
              "Specify the filtering policy applied to the routes to be advertised to a peer. By default, no such policy is specified.";
          }
        }
        case xpl-ref {
          description
            "Route filter.";
          container export-filter {
            description
              "Configure an export route-filter to filter the routes to be advertised to peers. By default, no route-filter is specified to filter the routes to be advertised to peers.";
            leaf name {
              type string;
              description
                "Specify an export route-filter name.";
            }
            leaf parameter {
              // NCS drop when statement
              type xpl:ncs_template_filter-parameter-type;
              description
                "Specify an export route-filter parameter.";
            }
          }
        }
      }
      leaf advertise-community {
        type string;
        // NCS drop default statement
        description
          "Enable/disable advertise the community attribute to a peer or a peer group.";
      }
      uses bgp:ncs_template_route-limit-type;
      uses bgp:ncs_template_path-attr-map-type;
    }
  }
  augment "/ncs:devices/ncs:device/ncs:live-status/ni:network-instance/ni:instances/ni:instance/bgp:bgp/bgp:base-process/bgp:peers/bgp:peer/bgp:afs/bgp:af" {
    description
      "BGP flow address family configuration.";
    container ipv4-flow {
      tailf:ncs-device-type "netconf";
      tailf:display-when "not(../../../../../../../../../../../ncs:module) or ../../../../../../../../../../../ncs:module[ncs:name='huawei-bgp-flow'] or (../../../../../../../../../../../ncs:live-status-protocol[not(ncs:capability)]) or (../../../../../../../../../../../ncs:live-status-protocol/ncs:capability/ncs:module[.='huawei-bgp-flow'])";
      // NCS drop when statement
      description
        "Configure IPv4-family flow options.";
      leaf advertise-community {
        type boolean;
        // NCS drop default statement
        description
          "Enable/disable advertise the community attribute to a peer or a peer group.";
      }
      leaf reflect-client {
        type boolean;
        // NCS drop default statement
        description
          "Enable/disable the local device as a route reflector (RR) and a peer or peer group as its client. This configuration is applicable between IBGP peers only. The configurations of RRs and its clients in an address family are valid only in this address family. Therefore, it is recommended to configure RRs and its clients in the specified address family that is required.";
      }
      leaf validation-disable {
        type boolean;
        // NCS drop default statement
        description
          "Enable/disable route validation.";
      }
      leaf redirect-ip {
        type boolean;
        // NCS drop default statement
        description
          "Enable/disable peer handle the extended community attribute redirect-ip.";
      }
      leaf redirect-ip-vaildation {
        type boolean;
        // NCS drop default statement
        description
          "Enable/disable the function to indicate whether validation redirect ip, and this command only support IPv4-family flow address family.";
      }
      leaf redirect-ip-rfc-compatible {
        type boolean;
        // NCS drop must statement
        // NCS drop default statement
        description
          "Enable/disable sending both number for the apply redirect IPv4 action.";
      }
      leaf redirect-ip-draft-compatible {
        type boolean;
        // NCS drop default statement
        description
          "Enable/disable sending both number for the apply redirect IPv4 action.";
      }
      uses live_ncs_bgp-peer-ipv4flow-cap-type;
      leaf graceful-restart-static-timer {
        type uint32 {
          range "3600..2147483647";
        }
        units "s";
        description
          "Specifies the maximum time during which a peer waits for a BGP session reestablishment.";
      }
      leaf destination-origin-as {
        type boolean;
        // NCS drop default statement
        description
          "Enable/disable the BGP peer origin validation.";
      }
      choice import-policy-type {
        description
          "Set route policy or filter.";
        case rtp-ref {
          description
            "Route policy.";
          leaf import-policy {
            type leafref {
              path "/ncs:devices/ncs:device/ncs:live-status/rtp:routing-policy/rtp:policy-definitions/rtp:policy-definition/rtp:name" {
                tailf:xpath-root 3;
              }
            }
            description
              "Specify the filtering policy applied to the routes learned from a peer. By default, no such policy is specified.";
          }
        }
        case xpl-ref {
          description
            "Route filter.";
          container import-filter {
            description
              "Configure an import route-filter to filter the routes received from peers. By default, no route-filter is specified to filter the routes imported from peers.";
            leaf name {
              type leafref {
                path "/ncs:devices/ncs:device/ncs:live-status/xpl:xpl/xpl:route-filters/xpl:route-filter/xpl:name" {
                  tailf:xpath-root 3;
                }
              }
              description
                "Specify an import route-filter name.";
            }
            leaf parameter {
              // NCS drop when statement
              type xpl:live_ncs_filter-parameter-type;
              description
                "Specify an import route-filter parameter.";
            }
          }
        }
      }
      choice export-policy-type {
        description
          "Set route policy or filter.";
        case rtp-ref {
          description
            "Route policy.";
          leaf export-policy {
            type leafref {
              path "/ncs:devices/ncs:device/ncs:live-status/rtp:routing-policy/rtp:policy-definitions/rtp:policy-definition/rtp:name" {
                tailf:xpath-root 3;
              }
            }
            description
              "Specify the filtering policy applied to the routes to be advertised to a peer. By default, no such policy is specified.";
          }
        }
        case xpl-ref {
          description
            "Route filter.";
          container export-filter {
            description
              "Configure an export route-filter to filter the routes to be advertised to peers. By default, no route-filter is specified to filter the routes to be advertised to peers.";
            leaf name {
              type leafref {
                path "/ncs:devices/ncs:device/ncs:live-status/xpl:xpl/xpl:route-filters/xpl:route-filter/xpl:name" {
                  tailf:xpath-root 3;
                }
              }
              description
                "Specify an export route-filter name.";
            }
            leaf parameter {
              // NCS drop when statement
              type xpl:live_ncs_filter-parameter-type;
              description
                "Specify an export route-filter parameter.";
            }
          }
        }
      }
      leaf advertise-large-community {
        type bgp:live_ncs_peer-enable-config-type;
        // NCS drop default statement
        description
          "Enable large-community attribute advertisement. The Link-state address family and the RPD address family do not support this element.";
      }
      leaf route-update-interval {
        type uint16 {
          range "0..600";
        }
        units "s";
        description
          "Specify the minimum interval at which Update packets are sent. By default, the interval at which Update packets are sent to IBGP peers is 15s,
           and the interval at which Update packets are sent to EBGP peers is 30s. When routes change, a router will send Update packets to notify its peers.
           If a route changes frequently, you can set an interval at which Update packets are sent to prevent the router from sending Update packets each time the route changes.
           This configuration is valid only to the routes learned from peers.";
        ext:dynamic-default;
      }
      leaf update-group-independent {
        type bgp:live_ncs_peer-comm-config-type;
        // NCS drop default statement
        description
          "Enable/disable the peer which can reside in an independent peer group.";
      }
      leaf route-policy-distribute {
        // NCS drop when statement
        type live_ncs_rpd-cap-type;
        description
          "Enable/disable route policy distribution (RPD) on a BGP device.";
      }
      uses bgp:live_ncs_route-limit-type;
      uses bgp:live_ncs_path-attr-map-type;
    }
    container ipv6-flow {
      tailf:ncs-device-type "netconf";
      tailf:display-when "not(../../../../../../../../../../../ncs:module) or ../../../../../../../../../../../ncs:module[ncs:name='huawei-bgp-flow'] or (../../../../../../../../../../../ncs:live-status-protocol[not(ncs:capability)]) or (../../../../../../../../../../../ncs:live-status-protocol/ncs:capability/ncs:module[.='huawei-bgp-flow'])";
      // NCS drop when statement
      description
        "Configure IPv6-family flow options.";
      leaf advertise-community {
        type boolean;
        // NCS drop default statement
        description
          "Enable/disable advertise the community attribute to a peer or a peer group.";
      }
      leaf reflect-client {
        type boolean;
        // NCS drop default statement
        description
          "Enable/disable the local device as a route reflector (RR) and a peer or peer group as its client. This configuration is applicable between IBGP peers only. The configurations of RRs and its clients in an address family are valid only in this address family. Therefore, it is recommended to configure RRs and its clients in the specified address family that is required.";
      }
      leaf validation-disable {
        type boolean;
        // NCS drop default statement
        description
          "Enable/disable route validation.";
      }
      leaf graceful-restart-static-timer {
        type uint32 {
          range "3600..2147483647";
        }
        units "s";
        description
          "Specifies the maximum time during which a peer waits for a BGP session reestablishment.";
      }
      choice import-policy-type {
        description
          "Set route policy or filter.";
        case rtp-ref {
          description
            "Route policy.";
          leaf import-policy {
            type leafref {
              path "/ncs:devices/ncs:device/ncs:live-status/rtp:routing-policy/rtp:policy-definitions/rtp:policy-definition/rtp:name" {
                tailf:xpath-root 3;
              }
            }
            description
              "Specify the filtering policy applied to the routes learned from a peer. By default, no such policy is specified.";
          }
        }
        case xpl-ref {
          description
            "Route filter.";
          container import-filter {
            description
              "Configure an import route-filter to filter the routes received from peers. By default, no route-filter is specified to filter the routes imported from peers.";
            leaf name {
              type leafref {
                path "/ncs:devices/ncs:device/ncs:live-status/xpl:xpl/xpl:route-filters/xpl:route-filter/xpl:name" {
                  tailf:xpath-root 3;
                }
              }
              description
                "Specify an import route-filter name.";
            }
            leaf parameter {
              // NCS drop when statement
              type xpl:live_ncs_filter-parameter-type;
              description
                "Specify an import route-filter parameter.";
            }
          }
        }
      }
      choice export-policy-type {
        description
          "Set route policy or filter.";
        case rtp-ref {
          description
            "Route policy.";
          leaf export-policy {
            type leafref {
              path "/ncs:devices/ncs:device/ncs:live-status/rtp:routing-policy/rtp:policy-definitions/rtp:policy-definition/rtp:name" {
                tailf:xpath-root 3;
              }
            }
            description
              "Specify the filtering policy applied to the routes to be advertised to a peer. By default, no such policy is specified.";
          }
        }
        case xpl-ref {
          description
            "Route filter.";
          container export-filter {
            description
              "Configure an export route-filter to filter the routes to be advertised to peers. By default, no route-filter is specified to filter the routes to be advertised to peers.";
            leaf name {
              type leafref {
                path "/ncs:devices/ncs:device/ncs:live-status/xpl:xpl/xpl:route-filters/xpl:route-filter/xpl:name" {
                  tailf:xpath-root 3;
                }
              }
              description
                "Specify an export route-filter name.";
            }
            leaf parameter {
              // NCS drop when statement
              type xpl:live_ncs_filter-parameter-type;
              description
                "Specify an export route-filter parameter.";
            }
          }
        }
      }
      leaf advertise-large-community {
        type bgp:live_ncs_peer-enable-config-type;
        // NCS drop default statement
        description
          "Enable large-community attribute advertisement. The Link-state address family and the RPD address family do not support this element.";
      }
      uses bgp:live_ncs_rt-update-interval-type;
      leaf update-group-independent {
        type bgp:live_ncs_peer-comm-config-type;
        // NCS drop default statement
        description
          "Enable/disable the peer which can reside in an independent peer group.";
      }
      uses bgp:live_ncs_route-limit-type;
      uses bgp:live_ncs_path-attr-map-type;
    }
    container vpnv4-flow {
      tailf:ncs-device-type "netconf";
      tailf:display-when "not(../../../../../../../../../../../ncs:module) or ../../../../../../../../../../../ncs:module[ncs:name='huawei-bgp-flow'] or (../../../../../../../../../../../ncs:live-status-protocol[not(ncs:capability)]) or (../../../../../../../../../../../ncs:live-status-protocol/ncs:capability/ncs:module[.='huawei-bgp-flow'])";
      // NCS drop when statement
      description
        "Configure IPv4 VPN flow options.";
      leaf advertise-large-community {
        type bgp:live_ncs_peer-enable-config-type;
        // NCS drop default statement
        description
          "Enable large-community attribute advertisement.";
      }
      uses bgp:live_ncs_reflect-client-type;
      leaf graceful-restart-static-timer {
        type uint32 {
          range "3600..2147483647";
        }
        units "s";
        description
          "Specifies the maximum time during which a peer waits for a BGP session reestablishment.";
      }
      leaf update-group-independent {
        type bgp:live_ncs_peer-comm-config-type;
        // NCS drop default statement
        description
          "Enable/disable the peer which can reside in an independent peer group.";
      }
      choice import-policy-type {
        description
          "Set route policy or filter.";
        case rtp-ref {
          description
            "Route policy.";
          leaf import-policy {
            type leafref {
              path "/ncs:devices/ncs:device/ncs:live-status/rtp:routing-policy/rtp:policy-definitions/rtp:policy-definition/rtp:name" {
                tailf:xpath-root 3;
              }
            }
            description
              "Specify the filtering policy applied to the routes learned from a peer. By default, no such policy is specified.";
          }
        }
        case xpl-ref {
          description
            "Route filter.";
          container import-filter {
            description
              "Configure an import route-filter to filter the routes received from peers. By default, no route-filter is specified to filter the routes imported from peers.";
            leaf name {
              type leafref {
                path "/ncs:devices/ncs:device/ncs:live-status/xpl:xpl/xpl:route-filters/xpl:route-filter/xpl:name" {
                  tailf:xpath-root 3;
                }
              }
              description
                "Specify an import route-filter name.";
            }
            leaf parameter {
              // NCS drop when statement
              type xpl:live_ncs_filter-parameter-type;
              description
                "Specify an import route-filter parameter.";
            }
          }
        }
      }
      choice export-policy-type {
        description
          "Set route policy or filter.";
        case rtp-ref {
          description
            "Route policy.";
          leaf export-policy {
            type leafref {
              path "/ncs:devices/ncs:device/ncs:live-status/rtp:routing-policy/rtp:policy-definitions/rtp:policy-definition/rtp:name" {
                tailf:xpath-root 3;
              }
            }
            description
              "Specify the filtering policy applied to the routes to be advertised to a peer. By default, no such policy is specified.";
          }
        }
        case xpl-ref {
          description
            "Route filter.";
          container export-filter {
            description
              "Configure an export route-filter to filter the routes to be advertised to peers. By default, no route-filter is specified to filter the routes to be advertised to peers.";
            leaf name {
              type leafref {
                path "/ncs:devices/ncs:device/ncs:live-status/xpl:xpl/xpl:route-filters/xpl:route-filter/xpl:name" {
                  tailf:xpath-root 3;
                }
              }
              description
                "Specify an export route-filter name.";
            }
            leaf parameter {
              // NCS drop when statement
              type xpl:live_ncs_filter-parameter-type;
              description
                "Specify an export route-filter parameter.";
            }
          }
        }
      }
      leaf advertise-community {
        type boolean;
        // NCS drop default statement
        description
          "Enable/disable advertise the community attribute to a peer or a peer group.";
      }
      leaf redirect-ip-rfc-compatible {
        type boolean;
        // NCS drop must statement
        // NCS drop default statement
        description
          "Enable/disable sending both number for the apply redirect IPv4 action.";
      }
      leaf redirect-ip-draft-compatible {
        type boolean;
        // NCS drop default statement
        description
          "Enable/disable sending both number for the apply redirect IPv4 action.";
      }
      uses bgp:live_ncs_route-limit-type;
      uses bgp:live_ncs_path-attr-map-type;
    }
    container vpnv6-flow {
      tailf:ncs-device-type "netconf";
      tailf:display-when "not(../../../../../../../../../../../ncs:module) or ../../../../../../../../../../../ncs:module[ncs:name='huawei-bgp-flow'] or (../../../../../../../../../../../ncs:live-status-protocol[not(ncs:capability)]) or (../../../../../../../../../../../ncs:live-status-protocol/ncs:capability/ncs:module[.='huawei-bgp-flow'])";
      // NCS drop when statement
      description
        "Configure IPv6 VPN flow options.";
      leaf advertise-large-community {
        type bgp:live_ncs_peer-enable-config-type;
        // NCS drop default statement
        description
          "Enable large-community attribute advertisement.";
      }
      uses bgp:live_ncs_reflect-client-type;
      leaf graceful-restart-static-timer {
        type uint32 {
          range "3600..2147483647";
        }
        units "s";
        description
          "Specifies the maximum time during which a peer waits for a BGP session reestablishment.";
      }
      choice import-policy-type {
        description
          "Set route policy or filter.";
        case rtp-ref {
          description
            "Route policy.";
          leaf import-policy {
            type leafref {
              path "/ncs:devices/ncs:device/ncs:live-status/rtp:routing-policy/rtp:policy-definitions/rtp:policy-definition/rtp:name" {
                tailf:xpath-root 3;
              }
            }
            description
              "Specify the filtering policy applied to the routes learned from a peer. By default, no such policy is specified.";
          }
        }
        case xpl-ref {
          description
            "Route filter.";
          container import-filter {
            description
              "Configure an import route-filter to filter the routes received from peers. By default, no route-filter is specified to filter the routes imported from peers.";
            leaf name {
              type leafref {
                path "/ncs:devices/ncs:device/ncs:live-status/xpl:xpl/xpl:route-filters/xpl:route-filter/xpl:name" {
                  tailf:xpath-root 3;
                }
              }
              description
                "Specify an import route-filter name.";
            }
            leaf parameter {
              // NCS drop when statement
              type xpl:live_ncs_filter-parameter-type;
              description
                "Specify an import route-filter parameter.";
            }
          }
        }
      }
      choice export-policy-type {
        description
          "Set route policy or filter.";
        case rtp-ref {
          description
            "Route policy.";
          leaf export-policy {
            type leafref {
              path "/ncs:devices/ncs:device/ncs:live-status/rtp:routing-policy/rtp:policy-definitions/rtp:policy-definition/rtp:name" {
                tailf:xpath-root 3;
              }
            }
            description
              "Specify the filtering policy applied to the routes to be advertised to a peer. By default, no such policy is specified.";
          }
        }
        case xpl-ref {
          description
            "Route filter.";
          container export-filter {
            description
              "Configure an export route-filter to filter the routes to be advertised to peers. By default, no route-filter is specified to filter the routes to be advertised to peers.";
            leaf name {
              type leafref {
                path "/ncs:devices/ncs:device/ncs:live-status/xpl:xpl/xpl:route-filters/xpl:route-filter/xpl:name" {
                  tailf:xpath-root 3;
                }
              }
              description
                "Specify an export route-filter name.";
            }
            leaf parameter {
              // NCS drop when statement
              type xpl:live_ncs_filter-parameter-type;
              description
                "Specify an export route-filter parameter.";
            }
          }
        }
      }
      leaf advertise-community {
        type boolean;
        // NCS drop default statement
        description
          "Enable/disable advertise the community attribute to a peer or a peer group.";
      }
      uses bgp:live_ncs_route-limit-type;
      uses bgp:live_ncs_path-attr-map-type;
    }
  }
  augment "/ncs:devices/ncs:device/ncs:config/ni:network-instance/ni:instances/ni:instance/bgp:bgp/bgp:base-process/bgp:peers/bgp:peer/bgp:afs/bgp:af" {
    description
      "BGP flow address family configuration.";
    container ipv4-flow {
      tailf:ncs-device-type "netconf";
      tailf:display-when "not(../../../../../../../../../../../ncs:module) or ../../../../../../../../../../../ncs:module[ncs:name='huawei-bgp-flow']";
      when "../bgp:type='ipv4flow'" {
        tailf:xpath-root 3;
      }
      description
        "Configure IPv4-family flow options.";
      leaf advertise-community {
        type boolean;
        default "false";
        description
          "Enable/disable advertise the community attribute to a peer or a peer group.";
      }
      leaf reflect-client {
        type boolean;
        default "false";
        description
          "Enable/disable the local device as a route reflector (RR) and a peer or peer group as its client. This configuration is applicable between IBGP peers only. The configurations of RRs and its clients in an address family are valid only in this address family. Therefore, it is recommended to configure RRs and its clients in the specified address family that is required.";
      }
      leaf validation-disable {
        type boolean;
        default "false";
        description
          "Enable/disable route validation.";
      }
      leaf redirect-ip {
        type boolean;
        default "false";
        description
          "Enable/disable peer handle the extended community attribute redirect-ip.";
      }
      leaf redirect-ip-vaildation {
        type boolean;
        default "false";
        description
          "Enable/disable the function to indicate whether validation redirect ip, and this command only support IPv4-family flow address family.";
      }
      leaf redirect-ip-rfc-compatible {
        type boolean;
        must "not(../redirect-ip-rfc-compatible='true' and ../redirect-ip-draft-compatible='true')" {
          tailf:xpath-root 3;
        }
        default "false";
        description
          "Enable/disable sending both number for the apply redirect IPv4 action.";
      }
      leaf redirect-ip-draft-compatible {
        type boolean;
        default "false";
        description
          "Enable/disable sending both number for the apply redirect IPv4 action.";
      }
      uses bgp-peer-ipv4flow-cap-type;
      leaf graceful-restart-static-timer {
        type uint32 {
          range "3600..2147483647";
        }
        units "s";
        description
          "Specifies the maximum time during which a peer waits for a BGP session reestablishment.";
      }
      leaf destination-origin-as {
        type boolean;
        default "false";
        description
          "Enable/disable the BGP peer origin validation.";
      }
      choice import-policy-type {
        description
          "Set route policy or filter.";
        case rtp-ref {
          description
            "Route policy.";
          leaf import-policy {
            type leafref {
              path "/ncs:devices/ncs:device/ncs:config/rtp:routing-policy/rtp:policy-definitions/rtp:policy-definition/rtp:name" {
                tailf:xpath-root 3;
              }
            }
            description
              "Specify the filtering policy applied to the routes learned from a peer. By default, no such policy is specified.";
          }
        }
        case xpl-ref {
          description
            "Route filter.";
          container import-filter {
            description
              "Configure an import route-filter to filter the routes received from peers. By default, no route-filter is specified to filter the routes imported from peers.";
            leaf name {
              type leafref {
                path "/ncs:devices/ncs:device/ncs:config/xpl:xpl/xpl:route-filters/xpl:route-filter/xpl:name" {
                  tailf:xpath-root 3;
                }
              }
              description
                "Specify an import route-filter name.";
            }
            leaf parameter {
              when '../name' {
                tailf:xpath-root 3;
              }
              type xpl:filter-parameter-type;
              description
                "Specify an import route-filter parameter.";
            }
          }
        }
      }
      choice export-policy-type {
        description
          "Set route policy or filter.";
        case rtp-ref {
          description
            "Route policy.";
          leaf export-policy {
            type leafref {
              path "/ncs:devices/ncs:device/ncs:config/rtp:routing-policy/rtp:policy-definitions/rtp:policy-definition/rtp:name" {
                tailf:xpath-root 3;
              }
            }
            description
              "Specify the filtering policy applied to the routes to be advertised to a peer. By default, no such policy is specified.";
          }
        }
        case xpl-ref {
          description
            "Route filter.";
          container export-filter {
            description
              "Configure an export route-filter to filter the routes to be advertised to peers. By default, no route-filter is specified to filter the routes to be advertised to peers.";
            leaf name {
              type leafref {
                path "/ncs:devices/ncs:device/ncs:config/xpl:xpl/xpl:route-filters/xpl:route-filter/xpl:name" {
                  tailf:xpath-root 3;
                }
              }
              description
                "Specify an export route-filter name.";
            }
            leaf parameter {
              when '../name' {
                tailf:xpath-root 3;
              }
              type xpl:filter-parameter-type;
              description
                "Specify an export route-filter parameter.";
            }
          }
        }
      }
      leaf advertise-large-community {
        type bgp:peer-enable-config-type;
        default "default";
        description
          "Enable large-community attribute advertisement. The Link-state address family and the RPD address family do not support this element.";
      }
      leaf route-update-interval {
        type uint16 {
          range "0..600";
        }
        units "s";
        description
          "Specify the minimum interval at which Update packets are sent. By default, the interval at which Update packets are sent to IBGP peers is 15s,
           and the interval at which Update packets are sent to EBGP peers is 30s. When routes change, a router will send Update packets to notify its peers.
           If a route changes frequently, you can set an interval at which Update packets are sent to prevent the router from sending Update packets each time the route changes.
           This configuration is valid only to the routes learned from peers.";
        ext:dynamic-default;
      }
      leaf update-group-independent {
        type bgp:peer-comm-config-type;
        default "default";
        description
          "Enable/disable the peer which can reside in an independent peer group.";
      }
      leaf route-policy-distribute {
        when "../../../../../../../../ni:name='_public_'" {
          tailf:xpath-root 3;
        }
        type rpd-cap-type;
        description
          "Enable/disable route policy distribution (RPD) on a BGP device.";
      }
      uses bgp:route-limit-type;
      uses bgp:path-attr-map-type;
    }
    container ipv6-flow {
      tailf:ncs-device-type "netconf";
      tailf:display-when "not(../../../../../../../../../../../ncs:module) or ../../../../../../../../../../../ncs:module[ncs:name='huawei-bgp-flow']";
      when "../bgp:type='ipv6flow'" {
        tailf:xpath-root 3;
      }
      description
        "Configure IPv6-family flow options.";
      leaf advertise-community {
        type boolean;
        default "false";
        description
          "Enable/disable advertise the community attribute to a peer or a peer group.";
      }
      leaf reflect-client {
        type boolean;
        default "false";
        description
          "Enable/disable the local device as a route reflector (RR) and a peer or peer group as its client. This configuration is applicable between IBGP peers only. The configurations of RRs and its clients in an address family are valid only in this address family. Therefore, it is recommended to configure RRs and its clients in the specified address family that is required.";
      }
      leaf validation-disable {
        type boolean;
        default "false";
        description
          "Enable/disable route validation.";
      }
      leaf graceful-restart-static-timer {
        type uint32 {
          range "3600..2147483647";
        }
        units "s";
        description
          "Specifies the maximum time during which a peer waits for a BGP session reestablishment.";
      }
      choice import-policy-type {
        description
          "Set route policy or filter.";
        case rtp-ref {
          description
            "Route policy.";
          leaf import-policy {
            type leafref {
              path "/ncs:devices/ncs:device/ncs:config/rtp:routing-policy/rtp:policy-definitions/rtp:policy-definition/rtp:name" {
                tailf:xpath-root 3;
              }
            }
            description
              "Specify the filtering policy applied to the routes learned from a peer. By default, no such policy is specified.";
          }
        }
        case xpl-ref {
          description
            "Route filter.";
          container import-filter {
            description
              "Configure an import route-filter to filter the routes received from peers. By default, no route-filter is specified to filter the routes imported from peers.";
            leaf name {
              type leafref {
                path "/ncs:devices/ncs:device/ncs:config/xpl:xpl/xpl:route-filters/xpl:route-filter/xpl:name" {
                  tailf:xpath-root 3;
                }
              }
              description
                "Specify an import route-filter name.";
            }
            leaf parameter {
              when '../name' {
                tailf:xpath-root 3;
              }
              type xpl:filter-parameter-type;
              description
                "Specify an import route-filter parameter.";
            }
          }
        }
      }
      choice export-policy-type {
        description
          "Set route policy or filter.";
        case rtp-ref {
          description
            "Route policy.";
          leaf export-policy {
            type leafref {
              path "/ncs:devices/ncs:device/ncs:config/rtp:routing-policy/rtp:policy-definitions/rtp:policy-definition/rtp:name" {
                tailf:xpath-root 3;
              }
            }
            description
              "Specify the filtering policy applied to the routes to be advertised to a peer. By default, no such policy is specified.";
          }
        }
        case xpl-ref {
          description
            "Route filter.";
          container export-filter {
            description
              "Configure an export route-filter to filter the routes to be advertised to peers. By default, no route-filter is specified to filter the routes to be advertised to peers.";
            leaf name {
              type leafref {
                path "/ncs:devices/ncs:device/ncs:config/xpl:xpl/xpl:route-filters/xpl:route-filter/xpl:name" {
                  tailf:xpath-root 3;
                }
              }
              description
                "Specify an export route-filter name.";
            }
            leaf parameter {
              when '../name' {
                tailf:xpath-root 3;
              }
              type xpl:filter-parameter-type;
              description
                "Specify an export route-filter parameter.";
            }
          }
        }
      }
      leaf advertise-large-community {
        type bgp:peer-enable-config-type;
        default "default";
        description
          "Enable large-community attribute advertisement. The Link-state address family and the RPD address family do not support this element.";
      }
      uses bgp:rt-update-interval-type;
      leaf update-group-independent {
        type bgp:peer-comm-config-type;
        default "default";
        description
          "Enable/disable the peer which can reside in an independent peer group.";
      }
      uses bgp:route-limit-type;
      uses bgp:path-attr-map-type;
    }
    container vpnv4-flow {
      tailf:ncs-device-type "netconf";
      tailf:display-when "not(../../../../../../../../../../../ncs:module) or ../../../../../../../../../../../ncs:module[ncs:name='huawei-bgp-flow']";
      when "../bgp:type='vpnv4flow'" {
        tailf:xpath-root 3;
      }
      description
        "Configure IPv4 VPN flow options.";
      leaf advertise-large-community {
        type bgp:peer-enable-config-type;
        default "default";
        description
          "Enable large-community attribute advertisement.";
      }
      uses bgp:reflect-client-type;
      leaf graceful-restart-static-timer {
        type uint32 {
          range "3600..2147483647";
        }
        units "s";
        description
          "Specifies the maximum time during which a peer waits for a BGP session reestablishment.";
      }
      leaf update-group-independent {
        type bgp:peer-comm-config-type;
        default "default";
        description
          "Enable/disable the peer which can reside in an independent peer group.";
      }
      choice import-policy-type {
        description
          "Set route policy or filter.";
        case rtp-ref {
          description
            "Route policy.";
          leaf import-policy {
            type leafref {
              path "/ncs:devices/ncs:device/ncs:config/rtp:routing-policy/rtp:policy-definitions/rtp:policy-definition/rtp:name" {
                tailf:xpath-root 3;
              }
            }
            description
              "Specify the filtering policy applied to the routes learned from a peer. By default, no such policy is specified.";
          }
        }
        case xpl-ref {
          description
            "Route filter.";
          container import-filter {
            description
              "Configure an import route-filter to filter the routes received from peers. By default, no route-filter is specified to filter the routes imported from peers.";
            leaf name {
              type leafref {
                path "/ncs:devices/ncs:device/ncs:config/xpl:xpl/xpl:route-filters/xpl:route-filter/xpl:name" {
                  tailf:xpath-root 3;
                }
              }
              description
                "Specify an import route-filter name.";
            }
            leaf parameter {
              when '../name' {
                tailf:xpath-root 3;
              }
              type xpl:filter-parameter-type;
              description
                "Specify an import route-filter parameter.";
            }
          }
        }
      }
      choice export-policy-type {
        description
          "Set route policy or filter.";
        case rtp-ref {
          description
            "Route policy.";
          leaf export-policy {
            type leafref {
              path "/ncs:devices/ncs:device/ncs:config/rtp:routing-policy/rtp:policy-definitions/rtp:policy-definition/rtp:name" {
                tailf:xpath-root 3;
              }
            }
            description
              "Specify the filtering policy applied to the routes to be advertised to a peer. By default, no such policy is specified.";
          }
        }
        case xpl-ref {
          description
            "Route filter.";
          container export-filter {
            description
              "Configure an export route-filter to filter the routes to be advertised to peers. By default, no route-filter is specified to filter the routes to be advertised to peers.";
            leaf name {
              type leafref {
                path "/ncs:devices/ncs:device/ncs:config/xpl:xpl/xpl:route-filters/xpl:route-filter/xpl:name" {
                  tailf:xpath-root 3;
                }
              }
              description
                "Specify an export route-filter name.";
            }
            leaf parameter {
              when '../name' {
                tailf:xpath-root 3;
              }
              type xpl:filter-parameter-type;
              description
                "Specify an export route-filter parameter.";
            }
          }
        }
      }
      leaf advertise-community {
        type boolean;
        default "false";
        description
          "Enable/disable advertise the community attribute to a peer or a peer group.";
      }
      leaf redirect-ip-rfc-compatible {
        type boolean;
        must "not(../redirect-ip-rfc-compatible='true' and ../redirect-ip-draft-compatible='true')" {
          tailf:xpath-root 3;
        }
        default "false";
        description
          "Enable/disable sending both number for the apply redirect IPv4 action.";
      }
      leaf redirect-ip-draft-compatible {
        type boolean;
        default "false";
        description
          "Enable/disable sending both number for the apply redirect IPv4 action.";
      }
      uses bgp:route-limit-type;
      uses bgp:path-attr-map-type;
    }
    container vpnv6-flow {
      tailf:ncs-device-type "netconf";
      tailf:display-when "not(../../../../../../../../../../../ncs:module) or ../../../../../../../../../../../ncs:module[ncs:name='huawei-bgp-flow']";
      when "../bgp:type='vpnv6flow'" {
        tailf:xpath-root 3;
      }
      description
        "Configure IPv6 VPN flow options.";
      leaf advertise-large-community {
        type bgp:peer-enable-config-type;
        default "default";
        description
          "Enable large-community attribute advertisement.";
      }
      uses bgp:reflect-client-type;
      leaf graceful-restart-static-timer {
        type uint32 {
          range "3600..2147483647";
        }
        units "s";
        description
          "Specifies the maximum time during which a peer waits for a BGP session reestablishment.";
      }
      choice import-policy-type {
        description
          "Set route policy or filter.";
        case rtp-ref {
          description
            "Route policy.";
          leaf import-policy {
            type leafref {
              path "/ncs:devices/ncs:device/ncs:config/rtp:routing-policy/rtp:policy-definitions/rtp:policy-definition/rtp:name" {
                tailf:xpath-root 3;
              }
            }
            description
              "Specify the filtering policy applied to the routes learned from a peer. By default, no such policy is specified.";
          }
        }
        case xpl-ref {
          description
            "Route filter.";
          container import-filter {
            description
              "Configure an import route-filter to filter the routes received from peers. By default, no route-filter is specified to filter the routes imported from peers.";
            leaf name {
              type leafref {
                path "/ncs:devices/ncs:device/ncs:config/xpl:xpl/xpl:route-filters/xpl:route-filter/xpl:name" {
                  tailf:xpath-root 3;
                }
              }
              description
                "Specify an import route-filter name.";
            }
            leaf parameter {
              when '../name' {
                tailf:xpath-root 3;
              }
              type xpl:filter-parameter-type;
              description
                "Specify an import route-filter parameter.";
            }
          }
        }
      }
      choice export-policy-type {
        description
          "Set route policy or filter.";
        case rtp-ref {
          description
            "Route policy.";
          leaf export-policy {
            type leafref {
              path "/ncs:devices/ncs:device/ncs:config/rtp:routing-policy/rtp:policy-definitions/rtp:policy-definition/rtp:name" {
                tailf:xpath-root 3;
              }
            }
            description
              "Specify the filtering policy applied to the routes to be advertised to a peer. By default, no such policy is specified.";
          }
        }
        case xpl-ref {
          description
            "Route filter.";
          container export-filter {
            description
              "Configure an export route-filter to filter the routes to be advertised to peers. By default, no route-filter is specified to filter the routes to be advertised to peers.";
            leaf name {
              type leafref {
                path "/ncs:devices/ncs:device/ncs:config/xpl:xpl/xpl:route-filters/xpl:route-filter/xpl:name" {
                  tailf:xpath-root 3;
                }
              }
              description
                "Specify an export route-filter name.";
            }
            leaf parameter {
              when '../name' {
                tailf:xpath-root 3;
              }
              type xpl:filter-parameter-type;
              description
                "Specify an export route-filter parameter.";
            }
          }
        }
      }
      leaf advertise-community {
        type boolean;
        default "false";
        description
          "Enable/disable advertise the community attribute to a peer or a peer group.";
      }
      uses bgp:route-limit-type;
      uses bgp:path-attr-map-type;
    }
  }
}
