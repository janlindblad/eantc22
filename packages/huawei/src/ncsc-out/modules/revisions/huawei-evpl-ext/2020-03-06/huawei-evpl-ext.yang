module huawei-evpl-ext {
  // Generated by yanger -t ncs
  tailf:mount-id "huawei-nc-1.0:huawei-nc-1.0";
  tailf:ncs-device-type "netconf";

  namespace "urn:huawei:yang:huawei-evpl-ext";
  prefix evpl-ext;

  import huawei-evpl {
    prefix evpl;
  }
  import huawei-qos {
    prefix qos;
  }
  import huawei-extension {
    prefix ext;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Evpl ext.";

  revision 2020-03-06 {
    description
      "Add pipe type.";
    reference "Huawei private.";
  }
  revision 2019-11-23 {
    description
      "Initial revision.";
    reference "Huawei private.";
  }
  ext:task-name "forwarding";

  typedef ncs_template_evpl-pipe-mode {
    type string;
    description
      "Evpl pipe mode.";
  }

  typedef ncs_template_evpl-service-class {
    type string;
    description
      "Description of CoS.";
  }

  typedef ncs_template_evpl-color {
    type string;
    description
      "Description of packet color.";
  }

  typedef ncs_template_evpl-trust-type {
    type string;
    description
      "Description of trust type.";
  }

  typedef ncs_rpc_notif_evpl-pipe-mode {
    type enumeration {
      enum "pipe" {
        value 1;
        description
          "Evpl pipe mode.";
      }
      enum "shortpipe" {
        value 2;
        description
          "Evpl short pipe mode.";
      }
      enum "uniform" {
        value 3;
        description
          "Evpl uniform mode.";
      }
    }
    description
      "Evpl pipe mode.";
  }

  typedef ncs_rpc_notif_evpl-service-class {
    type enumeration {
      enum "be" {
        value 0;
        description
          "Specify the CoS as BE.";
      }
      enum "af1" {
        value 1;
        description
          "Specify the CoS as AF1.";
      }
      enum "af2" {
        value 2;
        description
          "Specify the CoS as AF2.";
      }
      enum "af3" {
        value 3;
        description
          "Specify the CoS as AF3.";
      }
      enum "af4" {
        value 4;
        description
          "Specify the CoS as AF4.";
      }
      enum "ef" {
        value 5;
        description
          "Specify the CoS as EF.";
      }
      enum "cs6" {
        value 6;
        description
          "Specify the CoS as CS6.";
      }
      enum "cs7" {
        value 7;
        description
          "Specify the CoS as CS7.";
      }
    }
    description
      "Description of CoS.";
  }

  typedef ncs_rpc_notif_evpl-color {
    type enumeration {
      enum "green" {
        value 0;
        description
          "Specify the packet color as green.";
      }
      enum "yellow" {
        value 1;
        description
          "Specify the packet color as yellow.";
      }
      enum "red" {
        value 2;
        description
          "Specify the packet color as red.";
      }
    }
    description
      "Description of packet color.";
  }

  typedef ncs_rpc_notif_evpl-trust-type {
    type enumeration {
      enum "outpri" {
        value 0;
        description
          "Specify the trust type as OUTTER-VLAN-8021P.";
      }
      enum "inpri" {
        value 1;
        description
          "Specify the trust type as INNER-VLAN-8021P.";
      }
      enum "ipdscp" {
        value 2;
        description
          "Specify the trust type as IP-DSCP.";
      }
    }
    description
      "Description of trust type.";
  }

  typedef live_ncs_evpl-pipe-mode {
    type enumeration {
      enum "pipe" {
        value 1;
        description
          "Evpl pipe mode.";
      }
      enum "shortpipe" {
        value 2;
        description
          "Evpl short pipe mode.";
      }
      enum "uniform" {
        value 3;
        description
          "Evpl uniform mode.";
      }
    }
    description
      "Evpl pipe mode.";
  }

  typedef live_ncs_evpl-service-class {
    type enumeration {
      enum "be" {
        value 0;
        description
          "Specify the CoS as BE.";
      }
      enum "af1" {
        value 1;
        description
          "Specify the CoS as AF1.";
      }
      enum "af2" {
        value 2;
        description
          "Specify the CoS as AF2.";
      }
      enum "af3" {
        value 3;
        description
          "Specify the CoS as AF3.";
      }
      enum "af4" {
        value 4;
        description
          "Specify the CoS as AF4.";
      }
      enum "ef" {
        value 5;
        description
          "Specify the CoS as EF.";
      }
      enum "cs6" {
        value 6;
        description
          "Specify the CoS as CS6.";
      }
      enum "cs7" {
        value 7;
        description
          "Specify the CoS as CS7.";
      }
    }
    description
      "Description of CoS.";
  }

  typedef live_ncs_evpl-color {
    type enumeration {
      enum "green" {
        value 0;
        description
          "Specify the packet color as green.";
      }
      enum "yellow" {
        value 1;
        description
          "Specify the packet color as yellow.";
      }
      enum "red" {
        value 2;
        description
          "Specify the packet color as red.";
      }
    }
    description
      "Description of packet color.";
  }

  typedef live_ncs_evpl-trust-type {
    type enumeration {
      enum "outpri" {
        value 0;
        description
          "Specify the trust type as OUTTER-VLAN-8021P.";
      }
      enum "inpri" {
        value 1;
        description
          "Specify the trust type as INNER-VLAN-8021P.";
      }
      enum "ipdscp" {
        value 2;
        description
          "Specify the trust type as IP-DSCP.";
      }
    }
    description
      "Description of trust type.";
  }

  typedef evpl-pipe-mode {
    type enumeration {
      enum "pipe" {
        value 1;
        description
          "Evpl pipe mode.";
      }
      enum "shortpipe" {
        value 2;
        description
          "Evpl short pipe mode.";
      }
      enum "uniform" {
        value 3;
        description
          "Evpl uniform mode.";
      }
    }
    description
      "Evpl pipe mode.";
  }

  typedef evpl-service-class {
    type enumeration {
      enum "be" {
        value 0;
        description
          "Specify the CoS as BE.";
      }
      enum "af1" {
        value 1;
        description
          "Specify the CoS as AF1.";
      }
      enum "af2" {
        value 2;
        description
          "Specify the CoS as AF2.";
      }
      enum "af3" {
        value 3;
        description
          "Specify the CoS as AF3.";
      }
      enum "af4" {
        value 4;
        description
          "Specify the CoS as AF4.";
      }
      enum "ef" {
        value 5;
        description
          "Specify the CoS as EF.";
      }
      enum "cs6" {
        value 6;
        description
          "Specify the CoS as CS6.";
      }
      enum "cs7" {
        value 7;
        description
          "Specify the CoS as CS7.";
      }
    }
    description
      "Description of CoS.";
  }

  typedef evpl-color {
    type enumeration {
      enum "green" {
        value 0;
        description
          "Specify the packet color as green.";
      }
      enum "yellow" {
        value 1;
        description
          "Specify the packet color as yellow.";
      }
      enum "red" {
        value 2;
        description
          "Specify the packet color as red.";
      }
    }
    description
      "Description of packet color.";
  }

  typedef evpl-trust-type {
    type enumeration {
      enum "outpri" {
        value 0;
        description
          "Specify the trust type as OUTTER-VLAN-8021P.";
      }
      enum "inpri" {
        value 1;
        description
          "Specify the trust type as INNER-VLAN-8021P.";
      }
      enum "ipdscp" {
        value 2;
        description
          "Specify the trust type as IP-DSCP.";
      }
    }
    description
      "Description of trust type.";
  }

  augment "/ncs:devices/ncs:template/ncs:ned-id/ncs:config/evpl:evpl/evpl:instances/evpl:instance" {
    description
      "Evpl configuration.";
    container pipe {
      // NCS drop when statement
      description
        "Configure the diffserv mode of evpl.";
      leaf split-mode {
        type string;
        // NCS drop must statement
        // NCS drop default statement
        description
          "Enable/disable split mode.";
      }
      leaf pipe-mode {
        // NCS drop when statement
        type ncs_template_evpl-pipe-mode;
        // NCS drop must statement
        // NCS drop default statement
        description
          "Pipe mode.";
      }
      leaf ingress-pipe-mode {
        // NCS drop when statement
        type ncs_template_evpl-pipe-mode;
        // NCS drop must statement
        // NCS drop default statement
        description
          "Ingress pipe mode.";
      }
      leaf egress-pipe-mode {
        // NCS drop when statement
        type ncs_template_evpl-pipe-mode;
        // NCS drop must statement
        // NCS drop default statement
        description
          "Egress pipe mode.";
      }
      leaf service-class {
        // NCS drop when statement
        type ncs_template_evpl-service-class;
        // NCS drop must statement
        // NCS drop default statement
        description
          "Service class.";
      }
      leaf color {
        // NCS drop when statement
        type ncs_template_evpl-color;
        // NCS drop must statement
        // NCS drop default statement
        description
          "Color.";
      }
      leaf domain-name {
        // NCS drop when statement
        type string;
        // NCS drop must statement
        // NCS drop default statement
        description
          "Domain name.";
      }
      leaf trust-type {
        // NCS drop when statement
        type ncs_template_evpl-trust-type;
        // NCS drop must statement
        // NCS drop default statement
        description
          "Trust type.";
      }
    }
  }
  augment "/ncs:devices/ncs:device/ncs:live-status/evpl:evpl/evpl:instances/evpl:instance" {
    description
      "Evpl configuration.";
    container pipe {
      tailf:ncs-device-type "netconf";
      tailf:display-when "not(../../../../../ncs:module) or ../../../../../ncs:module[ncs:name='huawei-evpl-ext'] or (../../../../../ncs:live-status-protocol[not(ncs:capability)]) or (../../../../../ncs:live-status-protocol/ncs:capability/ncs:module[.='huawei-evpl-ext'])";
      // NCS drop when statement
      description
        "Configure the diffserv mode of evpl.";
      leaf split-mode {
        type boolean;
        // NCS drop must statement
        // NCS drop default statement
        description
          "Enable/disable split mode.";
      }
      leaf pipe-mode {
        // NCS drop when statement
        type live_ncs_evpl-pipe-mode;
        // NCS drop must statement
        // NCS drop default statement
        description
          "Pipe mode.";
      }
      leaf ingress-pipe-mode {
        // NCS drop when statement
        type live_ncs_evpl-pipe-mode;
        // NCS drop must statement
        // NCS drop default statement
        description
          "Ingress pipe mode.";
      }
      leaf egress-pipe-mode {
        // NCS drop when statement
        type live_ncs_evpl-pipe-mode;
        // NCS drop must statement
        // NCS drop default statement
        description
          "Egress pipe mode.";
      }
      leaf service-class {
        // NCS drop when statement
        type live_ncs_evpl-service-class;
        // NCS drop must statement
        // NCS drop default statement
        description
          "Service class.";
      }
      leaf color {
        // NCS drop when statement
        type live_ncs_evpl-color;
        // NCS drop must statement
        // NCS drop default statement
        description
          "Color.";
      }
      leaf domain-name {
        // NCS drop when statement
        type leafref {
          path "/ncs:devices/ncs:device/ncs:live-status/qos:qos/qos:classifier-template/qos:diffserv-domains/qos:diffserv-domain/qos:name" {
            tailf:xpath-root 3;
          }
        }
        // NCS drop must statement
        // NCS drop default statement
        description
          "Domain name.";
      }
      leaf trust-type {
        // NCS drop when statement
        type live_ncs_evpl-trust-type;
        // NCS drop must statement
        // NCS drop default statement
        description
          "Trust type.";
      }
    }
  }
  augment "/ncs:devices/ncs:device/ncs:config/evpl:evpl/evpl:instances/evpl:instance" {
    description
      "Evpl configuration.";
    container pipe {
      tailf:ncs-device-type "netconf";
      tailf:display-when "not(../../../../../ncs:module) or ../../../../../ncs:module[ncs:name='huawei-evpl-ext']";
      when "(../evpl:mode != 'vxlan-mode')" {
        tailf:xpath-root 3;
      }
      description
        "Configure the diffserv mode of evpl.";
      leaf split-mode {
        type boolean;
        must "((../split-mode='false' and not(../ingress-pipe-mode) and not(../egress-pipe-mode) and ../pipe-mode) or (../split-mode='true' and not(../pipe-mode) and ../ingress-pipe-mode and ../egress-pipe-mode and not(../ingress-pipe-mode='uniform' and ../egress-pipe-mode='uniform')))" {
          tailf:xpath-root 3;
        }
        default "false";
        description
          "Enable/disable split mode.";
      }
      leaf pipe-mode {
        when "../split-mode='false'" {
          tailf:xpath-root 3;
        }
        type evpl-pipe-mode;
        must "(../split-mode='false') and ((../pipe-mode='pipe' and (../service-class) and (../color)) or (../pipe-mode='shortpipe' and (../service-class) and (../color) and (../domain-name)) or (../pipe-mode='uniform'))" {
          tailf:xpath-root 3;
        }
        default "uniform";
        description
          "Pipe mode.";
      }
      leaf ingress-pipe-mode {
        when "../split-mode='true'" {
          tailf:xpath-root 3;
        }
        type evpl-pipe-mode;
        must "((../split-mode='true') and (((../service-class) and (../color) and (../ingress-pipe-mode='shortpipe' or ../ingress-pipe-mode='pipe')) or (../ingress-pipe-mode='uniform' and ../egress-pipe-mode!='uniform')))" {
          tailf:xpath-root 3;
        }
        default "uniform";
        description
          "Ingress pipe mode.";
      }
      leaf egress-pipe-mode {
        when "../split-mode='true'" {
          tailf:xpath-root 3;
        }
        type evpl-pipe-mode;
        must "((../split-mode='true') and (((../domain-name) and (../trust-type) and (../egress-pipe-mode='shortpipe')) or (../egress-pipe-mode='pipe') or (../egress-pipe-mode='uniform' and ../ingress-pipe-mode!='uniform')))" {
          tailf:xpath-root 3;
        }
        default "uniform";
        description
          "Egress pipe mode.";
      }
      leaf service-class {
        when "(../pipe-mode='pipe' or ../pipe-mode='shortpipe' or ../ingress-pipe-mode='pipe' or ../ingress-pipe-mode='shortpipe')" {
          tailf:xpath-root 3;
        }
        type evpl-service-class;
        must "(../pipe-mode='pipe' or ../pipe-mode='shortpipe' or ../ingress-pipe-mode='pipe' or ../ingress-pipe-mode='shortpipe')" {
          tailf:xpath-root 3;
        }
        default "be";
        description
          "Service class.";
      }
      leaf color {
        when "(../pipe-mode='pipe' or ../pipe-mode='shortpipe'  or ../ingress-pipe-mode='pipe' or ../ingress-pipe-mode='shortpipe')" {
          tailf:xpath-root 3;
        }
        type evpl-color;
        must "(../pipe-mode='pipe' or ../pipe-mode='shortpipe' or ../ingress-pipe-mode='pipe' or ../ingress-pipe-mode='shortpipe')" {
          tailf:xpath-root 3;
        }
        default "green";
        description
          "Color.";
      }
      leaf domain-name {
        when "(../pipe-mode='shortpipe'  or ../egress-pipe-mode='shortpipe')" {
          tailf:xpath-root 3;
        }
        type leafref {
          path "/ncs:devices/ncs:device/ncs:config/qos:qos/qos:classifier-template/qos:diffserv-domains/qos:diffserv-domain/qos:name" {
            tailf:xpath-root 3;
          }
        }
        must "(../pipe-mode='shortpipe' or ../egress-pipe-mode='shortpipe')" {
          tailf:xpath-root 3;
        }
        default "default";
        description
          "Domain name.";
      }
      leaf trust-type {
        when "../egress-pipe-mode='shortpipe'" {
          tailf:xpath-root 3;
        }
        type evpl-trust-type;
        must "../egress-pipe-mode='shortpipe'" {
          tailf:xpath-root 3;
        }
        default "outpri";
        description
          "Trust type.";
      }
    }
  }
}
