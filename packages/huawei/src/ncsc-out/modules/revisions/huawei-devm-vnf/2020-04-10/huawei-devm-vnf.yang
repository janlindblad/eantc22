module huawei-devm-vnf {
  // Generated by yanger -t ncs
  tailf:mount-id "huawei-nc-1.0:huawei-nc-1.0";
  tailf:ncs-device-type "netconf";

  namespace "urn:huawei:yang:huawei-devm-vnf";
  prefix devm-vnf;

  import huawei-extension {
    prefix ext;
  }
  import huawei-pub-type {
    prefix pub-type;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Configuration management module.";

  revision 2020-04-10 {
    description
      "Modify description warnings.";
    reference "Huawei private.";
  }
  revision 2019-07-01 {
    description
      "Initial revision.";
    reference "Huawei private.";
  }
  ext:task-name "device-mgr";

  typedef ncs_template_run-state-type {
    type string;
    description
      "Run state.";
  }

  typedef ncs_template_resource-type {
    type string;
    description
      "Resource source type.";
  }

  typedef ncs_template_standby-state-type {
    type string;
    description
      "Board standby state.";
  }

  typedef ncs_template_board-role-type {
    type string;
    description
      "Board role.";
  }

  typedef ncs_rpc_notif_run-state-type {
    type enumeration {
      enum "abnormal" {
        value 0;
        description
          "Abnormal.";
      }
      enum "normal" {
        value 1;
        description
          "Normal.";
      }
      enum "isolated" {
        value 2;
        description
          "Isolated.";
      }
      enum "notinstall" {
        value 3;
        description
          "Not install.";
      }
      enum "wrongtype" {
        value 4;
        description
          "Wrong type.";
      }
      enum "active" {
        value 5;
        description
          "Active.";
      }
      enum "inactive" {
        value 6;
        description
          "Inactive.";
      }
      enum "offline" {
        value 7;
        description
          "Offline.";
      }
      enum "stop" {
        value 8;
        description
          "Stop.";
      }
    }
    description
      "Run state.";
  }

  typedef ncs_rpc_notif_resource-type {
    type enumeration {
      enum "vm" {
        value 0;
        description
          "Virtual machine.";
      }
    }
    description
      "Resource source type.";
  }

  typedef ncs_rpc_notif_standby-state-type {
    type enumeration {
      enum "not-supported" {
        value 0;
        description
          "No standby state.";
      }
      enum "master" {
        value 1;
        description
          "Master board.";
      }
      enum "slave" {
        value 2;
        description
          "Slave board.";
      }
    }
    description
      "Board standby state.";
  }

  typedef ncs_rpc_notif_board-role-type {
    type enumeration {
      enum "unknown" {
        value 0;
        description
          "Unknown.";
      }
      enum "mmb" {
        value 1;
        description
          "MMB.";
      }
      enum "mb" {
        value 4;
        description
          "MB.";
      }
      enum "lc" {
        value 5;
        description
          "LC.";
      }
      enum "other" {
        value 200;
        description
          "OTHER.";
      }
      enum "na" {
        value 255;
        description
          "NA.";
      }
    }
    description
      "Board role.";
  }

  typedef live_ncs_run-state-type {
    type enumeration {
      enum "abnormal" {
        value 0;
        description
          "Abnormal.";
      }
      enum "normal" {
        value 1;
        description
          "Normal.";
      }
      enum "isolated" {
        value 2;
        description
          "Isolated.";
      }
      enum "notinstall" {
        value 3;
        description
          "Not install.";
      }
      enum "wrongtype" {
        value 4;
        description
          "Wrong type.";
      }
      enum "active" {
        value 5;
        description
          "Active.";
      }
      enum "inactive" {
        value 6;
        description
          "Inactive.";
      }
      enum "offline" {
        value 7;
        description
          "Offline.";
      }
      enum "stop" {
        value 8;
        description
          "Stop.";
      }
    }
    description
      "Run state.";
  }

  typedef live_ncs_resource-type {
    type enumeration {
      enum "vm" {
        value 0;
        description
          "Virtual machine.";
      }
    }
    description
      "Resource source type.";
  }

  typedef live_ncs_standby-state-type {
    type enumeration {
      enum "not-supported" {
        value 0;
        description
          "No standby state.";
      }
      enum "master" {
        value 1;
        description
          "Master board.";
      }
      enum "slave" {
        value 2;
        description
          "Slave board.";
      }
    }
    description
      "Board standby state.";
  }

  typedef live_ncs_board-role-type {
    type enumeration {
      enum "unknown" {
        value 0;
        description
          "Unknown.";
      }
      enum "mmb" {
        value 1;
        description
          "MMB.";
      }
      enum "mb" {
        value 4;
        description
          "MB.";
      }
      enum "lc" {
        value 5;
        description
          "LC.";
      }
      enum "other" {
        value 200;
        description
          "OTHER.";
      }
      enum "na" {
        value 255;
        description
          "NA.";
      }
    }
    description
      "Board role.";
  }

  typedef run-state-type {
    type enumeration {
      enum "abnormal" {
        value 0;
        description
          "Abnormal.";
      }
      enum "normal" {
        value 1;
        description
          "Normal.";
      }
      enum "isolated" {
        value 2;
        description
          "Isolated.";
      }
      enum "notinstall" {
        value 3;
        description
          "Not install.";
      }
      enum "wrongtype" {
        value 4;
        description
          "Wrong type.";
      }
      enum "active" {
        value 5;
        description
          "Active.";
      }
      enum "inactive" {
        value 6;
        description
          "Inactive.";
      }
      enum "offline" {
        value 7;
        description
          "Offline.";
      }
      enum "stop" {
        value 8;
        description
          "Stop.";
      }
    }
    description
      "Run state.";
  }

  typedef resource-type {
    type enumeration {
      enum "vm" {
        value 0;
        description
          "Virtual machine.";
      }
    }
    description
      "Resource source type.";
  }

  typedef standby-state-type {
    type enumeration {
      enum "not-supported" {
        value 0;
        description
          "No standby state.";
      }
      enum "master" {
        value 1;
        description
          "Master board.";
      }
      enum "slave" {
        value 2;
        description
          "Slave board.";
      }
    }
    description
      "Board standby state.";
  }

  typedef board-role-type {
    type enumeration {
      enum "unknown" {
        value 0;
        description
          "Unknown.";
      }
      enum "mmb" {
        value 1;
        description
          "MMB.";
      }
      enum "mb" {
        value 4;
        description
          "MB.";
      }
      enum "lc" {
        value 5;
        description
          "LC.";
      }
      enum "other" {
        value 200;
        description
          "OTHER.";
      }
      enum "na" {
        value 255;
        description
          "NA.";
      }
    }
    description
      "Board role.";
  }

  augment "/ncs:devices/ncs:device/ncs:config" {
    container devm-vnf {
      tailf:ncs-device-type "netconf";
      tailf:display-when "not(../../ncs:module) or ../../ncs:module[ncs:name='huawei-devm-vnf']";
      description
        "Virtualized network function (VNF) infomation.";
      container vnf-boards {
        description
          "List of virtualized network function (VNF) board.";
        list vnf-board {
          key "vnfc-name id";
          description
            "Configure virtualized network function (VNF) board.";
          leaf vnfc-name {
            type string {
              length "1..31";
            }
            description
              "Virtualized network function component (VNFC) name.";
          }
          leaf id {
            type uint32;
            description
              "Board ID.";
          }
          leaf type-name {
            ext:operation-exclude "update";
            type string {
              length "1..63";
            }
            mandatory true;
            description
              "Type name.";
          }
          // NCS drop config false leaf name
          // NCS drop config false leaf 'run-state'
          // NCS drop config false leaf 'resource-type'
          // NCS drop config false leaf 'resource-name'
          // NCS drop config false leaf 'standby-state'
          // NCS drop config false leaf role
          // NCS drop config false leaf 'up-time'
          // NCS drop config false leaf 'physical-index'
        }
      }
    }
  }
  augment "/ncs:devices/ncs:device/ncs:live-status" {
    container devm-vnf {
      tailf:ncs-device-type "netconf";
      tailf:display-when "not(../../ncs:module) or ../../ncs:module[ncs:name='huawei-devm-vnf'] or (../../ncs:live-status-protocol[not(ncs:capability)]) or (../../ncs:live-status-protocol/ncs:capability/ncs:module[.='huawei-devm-vnf'])";
      description
        "Virtualized network function (VNF) infomation.";
      container vnf-boards {
        description
          "List of virtualized network function (VNF) board.";
        list vnf-board {
          key "vnfc-name id";
          description
            "Configure virtualized network function (VNF) board.";
          leaf vnfc-name {
            type string {
              length "1..31";
            }
            description
              "Virtualized network function component (VNFC) name.";
          }
          leaf id {
            type uint32;
            description
              "Board ID.";
          }
          leaf type-name {
            ext:operation-exclude "update";
            type string {
              length "1..63";
            }
            // NCS drop mandatory statement
            description
              "Type name.";
          }
          leaf name {
            type string {
              length "1..63";
            }
            description
              "Board name.";
          }
          leaf run-state {
            type live_ncs_run-state-type;
            description
              "Running status.";
          }
          leaf resource-type {
            type live_ncs_resource-type;
            description
              "Resource Type.";
          }
          leaf resource-name {
            type string {
              length "1..63";
            }
            description
              "Name of a resource source.";
          }
          leaf standby-state {
            type live_ncs_standby-state-type;
            description
              "Standby state of a VNF board.";
          }
          leaf role {
            type live_ncs_board-role-type;
            description
              "MPU role.";
          }
          leaf up-time {
            type pub-type:live_ncs_time-tick;
            description
              "Running period.";
          }
          leaf physical-index {
            type uint32;
            description
              "Entity index.";
          }
        }
      }
    }
  }
  augment "/ncs:devices/ncs:template/ncs:ned-id/ncs:config" {
    container devm-vnf {
      description
        "Virtualized network function (VNF) infomation.";
      container vnf-boards {
        description
          "List of virtualized network function (VNF) board.";
        list vnf-board {
          // NCS patched for predictable order
          ordered-by user;
          key "vnfc-name id";
          description
            "Configure virtualized network function (VNF) board.";
          leaf vnfc-name {
            type string;
            description
              "Virtualized network function component (VNFC) name.";
          }
          leaf id {
            type string;
            description
              "Board ID.";
          }
          leaf type-name {
            ext:operation-exclude "update";
            type string;
            // NCS drop mandatory statement
            description
              "Type name.";
          }
          // NCS drop config false leaf name
          // NCS drop config false leaf 'run-state'
          // NCS drop config false leaf 'resource-type'
          // NCS drop config false leaf 'resource-name'
          // NCS drop config false leaf 'standby-state'
          // NCS drop config false leaf role
          // NCS drop config false leaf 'up-time'
          // NCS drop config false leaf 'physical-index'
        }
      }
    }
  }
}
