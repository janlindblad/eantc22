module huawei-bras-dynacl {
  // Generated by yanger -t ncs
  tailf:mount-id "huawei-nc-1.0:huawei-nc-1.0";
  tailf:ncs-device-type "netconf";

  namespace "urn:huawei:yang:huawei-bras-dynacl";
  prefix bras-dynacl;

  import huawei-extension {
    prefix ext;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Bras dynacl.";

  revision 2020-03-02 {
    description
      "Modify description.";
    reference "Huawei private.";
  }
  revision 2019-04-10 {
    description
      "Init revision.";
    reference "Huawei private.";
  }
  ext:task-name "aaa-access";

  augment "/ncs:devices/ncs:device/ncs:config" {
    container bras-dynacl {
      tailf:ncs-device-type "netconf";
      tailf:display-when "not(../../ncs:module) or ../../ncs:module[ncs:name='huawei-bras-dynacl']";
      description
        "Bras dynacl.";
      container remote-download-acl {
        description
          "Configure the RADIUS server to create dynamic ACLs.";
        leaf enable {
          type boolean;
          default "false";
          description
            "Enable/disable the RADIUS server to create dynamic ACLs.";
        }
      }
      container remote-download-user-group {
        description
          "Configure the RADIUS server to create dynamic user groups.";
        leaf enable {
          type boolean;
          default "false";
          description
            "Enable/disable the RADIUS server to create dynamic user groups.";
        }
      }
      container remote-user-group-check-interval {
        description
          "Configure an interval at which a device checks whether dynamic user groups created by the RADIUS server are used by online users or dynamic ACLs.";
        leaf interval-value {
          type uint32 {
            range "1..65535";
          }
          units "min";
          default "10";
          description
            "Specifies an interval at which the device checks whether a dynamic user group is in use.";
        }
      }
      container remote-download-acl-alarm-threshold {
        description
          "Configure the alarm threshold for the usage of classifier-behavior pairs dynamically delivered by the RADIUS server.";
        leaf threshold-value {
          type uint32 {
            range "1..100";
          }
          units "%";
          default "80";
          description
            "Specifies an alarm threshold.";
        }
      }
      container support-all-operate {
        description
          "Configure a BRAS to support all operation types of a dynamic ACL delivered using a RADIUS authentication response packet when a user goes online.";
        leaf enable {
          type boolean;
          default "false";
          description
            "Enable/disable a BRAS to support all operation types of a dynamic ACL delivered using a RADIUS authentication response packet when a user goes online.";
        }
      }
    }
  }
  augment "/ncs:devices/ncs:device/ncs:live-status" {
    container bras-dynacl {
      tailf:ncs-device-type "netconf";
      tailf:display-when "not(../../ncs:module) or ../../ncs:module[ncs:name='huawei-bras-dynacl'] or (../../ncs:live-status-protocol[not(ncs:capability)]) or (../../ncs:live-status-protocol/ncs:capability/ncs:module[.='huawei-bras-dynacl'])";
      description
        "Bras dynacl.";
      container remote-download-acl {
        description
          "Configure the RADIUS server to create dynamic ACLs.";
        leaf enable {
          type boolean;
          // NCS drop default statement
          description
            "Enable/disable the RADIUS server to create dynamic ACLs.";
        }
      }
      container remote-download-user-group {
        description
          "Configure the RADIUS server to create dynamic user groups.";
        leaf enable {
          type boolean;
          // NCS drop default statement
          description
            "Enable/disable the RADIUS server to create dynamic user groups.";
        }
      }
      container remote-user-group-check-interval {
        description
          "Configure an interval at which a device checks whether dynamic user groups created by the RADIUS server are used by online users or dynamic ACLs.";
        leaf interval-value {
          type uint32 {
            range "1..65535";
          }
          units "min";
          // NCS drop default statement
          description
            "Specifies an interval at which the device checks whether a dynamic user group is in use.";
        }
      }
      container remote-download-acl-alarm-threshold {
        description
          "Configure the alarm threshold for the usage of classifier-behavior pairs dynamically delivered by the RADIUS server.";
        leaf threshold-value {
          type uint32 {
            range "1..100";
          }
          units "%";
          // NCS drop default statement
          description
            "Specifies an alarm threshold.";
        }
      }
      container support-all-operate {
        description
          "Configure a BRAS to support all operation types of a dynamic ACL delivered using a RADIUS authentication response packet when a user goes online.";
        leaf enable {
          type boolean;
          // NCS drop default statement
          description
            "Enable/disable a BRAS to support all operation types of a dynamic ACL delivered using a RADIUS authentication response packet when a user goes online.";
        }
      }
    }
  }
  augment "/ncs:devices/ncs:template/ncs:ned-id/ncs:config" {
    container bras-dynacl {
      description
        "Bras dynacl.";
      container remote-download-acl {
        description
          "Configure the RADIUS server to create dynamic ACLs.";
        leaf enable {
          type string;
          // NCS drop default statement
          description
            "Enable/disable the RADIUS server to create dynamic ACLs.";
        }
      }
      container remote-download-user-group {
        description
          "Configure the RADIUS server to create dynamic user groups.";
        leaf enable {
          type string;
          // NCS drop default statement
          description
            "Enable/disable the RADIUS server to create dynamic user groups.";
        }
      }
      container remote-user-group-check-interval {
        description
          "Configure an interval at which a device checks whether dynamic user groups created by the RADIUS server are used by online users or dynamic ACLs.";
        leaf interval-value {
          type string;
          units "min";
          // NCS drop default statement
          description
            "Specifies an interval at which the device checks whether a dynamic user group is in use.";
        }
      }
      container remote-download-acl-alarm-threshold {
        description
          "Configure the alarm threshold for the usage of classifier-behavior pairs dynamically delivered by the RADIUS server.";
        leaf threshold-value {
          type string;
          units "%";
          // NCS drop default statement
          description
            "Specifies an alarm threshold.";
        }
      }
      container support-all-operate {
        description
          "Configure a BRAS to support all operation types of a dynamic ACL delivered using a RADIUS authentication response packet when a user goes online.";
        leaf enable {
          type string;
          // NCS drop default statement
          description
            "Enable/disable a BRAS to support all operation types of a dynamic ACL delivered using a RADIUS authentication response packet when a user goes online.";
        }
      }
    }
  }
}
