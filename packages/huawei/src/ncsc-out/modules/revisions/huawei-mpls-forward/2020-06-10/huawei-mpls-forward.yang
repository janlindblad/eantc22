module huawei-mpls-forward {
  // Generated by yanger -t ncs
  tailf:mount-id "huawei-nc-1.0:huawei-nc-1.0";
  tailf:ncs-device-type "netconf";

  yang-version 1;
  namespace "urn:huawei:yang:huawei-mpls-forward";
  prefix mpls-forward;

  import huawei-loadbalance {
    prefix loadbalance;
  }
  import huawei-network-instance {
    prefix ni;
  }
  import huawei-ifm {
    prefix ifm;
  }
  import huawei-l3vpn {
    prefix l3vpn;
  }
  import huawei-qos {
    prefix qos;
  }
  import huawei-mpls {
    prefix mpls;
  }
  import huawei-pub-type {
    prefix pub-type;
  }
  import huawei-extension {
    prefix ext;
  }
  import huawei-tunnel-management {
    prefix tnlm;
  }
  import huawei-mpls-te {
    prefix mpls-te;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "MPLS forward.";

  revision 2020-06-10 {
    description
      "Adding new nodes.";
    reference "Huawei private.";
  }
  revision 2020-05-18 {
    description
      "Updating nodes.";
    reference "Huawei private.";
  }
  revision 2020-03-25 {
    description
      "Modifying some non-standard descriptions.";
    reference "Huawei private.";
  }
  revision 2020-02-27 {
    description
      "Removing the invalid definition of enumeration type and modifying the invalid statements.";
    reference "Huawei private.";
  }
  revision 2019-03-27 {
    description
      "Initial revision.";
    reference "Huawei private.";
  }
  ext:task-name "forwarding";

  typedef ncs_template_hash-type {
    type string;
    description
      "Hash type.";
  }

  typedef ncs_template_l3vpn-ingpipe-mode {
    type string;
    description
      "The mode of the L3VPN ingress pipe mode.";
  }

  typedef ncs_template_l3vpn-egpipe-mode {
    type string;
    description
      "The mode of the L3VPN egress pipe mode.";
  }

  typedef ncs_template_l3vpn-pipe-mode {
    type string;
    description
      "The mode of the L3VPN pipe mode.";
  }

  typedef ncs_template_l3vpn-ttl-mode {
    type string;
    description
      "The mode of the L3VPN tunnel.";
  }

  typedef ncs_template_l3vpn-service-class {
    type string;
    description
      "The service class of L3VPN.";
  }

  typedef ncs_template_l3vpn-color {
    type string;
    description
      "The color of L3VPN.";
  }

  typedef ncs_template_deep-hash-flag {
    type string;
    description
      "Deep hash configuration flag.";
  }

  typedef ncs_template_deep-hash-fragment {
    type string;
    description
      "Deep hash configuration fragment.";
  }

  typedef ncs_template_enable-flag {
    type string;
    description
      "Enable flag type.";
  }

  typedef ncs_template_te-pipe-mode {
    type string;
    description
      "TE pipe mode.";
  }

  typedef ncs_template_te-pipe-service-class {
    type string;
    description
      "TE pipe service class.";
  }

  typedef ncs_template_te-pipe-color {
    type string;
    description
      "TE pipe color.";
  }

  typedef ncs_template_check-mode {
    type string;
    description
      "Check mode.";
  }

  typedef ncs_template_enl-exp-mode {
    type string;
    description
      "Explicit null label EXP mode.";
  }

  typedef ncs_template_enl-ttl-mode {
    type string;
    description
      "Explicit null label TTL mode.";
  }

  typedef ncs_template_ela-exp-mode {
    type string;
    description
      "Entropy label EXP mode.";
  }

  typedef ncs_template_ela-ttl-mode {
    type string;
    description
      "Entropy label TTL mode.";
  }

  typedef ncs_rpc_notif_hash-type {
    type enumeration {
      enum "flow" {
        value 194;
        description
          "Load balance based on flow.";
      }
      enum "packet" {
        value 195;
        description
          "Load balance based on packet.";
      }
    }
    description
      "Hash type.";
  }

  typedef ncs_rpc_notif_l3vpn-ingpipe-mode {
    type enumeration {
      enum "pipe" {
        value 1;
        description
          "Pipe mode.";
      }
      enum "shortpipe" {
        value 2;
        description
          "Short pipe mode.";
      }
      enum "uniform" {
        value 3;
        description
          "Uniform pipe mode.";
      }
    }
    description
      "The mode of the L3VPN ingress pipe mode.";
  }

  typedef ncs_rpc_notif_l3vpn-egpipe-mode {
    type enumeration {
      enum "pipe" {
        value 1;
        description
          "Pipe mode.";
      }
      enum "shortpipe" {
        value 2;
        description
          "Short pipe mode.";
      }
      enum "uniform" {
        value 3;
        description
          "Uniform pipe mode.";
      }
    }
    description
      "The mode of the L3VPN egress pipe mode.";
  }

  typedef ncs_rpc_notif_l3vpn-pipe-mode {
    type enumeration {
      enum "pipe" {
        value 1;
        description
          "Pipe mode.";
      }
      enum "shortpipe" {
        value 2;
        description
          "Short pipe mode.";
      }
      enum "uniform" {
        value 3;
        description
          "Uniform pipe mode.";
      }
    }
    description
      "The mode of the L3VPN pipe mode.";
  }

  typedef ncs_rpc_notif_l3vpn-ttl-mode {
    type enumeration {
      enum "pipe" {
        value 1;
        description
          "Pipe mode.";
      }
      enum "uniform" {
        value 3;
        description
          "Uniform pipe mode.";
      }
    }
    description
      "The mode of the L3VPN tunnel.";
  }

  typedef ncs_rpc_notif_l3vpn-service-class {
    type enumeration {
      enum "be" {
        value 0;
        description
          "BE service class.";
      }
      enum "af1" {
        value 1;
        description
          "AF1 service class.";
      }
      enum "af2" {
        value 2;
        description
          "AF2 service class.";
      }
      enum "af3" {
        value 3;
        description
          "AF3 service class.";
      }
      enum "af4" {
        value 4;
        description
          "AF4 service class.";
      }
      enum "ef" {
        value 5;
        description
          "EF service class.";
      }
      enum "cs6" {
        value 6;
        description
          "CS6 service class.";
      }
      enum "cs7" {
        value 7;
        description
          "CS7 service class.";
      }
    }
    description
      "The service class of L3VPN.";
  }

  typedef ncs_rpc_notif_l3vpn-color {
    type enumeration {
      enum "green" {
        value 0;
        description
          "Green.";
      }
      enum "yellow" {
        value 1;
        description
          "Yellow.";
      }
      enum "red" {
        value 2;
        description
          "Red.";
      }
    }
    description
      "The color of L3VPN.";
  }

  typedef ncs_rpc_notif_deep-hash-flag {
    type enumeration {
      enum "l3" {
        value 1;
        description
          "Hashed based on L3 IP.";
      }
    }
    description
      "Deep hash configuration flag.";
  }

  typedef ncs_rpc_notif_deep-hash-fragment {
    type enumeration {
      enum "ip" {
        value 1;
        description
          "Hash-field based on IP.";
      }
      enum "disable" {
        value 3;
        description
          "Hash-field not based on anything.";
      }
    }
    description
      "Deep hash configuration fragment.";
  }

  typedef ncs_rpc_notif_enable-flag {
    type enumeration {
      enum "enable" {
        value 1;
        description
          "The CFG is enabled.";
      }
      enum "disable" {
        value 0;
        description
          "The CFG is disabled.";
      }
    }
    description
      "Enable flag type.";
  }

  typedef ncs_rpc_notif_te-pipe-mode {
    type enumeration {
      enum "pipe" {
        value 1;
        description
          "Pipe mode.";
      }
      enum "uniform" {
        value 3;
        description
          "Uniform pipe mode.";
      }
    }
    description
      "TE pipe mode.";
  }

  typedef ncs_rpc_notif_te-pipe-service-class {
    type enumeration {
      enum "be" {
        value 0;
        description
          "Best effort (EF) service class.";
      }
      enum "af1" {
        value 1;
        description
          "Assured forwarding 1 (AF1) service class.";
      }
      enum "af2" {
        value 2;
        description
          "Assured forwarding 2 (AF2) service class.";
      }
      enum "af3" {
        value 3;
        description
          "Assured forwarding 3 (AF3) service class.";
      }
      enum "af4" {
        value 4;
        description
          "Assured forwarding 4 (AF4) service class.";
      }
      enum "ef" {
        value 5;
        description
          "Expedited forwarding (EF) service class.";
      }
      enum "cs6" {
        value 6;
        description
          "Class selector 6 (CS6) service class.";
      }
      enum "cs7" {
        value 7;
        description
          "Class selector 7 (CS7) service class.";
      }
    }
    description
      "TE pipe service class.";
  }

  typedef ncs_rpc_notif_te-pipe-color {
    type enumeration {
      enum "green" {
        value 0;
        description
          "Green.";
      }
      enum "yellow" {
        value 1;
        description
          "Yellow.";
      }
      enum "red" {
        value 2;
        description
          "Red.";
      }
    }
    description
      "TE pipe color.";
  }

  typedef ncs_rpc_notif_check-mode {
    type enumeration {
      enum "ip" {
        value 291;
        description
          "The check mode is IP.";
      }
      enum "label-contained-length" {
        value 292;
        description
          "The check mode is label-contained-length.";
      }
    }
    description
      "Check mode.";
  }

  typedef ncs_rpc_notif_enl-exp-mode {
    type enumeration {
      enum "pipe" {
        value 2;
        description
          "Pipe mode.";
      }
      enum "uniform" {
        value 1;
        description
          "Uniform pipe mode.";
      }
    }
    description
      "Explicit null label EXP mode.";
  }

  typedef ncs_rpc_notif_enl-ttl-mode {
    type enumeration {
      enum "pipe" {
        value 1;
        description
          "Pipe mode.";
      }
      enum "uniform" {
        value 0;
        description
          "Uniform pipe mode.";
      }
    }
    description
      "Explicit null label TTL mode.";
  }

  typedef ncs_rpc_notif_ela-exp-mode {
    type enumeration {
      enum "pipe" {
        value 2;
        description
          "Pipe mode.";
      }
      enum "uniform" {
        value 1;
        description
          "Uniform pipe mode.";
      }
    }
    description
      "Entropy label EXP mode.";
  }

  typedef ncs_rpc_notif_ela-ttl-mode {
    type enumeration {
      enum "pipe" {
        value 1;
        description
          "Pipe mode.";
      }
      enum "uniform" {
        value 0;
        description
          "Uniform pipe mode.";
      }
    }
    description
      "Entropy label TTL mode.";
  }

  typedef live_ncs_hash-type {
    type enumeration {
      enum "flow" {
        value 194;
        description
          "Load balance based on flow.";
      }
      enum "packet" {
        value 195;
        description
          "Load balance based on packet.";
      }
    }
    description
      "Hash type.";
  }

  typedef live_ncs_l3vpn-ingpipe-mode {
    type enumeration {
      enum "pipe" {
        value 1;
        description
          "Pipe mode.";
      }
      enum "shortpipe" {
        value 2;
        description
          "Short pipe mode.";
      }
      enum "uniform" {
        value 3;
        description
          "Uniform pipe mode.";
      }
    }
    description
      "The mode of the L3VPN ingress pipe mode.";
  }

  typedef live_ncs_l3vpn-egpipe-mode {
    type enumeration {
      enum "pipe" {
        value 1;
        description
          "Pipe mode.";
      }
      enum "shortpipe" {
        value 2;
        description
          "Short pipe mode.";
      }
      enum "uniform" {
        value 3;
        description
          "Uniform pipe mode.";
      }
    }
    description
      "The mode of the L3VPN egress pipe mode.";
  }

  typedef live_ncs_l3vpn-pipe-mode {
    type enumeration {
      enum "pipe" {
        value 1;
        description
          "Pipe mode.";
      }
      enum "shortpipe" {
        value 2;
        description
          "Short pipe mode.";
      }
      enum "uniform" {
        value 3;
        description
          "Uniform pipe mode.";
      }
    }
    description
      "The mode of the L3VPN pipe mode.";
  }

  typedef live_ncs_l3vpn-ttl-mode {
    type enumeration {
      enum "pipe" {
        value 1;
        description
          "Pipe mode.";
      }
      enum "uniform" {
        value 3;
        description
          "Uniform pipe mode.";
      }
    }
    description
      "The mode of the L3VPN tunnel.";
  }

  typedef live_ncs_l3vpn-service-class {
    type enumeration {
      enum "be" {
        value 0;
        description
          "BE service class.";
      }
      enum "af1" {
        value 1;
        description
          "AF1 service class.";
      }
      enum "af2" {
        value 2;
        description
          "AF2 service class.";
      }
      enum "af3" {
        value 3;
        description
          "AF3 service class.";
      }
      enum "af4" {
        value 4;
        description
          "AF4 service class.";
      }
      enum "ef" {
        value 5;
        description
          "EF service class.";
      }
      enum "cs6" {
        value 6;
        description
          "CS6 service class.";
      }
      enum "cs7" {
        value 7;
        description
          "CS7 service class.";
      }
    }
    description
      "The service class of L3VPN.";
  }

  typedef live_ncs_l3vpn-color {
    type enumeration {
      enum "green" {
        value 0;
        description
          "Green.";
      }
      enum "yellow" {
        value 1;
        description
          "Yellow.";
      }
      enum "red" {
        value 2;
        description
          "Red.";
      }
    }
    description
      "The color of L3VPN.";
  }

  typedef live_ncs_deep-hash-flag {
    type enumeration {
      enum "l3" {
        value 1;
        description
          "Hashed based on L3 IP.";
      }
    }
    description
      "Deep hash configuration flag.";
  }

  typedef live_ncs_deep-hash-fragment {
    type enumeration {
      enum "ip" {
        value 1;
        description
          "Hash-field based on IP.";
      }
      enum "disable" {
        value 3;
        description
          "Hash-field not based on anything.";
      }
    }
    description
      "Deep hash configuration fragment.";
  }

  typedef live_ncs_enable-flag {
    type enumeration {
      enum "enable" {
        value 1;
        description
          "The CFG is enabled.";
      }
      enum "disable" {
        value 0;
        description
          "The CFG is disabled.";
      }
    }
    description
      "Enable flag type.";
  }

  typedef live_ncs_te-pipe-mode {
    type enumeration {
      enum "pipe" {
        value 1;
        description
          "Pipe mode.";
      }
      enum "uniform" {
        value 3;
        description
          "Uniform pipe mode.";
      }
    }
    description
      "TE pipe mode.";
  }

  typedef live_ncs_te-pipe-service-class {
    type enumeration {
      enum "be" {
        value 0;
        description
          "Best effort (EF) service class.";
      }
      enum "af1" {
        value 1;
        description
          "Assured forwarding 1 (AF1) service class.";
      }
      enum "af2" {
        value 2;
        description
          "Assured forwarding 2 (AF2) service class.";
      }
      enum "af3" {
        value 3;
        description
          "Assured forwarding 3 (AF3) service class.";
      }
      enum "af4" {
        value 4;
        description
          "Assured forwarding 4 (AF4) service class.";
      }
      enum "ef" {
        value 5;
        description
          "Expedited forwarding (EF) service class.";
      }
      enum "cs6" {
        value 6;
        description
          "Class selector 6 (CS6) service class.";
      }
      enum "cs7" {
        value 7;
        description
          "Class selector 7 (CS7) service class.";
      }
    }
    description
      "TE pipe service class.";
  }

  typedef live_ncs_te-pipe-color {
    type enumeration {
      enum "green" {
        value 0;
        description
          "Green.";
      }
      enum "yellow" {
        value 1;
        description
          "Yellow.";
      }
      enum "red" {
        value 2;
        description
          "Red.";
      }
    }
    description
      "TE pipe color.";
  }

  typedef live_ncs_check-mode {
    type enumeration {
      enum "ip" {
        value 291;
        description
          "The check mode is IP.";
      }
      enum "label-contained-length" {
        value 292;
        description
          "The check mode is label-contained-length.";
      }
    }
    description
      "Check mode.";
  }

  typedef live_ncs_enl-exp-mode {
    type enumeration {
      enum "pipe" {
        value 2;
        description
          "Pipe mode.";
      }
      enum "uniform" {
        value 1;
        description
          "Uniform pipe mode.";
      }
    }
    description
      "Explicit null label EXP mode.";
  }

  typedef live_ncs_enl-ttl-mode {
    type enumeration {
      enum "pipe" {
        value 1;
        description
          "Pipe mode.";
      }
      enum "uniform" {
        value 0;
        description
          "Uniform pipe mode.";
      }
    }
    description
      "Explicit null label TTL mode.";
  }

  typedef live_ncs_ela-exp-mode {
    type enumeration {
      enum "pipe" {
        value 2;
        description
          "Pipe mode.";
      }
      enum "uniform" {
        value 1;
        description
          "Uniform pipe mode.";
      }
    }
    description
      "Entropy label EXP mode.";
  }

  typedef live_ncs_ela-ttl-mode {
    type enumeration {
      enum "pipe" {
        value 1;
        description
          "Pipe mode.";
      }
      enum "uniform" {
        value 0;
        description
          "Uniform pipe mode.";
      }
    }
    description
      "Entropy label TTL mode.";
  }

  typedef hash-type {
    type enumeration {
      enum "flow" {
        value 194;
        description
          "Load balance based on flow.";
      }
      enum "packet" {
        value 195;
        description
          "Load balance based on packet.";
      }
    }
    description
      "Hash type.";
  }

  typedef l3vpn-ingpipe-mode {
    type enumeration {
      enum "pipe" {
        value 1;
        description
          "Pipe mode.";
      }
      enum "shortpipe" {
        value 2;
        description
          "Short pipe mode.";
      }
      enum "uniform" {
        value 3;
        description
          "Uniform pipe mode.";
      }
    }
    description
      "The mode of the L3VPN ingress pipe mode.";
  }

  typedef l3vpn-egpipe-mode {
    type enumeration {
      enum "pipe" {
        value 1;
        description
          "Pipe mode.";
      }
      enum "shortpipe" {
        value 2;
        description
          "Short pipe mode.";
      }
      enum "uniform" {
        value 3;
        description
          "Uniform pipe mode.";
      }
    }
    description
      "The mode of the L3VPN egress pipe mode.";
  }

  typedef l3vpn-pipe-mode {
    type enumeration {
      enum "pipe" {
        value 1;
        description
          "Pipe mode.";
      }
      enum "shortpipe" {
        value 2;
        description
          "Short pipe mode.";
      }
      enum "uniform" {
        value 3;
        description
          "Uniform pipe mode.";
      }
    }
    description
      "The mode of the L3VPN pipe mode.";
  }

  typedef l3vpn-ttl-mode {
    type enumeration {
      enum "pipe" {
        value 1;
        description
          "Pipe mode.";
      }
      enum "uniform" {
        value 3;
        description
          "Uniform pipe mode.";
      }
    }
    description
      "The mode of the L3VPN tunnel.";
  }

  typedef l3vpn-service-class {
    type enumeration {
      enum "be" {
        value 0;
        description
          "BE service class.";
      }
      enum "af1" {
        value 1;
        description
          "AF1 service class.";
      }
      enum "af2" {
        value 2;
        description
          "AF2 service class.";
      }
      enum "af3" {
        value 3;
        description
          "AF3 service class.";
      }
      enum "af4" {
        value 4;
        description
          "AF4 service class.";
      }
      enum "ef" {
        value 5;
        description
          "EF service class.";
      }
      enum "cs6" {
        value 6;
        description
          "CS6 service class.";
      }
      enum "cs7" {
        value 7;
        description
          "CS7 service class.";
      }
    }
    description
      "The service class of L3VPN.";
  }

  typedef l3vpn-color {
    type enumeration {
      enum "green" {
        value 0;
        description
          "Green.";
      }
      enum "yellow" {
        value 1;
        description
          "Yellow.";
      }
      enum "red" {
        value 2;
        description
          "Red.";
      }
    }
    description
      "The color of L3VPN.";
  }

  typedef deep-hash-flag {
    type enumeration {
      enum "l3" {
        value 1;
        description
          "Hashed based on L3 IP.";
      }
    }
    description
      "Deep hash configuration flag.";
  }

  typedef deep-hash-fragment {
    type enumeration {
      enum "ip" {
        value 1;
        description
          "Hash-field based on IP.";
      }
      enum "disable" {
        value 3;
        description
          "Hash-field not based on anything.";
      }
    }
    description
      "Deep hash configuration fragment.";
  }

  typedef enable-flag {
    type enumeration {
      enum "enable" {
        value 1;
        description
          "The CFG is enabled.";
      }
      enum "disable" {
        value 0;
        description
          "The CFG is disabled.";
      }
    }
    description
      "Enable flag type.";
  }

  typedef te-pipe-mode {
    type enumeration {
      enum "pipe" {
        value 1;
        description
          "Pipe mode.";
      }
      enum "uniform" {
        value 3;
        description
          "Uniform pipe mode.";
      }
    }
    description
      "TE pipe mode.";
  }

  typedef te-pipe-service-class {
    type enumeration {
      enum "be" {
        value 0;
        description
          "Best effort (EF) service class.";
      }
      enum "af1" {
        value 1;
        description
          "Assured forwarding 1 (AF1) service class.";
      }
      enum "af2" {
        value 2;
        description
          "Assured forwarding 2 (AF2) service class.";
      }
      enum "af3" {
        value 3;
        description
          "Assured forwarding 3 (AF3) service class.";
      }
      enum "af4" {
        value 4;
        description
          "Assured forwarding 4 (AF4) service class.";
      }
      enum "ef" {
        value 5;
        description
          "Expedited forwarding (EF) service class.";
      }
      enum "cs6" {
        value 6;
        description
          "Class selector 6 (CS6) service class.";
      }
      enum "cs7" {
        value 7;
        description
          "Class selector 7 (CS7) service class.";
      }
    }
    description
      "TE pipe service class.";
  }

  typedef te-pipe-color {
    type enumeration {
      enum "green" {
        value 0;
        description
          "Green.";
      }
      enum "yellow" {
        value 1;
        description
          "Yellow.";
      }
      enum "red" {
        value 2;
        description
          "Red.";
      }
    }
    description
      "TE pipe color.";
  }

  typedef check-mode {
    type enumeration {
      enum "ip" {
        value 291;
        description
          "The check mode is IP.";
      }
      enum "label-contained-length" {
        value 292;
        description
          "The check mode is label-contained-length.";
      }
    }
    description
      "Check mode.";
  }

  typedef enl-exp-mode {
    type enumeration {
      enum "pipe" {
        value 2;
        description
          "Pipe mode.";
      }
      enum "uniform" {
        value 1;
        description
          "Uniform pipe mode.";
      }
    }
    description
      "Explicit null label EXP mode.";
  }

  typedef enl-ttl-mode {
    type enumeration {
      enum "pipe" {
        value 1;
        description
          "Pipe mode.";
      }
      enum "uniform" {
        value 0;
        description
          "Uniform pipe mode.";
      }
    }
    description
      "Explicit null label TTL mode.";
  }

  typedef ela-exp-mode {
    type enumeration {
      enum "pipe" {
        value 2;
        description
          "Pipe mode.";
      }
      enum "uniform" {
        value 1;
        description
          "Uniform pipe mode.";
      }
    }
    description
      "Entropy label EXP mode.";
  }

  typedef ela-ttl-mode {
    type enumeration {
      enum "pipe" {
        value 1;
        description
          "Pipe mode.";
      }
      enum "uniform" {
        value 0;
        description
          "Uniform pipe mode.";
      }
    }
    description
      "Entropy label TTL mode.";
  }

  augment "/ncs:devices/ncs:template/ncs:ned-id/ncs:config/loadbalance:loadbalance" {
    description
      "MPLS forward configuration to the load balance module.";
    container mpls-hashpacket {
      description
        "Configure load balance based on packet.";
      leaf hash-type {
        type ncs_template_hash-type;
        // NCS drop default statement
        description
          "Load balance mode.";
      }
    }
    container mpls-intfmtu {
      description
        "Configure interface MTU check mode.";
      leaf chkmode {
        type ncs_template_check-mode;
        // NCS drop default statement
        description
          "Check mode configuration.";
      }
    }
    container mpls-loadblc-elawords {
      description
        "Configure MPLS entropy label load balance control word enable.";
      leaf elawords-enable {
        type ncs_template_enable-flag;
        // NCS drop default statement
        description
          "MPLS entropy label load balance control word enable value.";
      }
    }
    container p2mp-load-balance-num {
      description
        "Configure P2MP trunk load balance.";
      leaf number {
        type string;
        // NCS drop default statement
        description
          "P2MP trunk load balance number.";
      }
    }
  }
  augment "/ncs:devices/ncs:device/ncs:live-status/loadbalance:loadbalance" {
    description
      "MPLS forward configuration to the load balance module.";
    container mpls-hashpacket {
      tailf:ncs-device-type "netconf";
      tailf:display-when "not(../../../ncs:module) or ../../../ncs:module[ncs:name='huawei-mpls-forward'] or (../../../ncs:live-status-protocol[not(ncs:capability)]) or (../../../ncs:live-status-protocol/ncs:capability/ncs:module[.='huawei-mpls-forward'])";
      description
        "Configure load balance based on packet.";
      leaf hash-type {
        type live_ncs_hash-type;
        // NCS drop default statement
        description
          "Load balance mode.";
      }
    }
    container mpls-intfmtu {
      tailf:ncs-device-type "netconf";
      tailf:display-when "not(../../../ncs:module) or ../../../ncs:module[ncs:name='huawei-mpls-forward'] or (../../../ncs:live-status-protocol[not(ncs:capability)]) or (../../../ncs:live-status-protocol/ncs:capability/ncs:module[.='huawei-mpls-forward'])";
      description
        "Configure interface MTU check mode.";
      leaf chkmode {
        type live_ncs_check-mode;
        // NCS drop default statement
        description
          "Check mode configuration.";
      }
    }
    container mpls-loadblc-elawords {
      tailf:ncs-device-type "netconf";
      tailf:display-when "not(../../../ncs:module) or ../../../ncs:module[ncs:name='huawei-mpls-forward'] or (../../../ncs:live-status-protocol[not(ncs:capability)]) or (../../../ncs:live-status-protocol/ncs:capability/ncs:module[.='huawei-mpls-forward'])";
      description
        "Configure MPLS entropy label load balance control word enable.";
      leaf elawords-enable {
        type live_ncs_enable-flag;
        // NCS drop default statement
        description
          "MPLS entropy label load balance control word enable value.";
      }
    }
    container p2mp-load-balance-num {
      tailf:ncs-device-type "netconf";
      tailf:display-when "not(../../../ncs:module) or ../../../ncs:module[ncs:name='huawei-mpls-forward'] or (../../../ncs:live-status-protocol[not(ncs:capability)]) or (../../../ncs:live-status-protocol/ncs:capability/ncs:module[.='huawei-mpls-forward'])";
      description
        "Configure P2MP trunk load balance.";
      leaf number {
        type uint32 {
          range "2..64";
        }
        // NCS drop default statement
        description
          "P2MP trunk load balance number.";
      }
    }
  }
  augment "/ncs:devices/ncs:device/ncs:config/loadbalance:loadbalance" {
    description
      "MPLS forward configuration to the load balance module.";
    container mpls-hashpacket {
      tailf:ncs-device-type "netconf";
      tailf:display-when "not(../../../ncs:module) or ../../../ncs:module[ncs:name='huawei-mpls-forward']";
      description
        "Configure load balance based on packet.";
      leaf hash-type {
        type hash-type;
        default "flow";
        description
          "Load balance mode.";
      }
    }
    container mpls-intfmtu {
      tailf:ncs-device-type "netconf";
      tailf:display-when "not(../../../ncs:module) or ../../../ncs:module[ncs:name='huawei-mpls-forward']";
      description
        "Configure interface MTU check mode.";
      leaf chkmode {
        type check-mode;
        default "ip";
        description
          "Check mode configuration.";
      }
    }
    container mpls-loadblc-elawords {
      tailf:ncs-device-type "netconf";
      tailf:display-when "not(../../../ncs:module) or ../../../ncs:module[ncs:name='huawei-mpls-forward']";
      description
        "Configure MPLS entropy label load balance control word enable.";
      leaf elawords-enable {
        type enable-flag;
        default "disable";
        description
          "MPLS entropy label load balance control word enable value.";
      }
    }
    container p2mp-load-balance-num {
      tailf:ncs-device-type "netconf";
      tailf:display-when "not(../../../ncs:module) or ../../../ncs:module[ncs:name='huawei-mpls-forward']";
      description
        "Configure P2MP trunk load balance.";
      leaf number {
        type uint32 {
          range "2..64";
        }
        default "16";
        description
          "P2MP trunk load balance number.";
      }
    }
  }
  augment "/ncs:devices/ncs:template/ncs:ned-id/ncs:config/ni:network-instance/ni:instances/ni:instance/l3vpn:afs/l3vpn:af" {
    description
      "MPLS forward configuration to the L3VPN module.";
    container vrfpipe {
      description
        "Configure L3VPN pipe.";
      leaf split-mode {
        type string;
        // NCS drop must statement
        // NCS drop default statement
        description
          "Enable/disable pipe mode.";
      }
      leaf pipe-mode {
        // NCS drop when statement
        type ncs_template_l3vpn-pipe-mode;
        // NCS drop default statement
        description
          "Pipe mode.";
      }
      leaf ingress-pipe-mode {
        // NCS drop when statement
        type ncs_template_l3vpn-ingpipe-mode;
        // NCS drop default statement
        description
          "Ingress pipe mode.";
      }
      leaf service-class {
        // NCS drop when statement
        type ncs_template_l3vpn-service-class;
        // NCS drop default statement
        description
          "Service class.";
      }
      leaf color {
        // NCS drop when statement
        type ncs_template_l3vpn-color;
        // NCS drop default statement
        description
          "Color.";
      }
      leaf egress-pipe-mode {
        // NCS drop when statement
        type ncs_template_l3vpn-egpipe-mode;
        // NCS drop default statement
        description
          "Egress pipe mode.";
      }
      leaf domain-name {
        // NCS drop when statement
        type string;
        // NCS drop default statement
        description
          "DS domain name.";
      }
    }
    container vpn-ttlmode {
      description
        "Configure TTL mode.";
      leaf ttlmode {
        type ncs_template_l3vpn-ttl-mode;
        // NCS drop default statement
        description
          "TTL mode value.";
      }
    }
  }
  augment "/ncs:devices/ncs:device/ncs:live-status/ni:network-instance/ni:instances/ni:instance/l3vpn:afs/l3vpn:af" {
    description
      "MPLS forward configuration to the L3VPN module.";
    container vrfpipe {
      tailf:ncs-device-type "netconf";
      tailf:display-when "not(../../../../../../../ncs:module) or ../../../../../../../ncs:module[ncs:name='huawei-mpls-forward'] or (../../../../../../../ncs:live-status-protocol[not(ncs:capability)]) or (../../../../../../../ncs:live-status-protocol/ncs:capability/ncs:module[.='huawei-mpls-forward'])";
      description
        "Configure L3VPN pipe.";
      leaf split-mode {
        type boolean;
        // NCS drop must statement
        // NCS drop default statement
        description
          "Enable/disable pipe mode.";
      }
      leaf pipe-mode {
        // NCS drop when statement
        type live_ncs_l3vpn-pipe-mode;
        // NCS drop default statement
        description
          "Pipe mode.";
      }
      leaf ingress-pipe-mode {
        // NCS drop when statement
        type live_ncs_l3vpn-ingpipe-mode;
        // NCS drop default statement
        description
          "Ingress pipe mode.";
      }
      leaf service-class {
        // NCS drop when statement
        type live_ncs_l3vpn-service-class;
        // NCS drop default statement
        description
          "Service class.";
      }
      leaf color {
        // NCS drop when statement
        type live_ncs_l3vpn-color;
        // NCS drop default statement
        description
          "Color.";
      }
      leaf egress-pipe-mode {
        // NCS drop when statement
        type live_ncs_l3vpn-egpipe-mode;
        // NCS drop default statement
        description
          "Egress pipe mode.";
      }
      leaf domain-name {
        // NCS drop when statement
        type leafref {
          path "/ncs:devices/ncs:device/ncs:live-status/qos:qos/qos:classifier-template/qos:diffserv-domains/qos:diffserv-domain/qos:name" {
            tailf:xpath-root 3;
          }
        }
        // NCS drop default statement
        description
          "DS domain name.";
      }
    }
    container vpn-ttlmode {
      tailf:ncs-device-type "netconf";
      tailf:display-when "not(../../../../../../../ncs:module) or ../../../../../../../ncs:module[ncs:name='huawei-mpls-forward'] or (../../../../../../../ncs:live-status-protocol[not(ncs:capability)]) or (../../../../../../../ncs:live-status-protocol/ncs:capability/ncs:module[.='huawei-mpls-forward'])";
      description
        "Configure TTL mode.";
      leaf ttlmode {
        type live_ncs_l3vpn-ttl-mode;
        // NCS drop default statement
        description
          "TTL mode value.";
      }
    }
  }
  augment "/ncs:devices/ncs:device/ncs:config/ni:network-instance/ni:instances/ni:instance/l3vpn:afs/l3vpn:af" {
    description
      "MPLS forward configuration to the L3VPN module.";
    container vrfpipe {
      tailf:ncs-device-type "netconf";
      tailf:display-when "not(../../../../../../../ncs:module) or ../../../../../../../ncs:module[ncs:name='huawei-mpls-forward']";
      description
        "Configure L3VPN pipe.";
      leaf split-mode {
        type boolean;
        must "((../split-mode='false' and ../pipe-mode and not(../ingress-pipe-mode) and not(../egress-pipe-mode)) or (../split-mode='true' and not(../pipe-mode) and ../ingress-pipe-mode and ../egress-pipe-mode))" {
          tailf:xpath-root 3;
        }
        default "false";
        description
          "Enable/disable pipe mode.";
      }
      leaf pipe-mode {
        when "../split-mode='false'" {
          tailf:xpath-root 3;
        }
        type l3vpn-pipe-mode;
        default "uniform";
        description
          "Pipe mode.";
      }
      leaf ingress-pipe-mode {
        when "../split-mode='true'" {
          tailf:xpath-root 3;
        }
        type l3vpn-ingpipe-mode;
        default "uniform";
        description
          "Ingress pipe mode.";
      }
      leaf service-class {
        when "(../pipe-mode='pipe' or ../pipe-mode='shortpipe' or ../ingress-pipe-mode='pipe' or ../ingress-pipe-mode='shortpipe')" {
          tailf:xpath-root 3;
        }
        type l3vpn-service-class;
        default "be";
        description
          "Service class.";
      }
      leaf color {
        when "(../pipe-mode='pipe' or ../pipe-mode='shortpipe'  or ../ingress-pipe-mode='pipe' or ../ingress-pipe-mode='shortpipe')" {
          tailf:xpath-root 3;
        }
        type l3vpn-color;
        default "green";
        description
          "Color.";
      }
      leaf egress-pipe-mode {
        when "../split-mode='true'" {
          tailf:xpath-root 3;
        }
        type l3vpn-egpipe-mode;
        default "uniform";
        description
          "Egress pipe mode.";
      }
      leaf domain-name {
        when "(../pipe-mode='shortpipe'  or ../egress-pipe-mode='shortpipe')" {
          tailf:xpath-root 3;
        }
        type leafref {
          path "/ncs:devices/ncs:device/ncs:config/qos:qos/qos:classifier-template/qos:diffserv-domains/qos:diffserv-domain/qos:name" {
            tailf:xpath-root 3;
          }
        }
        default "default";
        description
          "DS domain name.";
      }
    }
    container vpn-ttlmode {
      tailf:ncs-device-type "netconf";
      tailf:display-when "not(../../../../../../../ncs:module) or ../../../../../../../ncs:module[ncs:name='huawei-mpls-forward']";
      description
        "Configure TTL mode.";
      leaf ttlmode {
        type l3vpn-ttl-mode;
        default "pipe";
        description
          "TTL mode value.";
      }
    }
  }
  augment "/ncs:devices/ncs:template/ncs:ned-id/ncs:config/ifm:ifm/ifm:interfaces/ifm:interface" {
    description
      "MPLS forward configuration to the ifm module.";
    container deephashcfg {
      // NCS drop when statement
      description
        "Configure MPLS deep hash mode.";
      leaf fragment-field {
        type ncs_template_deep-hash-fragment;
        // NCS drop default statement
        description
          "MPLS deep hash fields.";
      }
      leaf deepmplshash {
        type ncs_template_deep-hash-flag;
        // NCS drop default statement
        description
          "MPLS deep hash value.";
      }
    }
    container if-poison-reverse {
      // NCS drop when statement
      presence "Enable poison reverse on an interface";
      description
        "Configure MPLS poison reverse on the interface.";
    }
    container if-p2mp-load-balance {
      // NCS drop when statement
      description
        "Configure Trunk-enable.";
      leaf loadbanlance-enable {
        type ncs_template_enable-flag;
        // NCS drop default statement
        description
          "Trunk enable flag.";
      }
      leaf root-loadbanlance-enable {
        type ncs_template_enable-flag;
        // NCS drop default statement
        description
          "Root node trunk enable flag.";
      }
      leaf root-loadbanlance-spmsidis {
        // NCS drop when statement
        type ncs_template_enable-flag;
        // NCS drop default statement
        description
          "Root node S-PMSI trunk disable flag.";
      }
    }
    container bgp-localifnet-traffic {
      // NCS drop when statement
      description
        "Configure the HQoS function for the traffic carried by a BGP local IFNET tunnel on an interface.";
      leaf localifnet-enable {
        type ncs_template_enable-flag;
        // NCS drop default statement
        description
          "Traffic enable flag.";
      }
    }
  }
  augment "/ncs:devices/ncs:device/ncs:live-status/ifm:ifm/ifm:interfaces/ifm:interface" {
    description
      "MPLS forward configuration to the ifm module.";
    container deephashcfg {
      tailf:ncs-device-type "netconf";
      tailf:display-when "not(../../../../../ncs:module) or ../../../../../ncs:module[ncs:name='huawei-mpls-forward'] or (../../../../../ncs:live-status-protocol[not(ncs:capability)]) or (../../../../../ncs:live-status-protocol/ncs:capability/ncs:module[.='huawei-mpls-forward'])";
      // NCS drop when statement
      description
        "Configure MPLS deep hash mode.";
      leaf fragment-field {
        type live_ncs_deep-hash-fragment;
        // NCS drop default statement
        description
          "MPLS deep hash fields.";
      }
      leaf deepmplshash {
        type live_ncs_deep-hash-flag;
        // NCS drop default statement
        description
          "MPLS deep hash value.";
      }
    }
    container if-poison-reverse {
      tailf:ncs-device-type "netconf";
      tailf:display-when "not(../../../../../ncs:module) or ../../../../../ncs:module[ncs:name='huawei-mpls-forward'] or (../../../../../ncs:live-status-protocol[not(ncs:capability)]) or (../../../../../ncs:live-status-protocol/ncs:capability/ncs:module[.='huawei-mpls-forward'])";
      // NCS drop when statement
      presence "Enable poison reverse on an interface";
      description
        "Configure MPLS poison reverse on the interface.";
    }
    container if-p2mp-load-balance {
      tailf:ncs-device-type "netconf";
      tailf:display-when "not(../../../../../ncs:module) or ../../../../../ncs:module[ncs:name='huawei-mpls-forward'] or (../../../../../ncs:live-status-protocol[not(ncs:capability)]) or (../../../../../ncs:live-status-protocol/ncs:capability/ncs:module[.='huawei-mpls-forward'])";
      // NCS drop when statement
      description
        "Configure Trunk-enable.";
      leaf loadbanlance-enable {
        type live_ncs_enable-flag;
        // NCS drop default statement
        description
          "Trunk enable flag.";
      }
      leaf root-loadbanlance-enable {
        type live_ncs_enable-flag;
        // NCS drop default statement
        description
          "Root node trunk enable flag.";
      }
      leaf root-loadbanlance-spmsidis {
        // NCS drop when statement
        type live_ncs_enable-flag;
        // NCS drop default statement
        description
          "Root node S-PMSI trunk disable flag.";
      }
    }
    container bgp-localifnet-traffic {
      tailf:ncs-device-type "netconf";
      tailf:display-when "not(../../../../../ncs:module) or ../../../../../ncs:module[ncs:name='huawei-mpls-forward'] or (../../../../../ncs:live-status-protocol[not(ncs:capability)]) or (../../../../../ncs:live-status-protocol/ncs:capability/ncs:module[.='huawei-mpls-forward'])";
      // NCS drop when statement
      description
        "Configure the HQoS function for the traffic carried by a BGP local IFNET tunnel on an interface.";
      leaf localifnet-enable {
        type live_ncs_enable-flag;
        // NCS drop default statement
        description
          "Traffic enable flag.";
      }
    }
  }
  augment "/ncs:devices/ncs:device/ncs:config/ifm:ifm/ifm:interfaces/ifm:interface" {
    description
      "MPLS forward configuration to the ifm module.";
    container deephashcfg {
      tailf:ncs-device-type "netconf";
      tailf:display-when "not(../../../../../ncs:module) or ../../../../../ncs:module[ncs:name='huawei-mpls-forward']";
      when "../ifm:type='Ethernet' or ../ifm:type='FlexE' or ../ifm:type='GigabitEthernet' or ../ifm:type='100GE' or ../ifm:type='10GE' or ../ifm:type='4x10GE' or ../ifm:type='10x10GE' or ../ifm:type='3x40GE' or ../ifm:type='4x25GE' or ../ifm:type='25GE' or ../ifm:type='50GE' or ../ifm:type='50|100GE' or ../ifm:type='XGigabitEthernet' or ../ifm:type='Pos' or ../ifm:type='40GE' or ../ifm:type='MEth' or ../ifm:type='400GE' or ../ifm:type='GEBrief' or ../ifm:type='200GE'" {
        tailf:xpath-root 3;
      }
      description
        "Configure MPLS deep hash mode.";
      leaf fragment-field {
        type deep-hash-fragment;
        default "disable";
        description
          "MPLS deep hash fields.";
      }
      leaf deepmplshash {
        type deep-hash-flag;
        default "l3";
        description
          "MPLS deep hash value.";
      }
    }
    container if-poison-reverse {
      tailf:ncs-device-type "netconf";
      tailf:display-when "not(../../../../../ncs:module) or ../../../../../ncs:module[ncs:name='huawei-mpls-forward']";
      when "../ifm:type='Ethernet' or ../ifm:type='FlexE' or ../ifm:type='GigabitEthernet' or ../ifm:type='100GE' or ../ifm:type='10GE' or ../ifm:type='4x10GE' or ../ifm:type='10x10GE' or ../ifm:type='3x40GE' or ../ifm:type='4x25GE' or ../ifm:type='25GE' or ../ifm:type='XGigabitEthernet' or ../ifm:type='Eth-Trunk' or ../ifm:type='Ip-Trunk' or ../ifm:type='400GE' or ../ifm:type='Pos' or ../ifm:type='40GE' or ../ifm:type='MEth' or ../ifm:type='GEBrief' or ../ifm:type='200GE' or ../ifm:type='50|100GE' or ../ifm:type='50GE'" {
        tailf:xpath-root 3;
      }
      presence "Enable poison reverse on an interface";
      description
        "Configure MPLS poison reverse on the interface.";
    }
    container if-p2mp-load-balance {
      tailf:ncs-device-type "netconf";
      tailf:display-when "not(../../../../../ncs:module) or ../../../../../ncs:module[ncs:name='huawei-mpls-forward']";
      when "../ifm:type='Eth-Trunk' or ../ifm:type='Ip-Trunk'" {
        tailf:xpath-root 3;
      }
      description
        "Configure Trunk-enable.";
      leaf loadbanlance-enable {
        type enable-flag;
        default "disable";
        description
          "Trunk enable flag.";
      }
      leaf root-loadbanlance-enable {
        type enable-flag;
        default "disable";
        description
          "Root node trunk enable flag.";
      }
      leaf root-loadbanlance-spmsidis {
        when "../root-loadbanlance-enable='enable' or /mpls:mpls/mpls-forward:p2mp-forceload/mpls-forward:forceload-enable='enable'" {
          tailf:xpath-root 3;
        }
        type enable-flag;
        default "disable";
        description
          "Root node S-PMSI trunk disable flag.";
      }
    }
    container bgp-localifnet-traffic {
      tailf:ncs-device-type "netconf";
      tailf:display-when "not(../../../../../ncs:module) or ../../../../../ncs:module[ncs:name='huawei-mpls-forward']";
      when "../ifm:type='GigabitEthernet' or ../ifm:type='XGigabitEthernet' or ../ifm:type='10GE' or ../ifm:type='25GE' or ../ifm:type='40GE' or ../ifm:type='50GE' or ../ifm:type='100GE' or ../ifm:type='200GE' or ../ifm:type = 'FlexE' or ../ifm:type='400GE' or ../ifm:type='50|100GE' or ../ifm:type='Ethernet' or ../ifm:type='Eth-Trunk' or ../ifm:type='Ip-Trunk' or ../ifm:type='Pos' or ../ifm:type='4x10GE' or ../ifm:type='10x10GE' or ../ifm:type='3x40GE' or ../ifm:type='4x25GE' or ../ifm:type='Mp-group' or ../ifm:type='Serial' or ../ifm:class='sub-interface'" {
        tailf:xpath-root 3;
      }
      description
        "Configure the HQoS function for the traffic carried by a BGP local IFNET tunnel on an interface.";
      leaf localifnet-enable {
        type enable-flag;
        default "disable";
        description
          "Traffic enable flag.";
      }
    }
  }
  augment "/ncs:devices/ncs:template/ncs:ned-id/ncs:config/ifm:ifm/ifm:interfaces/ifm:interface/tnlm:tunnel-protocol/tnlm:type/mpls-te:mpls-te/mpls-te:te-tunnel" {
    description
      "MPLS forward configuration to the MPLS TE tunnel module.";
    container mplstunnelpipe {
      description
        "Configure TE pipe mode.";
      leaf pipe-mode {
        type ncs_template_te-pipe-mode;
        // NCS drop default statement
        description
          "Specifies the pipe mode of TE tunnel.";
      }
      leaf service-class {
        // NCS drop when statement
        type ncs_template_te-pipe-service-class;
        // NCS drop default statement
        description
          "PHB of ingress packet.";
      }
      leaf color {
        // NCS drop when statement
        type ncs_template_te-pipe-color;
        // NCS drop default statement
        description
          "Color of ingress packet.";
      }
    }
    container mpls-tunnel-service-class {
      description
        "Configure specifies the service class of te tunnel.";
      leaf default-enable {
        type string;
        // NCS drop must statement
        // NCS drop default statement
        description
          "Enable/disable default service class.";
      }
      leaf be-enable {
        type string;
        // NCS drop must statement
        // NCS drop default statement
        description
          "Enable/disable BE service class.";
      }
      leaf af1-enable {
        type string;
        // NCS drop must statement
        // NCS drop default statement
        description
          "Enable/disable AF1 service class.";
      }
      leaf af2-enable {
        type string;
        // NCS drop must statement
        // NCS drop default statement
        description
          "Enable/disable AF2 service class.";
      }
      leaf af3-enable {
        type string;
        // NCS drop must statement
        // NCS drop default statement
        description
          "Enable/disable AF3 service class.";
      }
      leaf af4-enable {
        type string;
        // NCS drop must statement
        // NCS drop default statement
        description
          "Enable/disable AF4 service class.";
      }
      leaf ef-enable {
        type string;
        // NCS drop must statement
        // NCS drop default statement
        description
          "Enable/disable EF service class.";
      }
      leaf cs6-enable {
        type string;
        // NCS drop must statement
        // NCS drop default statement
        description
          "Enable/disable CS6 service class.";
      }
      leaf cs7-enable {
        type string;
        // NCS drop must statement
        // NCS drop default statement
        description
          "Enable/disable CS7 service class.";
      }
    }
    container mpls-tunnel-dscp {
      // NCS drop when statement
      description
        "Configure DSCP value.";
      leaf ipv4-defalut {
        type string;
        // NCS drop default statement
        description
          "Enable/disable default of IPv4.";
      }
      leaf ipv6-defalut {
        type string;
        // NCS drop default statement
        description
          "Enable/disable default of IPv6.";
      }
      leaf ipv4-dscp-value {
        type string;
        // NCS drop must statement
        // NCS drop default statement
        description
          "IPv4 DSCP, in the format of 0,1,2,3-10,63. A DSCP value is an integer ranging from 0 to 63.Entering an asterisk (*) deletes DSCP configuration.";
      }
      leaf ipv6-dscp-value {
        type string;
        // NCS drop must statement
        // NCS drop default statement
        description
          "IPv6 DSCP, in the format of 0,1,2,3-10,63. A DSCP value is an integer ranging from 0 to 63.Entering an asterisk (*) deletes DSCP configuration.";
      }
    }
  }
  augment "/ncs:devices/ncs:device/ncs:live-status/ifm:ifm/ifm:interfaces/ifm:interface/tnlm:tunnel-protocol/tnlm:type/mpls-te:mpls-te/mpls-te:te-tunnel" {
    description
      "MPLS forward configuration to the MPLS TE tunnel module.";
    container mplstunnelpipe {
      tailf:ncs-device-type "netconf";
      tailf:display-when "not(../../../../../../../../../ncs:module) or ../../../../../../../../../ncs:module[ncs:name='huawei-mpls-forward'] or (../../../../../../../../../ncs:live-status-protocol[not(ncs:capability)]) or (../../../../../../../../../ncs:live-status-protocol/ncs:capability/ncs:module[.='huawei-mpls-forward'])";
      description
        "Configure TE pipe mode.";
      leaf pipe-mode {
        type live_ncs_te-pipe-mode;
        // NCS drop default statement
        description
          "Specifies the pipe mode of TE tunnel.";
      }
      leaf service-class {
        // NCS drop when statement
        type live_ncs_te-pipe-service-class;
        // NCS drop default statement
        description
          "PHB of ingress packet.";
      }
      leaf color {
        // NCS drop when statement
        type live_ncs_te-pipe-color;
        // NCS drop default statement
        description
          "Color of ingress packet.";
      }
    }
    container mpls-tunnel-service-class {
      tailf:ncs-device-type "netconf";
      tailf:display-when "not(../../../../../../../../../ncs:module) or ../../../../../../../../../ncs:module[ncs:name='huawei-mpls-forward'] or (../../../../../../../../../ncs:live-status-protocol[not(ncs:capability)]) or (../../../../../../../../../ncs:live-status-protocol/ncs:capability/ncs:module[.='huawei-mpls-forward'])";
      description
        "Configure specifies the service class of te tunnel.";
      leaf default-enable {
        type boolean;
        // NCS drop must statement
        // NCS drop default statement
        description
          "Enable/disable default service class.";
      }
      leaf be-enable {
        type boolean;
        // NCS drop must statement
        // NCS drop default statement
        description
          "Enable/disable BE service class.";
      }
      leaf af1-enable {
        type boolean;
        // NCS drop must statement
        // NCS drop default statement
        description
          "Enable/disable AF1 service class.";
      }
      leaf af2-enable {
        type boolean;
        // NCS drop must statement
        // NCS drop default statement
        description
          "Enable/disable AF2 service class.";
      }
      leaf af3-enable {
        type boolean;
        // NCS drop must statement
        // NCS drop default statement
        description
          "Enable/disable AF3 service class.";
      }
      leaf af4-enable {
        type boolean;
        // NCS drop must statement
        // NCS drop default statement
        description
          "Enable/disable AF4 service class.";
      }
      leaf ef-enable {
        type boolean;
        // NCS drop must statement
        // NCS drop default statement
        description
          "Enable/disable EF service class.";
      }
      leaf cs6-enable {
        type boolean;
        // NCS drop must statement
        // NCS drop default statement
        description
          "Enable/disable CS6 service class.";
      }
      leaf cs7-enable {
        type boolean;
        // NCS drop must statement
        // NCS drop default statement
        description
          "Enable/disable CS7 service class.";
      }
    }
    container mpls-tunnel-dscp {
      tailf:ncs-device-type "netconf";
      tailf:display-when "not(../../../../../../../../../ncs:module) or ../../../../../../../../../ncs:module[ncs:name='huawei-mpls-forward'] or (../../../../../../../../../ncs:live-status-protocol[not(ncs:capability)]) or (../../../../../../../../../ncs:live-status-protocol/ncs:capability/ncs:module[.='huawei-mpls-forward'])";
      // NCS drop when statement
      description
        "Configure DSCP value.";
      leaf ipv4-defalut {
        type boolean;
        // NCS drop default statement
        description
          "Enable/disable default of IPv4.";
      }
      leaf ipv6-defalut {
        type boolean;
        // NCS drop default statement
        description
          "Enable/disable default of IPv6.";
      }
      leaf ipv4-dscp-value {
        type string {
          length "1..512";
        }
        // NCS drop must statement
        // NCS drop default statement
        description
          "IPv4 DSCP, in the format of 0,1,2,3-10,63. A DSCP value is an integer ranging from 0 to 63.Entering an asterisk (*) deletes DSCP configuration.";
      }
      leaf ipv6-dscp-value {
        type string {
          length "1..512";
        }
        // NCS drop must statement
        // NCS drop default statement
        description
          "IPv6 DSCP, in the format of 0,1,2,3-10,63. A DSCP value is an integer ranging from 0 to 63.Entering an asterisk (*) deletes DSCP configuration.";
      }
    }
  }
  augment "/ncs:devices/ncs:device/ncs:config/ifm:ifm/ifm:interfaces/ifm:interface/tnlm:tunnel-protocol/tnlm:type/mpls-te:mpls-te/mpls-te:te-tunnel" {
    description
      "MPLS forward configuration to the MPLS TE tunnel module.";
    container mplstunnelpipe {
      tailf:ncs-device-type "netconf";
      tailf:display-when "not(../../../../../../../../../ncs:module) or ../../../../../../../../../ncs:module[ncs:name='huawei-mpls-forward']";
      description
        "Configure TE pipe mode.";
      leaf pipe-mode {
        type te-pipe-mode;
        default "uniform";
        description
          "Specifies the pipe mode of TE tunnel.";
      }
      leaf service-class {
        when "not(../pipe-mode='uniform')" {
          tailf:xpath-root 3;
        }
        type te-pipe-service-class;
        default "be";
        description
          "PHB of ingress packet.";
      }
      leaf color {
        when "not(../pipe-mode='uniform')" {
          tailf:xpath-root 3;
        }
        type te-pipe-color;
        default "green";
        description
          "Color of ingress packet.";
      }
    }
    container mpls-tunnel-service-class {
      tailf:ncs-device-type "netconf";
      tailf:display-when "not(../../../../../../../../../ncs:module) or ../../../../../../../../../ncs:module[ncs:name='huawei-mpls-forward']";
      description
        "Configure specifies the service class of te tunnel.";
      leaf default-enable {
        type boolean;
        must "(../default-enable='false') or not(../af1-enable='true' or ../af2-enable='true' or ../af3-enable='true' or ../af4-enable='true' or ../be-enable='true' or ../cs6-enable='true' or ../cs7-enable='true' or ../ef-enable='true')" {
          tailf:xpath-root 3;
        }
        default "false";
        description
          "Enable/disable default service class.";
      }
      leaf be-enable {
        type boolean;
        must "../be-enable='false' or ../default-enable='false'" {
          tailf:xpath-root 3;
        }
        default "false";
        description
          "Enable/disable BE service class.";
      }
      leaf af1-enable {
        type boolean;
        must "../af1-enable='false' or ../default-enable='false'" {
          tailf:xpath-root 3;
        }
        default "false";
        description
          "Enable/disable AF1 service class.";
      }
      leaf af2-enable {
        type boolean;
        must "../af2-enable='false' or ../default-enable='false'" {
          tailf:xpath-root 3;
        }
        default "false";
        description
          "Enable/disable AF2 service class.";
      }
      leaf af3-enable {
        type boolean;
        must "../af3-enable='false' or ../default-enable='false'" {
          tailf:xpath-root 3;
        }
        default "false";
        description
          "Enable/disable AF3 service class.";
      }
      leaf af4-enable {
        type boolean;
        must "../af4-enable='false' or ../default-enable='false'" {
          tailf:xpath-root 3;
        }
        default "false";
        description
          "Enable/disable AF4 service class.";
      }
      leaf ef-enable {
        type boolean;
        must "../ef-enable='false' or ../default-enable='false'" {
          tailf:xpath-root 3;
        }
        default "false";
        description
          "Enable/disable EF service class.";
      }
      leaf cs6-enable {
        type boolean;
        must "../cs6-enable='false' or ../default-enable='false'" {
          tailf:xpath-root 3;
        }
        default "false";
        description
          "Enable/disable CS6 service class.";
      }
      leaf cs7-enable {
        type boolean;
        must "../cs7-enable='false' or ../default-enable='false'" {
          tailf:xpath-root 3;
        }
        default "false";
        description
          "Enable/disable CS7 service class.";
      }
    }
    container mpls-tunnel-dscp {
      tailf:ncs-device-type "netconf";
      tailf:display-when "not(../../../../../../../../../ncs:module) or ../../../../../../../../../ncs:module[ncs:name='huawei-mpls-forward']";
      when "../mpls-te:common-attributes/mpls-te:signal-protocol='segment-routing'" {
        tailf:xpath-root 3;
      }
      description
        "Configure DSCP value.";
      leaf ipv4-defalut {
        type boolean;
        default "false";
        description
          "Enable/disable default of IPv4.";
      }
      leaf ipv6-defalut {
        type boolean;
        default "false";
        description
          "Enable/disable default of IPv6.";
      }
      leaf ipv4-dscp-value {
        type string {
          length "1..512";
        }
        must "../ipv4-dscp-value='*' or ../ipv4-defalut='false'" {
          tailf:xpath-root 3;
        }
        default "*";
        description
          "IPv4 DSCP, in the format of 0,1,2,3-10,63. A DSCP value is an integer ranging from 0 to 63.Entering an asterisk (*) deletes DSCP configuration.";
      }
      leaf ipv6-dscp-value {
        type string {
          length "1..512";
        }
        must "../ipv6-dscp-value='*' or ../ipv6-defalut='false'" {
          tailf:xpath-root 3;
        }
        default "*";
        description
          "IPv6 DSCP, in the format of 0,1,2,3-10,63. A DSCP value is an integer ranging from 0 to 63.Entering an asterisk (*) deletes DSCP configuration.";
      }
    }
  }
  augment "/ncs:devices/ncs:template/ncs:ned-id/ncs:config/mpls:mpls" {
    description
      "MPLS forward configuration to the MPLS module.";
    container ds-enhance {
      description
        "Configure global shortpipe.";
      leaf enhance-enable {
        type ncs_template_enable-flag;
        // NCS drop default statement
        description
          "Shortpipe global enhance enable.";
      }
    }
    container p2mp-fastswitch {
      description
        "Configure P2MP fast switch.";
      leaf fastswitch-enable {
        type ncs_template_enable-flag;
        // NCS drop default statement
        description
          "P2MP global fast switch.";
      }
    }
    container p2mp-forceload {
      description
        "Configure P2MP forceload.";
      leaf forceload-enable {
        type ncs_template_enable-flag;
        // NCS drop default statement
        description
          "P2MP force loadbalance.";
      }
    }
    container p2mp-frrwtrtime {
      description
        "Configure P2MP FRR WTR for forwarding plane.";
      leaf frrwtrtime-forpdt {
        type string;
        units "s";
        // NCS drop default statement
        description
          "P2MP FRR WTR for forwarding plane.";
      }
    }
    container te-reverse-path-forwarding {
      description
        "Configure MPLS TE global RPF capability.";
      leaf te-rpf-enable {
        type ncs_template_enable-flag;
        // NCS drop default statement
        description
          "MPLS TE RPF capability enable.";
      }
    }
    container bgp-separate {
      description
        "Configure MPLS multiple hop disjoint.";
      leaf bgpsepen {
        type string;
        // NCS drop default statement
        description
          "Enable/disable MPLS multi-tunnel encapsulation decoupling.";
      }
    }
    container ldp-separate {
      description
        "Configure MPLS global convergence enhancement.";
      leaf ldpsepen {
        type string;
        // NCS drop default statement
        description
          "Enable/disable LDP-SRBE convergence enhancement.";
      }
    }
    container te-multiprot {
      description
        "Configure MPLS TE global multi-protect fast switch.";
      leaf multi-protect-enable {
        type string;
        // NCS drop default statement
        description
          "Enable/disable MPLS TE multi-protect fast switch.";
      }
    }
    // NCS drop config false container 'active-tnl'
    // NCS drop config false container 'disp-convergence-mode'
  }
  augment "/ncs:devices/ncs:device/ncs:live-status/mpls:mpls" {
    description
      "MPLS forward configuration to the MPLS module.";
    container ds-enhance {
      tailf:ncs-device-type "netconf";
      tailf:display-when "not(../../../ncs:module) or ../../../ncs:module[ncs:name='huawei-mpls-forward'] or (../../../ncs:live-status-protocol[not(ncs:capability)]) or (../../../ncs:live-status-protocol/ncs:capability/ncs:module[.='huawei-mpls-forward'])";
      description
        "Configure global shortpipe.";
      leaf enhance-enable {
        type live_ncs_enable-flag;
        // NCS drop default statement
        description
          "Shortpipe global enhance enable.";
      }
    }
    container p2mp-fastswitch {
      tailf:ncs-device-type "netconf";
      tailf:display-when "not(../../../ncs:module) or ../../../ncs:module[ncs:name='huawei-mpls-forward'] or (../../../ncs:live-status-protocol[not(ncs:capability)]) or (../../../ncs:live-status-protocol/ncs:capability/ncs:module[.='huawei-mpls-forward'])";
      description
        "Configure P2MP fast switch.";
      leaf fastswitch-enable {
        type live_ncs_enable-flag;
        // NCS drop default statement
        description
          "P2MP global fast switch.";
      }
    }
    container p2mp-forceload {
      tailf:ncs-device-type "netconf";
      tailf:display-when "not(../../../ncs:module) or ../../../ncs:module[ncs:name='huawei-mpls-forward'] or (../../../ncs:live-status-protocol[not(ncs:capability)]) or (../../../ncs:live-status-protocol/ncs:capability/ncs:module[.='huawei-mpls-forward'])";
      description
        "Configure P2MP forceload.";
      leaf forceload-enable {
        type live_ncs_enable-flag;
        // NCS drop default statement
        description
          "P2MP force loadbalance.";
      }
    }
    container p2mp-frrwtrtime {
      tailf:ncs-device-type "netconf";
      tailf:display-when "not(../../../ncs:module) or ../../../ncs:module[ncs:name='huawei-mpls-forward'] or (../../../ncs:live-status-protocol[not(ncs:capability)]) or (../../../ncs:live-status-protocol/ncs:capability/ncs:module[.='huawei-mpls-forward'])";
      description
        "Configure P2MP FRR WTR for forwarding plane.";
      leaf frrwtrtime-forpdt {
        type uint32 {
          range "5..600";
        }
        units "s";
        // NCS drop default statement
        description
          "P2MP FRR WTR for forwarding plane.";
      }
    }
    container te-reverse-path-forwarding {
      tailf:ncs-device-type "netconf";
      tailf:display-when "not(../../../ncs:module) or ../../../ncs:module[ncs:name='huawei-mpls-forward'] or (../../../ncs:live-status-protocol[not(ncs:capability)]) or (../../../ncs:live-status-protocol/ncs:capability/ncs:module[.='huawei-mpls-forward'])";
      description
        "Configure MPLS TE global RPF capability.";
      leaf te-rpf-enable {
        type live_ncs_enable-flag;
        // NCS drop default statement
        description
          "MPLS TE RPF capability enable.";
      }
    }
    container bgp-separate {
      tailf:ncs-device-type "netconf";
      tailf:display-when "not(../../../ncs:module) or ../../../ncs:module[ncs:name='huawei-mpls-forward'] or (../../../ncs:live-status-protocol[not(ncs:capability)]) or (../../../ncs:live-status-protocol/ncs:capability/ncs:module[.='huawei-mpls-forward'])";
      description
        "Configure MPLS multiple hop disjoint.";
      leaf bgpsepen {
        type boolean;
        // NCS drop default statement
        description
          "Enable/disable MPLS multi-tunnel encapsulation decoupling.";
      }
    }
    container ldp-separate {
      tailf:ncs-device-type "netconf";
      tailf:display-when "not(../../../ncs:module) or ../../../ncs:module[ncs:name='huawei-mpls-forward'] or (../../../ncs:live-status-protocol[not(ncs:capability)]) or (../../../ncs:live-status-protocol/ncs:capability/ncs:module[.='huawei-mpls-forward'])";
      description
        "Configure MPLS global convergence enhancement.";
      leaf ldpsepen {
        type boolean;
        // NCS drop default statement
        description
          "Enable/disable LDP-SRBE convergence enhancement.";
      }
    }
    container te-multiprot {
      tailf:ncs-device-type "netconf";
      tailf:display-when "not(../../../ncs:module) or ../../../ncs:module[ncs:name='huawei-mpls-forward'] or (../../../ncs:live-status-protocol[not(ncs:capability)]) or (../../../ncs:live-status-protocol/ncs:capability/ncs:module[.='huawei-mpls-forward'])";
      description
        "Configure MPLS TE global multi-protect fast switch.";
      leaf multi-protect-enable {
        type boolean;
        // NCS drop default statement
        description
          "Enable/disable MPLS TE multi-protect fast switch.";
      }
    }
    container active-tnl {
      tailf:ncs-device-type "netconf";
      tailf:display-when "not(../../../ncs:module) or ../../../ncs:module[ncs:name='huawei-mpls-forward'] or (../../../ncs:live-status-protocol[not(ncs:capability)]) or (../../../ncs:live-status-protocol/ncs:capability/ncs:module[.='huawei-mpls-forward'])";
      description
        "Statistics of MPLS TE LSP state INFOs.";
      list tnlactinfo {
        key "interfacename";
        description
          "Statistics of MPLS TE LSP state INFOs.";
        leaf interfacename {
          type pub-type:live_ncs_if-name;
          description
            "Specifies an MPLS TE interface name.";
        }
        leaf activepath {
          type string {
            length "1..30";
          }
          description
            "MPLS TE LSP forward type.";
        }
        leaf tunnelid {
          type pub-type:live_ncs_hex-binary;
          description
            "Tunnel ID.";
        }
        leaf outinterface {
          type string {
            length "1..30";
          }
          description
            "The tunnel out interface.";
        }
      }
    }
    container disp-convergence-mode {
      tailf:ncs-device-type "netconf";
      tailf:display-when "not(../../../ncs:module) or ../../../ncs:module[ncs:name='huawei-mpls-forward'] or (../../../ncs:live-status-protocol[not(ncs:capability)]) or (../../../ncs:live-status-protocol/ncs:capability/ncs:module[.='huawei-mpls-forward'])";
      description
        "Operational state of convergence mode state info.";
      leaf is-enable {
        type boolean;
        // NCS drop default statement
        description
          "Convergence mode enable check.";
      }
    }
  }
  augment "/ncs:devices/ncs:device/ncs:config/mpls:mpls" {
    description
      "MPLS forward configuration to the MPLS module.";
    container ds-enhance {
      tailf:ncs-device-type "netconf";
      tailf:display-when "not(../../../ncs:module) or ../../../ncs:module[ncs:name='huawei-mpls-forward']";
      description
        "Configure global shortpipe.";
      leaf enhance-enable {
        type enable-flag;
        default "disable";
        description
          "Shortpipe global enhance enable.";
      }
    }
    container p2mp-fastswitch {
      tailf:ncs-device-type "netconf";
      tailf:display-when "not(../../../ncs:module) or ../../../ncs:module[ncs:name='huawei-mpls-forward']";
      description
        "Configure P2MP fast switch.";
      leaf fastswitch-enable {
        type enable-flag;
        default "disable";
        description
          "P2MP global fast switch.";
      }
    }
    container p2mp-forceload {
      tailf:ncs-device-type "netconf";
      tailf:display-when "not(../../../ncs:module) or ../../../ncs:module[ncs:name='huawei-mpls-forward']";
      description
        "Configure P2MP forceload.";
      leaf forceload-enable {
        type enable-flag;
        default "disable";
        description
          "P2MP force loadbalance.";
      }
    }
    container p2mp-frrwtrtime {
      tailf:ncs-device-type "netconf";
      tailf:display-when "not(../../../ncs:module) or ../../../ncs:module[ncs:name='huawei-mpls-forward']";
      description
        "Configure P2MP FRR WTR for forwarding plane.";
      leaf frrwtrtime-forpdt {
        type uint32 {
          range "5..600";
        }
        units "s";
        default "5";
        description
          "P2MP FRR WTR for forwarding plane.";
      }
    }
    container te-reverse-path-forwarding {
      tailf:ncs-device-type "netconf";
      tailf:display-when "not(../../../ncs:module) or ../../../ncs:module[ncs:name='huawei-mpls-forward']";
      description
        "Configure MPLS TE global RPF capability.";
      leaf te-rpf-enable {
        type enable-flag;
        default "enable";
        description
          "MPLS TE RPF capability enable.";
      }
    }
    container bgp-separate {
      tailf:ncs-device-type "netconf";
      tailf:display-when "not(../../../ncs:module) or ../../../ncs:module[ncs:name='huawei-mpls-forward']";
      description
        "Configure MPLS multiple hop disjoint.";
      leaf bgpsepen {
        type boolean;
        default "false";
        description
          "Enable/disable MPLS multi-tunnel encapsulation decoupling.";
      }
    }
    container ldp-separate {
      tailf:ncs-device-type "netconf";
      tailf:display-when "not(../../../ncs:module) or ../../../ncs:module[ncs:name='huawei-mpls-forward']";
      description
        "Configure MPLS global convergence enhancement.";
      leaf ldpsepen {
        type boolean;
        default "false";
        description
          "Enable/disable LDP-SRBE convergence enhancement.";
      }
    }
    container te-multiprot {
      tailf:ncs-device-type "netconf";
      tailf:display-when "not(../../../ncs:module) or ../../../ncs:module[ncs:name='huawei-mpls-forward']";
      description
        "Configure MPLS TE global multi-protect fast switch.";
      leaf multi-protect-enable {
        type boolean;
        default "false";
        description
          "Enable/disable MPLS TE multi-protect fast switch.";
      }
    }
    // NCS drop config false container 'active-tnl'
    // NCS drop config false container 'disp-convergence-mode'
  }
  augment "/ncs:devices/ncs:template/ncs:ned-id/ncs:config/mpls:mpls/mpls:common/mpls:global" {
    // NCS drop when statement
    description
      "MPLS forward configuration to the MPLS module.";
    container exp-ttl-mode {
      description
        "Configure pipe mode for explicit null label.";
      leaf exppipemode {
        type ncs_template_enl-exp-mode;
        // NCS drop default statement
        description
          "Pipe mode of EXP for explicit null label.";
      }
      leaf ttlpipemode {
        type ncs_template_enl-ttl-mode;
        // NCS drop default statement
        description
          "Pipe mode of TTL for explicit null label.";
      }
    }
    container entropy-label-mode {
      description
        "Configure pipe mode for entropy label.";
      leaf exp-pipemode {
        type ncs_template_ela-exp-mode;
        // NCS drop default statement
        description
          "Pipe mode of EXP for entropy label.";
      }
      leaf ttl-pipemode {
        type ncs_template_ela-ttl-mode;
        // NCS drop default statement
        description
          "Pipe mode of TTL for entropy label.";
      }
    }
  }
  augment "/ncs:devices/ncs:device/ncs:live-status/mpls:mpls/mpls:common/mpls:global" {
    // NCS drop when statement
    description
      "MPLS forward configuration to the MPLS module.";
    container exp-ttl-mode {
      tailf:ncs-device-type "netconf";
      tailf:display-when "not(../../../../../ncs:module) or ../../../../../ncs:module[ncs:name='huawei-mpls-forward'] or (../../../../../ncs:live-status-protocol[not(ncs:capability)]) or (../../../../../ncs:live-status-protocol/ncs:capability/ncs:module[.='huawei-mpls-forward'])";
      description
        "Configure pipe mode for explicit null label.";
      leaf exppipemode {
        type live_ncs_enl-exp-mode;
        // NCS drop default statement
        description
          "Pipe mode of EXP for explicit null label.";
      }
      leaf ttlpipemode {
        type live_ncs_enl-ttl-mode;
        // NCS drop default statement
        description
          "Pipe mode of TTL for explicit null label.";
      }
    }
    container entropy-label-mode {
      tailf:ncs-device-type "netconf";
      tailf:display-when "not(../../../../../ncs:module) or ../../../../../ncs:module[ncs:name='huawei-mpls-forward'] or (../../../../../ncs:live-status-protocol[not(ncs:capability)]) or (../../../../../ncs:live-status-protocol/ncs:capability/ncs:module[.='huawei-mpls-forward'])";
      description
        "Configure pipe mode for entropy label.";
      leaf exp-pipemode {
        type live_ncs_ela-exp-mode;
        // NCS drop default statement
        description
          "Pipe mode of EXP for entropy label.";
      }
      leaf ttl-pipemode {
        type live_ncs_ela-ttl-mode;
        // NCS drop default statement
        description
          "Pipe mode of TTL for entropy label.";
      }
    }
  }
  augment "/ncs:devices/ncs:device/ncs:config/mpls:mpls/mpls:common/mpls:global" {
    when "/mpls:mpls/mpls:common/mpls:global/mpls:mpls-enable='true'" {
      tailf:xpath-root 3;
    }
    description
      "MPLS forward configuration to the MPLS module.";
    container exp-ttl-mode {
      tailf:ncs-device-type "netconf";
      tailf:display-when "not(../../../../../ncs:module) or ../../../../../ncs:module[ncs:name='huawei-mpls-forward']";
      description
        "Configure pipe mode for explicit null label.";
      leaf exppipemode {
        type enl-exp-mode;
        default "uniform";
        description
          "Pipe mode of EXP for explicit null label.";
      }
      leaf ttlpipemode {
        type enl-ttl-mode;
        default "uniform";
        description
          "Pipe mode of TTL for explicit null label.";
      }
    }
    container entropy-label-mode {
      tailf:ncs-device-type "netconf";
      tailf:display-when "not(../../../../../ncs:module) or ../../../../../ncs:module[ncs:name='huawei-mpls-forward']";
      description
        "Configure pipe mode for entropy label.";
      leaf exp-pipemode {
        type ela-exp-mode;
        default "uniform";
        description
          "Pipe mode of EXP for entropy label.";
      }
      leaf ttl-pipemode {
        type ela-ttl-mode;
        default "uniform";
        description
          "Pipe mode of TTL for entropy label.";
      }
    }
  }
  augment "/ncs:devices/ncs:template/ncs:ned-id/ncs:config/mpls:mpls/mpls:common" {
    description
      "MPLS forward configuration to the MPLS module.";
    container mpls-forward {
      description
        "Configure MPLS forward configuration to the MPLS module.";
      container static-label-only {
        description
          "Configure the parameters related to the exclusive static label range. The function takes effect after the device is restarted.";
        leaf max-label {
          type string;
          description
            "The static label in the exclusive range ranges from 16 to the configured value. The labels that exceed the range can be used by both static and dynamic services.";
        }
      }
    }
  }
  augment "/ncs:devices/ncs:device/ncs:live-status/mpls:mpls/mpls:common" {
    description
      "MPLS forward configuration to the MPLS module.";
    container mpls-forward {
      tailf:ncs-device-type "netconf";
      tailf:display-when "not(../../../../ncs:module) or ../../../../ncs:module[ncs:name='huawei-mpls-forward'] or (../../../../ncs:live-status-protocol[not(ncs:capability)]) or (../../../../ncs:live-status-protocol/ncs:capability/ncs:module[.='huawei-mpls-forward'])";
      description
        "Configure MPLS forward configuration to the MPLS module.";
      container static-label-only {
        description
          "Configure the parameters related to the exclusive static label range. The function takes effect after the device is restarted.";
        leaf max-label {
          type uint32 {
            range "2048..15999";
          }
          description
            "The static label in the exclusive range ranges from 16 to the configured value. The labels that exceed the range can be used by both static and dynamic services.";
        }
      }
    }
  }
  augment "/ncs:devices/ncs:device/ncs:config/mpls:mpls/mpls:common" {
    description
      "MPLS forward configuration to the MPLS module.";
    container mpls-forward {
      tailf:ncs-device-type "netconf";
      tailf:display-when "not(../../../../ncs:module) or ../../../../ncs:module[ncs:name='huawei-mpls-forward']";
      description
        "Configure MPLS forward configuration to the MPLS module.";
      container static-label-only {
        description
          "Configure the parameters related to the exclusive static label range. The function takes effect after the device is restarted.";
        leaf max-label {
          type uint32 {
            range "2048..15999";
          }
          description
            "The static label in the exclusive range ranges from 16 to the configured value. The labels that exceed the range can be used by both static and dynamic services.";
        }
      }
    }
  }
}
