module huawei-y1731-statistics {
  // Generated by yanger -t ncs
  tailf:mount-id "huawei-nc-1.0:huawei-nc-1.0";
  tailf:ncs-device-type "netconf";

  yang-version 1;
  namespace "urn:huawei:yang:huawei-y1731-statistics";
  prefix y1731-statistics;

  import huawei-y1731 {
    prefix y1731;
  }
  import huawei-devm {
    prefix devm;
  }
  import huawei-extension {
    prefix ext;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Y1731-statistics.";

  revision 2020-03-05 {
    description
      "Modify description.";
    reference "Huawei private.";
  }
  revision 2020-02-20 {
    description
      "Add task-name.";
    reference "Huawei private.";
  }
  revision 2019-12-27 {
    description
      "Init revision.";
    reference "Huawei private.";
  }
  ext:task-name "y1731";

  augment "/ncs:devices/ncs:device/ncs:rpc" {
    container rpc-reset-ccm-receive-statistics {
      tailf:ncs-device-type "netconf";
      tailf:display-when "not(../../ncs:module) or ../../ncs:module[ncs:name='huawei-y1731-statistics']";
      tailf:action reset-ccm-receive-statistics {
        tailf:actionpoint ncsproxy {
          tailf:internal;
        }
        description
          "Reset ccm receive statistics.";
        ext:node-ref "/y1731:y1731/y1731:global-enable/y1731:mds/y1731:md";
        input {
          leaf md {
            type string;
            description
              "Specifies the name of a MD.";
          }
          leaf ma {
            type string;
            description
              "Specifies the name of a MA.";
          }
          leaf mep-id {
            type string;
            description
              "Specifies the ID of a MEP.";
          }
          leaf rmep-id {
            type string;
            description
              "Specifies the ID of a remote MEP.";
          }
        }
      }
    }
  }
  augment "/ncs:devices/ncs:device-group/ncs:ned-id/ncs:rpc" {
    container rpc-reset-ccm-receive-statistics {
      tailf:ncs-device-type "netconf";
      tailf:display-when "/ncs:devices/ncs:device[ncs:name=current()/../../../ncs:member]/ncs:module[ncs:name='huawei-y1731-statistics']";
      tailf:action reset-ccm-receive-statistics {
        tailf:actionpoint ncsproxy {
          tailf:internal;
        }
        description
          "Reset ccm receive statistics.";
        ext:node-ref "/y1731:y1731/y1731:global-enable/y1731:mds/y1731:md";
        input {
          leaf md {
            type string;
            description
              "Specifies the name of a MD.";
          }
          leaf ma {
            type string;
            description
              "Specifies the name of a MA.";
          }
          leaf mep-id {
            type string;
            description
              "Specifies the ID of a MEP.";
          }
          leaf rmep-id {
            type string;
            description
              "Specifies the ID of a remote MEP.";
          }
        }
      }
    }
  }
  augment "/ncs:devices/ncs:device/ncs:rpc" {
    container rpc-reset-ccm-send-statistics {
      tailf:ncs-device-type "netconf";
      tailf:display-when "not(../../ncs:module) or ../../ncs:module[ncs:name='huawei-y1731-statistics']";
      tailf:action reset-ccm-send-statistics {
        tailf:actionpoint ncsproxy {
          tailf:internal;
        }
        description
          "Reset ccm send statistics.";
        ext:node-ref "/y1731:y1731/y1731:global-enable/y1731:mds/y1731:md";
        input {
          leaf md {
            type string;
            description
              "Specifies the name of a MD.";
          }
          leaf ma {
            type string;
            description
              "Specifies the name of a MA.";
          }
          leaf mep-id {
            type string;
            description
              "Specifies the ID of a MEP.";
          }
        }
      }
    }
  }
  augment "/ncs:devices/ncs:device-group/ncs:ned-id/ncs:rpc" {
    container rpc-reset-ccm-send-statistics {
      tailf:ncs-device-type "netconf";
      tailf:display-when "/ncs:devices/ncs:device[ncs:name=current()/../../../ncs:member]/ncs:module[ncs:name='huawei-y1731-statistics']";
      tailf:action reset-ccm-send-statistics {
        tailf:actionpoint ncsproxy {
          tailf:internal;
        }
        description
          "Reset ccm send statistics.";
        ext:node-ref "/y1731:y1731/y1731:global-enable/y1731:mds/y1731:md";
        input {
          leaf md {
            type string;
            description
              "Specifies the name of a MD.";
          }
          leaf ma {
            type string;
            description
              "Specifies the name of a MA.";
          }
          leaf mep-id {
            type string;
            description
              "Specifies the ID of a MEP.";
          }
        }
      }
    }
  }
  augment "/ncs:devices/ncs:template/ncs:ned-id/ncs:config/y1731:y1731" {
    description
      "Configure y1731.";
    container ccm-statistics {
      description
        "Configure statistics about CCMs.";
      leaf cfm-statistic-enable {
        type string;
        // NCS drop must statement
        // NCS drop default statement
        description
          "Enable/disable the CCM statistics function.";
      }
      // NCS drop config false container 'ccm-sends'
      // NCS drop config false container 'ccm-receives'
    }
    container inner-priority {
      description
        "Configure Y1731.";
      leaf inner-priority-enable {
        type string;
        // NCS drop default statement
        description
          "Enable/disable Y1731 inner priority function.";
      }
    }
    container cfm-level-check {
      description
        "Configure CFM.";
      leaf level-check-strict {
        type string;
        // NCS drop default statement
        description
          "Enable/disable strict check for MD levels of CFM (802.1ag) packets.";
      }
    }
  }
  augment "/ncs:devices/ncs:device/ncs:live-status/y1731:y1731" {
    description
      "Configure y1731.";
    container ccm-statistics {
      tailf:ncs-device-type "netconf";
      tailf:display-when "not(../../../ncs:module) or ../../../ncs:module[ncs:name='huawei-y1731-statistics'] or (../../../ncs:live-status-protocol[not(ncs:capability)]) or (../../../ncs:live-status-protocol/ncs:capability/ncs:module[.='huawei-y1731-statistics'])";
      description
        "Configure statistics about CCMs.";
      leaf cfm-statistic-enable {
        type boolean;
        // NCS drop must statement
        // NCS drop default statement
        description
          "Enable/disable the CCM statistics function.";
      }
      container ccm-sends {
        description
          "List of statistics about CCMs sent.";
        list ccm-send {
          key "md ma mep-id";
          description
            "Statistics of CCMs sent.";
          leaf md {
            type string {
              length "1..43";
            }
            description
              "Specifies the name of a MD.";
          }
          leaf ma {
            type string {
              length "1..43";
            }
            description
              "Specifies the name of a MA.";
          }
          leaf mep-id {
            type uint32 {
              range "1..8191";
            }
            description
              "Specifies the ID of a MEP.";
          }
          leaf send-packet {
            type uint64;
            description
              "Displays the number of CCMs sent by the MEP.";
          }
        }
      }
      container ccm-receives {
        description
          "List of statistics about CCMs received.";
        list ccm-receive {
          key "md ma mep-id rmep-id";
          description
            "Statistics of CCMs received.";
          leaf md {
            type string {
              length "1..43";
            }
            description
              "Specifies the name of a MD.";
          }
          leaf ma {
            type string {
              length "1..43";
            }
            description
              "Specifies the name of a MA.";
          }
          leaf mep-id {
            type uint32 {
              range "1..8191";
            }
            description
              "Specifies the ID of a MEP.";
          }
          leaf rmep-id {
            type uint32 {
              range "1..8191";
            }
            description
              "Specifies the ID of a remote MEP.";
          }
          leaf receive-packet {
            type uint64;
            description
              "Displays the number of CCMs received by the MEP.";
          }
          leaf rdi-packet {
            type uint64;
            description
              "Displays the number of CCMs with the RDI flag set to 1 that the MEP receives.";
          }
          leaf tlv-packet {
            type uint64;
            description
              "Displays the number of CCMs carrying the Sender ID TLV, Port Status TLV, or Interface Status TLV field that the MEP receives.";
          }
          leaf mac-err-packet {
            type uint64;
            description
              "Displays the number of CCMs carrying the MAC address different from the MAC address configured on the remote MEP that the MEP receives.";
          }
          leaf freq-err-packet {
            type uint64;
            description
              "Displays the number of CCMs carrying the correct MEG level, MEG ID, and MEP ID but the incorrect transmission interval that the MEP receives.";
          }
          leaf ma-id-err-packet {
            type uint64;
            description
              "Displays the number of CCMs carrying the correct MEG level but the incorrect MEG ID (MAID) that the MEP receives.";
          }
        }
      }
    }
    container inner-priority {
      tailf:ncs-device-type "netconf";
      tailf:display-when "not(../../../ncs:module) or ../../../ncs:module[ncs:name='huawei-y1731-statistics'] or (../../../ncs:live-status-protocol[not(ncs:capability)]) or (../../../ncs:live-status-protocol/ncs:capability/ncs:module[.='huawei-y1731-statistics'])";
      description
        "Configure Y1731.";
      leaf inner-priority-enable {
        type boolean;
        // NCS drop default statement
        description
          "Enable/disable Y1731 inner priority function.";
      }
    }
    container cfm-level-check {
      tailf:ncs-device-type "netconf";
      tailf:display-when "not(../../../ncs:module) or ../../../ncs:module[ncs:name='huawei-y1731-statistics'] or (../../../ncs:live-status-protocol[not(ncs:capability)]) or (../../../ncs:live-status-protocol/ncs:capability/ncs:module[.='huawei-y1731-statistics'])";
      description
        "Configure CFM.";
      leaf level-check-strict {
        type boolean;
        // NCS drop default statement
        description
          "Enable/disable strict check for MD levels of CFM (802.1ag) packets.";
      }
    }
  }
  augment "/ncs:devices/ncs:device/ncs:config/y1731:y1731" {
    description
      "Configure y1731.";
    container ccm-statistics {
      tailf:ncs-device-type "netconf";
      tailf:display-when "not(../../../ncs:module) or ../../../ncs:module[ncs:name='huawei-y1731-statistics']";
      description
        "Configure statistics about CCMs.";
      leaf cfm-statistic-enable {
        type boolean;
        must "(../cfm-statistic-enable = 'true' and /y1731:y1731/y1731:global-enable) or ../cfm-statistic-enable = 'false'" {
          tailf:xpath-root 3;
        }
        default "false";
        description
          "Enable/disable the CCM statistics function.";
      }
      // NCS drop config false container 'ccm-sends'
      // NCS drop config false container 'ccm-receives'
    }
    container inner-priority {
      tailf:ncs-device-type "netconf";
      tailf:display-when "not(../../../ncs:module) or ../../../ncs:module[ncs:name='huawei-y1731-statistics']";
      description
        "Configure Y1731.";
      leaf inner-priority-enable {
        type boolean;
        default "false";
        description
          "Enable/disable Y1731 inner priority function.";
      }
    }
    container cfm-level-check {
      tailf:ncs-device-type "netconf";
      tailf:display-when "not(../../../ncs:module) or ../../../ncs:module[ncs:name='huawei-y1731-statistics']";
      description
        "Configure CFM.";
      leaf level-check-strict {
        type boolean;
        default "true";
        description
          "Enable/disable strict check for MD levels of CFM (802.1ag) packets.";
      }
    }
  }
  augment "/ncs:devices/ncs:template/ncs:ned-id/ncs:config/devm:devm/devm:lpu-boards/devm:lpu-board" {
    description
      "Configure cfm.";
    container cfm-mac-level-enable-lpu {
      description
        "Configure CFM MAC level check.";
      leaf mac-level-enable {
        type string;
        // NCS drop default statement
        description
          "Enable/disable MAC level check.";
      }
    }
  }
  augment "/ncs:devices/ncs:device/ncs:live-status/devm:devm/devm:lpu-boards/devm:lpu-board" {
    description
      "Configure cfm.";
    container cfm-mac-level-enable-lpu {
      tailf:ncs-device-type "netconf";
      tailf:display-when "not(../../../../../ncs:module) or ../../../../../ncs:module[ncs:name='huawei-y1731-statistics'] or (../../../../../ncs:live-status-protocol[not(ncs:capability)]) or (../../../../../ncs:live-status-protocol/ncs:capability/ncs:module[.='huawei-y1731-statistics'])";
      description
        "Configure CFM MAC level check.";
      leaf mac-level-enable {
        type boolean;
        // NCS drop default statement
        description
          "Enable/disable MAC level check.";
      }
    }
  }
  augment "/ncs:devices/ncs:device/ncs:config/devm:devm/devm:lpu-boards/devm:lpu-board" {
    description
      "Configure cfm.";
    container cfm-mac-level-enable-lpu {
      tailf:ncs-device-type "netconf";
      tailf:display-when "not(../../../../../ncs:module) or ../../../../../ncs:module[ncs:name='huawei-y1731-statistics']";
      description
        "Configure CFM MAC level check.";
      leaf mac-level-enable {
        type boolean;
        default "true";
        description
          "Enable/disable MAC level check.";
      }
    }
  }
  augment "/ncs:devices/ncs:template/ncs:ned-id/ncs:config/devm:devm/devm:mpu-boards/devm:mpu-board" {
    description
      "Configure cfm.";
    container cfm-mac-level-enable-mpu {
      description
        "Configure CFM MAC level check.";
      leaf mac-level-enable {
        type string;
        // NCS drop default statement
        description
          "Enable/disable MAC level check.";
      }
    }
  }
  augment "/ncs:devices/ncs:device/ncs:live-status/devm:devm/devm:mpu-boards/devm:mpu-board" {
    description
      "Configure cfm.";
    container cfm-mac-level-enable-mpu {
      tailf:ncs-device-type "netconf";
      tailf:display-when "not(../../../../../ncs:module) or ../../../../../ncs:module[ncs:name='huawei-y1731-statistics'] or (../../../../../ncs:live-status-protocol[not(ncs:capability)]) or (../../../../../ncs:live-status-protocol/ncs:capability/ncs:module[.='huawei-y1731-statistics'])";
      description
        "Configure CFM MAC level check.";
      leaf mac-level-enable {
        type boolean;
        // NCS drop default statement
        description
          "Enable/disable MAC level check.";
      }
    }
  }
  augment "/ncs:devices/ncs:device/ncs:config/devm:devm/devm:mpu-boards/devm:mpu-board" {
    description
      "Configure cfm.";
    container cfm-mac-level-enable-mpu {
      tailf:ncs-device-type "netconf";
      tailf:display-when "not(../../../../../ncs:module) or ../../../../../ncs:module[ncs:name='huawei-y1731-statistics']";
      description
        "Configure CFM MAC level check.";
      leaf mac-level-enable {
        type boolean;
        default "true";
        description
          "Enable/disable MAC level check.";
      }
    }
  }
}
