module huawei-mplstpoam {
  // Generated by yanger -t ncs
  tailf:mount-id "huawei-nc-1.0:huawei-nc-1.0";
  tailf:ncs-device-type "netconf";

  yang-version 1;
  namespace "urn:huawei:yang:huawei-mplstpoam";
  prefix mplstpoam;

  import huawei-extension {
    prefix ext;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Multiprotocol Label Switching-Transport Profile (MPLS-TP), operations, administration and maintenance (OAM), mainly provides functions: fault management, performance monitoring, and protection switching.";

  revision 2019-12-27 {
    description
      "Solve some errors.";
    reference "Huawei private.";
  }
  revision 2019-04-18 {
    description
      "Initial revision.";
    reference "Huawei private.";
  }
  ext:task-name "tpoam";

  typedef ncs_template_standard-type {
    type string;
    description
      "Standard type.";
  }

  typedef ncs_template_channel-type {
    type string;
    description
      "Channel type.";
  }

  typedef ncs_template_pw-mode {
    type string;
    description
      "PW mode.";
  }

  typedef ncs_template_gal-pw {
    type string;
    description
      "Gal PW type.";
  }

  typedef ncs_template_protocol-state-type {
    type string;
    description
      "Protocol state type.";
  }

  typedef ncs_rpc_notif_standard-type {
    type enumeration {
      enum "y1711" {
        value 0;
        description
          "Protocol is Y.1711.";
      }
      enum "y1731" {
        value 1;
        description
          "Protocol is Y.1731.";
      }
    }
    description
      "Standard type.";
  }

  typedef ncs_rpc_notif_channel-type {
    type enumeration {
      enum "0x7ffa" {
        value 0;
        description
          "ACH is 0x7FFA.";
      }
      enum "0x8902" {
        value 1;
        description
          "ACH is 0x8902.";
      }
    }
    description
      "Channel type.";
  }

  typedef ncs_rpc_notif_pw-mode {
    type enumeration {
      enum "standard" {
        value 0;
        description
          "The MPLS-TP PW mode is standard.";
      }
      enum "private" {
        value 1;
        description
          "The MPLS-TP PW mode is private.";
      }
    }
    description
      "PW mode.";
  }

  typedef ncs_rpc_notif_gal-pw {
    type enumeration {
      enum "label-13" {
        value 0;
        description
          "The Gal is 13.";
      }
      enum "label-14" {
        value 1;
        description
          "The Gal is 14.";
      }
      enum "disable" {
        value 2;
        description
          "The GAL type is disable.";
      }
      enum "route-mode" {
        value 3;
        description
          "The GAL type is route-mode.";
      }
      enum "ptn-mode" {
        value 4;
        description
          "The GAL type is ptn-mode.";
      }
    }
    description
      "Gal PW type.";
  }

  typedef ncs_rpc_notif_protocol-state-type {
    type enumeration {
      enum "no-config" {
        value 0;
        description
          "No OAM is configured.";
      }
      enum "y1711" {
        value 1;
        description
          "Only configure Y.1711.";
      }
      enum "y1731" {
        value 2;
        description
          "Only configure Y.1731.";
      }
      enum "y1711-y1731" {
        value 3;
        description
          "Mixed mode is configured.";
      }
    }
    description
      "Protocol state type.";
  }

  typedef live_ncs_standard-type {
    type enumeration {
      enum "y1711" {
        value 0;
        description
          "Protocol is Y.1711.";
      }
      enum "y1731" {
        value 1;
        description
          "Protocol is Y.1731.";
      }
    }
    description
      "Standard type.";
  }

  typedef live_ncs_channel-type {
    type enumeration {
      enum "0x7ffa" {
        value 0;
        description
          "ACH is 0x7FFA.";
      }
      enum "0x8902" {
        value 1;
        description
          "ACH is 0x8902.";
      }
    }
    description
      "Channel type.";
  }

  typedef live_ncs_pw-mode {
    type enumeration {
      enum "standard" {
        value 0;
        description
          "The MPLS-TP PW mode is standard.";
      }
      enum "private" {
        value 1;
        description
          "The MPLS-TP PW mode is private.";
      }
    }
    description
      "PW mode.";
  }

  typedef live_ncs_gal-pw {
    type enumeration {
      enum "label-13" {
        value 0;
        description
          "The Gal is 13.";
      }
      enum "label-14" {
        value 1;
        description
          "The Gal is 14.";
      }
      enum "disable" {
        value 2;
        description
          "The GAL type is disable.";
      }
      enum "route-mode" {
        value 3;
        description
          "The GAL type is route-mode.";
      }
      enum "ptn-mode" {
        value 4;
        description
          "The GAL type is ptn-mode.";
      }
    }
    description
      "Gal PW type.";
  }

  typedef live_ncs_protocol-state-type {
    type enumeration {
      enum "no-config" {
        value 0;
        description
          "No OAM is configured.";
      }
      enum "y1711" {
        value 1;
        description
          "Only configure Y.1711.";
      }
      enum "y1731" {
        value 2;
        description
          "Only configure Y.1731.";
      }
      enum "y1711-y1731" {
        value 3;
        description
          "Mixed mode is configured.";
      }
    }
    description
      "Protocol state type.";
  }

  typedef standard-type {
    type enumeration {
      enum "y1711" {
        value 0;
        description
          "Protocol is Y.1711.";
      }
      enum "y1731" {
        value 1;
        description
          "Protocol is Y.1731.";
      }
    }
    description
      "Standard type.";
  }

  typedef channel-type {
    type enumeration {
      enum "0x7ffa" {
        value 0;
        description
          "ACH is 0x7FFA.";
      }
      enum "0x8902" {
        value 1;
        description
          "ACH is 0x8902.";
      }
    }
    description
      "Channel type.";
  }

  typedef pw-mode {
    type enumeration {
      enum "standard" {
        value 0;
        description
          "The MPLS-TP PW mode is standard.";
      }
      enum "private" {
        value 1;
        description
          "The MPLS-TP PW mode is private.";
      }
    }
    description
      "PW mode.";
  }

  typedef gal-pw {
    type enumeration {
      enum "label-13" {
        value 0;
        description
          "The Gal is 13.";
      }
      enum "label-14" {
        value 1;
        description
          "The Gal is 14.";
      }
      enum "disable" {
        value 2;
        description
          "The GAL type is disable.";
      }
      enum "route-mode" {
        value 3;
        description
          "The GAL type is route-mode.";
      }
      enum "ptn-mode" {
        value 4;
        description
          "The GAL type is ptn-mode.";
      }
    }
    description
      "Gal PW type.";
  }

  typedef protocol-state-type {
    type enumeration {
      enum "no-config" {
        value 0;
        description
          "No OAM is configured.";
      }
      enum "y1711" {
        value 1;
        description
          "Only configure Y.1711.";
      }
      enum "y1731" {
        value 2;
        description
          "Only configure Y.1731.";
      }
      enum "y1711-y1731" {
        value 3;
        description
          "Mixed mode is configured.";
      }
    }
    description
      "Protocol state type.";
  }

  augment "/ncs:devices/ncs:device/ncs:config" {
    container mplstpoam {
      tailf:ncs-device-type "netconf";
      tailf:display-when "not(../../ncs:module) or ../../ncs:module[ncs:name='huawei-mplstpoam']";
      description
        "MPLStpoam.";
      container global {
        description
          "Configure global MPLS-TP OAM attribute.";
        leaf oam-standard {
          type standard-type;
          default "y1711";
          description
            "Default OAM standard protocol.";
        }
        leaf icc-string {
          type string {
            length "1..6";
          }
          description
            "MPLS-TP OAM ICC ID.";
        }
        leaf ais-enable {
          type boolean;
          default "false";
          description
            "Enable/disable MPLS-TP OAM AIS.";
        }
        leaf channel-type {
          type channel-type;
          default "0x7ffa";
          description
            "0x7ffa identifies MPLS-TP OAM packets in compliance with Y.1731. 0x8902 identifies MPLS-TP OAM packets in compliance with relevant standards.";
        }
        leaf csf-enable {
          type boolean;
          default "false";
          description
            "Enable/disable MPLS-TP OAM CSF.";
        }
        leaf mpls-tp-mode {
          type pw-mode;
          default "standard";
          description
            "PW mode of MPLS-TP OAM.";
        }
        leaf gal-mode {
          type gal-pw;
          default "ptn-mode";
          description
            "PW GAL mode of MPLS-TP OAM.";
        }
        // NCS drop config false leaf 'protocol-status'
        // NCS drop config false leaf 'oam-num'
      }
    }
  }
  augment "/ncs:devices/ncs:device/ncs:live-status" {
    container mplstpoam {
      tailf:ncs-device-type "netconf";
      tailf:display-when "not(../../ncs:module) or ../../ncs:module[ncs:name='huawei-mplstpoam'] or (../../ncs:live-status-protocol[not(ncs:capability)]) or (../../ncs:live-status-protocol/ncs:capability/ncs:module[.='huawei-mplstpoam'])";
      description
        "MPLStpoam.";
      container global {
        description
          "Configure global MPLS-TP OAM attribute.";
        leaf oam-standard {
          type live_ncs_standard-type;
          // NCS drop default statement
          description
            "Default OAM standard protocol.";
        }
        leaf icc-string {
          type string {
            length "1..6";
          }
          description
            "MPLS-TP OAM ICC ID.";
        }
        leaf ais-enable {
          type boolean;
          // NCS drop default statement
          description
            "Enable/disable MPLS-TP OAM AIS.";
        }
        leaf channel-type {
          type live_ncs_channel-type;
          // NCS drop default statement
          description
            "0x7ffa identifies MPLS-TP OAM packets in compliance with Y.1731. 0x8902 identifies MPLS-TP OAM packets in compliance with relevant standards.";
        }
        leaf csf-enable {
          type boolean;
          // NCS drop default statement
          description
            "Enable/disable MPLS-TP OAM CSF.";
        }
        leaf mpls-tp-mode {
          type live_ncs_pw-mode;
          // NCS drop default statement
          description
            "PW mode of MPLS-TP OAM.";
        }
        leaf gal-mode {
          type live_ncs_gal-pw;
          // NCS drop default statement
          description
            "PW GAL mode of MPLS-TP OAM.";
        }
        leaf protocol-status {
          type live_ncs_protocol-state-type;
          // NCS drop default statement
          description
            "OAM status.";
        }
        leaf oam-num {
          type uint32;
          description
            "Total number of OAM instances, including MPLS OAM and MPLS-TP OAM instances.";
        }
      }
    }
  }
  augment "/ncs:devices/ncs:template/ncs:ned-id/ncs:config" {
    container mplstpoam {
      description
        "MPLStpoam.";
      container global {
        description
          "Configure global MPLS-TP OAM attribute.";
        leaf oam-standard {
          type ncs_template_standard-type;
          // NCS drop default statement
          description
            "Default OAM standard protocol.";
        }
        leaf icc-string {
          type string;
          description
            "MPLS-TP OAM ICC ID.";
        }
        leaf ais-enable {
          type string;
          // NCS drop default statement
          description
            "Enable/disable MPLS-TP OAM AIS.";
        }
        leaf channel-type {
          type ncs_template_channel-type;
          // NCS drop default statement
          description
            "0x7ffa identifies MPLS-TP OAM packets in compliance with Y.1731. 0x8902 identifies MPLS-TP OAM packets in compliance with relevant standards.";
        }
        leaf csf-enable {
          type string;
          // NCS drop default statement
          description
            "Enable/disable MPLS-TP OAM CSF.";
        }
        leaf mpls-tp-mode {
          type ncs_template_pw-mode;
          // NCS drop default statement
          description
            "PW mode of MPLS-TP OAM.";
        }
        leaf gal-mode {
          type ncs_template_gal-pw;
          // NCS drop default statement
          description
            "PW GAL mode of MPLS-TP OAM.";
        }
        // NCS drop config false leaf 'protocol-status'
        // NCS drop config false leaf 'oam-num'
      }
    }
  }
}
