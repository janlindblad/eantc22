module huawei-trafficmng {
  // Generated by yanger -t ncs
  tailf:mount-id "huawei-nc-1.0:huawei-nc-1.0";
  tailf:ncs-device-type "netconf";

  namespace "urn:huawei:yang:huawei-trafficmng";
  prefix trafficmng;

  import huawei-extension {
    prefix ext;
  }
  import huawei-devm {
    prefix devm;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Traffic management.";

  revision 2019-12-21 {
    description
      "Add new nodes.";
    reference "Huawei private.";
  }
  revision 2019-07-21 {
    description
      "Initial revision.";
    reference "Huawei private.";
  }
  ext:task-name "device-mgr";

  typedef ncs_template_board-type {
    type string;
    description
      "The type of board.";
  }

  typedef ncs_template_lpu-switch-status {
    type string;
    description
      "The status of switch.";
  }

  typedef ncs_template_choice-enable-type {
    type string;
    description
      "Enable warm backup.";
  }

  typedef ncs_rpc_notif_board-type {
    type enumeration {
      enum "sfu" {
        value 0;
        description
          "Tm board type SFU.";
      }
      enum "lpu" {
        value 1;
        description
          "Tm board type LPU.";
      }
    }
    description
      "The type of board.";
  }

  typedef ncs_rpc_notif_lpu-switch-status {
    type enumeration {
      enum "close" {
        value 0;
        description
          "Close status.";
      }
      enum "open" {
        value 1;
        description
          "Open status.";
      }
      enum "init" {
        value 2;
        description
          "Init status.";
      }
      enum "link-lost-error" {
        value 3;
        description
          "Link lost error status.";
      }
      enum "crc-error" {
        value 4;
        description
          "Crc error status.";
      }
      enum "packet-error" {
        value 5;
        description
          "Packet error status.";
      }
      enum "unstable-error" {
        value 6;
        description
          "Unstable error status.";
      }
      enum "isoswf-error" {
        value 11;
        description
          "Isoswf error status.";
      }
      enum "isotm-error" {
        value 26;
        description
          "Isotm error status.";
      }
      enum "linkv" {
        value 42;
        description
          "Linkv status.";
      }
      enum "tx-off" {
        value 49;
        description
          "TX off status.";
      }
    }
    description
      "The status of switch.";
  }

  typedef ncs_rpc_notif_choice-enable-type {
    type enumeration {
      enum "enable" {
        value 0;
        description
          "Enable.";
      }
    }
    description
      "Enable warm backup.";
  }

  typedef live_ncs_board-type {
    type enumeration {
      enum "sfu" {
        value 0;
        description
          "Tm board type SFU.";
      }
      enum "lpu" {
        value 1;
        description
          "Tm board type LPU.";
      }
    }
    description
      "The type of board.";
  }

  typedef live_ncs_lpu-switch-status {
    type enumeration {
      enum "close" {
        value 0;
        description
          "Close status.";
      }
      enum "open" {
        value 1;
        description
          "Open status.";
      }
      enum "init" {
        value 2;
        description
          "Init status.";
      }
      enum "link-lost-error" {
        value 3;
        description
          "Link lost error status.";
      }
      enum "crc-error" {
        value 4;
        description
          "Crc error status.";
      }
      enum "packet-error" {
        value 5;
        description
          "Packet error status.";
      }
      enum "unstable-error" {
        value 6;
        description
          "Unstable error status.";
      }
      enum "isoswf-error" {
        value 11;
        description
          "Isoswf error status.";
      }
      enum "isotm-error" {
        value 26;
        description
          "Isotm error status.";
      }
      enum "linkv" {
        value 42;
        description
          "Linkv status.";
      }
      enum "tx-off" {
        value 49;
        description
          "TX off status.";
      }
    }
    description
      "The status of switch.";
  }

  typedef live_ncs_choice-enable-type {
    type enumeration {
      enum "enable" {
        value 0;
        description
          "Enable.";
      }
    }
    description
      "Enable warm backup.";
  }

  typedef board-type {
    type enumeration {
      enum "sfu" {
        value 0;
        description
          "Tm board type SFU.";
      }
      enum "lpu" {
        value 1;
        description
          "Tm board type LPU.";
      }
    }
    description
      "The type of board.";
  }

  typedef lpu-switch-status {
    type enumeration {
      enum "close" {
        value 0;
        description
          "Close status.";
      }
      enum "open" {
        value 1;
        description
          "Open status.";
      }
      enum "init" {
        value 2;
        description
          "Init status.";
      }
      enum "link-lost-error" {
        value 3;
        description
          "Link lost error status.";
      }
      enum "crc-error" {
        value 4;
        description
          "Crc error status.";
      }
      enum "packet-error" {
        value 5;
        description
          "Packet error status.";
      }
      enum "unstable-error" {
        value 6;
        description
          "Unstable error status.";
      }
      enum "isoswf-error" {
        value 11;
        description
          "Isoswf error status.";
      }
      enum "isotm-error" {
        value 26;
        description
          "Isotm error status.";
      }
      enum "linkv" {
        value 42;
        description
          "Linkv status.";
      }
      enum "tx-off" {
        value 49;
        description
          "TX off status.";
      }
    }
    description
      "The status of switch.";
  }

  typedef choice-enable-type {
    type enumeration {
      enum "enable" {
        value 0;
        description
          "Enable.";
      }
    }
    description
      "Enable warm backup.";
  }

  augment "/ncs:devices/ncs:device/ncs:config" {
    container trafficmng {
      tailf:ncs-device-type "netconf";
      tailf:display-when "not(../../ncs:module) or ../../ncs:module[ncs:name='huawei-trafficmng']";
      description
        "Specify configuration information of traffic management.";
      container board-alarm-sfu-thresholds {
        description
          "List of link-lost alarm config with board sfu.";
        list board-alarm-sfu-threshold {
          key "slot-id";
          description
            "Configure link-lost alarm value.";
          leaf slot-id {
            type string {
              length "1..32";
              pattern '(c[cl]c\d+/)?\d+';
            }
            description
              "Slot ID of board.";
          }
          leaf value {
            type uint32 {
              range "1..64";
            }
            mandatory true;
            description
              "Value of link-lost.";
          }
        }
      }
      container board-alarm-lpu-thresholds {
        description
          "List of link-lost alarm config with board lpu.";
        list board-alarm-lpu-threshold {
          key "slot-id";
          description
            "Configure link-lost alarm value.";
          leaf slot-id {
            type leafref {
              path "/ncs:devices/ncs:device/ncs:config/devm:devm/devm:lpu-boards/devm:lpu-board/devm:position" {
                tailf:xpath-root 3;
              }
            }
            description
              "Slot ID of board.";
          }
          leaf value {
            type uint32 {
              range "1..16";
            }
            mandatory true;
            description
              "Value of link lost.";
          }
        }
      }
      container sfu-warm-backup-switch {
        description
          "Configure SFU warm backup enable.";
        leaf enable {
          type choice-enable-type;
          description
            "Enable/disable SFU warm backup.";
        }
      }
      container packet-loss-alarms {
        description
          "List of statistics alarm thresholds.";
        list packet-loss-alarm {
          key "slot-id";
          description
            "Configure statistics alarm threshold.";
          leaf slot-id {
            type leafref {
              path "/ncs:devices/ncs:device/ncs:config/devm:devm/devm:lpu-boards/devm:lpu-board/devm:position" {
                tailf:xpath-root 3;
              }
            }
            description
              "Slot ID of board.";
          }
          leaf packets {
            type uint32 {
              range "1..4294967295";
            }
            units "packet";
            default "10000";
            description
              "Packets.";
          }
          leaf seconds {
            type uint32 {
              range "5..3600";
            }
            units "s";
            default "60";
            description
              "Seconds.";
          }
        }
      }
      container lpu-backpressure-switch {
        description
          "Configure LPU backpressure.";
        leaf enable {
          type choice-enable-type;
          description
            "Enable/disable LPU backpressure.";
        }
      }
      // NCS drop config false container 'tm-sfu-informations'
      // NCS drop config false container 'tm-lpu-statuss'
    }
  }
  augment "/ncs:devices/ncs:device/ncs:live-status" {
    container trafficmng {
      tailf:ncs-device-type "netconf";
      tailf:display-when "not(../../ncs:module) or ../../ncs:module[ncs:name='huawei-trafficmng'] or (../../ncs:live-status-protocol[not(ncs:capability)]) or (../../ncs:live-status-protocol/ncs:capability/ncs:module[.='huawei-trafficmng'])";
      description
        "Specify configuration information of traffic management.";
      container board-alarm-sfu-thresholds {
        description
          "List of link-lost alarm config with board sfu.";
        list board-alarm-sfu-threshold {
          key "slot-id";
          description
            "Configure link-lost alarm value.";
          leaf slot-id {
            type string {
              length "1..32";
              pattern '(c[cl]c\d+/)?\d+';
            }
            description
              "Slot ID of board.";
          }
          leaf value {
            type uint32 {
              range "1..64";
            }
            // NCS drop mandatory statement
            description
              "Value of link-lost.";
          }
        }
      }
      container board-alarm-lpu-thresholds {
        description
          "List of link-lost alarm config with board lpu.";
        list board-alarm-lpu-threshold {
          key "slot-id";
          description
            "Configure link-lost alarm value.";
          leaf slot-id {
            type leafref {
              path "/ncs:devices/ncs:device/ncs:live-status/devm:devm/devm:lpu-boards/devm:lpu-board/devm:position" {
                tailf:xpath-root 3;
              }
            }
            description
              "Slot ID of board.";
          }
          leaf value {
            type uint32 {
              range "1..16";
            }
            // NCS drop mandatory statement
            description
              "Value of link lost.";
          }
        }
      }
      container sfu-warm-backup-switch {
        description
          "Configure SFU warm backup enable.";
        leaf enable {
          type live_ncs_choice-enable-type;
          description
            "Enable/disable SFU warm backup.";
        }
      }
      container packet-loss-alarms {
        description
          "List of statistics alarm thresholds.";
        list packet-loss-alarm {
          key "slot-id";
          description
            "Configure statistics alarm threshold.";
          leaf slot-id {
            type leafref {
              path "/ncs:devices/ncs:device/ncs:live-status/devm:devm/devm:lpu-boards/devm:lpu-board/devm:position" {
                tailf:xpath-root 3;
              }
            }
            description
              "Slot ID of board.";
          }
          leaf packets {
            type uint32 {
              range "1..4294967295";
            }
            units "packet";
            // NCS drop default statement
            description
              "Packets.";
          }
          leaf seconds {
            type uint32 {
              range "5..3600";
            }
            units "s";
            // NCS drop default statement
            description
              "Seconds.";
          }
        }
      }
      container lpu-backpressure-switch {
        description
          "Configure LPU backpressure.";
        leaf enable {
          type live_ncs_choice-enable-type;
          description
            "Enable/disable LPU backpressure.";
        }
      }
      container tm-sfu-informations {
        description
          "List of tm SFU information.";
        list tm-sfu-information {
          key "slot-id";
          description
            "Operational state of tm SFU.";
          leaf slot-id {
            type string {
              length "1..32";
              pattern '(c[cl]c\d+/)?(SFU)?\d+';
            }
            description
              "Slot id.";
          }
          container inbound-switch-port-statuss {
            description
              "List of SFU switch input port status.";
            list inbound-switch-port-status {
              key "chip-number port";
              description
                "Operational state of SFU switch input port.";
              leaf chip-number {
                type uint32 {
                  range "0..7";
                }
                description
                  "Chip number.";
              }
              leaf port {
                type uint32 {
                  range "0..200";
                }
                description
                  "Input port.";
              }
              leaf status {
                type live_ncs_lpu-switch-status;
                description
                  "Input status.";
              }
            }
          }
          container outbound-switch-port-statuss {
            description
              "List of SFU switch output port status.";
            list outbound-switch-port-status {
              key "chip-number port";
              description
                "Operational state of SFU switch output port.";
              leaf chip-number {
                type uint32 {
                  range "0..7";
                }
                description
                  "Chip number.";
              }
              leaf port {
                type uint32 {
                  range "0..200";
                }
                description
                  "Output port.";
              }
              leaf status {
                type live_ncs_lpu-switch-status;
                description
                  "Output status.";
              }
            }
          }
          container sfu-statistics {
            description
              "List of SFU statistics.";
            list sfu-statistic {
              key "chip-id";
              description
                "Statistics of SFU.";
              leaf chip-id {
                type uint32 {
                  range "0..7";
                }
                description
                  "Chip ID.";
              }
              leaf pass-cells {
                type uint64;
                description
                  "Pass cells.";
              }
              leaf discard-cells {
                type uint64;
                description
                  "Discard cells.";
              }
              leaf send-cells {
                type uint64;
                description
                  "Send cells.";
              }
            }
          }
        }
      }
      container tm-lpu-statuss {
        description
          "List of the status of the switch port on an LPU.";
        list tm-lpu-status {
          key "slot-id";
          description
            "Operational state of the switch port on an LPU.";
          leaf slot-id {
            type string {
              length "1..32";
              pattern '(c[cl]c\d+/)?\d+';
            }
            description
              "Slot ID.";
          }
          container inbound-switch-port-statuss {
            description
              "List of LPU switch input port status.";
            list inbound-switch-port-status {
              key "chip-number port";
              description
                "Operational state of LPU switch input port.";
              leaf chip-number {
                type uint32 {
                  range "0..7";
                }
                description
                  "Chip number.";
              }
              leaf port {
                type uint32 {
                  range "0..200";
                }
                description
                  "Input port.";
              }
              leaf status {
                type live_ncs_lpu-switch-status;
                description
                  "Input status.";
              }
            }
          }
          container outbound-switch-port-statuss {
            description
              "List of LPU switch output port status.";
            list outbound-switch-port-status {
              key "chip-number port";
              description
                "Operational state of LPU switch output port.";
              leaf chip-number {
                type uint32 {
                  range "0..7";
                }
                description
                  "Chip number.";
              }
              leaf port {
                type uint32 {
                  range "0..200";
                }
                description
                  "Output port.";
              }
              leaf status {
                type live_ncs_lpu-switch-status;
                description
                  "Output status.";
              }
            }
          }
          container tm-statisticss {
            description
              "List of tm statistics.";
            list tm-statistics {
              key "chip-id";
              description
                "Tm statistics.";
              leaf chip-id {
                type uint32 {
                  range "0..7";
                }
                description
                  "Chip ID.";
              }
              leaf pass-packets-in {
                type uint64;
                units "packet";
                description
                  "Number of packets entered by NP to FABRIC.";
              }
              leaf discard-packets-in {
                type uint64;
                units "packet";
                description
                  "Number of packets discarded from NP to FABRIC.";
              }
              leaf send-cells-in {
                type uint64;
                description
                  "Number of cells from NP to FABRIC out.";
              }
              leaf pass-cells-out {
                type uint64;
                description
                  "Number of cells entered by FABRIC to NP.";
              }
              leaf pass-packets-out {
                type uint64;
                units "packet";
                description
                  "Number of packets entered by FABRIC to NP.";
              }
              leaf discard-packets-out {
                type uint64;
                units "packet";
                description
                  "Number of packets discarded by FABRIC to NP.";
              }
              leaf send-packets-out {
                type uint64;
                units "packet";
                description
                  "Number of packages from FABRIC to NP.";
              }
            }
          }
        }
      }
    }
  }
  augment "/ncs:devices/ncs:template/ncs:ned-id/ncs:config" {
    container trafficmng {
      description
        "Specify configuration information of traffic management.";
      container board-alarm-sfu-thresholds {
        description
          "List of link-lost alarm config with board sfu.";
        list board-alarm-sfu-threshold {
          // NCS patched for predictable order
          ordered-by user;
          key "slot-id";
          description
            "Configure link-lost alarm value.";
          leaf slot-id {
            type string;
            description
              "Slot ID of board.";
          }
          leaf value {
            type string;
            // NCS drop mandatory statement
            description
              "Value of link-lost.";
          }
        }
      }
      container board-alarm-lpu-thresholds {
        description
          "List of link-lost alarm config with board lpu.";
        list board-alarm-lpu-threshold {
          // NCS patched for predictable order
          ordered-by user;
          key "slot-id";
          description
            "Configure link-lost alarm value.";
          leaf slot-id {
            type string;
            description
              "Slot ID of board.";
          }
          leaf value {
            type string;
            // NCS drop mandatory statement
            description
              "Value of link lost.";
          }
        }
      }
      container sfu-warm-backup-switch {
        description
          "Configure SFU warm backup enable.";
        leaf enable {
          type ncs_template_choice-enable-type;
          description
            "Enable/disable SFU warm backup.";
        }
      }
      container packet-loss-alarms {
        description
          "List of statistics alarm thresholds.";
        list packet-loss-alarm {
          // NCS patched for predictable order
          ordered-by user;
          key "slot-id";
          description
            "Configure statistics alarm threshold.";
          leaf slot-id {
            type string;
            description
              "Slot ID of board.";
          }
          leaf packets {
            type string;
            units "packet";
            // NCS drop default statement
            description
              "Packets.";
          }
          leaf seconds {
            type string;
            units "s";
            // NCS drop default statement
            description
              "Seconds.";
          }
        }
      }
      container lpu-backpressure-switch {
        description
          "Configure LPU backpressure.";
        leaf enable {
          type ncs_template_choice-enable-type;
          description
            "Enable/disable LPU backpressure.";
        }
      }
      // NCS drop config false container 'tm-sfu-informations'
      // NCS drop config false container 'tm-lpu-statuss'
    }
  }
}
