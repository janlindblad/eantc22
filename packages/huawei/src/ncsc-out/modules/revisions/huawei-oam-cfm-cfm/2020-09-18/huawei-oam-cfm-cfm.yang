module huawei-oam-cfm-cfm {
  // Generated by yanger -t ncs
  tailf:mount-id "huawei-nc-1.0:huawei-nc-1.0";
  tailf:ncs-device-type "netconf";

  namespace "urn:huawei:yang:huawei-oam-cfm-cfm";
  prefix oam-cfm-cfm;

  import huawei-extension {
    prefix ext;
  }
  import huawei-oammgr {
    prefix oammgr;
  }
  import huawei-y1731 {
    prefix y1731;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Configure the operation, administration and maintenance (OAM) association function.";

  revision 2020-09-18 {
    description
      "Initial revision.";
    reference "Huawei private.";
  }
  ext:task-name "oammgr";

  typedef ncs_template_cfm-bind-cfm-type {
    type string;
    description
      "Binding type.";
  }

  typedef ncs_rpc_notif_cfm-bind-cfm-type {
    type enumeration {
      enum "CFM1-CFM2" {
        value 1;
        description
          "Type that CFM1 transfers fault information to CFM2.";
      }
      enum "CFM2-CFM1" {
        value 2;
        description
          "Type that CFM2 transfers fault information to CFM1.";
      }
    }
    description
      "Binding type.";
  }

  typedef live_ncs_cfm-bind-cfm-type {
    type enumeration {
      enum "CFM1-CFM2" {
        value 1;
        description
          "Type that CFM1 transfers fault information to CFM2.";
      }
      enum "CFM2-CFM1" {
        value 2;
        description
          "Type that CFM2 transfers fault information to CFM1.";
      }
    }
    description
      "Binding type.";
  }

  typedef cfm-bind-cfm-type {
    type enumeration {
      enum "CFM1-CFM2" {
        value 1;
        description
          "Type that CFM1 transfers fault information to CFM2.";
      }
      enum "CFM2-CFM1" {
        value 2;
        description
          "Type that CFM2 transfers fault information to CFM1.";
      }
    }
    description
      "Binding type.";
  }

  augment "/ncs:devices/ncs:template/ncs:ned-id/ncs:config/oammgr:oammgr" {
    description
      "Configure the operation, administration and maintenance (OAM) association function.";
    container cfm-bind-cfms {
      description
        "List of associations between CFM and CFM.";
      list cfm-bind-cfm {
        // NCS patched for predictable order
        ordered-by user;
        // NCS drop must statement
        key "md-name1 ma-name1 md-name2 ma-name2 bind-type";
        unique "md-name1 ma-name1 bind-type";
        unique "md-name2 ma-name2 bind-type";
        description
          "Configure an instance of an association between CFM and CFM.";
        leaf md-name1 {
          type string;
          description
            "Configure the name of the first MD.";
        }
        leaf ma-name1 {
          type string;
          description
            "Configure the name of the first MA.";
        }
        leaf md-name2 {
          type string;
          description
            "Configure the name of the second MD.";
        }
        leaf ma-name2 {
          type string;
          description
            "Configure the name of the second MA.";
        }
        leaf bind-type {
          type ncs_template_cfm-bind-cfm-type;
          description
            "Configure a binding type.";
        }
      }
    }
  }
  augment "/ncs:devices/ncs:device/ncs:live-status/oammgr:oammgr" {
    description
      "Configure the operation, administration and maintenance (OAM) association function.";
    container cfm-bind-cfms {
      tailf:ncs-device-type "netconf";
      tailf:display-when "not(../../../ncs:module) or ../../../ncs:module[ncs:name='huawei-oam-cfm-cfm'] or (../../../ncs:live-status-protocol[not(ncs:capability)]) or (../../../ncs:live-status-protocol/ncs:capability/ncs:module[.='huawei-oam-cfm-cfm'])";
      description
        "List of associations between CFM and CFM.";
      list cfm-bind-cfm {
        // NCS drop must statement
        key "md-name1 ma-name1 md-name2 ma-name2 bind-type";
        unique "md-name1 ma-name1 bind-type";
        unique "md-name2 ma-name2 bind-type";
        description
          "Configure an instance of an association between CFM and CFM.";
        leaf md-name1 {
          type leafref {
            path "/ncs:devices/ncs:device/ncs:live-status/y1731:y1731/y1731:global-enable/y1731:mds/y1731:md/y1731:name" {
              tailf:xpath-root 3;
            }
          }
          description
            "Configure the name of the first MD.";
        }
        leaf ma-name1 {
          type leafref {
            path "/ncs:devices/ncs:device/ncs:live-status/y1731:y1731/y1731:global-enable/y1731:mds/y1731:md[y1731:name=current()/../md-name1]/y1731:mas/y1731:ma/y1731:name" {
              tailf:xpath-root 3;
            }
          }
          description
            "Configure the name of the first MA.";
        }
        leaf md-name2 {
          type leafref {
            path "/ncs:devices/ncs:device/ncs:live-status/y1731:y1731/y1731:global-enable/y1731:mds/y1731:md/y1731:name" {
              tailf:xpath-root 3;
            }
          }
          description
            "Configure the name of the second MD.";
        }
        leaf ma-name2 {
          type leafref {
            path "/ncs:devices/ncs:device/ncs:live-status/y1731:y1731/y1731:global-enable/y1731:mds/y1731:md[y1731:name=current()/../md-name2]/y1731:mas/y1731:ma/y1731:name" {
              tailf:xpath-root 3;
            }
          }
          description
            "Configure the name of the second MA.";
        }
        leaf bind-type {
          type live_ncs_cfm-bind-cfm-type;
          description
            "Configure a binding type.";
        }
      }
    }
  }
  augment "/ncs:devices/ncs:device/ncs:config/oammgr:oammgr" {
    description
      "Configure the operation, administration and maintenance (OAM) association function.";
    container cfm-bind-cfms {
      tailf:ncs-device-type "netconf";
      tailf:display-when "not(../../../ncs:module) or ../../../ncs:module[ncs:name='huawei-oam-cfm-cfm']";
      description
        "List of associations between CFM and CFM.";
      list cfm-bind-cfm {
        must 'not((md-name1=md-name2) and (ma-name1=ma-name2))' {
          tailf:xpath-root 3;
        }
        key "md-name1 ma-name1 md-name2 ma-name2 bind-type";
        unique "md-name1 ma-name1 bind-type";
        unique "md-name2 ma-name2 bind-type";
        description
          "Configure an instance of an association between CFM and CFM.";
        leaf md-name1 {
          type leafref {
            path "/ncs:devices/ncs:device/ncs:config/y1731:y1731/y1731:global-enable/y1731:mds/y1731:md/y1731:name" {
              tailf:xpath-root 3;
            }
          }
          description
            "Configure the name of the first MD.";
        }
        leaf ma-name1 {
          type leafref {
            path "/ncs:devices/ncs:device/ncs:config/y1731:y1731/y1731:global-enable/y1731:mds/y1731:md[y1731:name=current()/../md-name1]/y1731:mas/y1731:ma/y1731:name" {
              tailf:xpath-root 3;
            }
          }
          description
            "Configure the name of the first MA.";
        }
        leaf md-name2 {
          type leafref {
            path "/ncs:devices/ncs:device/ncs:config/y1731:y1731/y1731:global-enable/y1731:mds/y1731:md/y1731:name" {
              tailf:xpath-root 3;
            }
          }
          description
            "Configure the name of the second MD.";
        }
        leaf ma-name2 {
          type leafref {
            path "/ncs:devices/ncs:device/ncs:config/y1731:y1731/y1731:global-enable/y1731:mds/y1731:md[y1731:name=current()/../md-name2]/y1731:mas/y1731:ma/y1731:name" {
              tailf:xpath-root 3;
            }
          }
          description
            "Configure the name of the second MA.";
        }
        leaf bind-type {
          type cfm-bind-cfm-type;
          description
            "Configure a binding type.";
        }
      }
    }
  }
}
