module huawei-link-heartbeat {
  // Generated by yanger -t ncs
  tailf:mount-id "huawei-nc-1.0:huawei-nc-1.0";
  tailf:ncs-device-type "netconf";

  yang-version 1;
  namespace "urn:huawei:yang:huawei-link-heartbeat";
  prefix link-heartbeat;

  import huawei-ifm {
    prefix ifm;
  }
  import huawei-extension {
    prefix ext;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Link-heartbeat is the way of detecting the link quality by sending heart packets between two devices.";

  revision 2020-04-22 {
    description
      "Initial revision.";
    reference "Huawei private.";
  }
  ext:task-name "forwarding";

  typedef ncs_template_state {
    type string;
    description
      "Link-heartbeat state type.";
  }

  typedef ncs_template_state-flag {
    type string;
    description
      "Link-heartbeat state flag type.";
  }

  typedef ncs_template_port-ready {
    type string;
    description
      "Link-heartbeat state flag type.";
  }

  typedef ncs_rpc_notif_state {
    type enumeration {
      enum "init" {
        value 0;
        description
          "Indicates that link-heartbeat status is initial.";
      }
      enum "normal" {
        value 1;
        description
          "Indicates that link-heartbeat status is normal.";
      }
      enum "approach" {
        value 2;
        description
          "Indicates that link-heartbeat status is approach.";
      }
      enum "diagnose" {
        value 3;
        description
          "Indicates that link-heartbeat status is diagnose.";
      }
    }
    description
      "Link-heartbeat state type.";
  }

  typedef ncs_rpc_notif_state-flag {
    type enumeration {
      enum "normal" {
        value 0;
        description
          "Indicates that link-heartbeat state is normal.";
      }
      enum "alarm" {
        value 1;
        description
          "Indicates that link-heartbeat state is alarm.";
      }
    }
    description
      "Link-heartbeat state flag type.";
  }

  typedef ncs_rpc_notif_port-ready {
    type enumeration {
      enum "not-ready" {
        value 0;
        description
          "A port is not ready to send packets.";
      }
      enum "ready" {
        value 1;
        description
          "A port is ready to send packets.";
      }
    }
    description
      "Link-heartbeat state flag type.";
  }

  typedef live_ncs_state {
    type enumeration {
      enum "init" {
        value 0;
        description
          "Indicates that link-heartbeat status is initial.";
      }
      enum "normal" {
        value 1;
        description
          "Indicates that link-heartbeat status is normal.";
      }
      enum "approach" {
        value 2;
        description
          "Indicates that link-heartbeat status is approach.";
      }
      enum "diagnose" {
        value 3;
        description
          "Indicates that link-heartbeat status is diagnose.";
      }
    }
    description
      "Link-heartbeat state type.";
  }

  typedef live_ncs_state-flag {
    type enumeration {
      enum "normal" {
        value 0;
        description
          "Indicates that link-heartbeat state is normal.";
      }
      enum "alarm" {
        value 1;
        description
          "Indicates that link-heartbeat state is alarm.";
      }
    }
    description
      "Link-heartbeat state flag type.";
  }

  typedef live_ncs_port-ready {
    type enumeration {
      enum "not-ready" {
        value 0;
        description
          "A port is not ready to send packets.";
      }
      enum "ready" {
        value 1;
        description
          "A port is ready to send packets.";
      }
    }
    description
      "Link-heartbeat state flag type.";
  }

  typedef state {
    type enumeration {
      enum "init" {
        value 0;
        description
          "Indicates that link-heartbeat status is initial.";
      }
      enum "normal" {
        value 1;
        description
          "Indicates that link-heartbeat status is normal.";
      }
      enum "approach" {
        value 2;
        description
          "Indicates that link-heartbeat status is approach.";
      }
      enum "diagnose" {
        value 3;
        description
          "Indicates that link-heartbeat status is diagnose.";
      }
    }
    description
      "Link-heartbeat state type.";
  }

  typedef state-flag {
    type enumeration {
      enum "normal" {
        value 0;
        description
          "Indicates that link-heartbeat state is normal.";
      }
      enum "alarm" {
        value 1;
        description
          "Indicates that link-heartbeat state is alarm.";
      }
    }
    description
      "Link-heartbeat state flag type.";
  }

  typedef port-ready {
    type enumeration {
      enum "not-ready" {
        value 0;
        description
          "A port is not ready to send packets.";
      }
      enum "ready" {
        value 1;
        description
          "A port is ready to send packets.";
      }
    }
    description
      "Link-heartbeat state flag type.";
  }

  augment "/ncs:devices/ncs:device/ncs:config" {
    // NCS drop config false container 'link-heartbeat'
  }
  augment "/ncs:devices/ncs:device/ncs:live-status" {
    container link-heartbeat {
      tailf:ncs-device-type "netconf";
      tailf:display-when "not(../../ncs:module) or ../../ncs:module[ncs:name='huawei-link-heartbeat'] or (../../ncs:live-status-protocol[not(ncs:capability)]) or (../../ncs:live-status-protocol/ncs:capability/ncs:module[.='huawei-link-heartbeat'])";
      description
        "Link-heartbeat is the way of detecting the link quality by sending heart packets between two devices.";
      container interfaces {
        description
          "List of the link-heartbeat query on the local interface.";
        list interface {
          key "if-name";
          description
            "Operational data of the link-heartbeat query on the local interface.";
          leaf if-name {
            type leafref {
              path "/ncs:devices/ncs:device/ncs:live-status/ifm:ifm/ifm:interfaces/ifm:interface/ifm:name" {
                tailf:xpath-root 3;
              }
            }
            description
              "Specifies the name of the interface enabled with link-heartbeat.";
          }
          leaf member-if-name {
            // NCS drop when statement
            type leafref {
              path "/ncs:devices/ncs:device/ncs:live-status/ifm:ifm/ifm:interfaces/ifm:interface/ifm:name" {
                tailf:xpath-root 3;
              }
            }
            description
              "Indicates the sending packet interface name for link-heartbeat.";
          }
          leaf detect-status {
            type live_ncs_state;
            description
              "Indicates the link-heartbeat detect status.";
          }
          leaf send-packet-num {
            type uint16;
            units "packet";
            description
              "Indicates the send number of packets.";
          }
          leaf rcv-packet-num {
            type uint16;
            units "packet";
            description
              "Indicates the receive number of packets.";
          }
          leaf loss-alarm {
            type live_ncs_state-flag;
            description
              "Indicates whether the alarm of loss packets occurs.";
          }
          leaf modify-alarm {
            type live_ncs_state-flag;
            description
              "Indicates whether the alarm of modify packets occurs.";
          }
          leaf port-ready {
            type live_ncs_port-ready;
            description
              "Whether a port is ready to send packets.";
          }
          leaf port-ready-reason {
            type string {
              length "1..100";
            }
            description
              "Indicates the reason of a port is ready or not ready.";
          }
        }
      }
    }
  }
  augment "/ncs:devices/ncs:template/ncs:ned-id/ncs:config" {
    // NCS drop config false container 'link-heartbeat'
  }
}
