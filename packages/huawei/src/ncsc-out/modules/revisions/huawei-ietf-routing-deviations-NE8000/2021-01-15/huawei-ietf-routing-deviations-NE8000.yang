module huawei-ietf-routing-deviations-NE8000 {
  // Generated by yanger -t ncs
  tailf:mount-id "huawei-nc-1.0:huawei-nc-1.0";
  tailf:ncs-device-type "netconf";

  yang-version 1.1;
  namespace "urn:huawei:yang:huawei-ietf-routing-deviations-NE8000";
  prefix rt-devs-NE8000-ietf;

  import ietf-routing {
    prefix rt;
  }
  import huawei-extension {
    prefix ext;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Deviations for ietf-network model.";

  revision 2021-01-15 {
    description
      "Initial revision.";
    reference "Huawei private.";
  }
  ext:deviation-ext "/rt:routing/rt:control-plane-protocols/rt:control-plane-protocol" {
    ext:deviate-ext "add" {
      ext:generated-by "system" {
        when "./name = 'default'" {
          tailf:xpath-root 3;
        }
        description
          "The default protocol is generated automatically.";
      }
    }
  }

  deviation "/ncs:devices/ncs:template/ncs:ned-id/ncs:config/rt:routing/rt:router-id" {
    deviate not-supported;
  }
  deviation "/ncs:devices/ncs:device/ncs:live-status/rt:routing/rt:router-id" {
    deviate not-supported;
  }
  deviation "/ncs:devices/ncs:device/ncs:config/rt:routing/rt:router-id" {
    deviate not-supported;
  }
  deviation "/ncs:devices/ncs:device/ncs:live-status/rt:routing/rt:interfaces" {
    deviate not-supported;
  }
  deviation "/ncs:devices/ncs:template/ncs:ned-id/ncs:config/rt:routing/rt:control-plane-protocols/rt:control-plane-protocol/rt:name" {
    deviate replace {
      type string;
    }
  }
  deviation "/ncs:devices/ncs:device/ncs:live-status/rt:routing/rt:control-plane-protocols/rt:control-plane-protocol/rt:name" {
    deviate replace {
      type string {
        length "1..10";
      }
    }
  }
  deviation "/ncs:devices/ncs:device/ncs:config/rt:routing/rt:control-plane-protocols/rt:control-plane-protocol/rt:name" {
    deviate replace {
      type string {
        length "1..10";
      }
    }
  }
  deviation "/ncs:devices/ncs:template/ncs:ned-id/ncs:config/rt:routing/rt:control-plane-protocols/rt:control-plane-protocol/rt:description" {
    deviate not-supported;
  }
  deviation "/ncs:devices/ncs:device/ncs:live-status/rt:routing/rt:control-plane-protocols/rt:control-plane-protocol/rt:description" {
    deviate not-supported;
  }
  deviation "/ncs:devices/ncs:device/ncs:config/rt:routing/rt:control-plane-protocols/rt:control-plane-protocol/rt:description" {
    deviate not-supported;
  }
  deviation "/ncs:devices/ncs:template/ncs:ned-id/ncs:config/rt:routing/rt:control-plane-protocols/rt:control-plane-protocol/rt:name" {
    deviate add {
      // NCS drop must statement
    }
  }
  deviation "/ncs:devices/ncs:device/ncs:live-status/rt:routing/rt:control-plane-protocols/rt:control-plane-protocol/rt:name" {
    deviate add {
      // NCS drop must statement
    }
  }
  deviation "/ncs:devices/ncs:device/ncs:config/rt:routing/rt:control-plane-protocols/rt:control-plane-protocol/rt:name" {
    deviate add {
      must "((../type='rt:static' or ../type='rt:direct') and ../name='default')" {
        tailf:xpath-root 3;
      }
    }
  }
  deviation "/ncs:devices/ncs:template/ncs:ned-id/ncs:config/rt:routing/rt:ribs" {
    deviate not-supported;
  }
  deviation "/ncs:devices/ncs:device/ncs:live-status/rt:routing/rt:ribs" {
    deviate not-supported;
  }
  deviation "/ncs:devices/ncs:device/ncs:config/rt:routing/rt:ribs" {
    deviate not-supported;
  }
  deviation "/ncs:devices/ncs:device/ncs:live-status/rt:routing-state" {
    deviate not-supported;
  }
}
