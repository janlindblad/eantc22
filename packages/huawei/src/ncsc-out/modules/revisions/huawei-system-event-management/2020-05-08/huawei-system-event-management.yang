module huawei-system-event-management {
  // Generated by yanger -t ncs
  tailf:mount-id "huawei-nc-1.0:huawei-nc-1.0";
  tailf:ncs-device-type "netconf";

  namespace "urn:huawei:yang:huawei-system-event-management";
  prefix sem;

  import huawei-extension {
    prefix ext;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "System Event Management (SEM).";

  revision 2020-05-08 {
    description
      "Initial revision.";
    reference "Huawei private.";
  }
  ext:task-name "device-mgr";

  typedef ncs_template_slave-switch-mode {
    type string;
    description
      "Switchover enable type.";
  }

  typedef ncs_template_slave-switch-policy {
    type string;
    description
      "Switchover policy.";
  }

  typedef ncs_rpc_notif_slave-switch-mode {
    type enumeration {
      enum "enable" {
        value 0;
        description
          "Enable.";
      }
      enum "disable" {
        value 1;
        description
          "Disable.";
      }
    }
    description
      "Switchover enable type.";
  }

  typedef ncs_rpc_notif_slave-switch-policy {
    type enumeration {
      enum "board-switchover" {
        value 0;
        description
          "Board switchover.";
      }
      enum "process-switchover" {
        value 1;
        description
          "Process switchover.";
      }
    }
    description
      "Switchover policy.";
  }

  typedef live_ncs_slave-switch-mode {
    type enumeration {
      enum "enable" {
        value 0;
        description
          "Enable.";
      }
      enum "disable" {
        value 1;
        description
          "Disable.";
      }
    }
    description
      "Switchover enable type.";
  }

  typedef live_ncs_slave-switch-policy {
    type enumeration {
      enum "board-switchover" {
        value 0;
        description
          "Board switchover.";
      }
      enum "process-switchover" {
        value 1;
        description
          "Process switchover.";
      }
    }
    description
      "Switchover policy.";
  }

  typedef slave-switch-mode {
    type enumeration {
      enum "enable" {
        value 0;
        description
          "Enable.";
      }
      enum "disable" {
        value 1;
        description
          "Disable.";
      }
    }
    description
      "Switchover enable type.";
  }

  typedef slave-switch-policy {
    type enumeration {
      enum "board-switchover" {
        value 0;
        description
          "Board switchover.";
      }
      enum "process-switchover" {
        value 1;
        description
          "Process switchover.";
      }
    }
    description
      "Switchover policy.";
  }

  augment "/ncs:devices/ncs:device/ncs:rpc" {
    container rpc-switch-over {
      tailf:ncs-device-type "netconf";
      tailf:display-when "not(../../ncs:module) or ../../ncs:module[ncs:name='huawei-system-event-management']";
      tailf:action switch-over {
        tailf:actionpoint ncsproxy {
          tailf:internal;
        }
        description
          "Switch over.";
        input {
          leaf chassis-name {
            type string {
              length "1..31";
            }
            description
              "Chassis name.";
          }
          leaf position {
            type string {
              length "1..32";
            }
            description
              "Chassis position.";
          }
        }
      }
    }
  }
  augment "/ncs:devices/ncs:device-group/ncs:ned-id/ncs:rpc" {
    container rpc-switch-over {
      tailf:ncs-device-type "netconf";
      tailf:display-when "/ncs:devices/ncs:device[ncs:name=current()/../../../ncs:member]/ncs:module[ncs:name='huawei-system-event-management']";
      tailf:action switch-over {
        tailf:actionpoint ncsproxy {
          tailf:internal;
        }
        description
          "Switch over.";
        input {
          leaf chassis-name {
            type string {
              length "1..31";
            }
            description
              "Chassis name.";
          }
          leaf position {
            type string {
              length "1..32";
            }
            description
              "Chassis position.";
          }
        }
      }
    }
  }
  augment "/ncs:devices/ncs:device/ncs:config" {
    container system-event-management {
      tailf:ncs-device-type "netconf";
      tailf:display-when "not(../../ncs:module) or ../../ncs:module[ncs:name='huawei-system-event-management']";
      description
        "System Event Management (SEM).";
      container slave-switch {
        description
          "Configure swithover.";
        leaf enable {
          type slave-switch-mode;
          default "enable";
          description
            "Indicates whether to enable slave switch.";
        }
        // NCS drop config false leaf status
        // NCS drop config false leaf 'primary-board-postion'
        // NCS drop config false leaf 'slave-board-postion'
      }
      container multi-chassis-slave-switch {
        description
          "Configure multi chassis swithover list.";
        list config {
          key "chassis-name";
          ext:generated-by "system";
          ext:operation-exclude "create";
          description
            "Configure chassis swithover.";
          leaf chassis-name {
            type string {
              length "1..31";
            }
            description
              "Chassis name.";
          }
          leaf enable {
            type slave-switch-mode;
            default "enable";
            description
              "Indicates whether to enable slave switch.";
          }
        }
        // NCS drop config false list state
      }
      container batch-backup-timeout {
        description
          "Configure batch backup timeout.";
        leaf self-healing-timeout {
          type uint32 {
            range "10..14400";
          }
          units "min";
          description
            "Self healing timeout.";
        }
      }
      container chassis-batch-backup-timeouts {
        description
          "List of chassis batch backup timeout configs.";
        list chassis-batch-backup-timeout {
          key "chassis-name";
          ext:generated-by "system";
          ext:operation-exclude "create";
          description
            "Configure chassis batch backup timeout.";
          leaf chassis-name {
            type string {
              length "1..31";
            }
            description
              "Chassis name.";
          }
          leaf self-healing-timeout {
            type uint32 {
              range "10..14400";
            }
            units "min";
            description
              "Self healing timeout.";
          }
        }
      }
    }
  }
  augment "/ncs:devices/ncs:device/ncs:live-status" {
    container system-event-management {
      tailf:ncs-device-type "netconf";
      tailf:display-when "not(../../ncs:module) or ../../ncs:module[ncs:name='huawei-system-event-management'] or (../../ncs:live-status-protocol[not(ncs:capability)]) or (../../ncs:live-status-protocol/ncs:capability/ncs:module[.='huawei-system-event-management'])";
      description
        "System Event Management (SEM).";
      container slave-switch {
        description
          "Configure swithover.";
        leaf enable {
          type live_ncs_slave-switch-mode;
          // NCS drop default statement
          description
            "Indicates whether to enable slave switch.";
        }
        leaf status {
          type string {
            length "1..80";
          }
          description
            "Switchover status.";
        }
        leaf primary-board-postion {
          type string {
            length "1..32";
          }
          description
            "Master board position.";
        }
        leaf slave-board-postion {
          type string {
            length "1..32";
          }
          description
            "Slave board position.";
        }
      }
      container multi-chassis-slave-switch {
        description
          "Configure multi chassis swithover list.";
        list config {
          key "chassis-name";
          ext:generated-by "system";
          ext:operation-exclude "create";
          description
            "Configure chassis swithover.";
          leaf chassis-name {
            type string {
              length "1..31";
            }
            description
              "Chassis name.";
          }
          leaf enable {
            type live_ncs_slave-switch-mode;
            // NCS drop default statement
            description
              "Indicates whether to enable slave switch.";
          }
        }
        list state {
          key "chassis-name";
          description
            "Display chassis switchover state.";
          leaf chassis-name {
            type string {
              length "0..31";
            }
            description
              "Chassis name.";
          }
          leaf status {
            type string {
              length "1..80";
            }
            description
              "Switch state.";
          }
          leaf policy {
            type live_ncs_slave-switch-policy;
            description
              "Switchover status.";
          }
          leaf primary-board-postion {
            type string {
              length "0..32";
            }
            description
              "Main board postion.";
          }
          leaf slave-board-postion {
            type string {
              length "0..32";
            }
            description
              "Slave board postion.";
          }
        }
      }
      container batch-backup-timeout {
        description
          "Configure batch backup timeout.";
        leaf self-healing-timeout {
          type uint32 {
            range "10..14400";
          }
          units "min";
          description
            "Self healing timeout.";
        }
      }
      container chassis-batch-backup-timeouts {
        description
          "List of chassis batch backup timeout configs.";
        list chassis-batch-backup-timeout {
          key "chassis-name";
          ext:generated-by "system";
          ext:operation-exclude "create";
          description
            "Configure chassis batch backup timeout.";
          leaf chassis-name {
            type string {
              length "1..31";
            }
            description
              "Chassis name.";
          }
          leaf self-healing-timeout {
            type uint32 {
              range "10..14400";
            }
            units "min";
            description
              "Self healing timeout.";
          }
        }
      }
    }
  }
  augment "/ncs:devices/ncs:template/ncs:ned-id/ncs:config" {
    container system-event-management {
      description
        "System Event Management (SEM).";
      container slave-switch {
        description
          "Configure swithover.";
        leaf enable {
          type ncs_template_slave-switch-mode;
          // NCS drop default statement
          description
            "Indicates whether to enable slave switch.";
        }
        // NCS drop config false leaf status
        // NCS drop config false leaf 'primary-board-postion'
        // NCS drop config false leaf 'slave-board-postion'
      }
      container multi-chassis-slave-switch {
        description
          "Configure multi chassis swithover list.";
        list config {
          // NCS patched for predictable order
          ordered-by user;
          key "chassis-name";
          ext:generated-by "system";
          ext:operation-exclude "create";
          description
            "Configure chassis swithover.";
          leaf chassis-name {
            type string;
            description
              "Chassis name.";
          }
          leaf enable {
            type ncs_template_slave-switch-mode;
            // NCS drop default statement
            description
              "Indicates whether to enable slave switch.";
          }
        }
        // NCS drop config false list state
      }
      container batch-backup-timeout {
        description
          "Configure batch backup timeout.";
        leaf self-healing-timeout {
          type string;
          units "min";
          description
            "Self healing timeout.";
        }
      }
      container chassis-batch-backup-timeouts {
        description
          "List of chassis batch backup timeout configs.";
        list chassis-batch-backup-timeout {
          // NCS patched for predictable order
          ordered-by user;
          key "chassis-name";
          ext:generated-by "system";
          ext:operation-exclude "create";
          description
            "Configure chassis batch backup timeout.";
          leaf chassis-name {
            type string;
            description
              "Chassis name.";
          }
          leaf self-healing-timeout {
            type string;
            units "min";
            description
              "Self healing timeout.";
          }
        }
      }
    }
  }
}
