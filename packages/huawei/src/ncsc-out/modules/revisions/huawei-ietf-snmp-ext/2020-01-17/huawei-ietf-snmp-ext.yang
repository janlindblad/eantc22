module huawei-ietf-snmp-ext {
  // Generated by yanger -t ncs
  tailf:mount-id "huawei-nc-1.0:huawei-nc-1.0";
  tailf:ncs-device-type "netconf";

  namespace "urn:huawei:yang:huawei-ietf-snmp-ext";
  prefix hw-snmp-ext;

  import ietf-snmp {
    prefix snmp;
  }
  import huawei-extension {
    prefix ext;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Expand ietf-snmp.yang.";

  revision 2020-01-17 {
    description
      "Initial revision.";
    reference "Expand ietf-snmp.yang.";
  }
  ext:task-name "ietf-snmp";

  typedef ncs_template_key-hex-string {
    type string;
    description
      "A hexadecimal string with octets represented as hex digits separated by colons.";
  }

  typedef ncs_rpc_notif_key-hex-string {
    type string {
      length "2..max";
      pattern '([0-9a-fA-F]{2}(:[0-9a-fA-F]{2})*)?';
    }
    description
      "A hexadecimal string with octets represented as hex digits separated by colons.";
  }

  typedef live_ncs_key-hex-string {
    type string {
      length "2..max";
      pattern '([0-9a-fA-F]{2}(:[0-9a-fA-F]{2})*)?';
    }
    description
      "A hexadecimal string with octets represented as hex digits separated by colons.";
  }

  typedef key-hex-string {
    type string {
      length "2..max";
      pattern '([0-9a-fA-F]{2}(:[0-9a-fA-F]{2})*)?';
    }
    description
      "A hexadecimal string with octets represented as hex digits separated by colons.";
  }

  augment "/ncs:devices/ncs:template/ncs:ned-id/ncs:config/snmp:snmp/snmp:usm/snmp:local/snmp:user/snmp:auth/snmp:protocol" {
    description
      "Authentication algorithm.";
    case sha2-224 {
      description
        "SHA224 authentication algorithm.";
      container sha2-224 {
        description
          "Configure SNMPv3 user authen protocol.";
        leaf key {
          type ncs_template_key-hex-string;
          // NCS drop mandatory statement
          description
            "Localized key specified as a list of colon-specified hexadecimal octets.";
        }
      }
    }
    case sha2-256 {
      description
        "SHA256 authentication algorithml.";
      container sha2-256 {
        description
          "Configure SNMPv3 user authen protocol.";
        leaf key {
          type ncs_template_key-hex-string;
          // NCS drop mandatory statement
          description
            "Localized key specified as a list of colon-specified hexadecimal octets.";
        }
      }
    }
    case sha2-384 {
      description
        "SHA384 authentication algorithm.";
      container sha2-384 {
        description
          "Configure SNMPv3 user authen protocol.";
        leaf key {
          type ncs_template_key-hex-string;
          // NCS drop mandatory statement
          description
            "Localized key specified as a list of colon-specified hexadecimal octets.";
        }
      }
    }
    case sha2-512 {
      description
        "SHA512 authentication algorithm.";
      container sha2-512 {
        description
          "Configure SNMPv3 user authen protocol.";
        leaf key {
          type ncs_template_key-hex-string;
          // NCS drop mandatory statement
          description
            "Localized key specified as a list of colon-specified hexadecimal octets.";
        }
      }
    }
  }
  augment "/ncs:devices/ncs:device/ncs:live-status/snmp:snmp/snmp:usm/snmp:local/snmp:user/snmp:auth/snmp:protocol" {
    description
      "Authentication algorithm.";
    case sha2-224 {
      description
        "SHA224 authentication algorithm.";
      container sha2-224 {
        description
          "Configure SNMPv3 user authen protocol.";
        leaf key {
          type live_ncs_key-hex-string;
          // NCS drop mandatory statement
          description
            "Localized key specified as a list of colon-specified hexadecimal octets.";
        }
      }
    }
    case sha2-256 {
      description
        "SHA256 authentication algorithml.";
      container sha2-256 {
        description
          "Configure SNMPv3 user authen protocol.";
        leaf key {
          type live_ncs_key-hex-string;
          // NCS drop mandatory statement
          description
            "Localized key specified as a list of colon-specified hexadecimal octets.";
        }
      }
    }
    case sha2-384 {
      description
        "SHA384 authentication algorithm.";
      container sha2-384 {
        description
          "Configure SNMPv3 user authen protocol.";
        leaf key {
          type live_ncs_key-hex-string;
          // NCS drop mandatory statement
          description
            "Localized key specified as a list of colon-specified hexadecimal octets.";
        }
      }
    }
    case sha2-512 {
      description
        "SHA512 authentication algorithm.";
      container sha2-512 {
        description
          "Configure SNMPv3 user authen protocol.";
        leaf key {
          type live_ncs_key-hex-string;
          // NCS drop mandatory statement
          description
            "Localized key specified as a list of colon-specified hexadecimal octets.";
        }
      }
    }
  }
  augment "/ncs:devices/ncs:device/ncs:config/snmp:snmp/snmp:usm/snmp:local/snmp:user/snmp:auth/snmp:protocol" {
    description
      "Authentication algorithm.";
    case sha2-224 {
      description
        "SHA224 authentication algorithm.";
      container sha2-224 {
        description
          "Configure SNMPv3 user authen protocol.";
        leaf key {
          type key-hex-string;
          mandatory true;
          description
            "Localized key specified as a list of colon-specified hexadecimal octets.";
        }
      }
    }
    case sha2-256 {
      description
        "SHA256 authentication algorithml.";
      container sha2-256 {
        description
          "Configure SNMPv3 user authen protocol.";
        leaf key {
          type key-hex-string;
          mandatory true;
          description
            "Localized key specified as a list of colon-specified hexadecimal octets.";
        }
      }
    }
    case sha2-384 {
      description
        "SHA384 authentication algorithm.";
      container sha2-384 {
        description
          "Configure SNMPv3 user authen protocol.";
        leaf key {
          type key-hex-string;
          mandatory true;
          description
            "Localized key specified as a list of colon-specified hexadecimal octets.";
        }
      }
    }
    case sha2-512 {
      description
        "SHA512 authentication algorithm.";
      container sha2-512 {
        description
          "Configure SNMPv3 user authen protocol.";
        leaf key {
          type key-hex-string;
          mandatory true;
          description
            "Localized key specified as a list of colon-specified hexadecimal octets.";
        }
      }
    }
  }
  augment "/ncs:devices/ncs:template/ncs:ned-id/ncs:config/snmp:snmp/snmp:usm/snmp:remote/snmp:user/snmp:auth/snmp:protocol" {
    description
      "SNMPv3 remote user authen protocol.";
    case sha2-224 {
      description
        "SHA224 authentication algorithm.";
      container sha2-224 {
        description
          "Configure SNMPv3 user authen protocol.";
        leaf key {
          type ncs_template_key-hex-string;
          // NCS drop mandatory statement
          description
            "Localized key specified as a list of colon-specified hexadecimal octets.";
        }
      }
    }
    case sha2-256 {
      description
        "SHA256 authentication algorithm.";
      container sha2-256 {
        description
          "Configure SNMPv3 user authen protocol.";
        leaf key {
          type ncs_template_key-hex-string;
          // NCS drop mandatory statement
          description
            "Localized key specified as a list of colon-specified hexadecimal octets.";
        }
      }
    }
    case sha2-384 {
      description
        "SHA384 authentication algorithm.";
      container sha2-384 {
        description
          "Configure SNMPv3 user authen protocol.";
        leaf key {
          type ncs_template_key-hex-string;
          // NCS drop mandatory statement
          description
            "Localized key specified as a list of colon-specified hexadecimal octets.";
        }
      }
    }
    case sha2-512 {
      description
        "SHA512 authentication algorithm.";
      container sha2-512 {
        description
          "Configure SNMPv3 user authen protocol.";
        leaf key {
          type ncs_template_key-hex-string;
          // NCS drop mandatory statement
          description
            "Localized key specified as a list of colon-specified hexadecimal octets.";
        }
      }
    }
  }
  augment "/ncs:devices/ncs:device/ncs:live-status/snmp:snmp/snmp:usm/snmp:remote/snmp:user/snmp:auth/snmp:protocol" {
    description
      "SNMPv3 remote user authen protocol.";
    case sha2-224 {
      description
        "SHA224 authentication algorithm.";
      container sha2-224 {
        description
          "Configure SNMPv3 user authen protocol.";
        leaf key {
          type live_ncs_key-hex-string;
          // NCS drop mandatory statement
          description
            "Localized key specified as a list of colon-specified hexadecimal octets.";
        }
      }
    }
    case sha2-256 {
      description
        "SHA256 authentication algorithm.";
      container sha2-256 {
        description
          "Configure SNMPv3 user authen protocol.";
        leaf key {
          type live_ncs_key-hex-string;
          // NCS drop mandatory statement
          description
            "Localized key specified as a list of colon-specified hexadecimal octets.";
        }
      }
    }
    case sha2-384 {
      description
        "SHA384 authentication algorithm.";
      container sha2-384 {
        description
          "Configure SNMPv3 user authen protocol.";
        leaf key {
          type live_ncs_key-hex-string;
          // NCS drop mandatory statement
          description
            "Localized key specified as a list of colon-specified hexadecimal octets.";
        }
      }
    }
    case sha2-512 {
      description
        "SHA512 authentication algorithm.";
      container sha2-512 {
        description
          "Configure SNMPv3 user authen protocol.";
        leaf key {
          type live_ncs_key-hex-string;
          // NCS drop mandatory statement
          description
            "Localized key specified as a list of colon-specified hexadecimal octets.";
        }
      }
    }
  }
  augment "/ncs:devices/ncs:device/ncs:config/snmp:snmp/snmp:usm/snmp:remote/snmp:user/snmp:auth/snmp:protocol" {
    description
      "SNMPv3 remote user authen protocol.";
    case sha2-224 {
      description
        "SHA224 authentication algorithm.";
      container sha2-224 {
        description
          "Configure SNMPv3 user authen protocol.";
        leaf key {
          type key-hex-string;
          mandatory true;
          description
            "Localized key specified as a list of colon-specified hexadecimal octets.";
        }
      }
    }
    case sha2-256 {
      description
        "SHA256 authentication algorithm.";
      container sha2-256 {
        description
          "Configure SNMPv3 user authen protocol.";
        leaf key {
          type key-hex-string;
          mandatory true;
          description
            "Localized key specified as a list of colon-specified hexadecimal octets.";
        }
      }
    }
    case sha2-384 {
      description
        "SHA384 authentication algorithm.";
      container sha2-384 {
        description
          "Configure SNMPv3 user authen protocol.";
        leaf key {
          type key-hex-string;
          mandatory true;
          description
            "Localized key specified as a list of colon-specified hexadecimal octets.";
        }
      }
    }
    case sha2-512 {
      description
        "SHA512 authentication algorithm.";
      container sha2-512 {
        description
          "Configure SNMPv3 user authen protocol.";
        leaf key {
          type key-hex-string;
          mandatory true;
          description
            "Localized key specified as a list of colon-specified hexadecimal octets.";
        }
      }
    }
  }
}
