module huawei-mpls-forward-l2vpn {
  // Generated by yanger -t ncs
  tailf:mount-id "huawei-nc-1.0:huawei-nc-1.0";
  tailf:ncs-device-type "netconf";

  yang-version 1;
  namespace "urn:huawei:yang:huawei-mpls-forward-l2vpn";
  prefix mpls-forward-l2vpn;

  import huawei-l2vpn {
    prefix l2vpn;
  }
  import huawei-extension {
    prefix ext;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "MPLS forward for L2VPN.";

  revision 2020-07-29 {
    description
      "Initial revision.";
    reference "Huawei private.";
  }
  ext:task-name "forwarding";

  augment "/ncs:devices/ncs:template/ncs:ned-id/ncs:config/l2vpn:l2vpn/l2vpn:instances/l2vpn:instance/l2vpn:vpls/l2vpn:ipmsi/l2vpn:leaf" {
    description
      "Configure a MPLS P2MP loopback board.";
    container mpls-p2mp-slot {
      description
        "Configure a MPLS P2MP loopback board.";
      leaf slotid {
        type string;
        description
          "Slot ID.";
      }
    }
  }
  augment "/ncs:devices/ncs:device/ncs:live-status/l2vpn:l2vpn/l2vpn:instances/l2vpn:instance/l2vpn:vpls/l2vpn:ipmsi/l2vpn:leaf" {
    description
      "Configure a MPLS P2MP loopback board.";
    container mpls-p2mp-slot {
      tailf:ncs-device-type "netconf";
      tailf:display-when "not(../../../../../../../../ncs:module) or ../../../../../../../../ncs:module[ncs:name='huawei-mpls-forward-l2vpn'] or (../../../../../../../../ncs:live-status-protocol[not(ncs:capability)]) or (../../../../../../../../ncs:live-status-protocol/ncs:capability/ncs:module[.='huawei-mpls-forward-l2vpn'])";
      description
        "Configure a MPLS P2MP loopback board.";
      leaf slotid {
        type string {
          length "1..32";
        }
        description
          "Slot ID.";
      }
    }
  }
  augment "/ncs:devices/ncs:device/ncs:config/l2vpn:l2vpn/l2vpn:instances/l2vpn:instance/l2vpn:vpls/l2vpn:ipmsi/l2vpn:leaf" {
    description
      "Configure a MPLS P2MP loopback board.";
    container mpls-p2mp-slot {
      tailf:ncs-device-type "netconf";
      tailf:display-when "not(../../../../../../../../ncs:module) or ../../../../../../../../ncs:module[ncs:name='huawei-mpls-forward-l2vpn']";
      description
        "Configure a MPLS P2MP loopback board.";
      leaf slotid {
        type string {
          length "1..32";
        }
        description
          "Slot ID.";
      }
    }
  }
}
