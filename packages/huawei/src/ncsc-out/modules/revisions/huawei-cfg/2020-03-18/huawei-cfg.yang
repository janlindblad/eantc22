module huawei-cfg {
  // Generated by yanger -t ncs
  tailf:mount-id "huawei-nc-1.0:huawei-nc-1.0";
  tailf:ncs-device-type "netconf";

  yang-version 1.1;
  namespace "urn:huawei:yang:huawei-cfg";
  prefix cfg;

  import huawei-pub-type {
    prefix pub-type;
  }
  import ietf-inet-types {
    prefix inet;
  }
  import ietf-yang-types {
    prefix yang;
  }
  import huawei-extension {
    prefix ext;
  }
  import huawei-ifm {
    prefix ifm;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Configuration management module.";

  revision 2020-03-18 {
    description
      "Fix units problems.";
    reference "Huawei private.";
  }
  revision 2020-02-21 {
    description
      "Initial revision.";
    reference "Huawei private.";
  }
  ext:task-name "config";

  typedef ncs_template_config-checkpoint-client {
    type string;
    description
      "Client type.";
  }

  typedef ncs_template_cfg-server-type {
    type string;
    description
      "Server type.";
  }

  typedef ncs_template_cfg-operation-type {
    type string;
    description
      "Operation type.";
  }

  typedef ncs_template_cfg-operation-state {
    type string;
    description
      "Operation state.";
  }

  typedef ncs_template_command-result {
    type string;
    description
      "Command result.";
  }

  typedef ncs_template_cfg-hwcm-operation-type {
    type string;
    description
      "HWCM operation type.";
  }

  typedef ncs_template_cfg-service-type {
    type string;
    description
      "File service type.";
  }

  typedef ncs_template_load-config-type {
    type string;
    description
      "Load configuration type.";
  }

  typedef ncs_rpc_notif_config-checkpoint-client {
    type enumeration {
      enum "cli" {
        value 0;
        description
          "The client that creates a configuration checkpoint is CLI.";
      }
      enum "netconf" {
        value 1;
        description
          "The client that generates a configuration checkpoint is NETCONF.";
      }
      enum "snmp" {
        value 2;
        description
          "The client that creates a configuration checkpoint is SNMP.";
      }
      enum "rollback" {
        value 3;
        description
          "The client that generates a configuration checkpoint is rollback. A configuration checkpoint is generated because a rollback command is run.";
      }
      enum "y2" {
        value 4;
        description
          "The client that generates a configuration checkpoint is y2. A configuration checkpoint is generated because the startup configuration of the system is different from the latest configuration checkpoint.";
      }
      enum "restore" {
        value 5;
        description
          "The client that generates a configuration checkpoint is restore. A configuration checkpoint is generated because the startup configuration of the system is different from the latest configuration checkpoint.";
      }
      enum "system" {
        value 6;
        description
          "The client that generates a configuration checkpoint is system. A configuration checkpoint is generated because the current user information cannot be obtained.";
      }
      enum "mml" {
        value 7;
        description
          "The client that generates a configuration checkpoint is mml. A configuration checkpoint is generated because the startup configuration of the system is different from the latest configuration checkpoint.";
      }
      enum "inner" {
        value 8;
        description
          "The client that generates a configuration checkpoint is inner. A configuration checkpoint is generated because the startup configuration of the system is different from the latest configuration checkpoint.";
      }
    }
    description
      "Client type.";
  }

  typedef ncs_rpc_notif_cfg-server-type {
    type enumeration {
      enum "ftp" {
        value 1;
        description
          "FTP protocol.";
      }
      enum "tftp" {
        value 2;
        description
          "TFTP protocol.";
      }
      enum "sftp" {
        value 3;
        description
          "SFTP protocol.";
      }
    }
    description
      "Server type.";
  }

  typedef ncs_rpc_notif_cfg-operation-type {
    type enumeration {
      enum "running2net" {
        value 1;
        description
          "Back up the device configuration to a server.";
      }
      enum "net2startup" {
        value 2;
        description
          "Configure the configuration file on the server as the next startup configuration file.";
      }
    }
    description
      "Operation type.";
  }

  typedef ncs_rpc_notif_cfg-operation-state {
    type enumeration {
      enum "running" {
        value 1;
        description
          "The operation is being processed.";
      }
      enum "success" {
        value 2;
        description
          "The operation is successful.";
      }
      enum "invalid-operation" {
        value 3;
        description
          "Invalid operation.";
      }
      enum "invalid-server-address" {
        value 4;
        description
          "Invalid server IP address.";
      }
      enum "invalid-source-name" {
        value 5;
        description
          "Invalid source file name.";
      }
      enum "invalid-dest-name" {
        value 6;
        description
          "Invalid destination file name.";
      }
      enum "device-busy" {
        value 7;
        description
          "The device is busy.";
      }
      enum "device-full" {
        value 8;
        description
          "The disk space of the device is full.";
      }
      enum "file-open-error" {
        value 9;
        description
          "The file fails to be opened.";
      }
      enum "file-transfer-error" {
        value 10;
        description
          "The file fails to be transferred.";
      }
      enum "auth-fail" {
        value 11;
        description
          "The server authentication fails.";
      }
      enum "timeout" {
        value 12;
        description
          "File transfer timeout.";
      }
      enum "startup-file-locked" {
        value 13;
        description
          "Startup file locked.";
      }
      enum "unknown-failure" {
        value 14;
        description
          "Unknown error.";
      }
    }
    description
      "Operation state.";
  }

  typedef ncs_rpc_notif_command-result {
    type enumeration {
      enum "unknown-command" {
        value 0;
        description
          "The failed reason of a configuration command is unknown command.";
      }
      enum "execute-failed" {
        value 1;
        description
          "The failed reason of a configuration command is executed failed.";
      }
      enum "execute-timeout" {
        value 2;
        description
          "The failed reason of a configuration command is executed timeout.";
      }
    }
    description
      "Command result.";
  }

  typedef ncs_rpc_notif_cfg-hwcm-operation-type {
    type enumeration {
      enum "running2startup" {
        value 1;
        description
          "Save the running configuration to the next startup configuration file.";
      }
      enum "startup2running" {
        value 2;
        description
          "Load the next startup configuration file to the device.";
      }
      enum "running2net" {
        value 3;
        description
          "Back up the device configuration to a server.";
      }
      enum "net2running" {
        value 4;
        description
          "Download the configuration file from the server to the device and run it.";
      }
      enum "net2startup" {
        value 5;
        description
          "Configure the configuration file on the server as the next startup configuration file.";
      }
      enum "startup2net" {
        value 6;
        description
          "Back up the next startup configuration file to a server.";
      }
      enum "delstartup" {
        value 7;
        description
          "Delete the next startup configuration file.";
      }
    }
    description
      "HWCM operation type.";
  }

  typedef ncs_rpc_notif_cfg-service-type {
    type enumeration {
      enum "common" {
        value 0;
        description
          "Common service type.";
      }
      enum "cfg" {
        value 4;
        description
          "CFG service type.";
      }
    }
    description
      "File service type.";
  }

  typedef ncs_rpc_notif_load-config-type {
    type enumeration {
      enum "merge" {
        value 0;
        description
          "Merge contents with existing configuration.";
      }
    }
    description
      "Load configuration type.";
  }

  typedef live_ncs_config-checkpoint-client {
    type enumeration {
      enum "cli" {
        value 0;
        description
          "The client that creates a configuration checkpoint is CLI.";
      }
      enum "netconf" {
        value 1;
        description
          "The client that generates a configuration checkpoint is NETCONF.";
      }
      enum "snmp" {
        value 2;
        description
          "The client that creates a configuration checkpoint is SNMP.";
      }
      enum "rollback" {
        value 3;
        description
          "The client that generates a configuration checkpoint is rollback. A configuration checkpoint is generated because a rollback command is run.";
      }
      enum "y2" {
        value 4;
        description
          "The client that generates a configuration checkpoint is y2. A configuration checkpoint is generated because the startup configuration of the system is different from the latest configuration checkpoint.";
      }
      enum "restore" {
        value 5;
        description
          "The client that generates a configuration checkpoint is restore. A configuration checkpoint is generated because the startup configuration of the system is different from the latest configuration checkpoint.";
      }
      enum "system" {
        value 6;
        description
          "The client that generates a configuration checkpoint is system. A configuration checkpoint is generated because the current user information cannot be obtained.";
      }
      enum "mml" {
        value 7;
        description
          "The client that generates a configuration checkpoint is mml. A configuration checkpoint is generated because the startup configuration of the system is different from the latest configuration checkpoint.";
      }
      enum "inner" {
        value 8;
        description
          "The client that generates a configuration checkpoint is inner. A configuration checkpoint is generated because the startup configuration of the system is different from the latest configuration checkpoint.";
      }
    }
    description
      "Client type.";
  }

  typedef live_ncs_cfg-server-type {
    type enumeration {
      enum "ftp" {
        value 1;
        description
          "FTP protocol.";
      }
      enum "tftp" {
        value 2;
        description
          "TFTP protocol.";
      }
      enum "sftp" {
        value 3;
        description
          "SFTP protocol.";
      }
    }
    description
      "Server type.";
  }

  typedef live_ncs_cfg-operation-type {
    type enumeration {
      enum "running2net" {
        value 1;
        description
          "Back up the device configuration to a server.";
      }
      enum "net2startup" {
        value 2;
        description
          "Configure the configuration file on the server as the next startup configuration file.";
      }
    }
    description
      "Operation type.";
  }

  typedef live_ncs_cfg-operation-state {
    type enumeration {
      enum "running" {
        value 1;
        description
          "The operation is being processed.";
      }
      enum "success" {
        value 2;
        description
          "The operation is successful.";
      }
      enum "invalid-operation" {
        value 3;
        description
          "Invalid operation.";
      }
      enum "invalid-server-address" {
        value 4;
        description
          "Invalid server IP address.";
      }
      enum "invalid-source-name" {
        value 5;
        description
          "Invalid source file name.";
      }
      enum "invalid-dest-name" {
        value 6;
        description
          "Invalid destination file name.";
      }
      enum "device-busy" {
        value 7;
        description
          "The device is busy.";
      }
      enum "device-full" {
        value 8;
        description
          "The disk space of the device is full.";
      }
      enum "file-open-error" {
        value 9;
        description
          "The file fails to be opened.";
      }
      enum "file-transfer-error" {
        value 10;
        description
          "The file fails to be transferred.";
      }
      enum "auth-fail" {
        value 11;
        description
          "The server authentication fails.";
      }
      enum "timeout" {
        value 12;
        description
          "File transfer timeout.";
      }
      enum "startup-file-locked" {
        value 13;
        description
          "Startup file locked.";
      }
      enum "unknown-failure" {
        value 14;
        description
          "Unknown error.";
      }
    }
    description
      "Operation state.";
  }

  typedef live_ncs_command-result {
    type enumeration {
      enum "unknown-command" {
        value 0;
        description
          "The failed reason of a configuration command is unknown command.";
      }
      enum "execute-failed" {
        value 1;
        description
          "The failed reason of a configuration command is executed failed.";
      }
      enum "execute-timeout" {
        value 2;
        description
          "The failed reason of a configuration command is executed timeout.";
      }
    }
    description
      "Command result.";
  }

  typedef live_ncs_cfg-hwcm-operation-type {
    type enumeration {
      enum "running2startup" {
        value 1;
        description
          "Save the running configuration to the next startup configuration file.";
      }
      enum "startup2running" {
        value 2;
        description
          "Load the next startup configuration file to the device.";
      }
      enum "running2net" {
        value 3;
        description
          "Back up the device configuration to a server.";
      }
      enum "net2running" {
        value 4;
        description
          "Download the configuration file from the server to the device and run it.";
      }
      enum "net2startup" {
        value 5;
        description
          "Configure the configuration file on the server as the next startup configuration file.";
      }
      enum "startup2net" {
        value 6;
        description
          "Back up the next startup configuration file to a server.";
      }
      enum "delstartup" {
        value 7;
        description
          "Delete the next startup configuration file.";
      }
    }
    description
      "HWCM operation type.";
  }

  typedef live_ncs_cfg-service-type {
    type enumeration {
      enum "common" {
        value 0;
        description
          "Common service type.";
      }
      enum "cfg" {
        value 4;
        description
          "CFG service type.";
      }
    }
    description
      "File service type.";
  }

  typedef live_ncs_load-config-type {
    type enumeration {
      enum "merge" {
        value 0;
        description
          "Merge contents with existing configuration.";
      }
    }
    description
      "Load configuration type.";
  }

  typedef config-checkpoint-client {
    type enumeration {
      enum "cli" {
        value 0;
        description
          "The client that creates a configuration checkpoint is CLI.";
      }
      enum "netconf" {
        value 1;
        description
          "The client that generates a configuration checkpoint is NETCONF.";
      }
      enum "snmp" {
        value 2;
        description
          "The client that creates a configuration checkpoint is SNMP.";
      }
      enum "rollback" {
        value 3;
        description
          "The client that generates a configuration checkpoint is rollback. A configuration checkpoint is generated because a rollback command is run.";
      }
      enum "y2" {
        value 4;
        description
          "The client that generates a configuration checkpoint is y2. A configuration checkpoint is generated because the startup configuration of the system is different from the latest configuration checkpoint.";
      }
      enum "restore" {
        value 5;
        description
          "The client that generates a configuration checkpoint is restore. A configuration checkpoint is generated because the startup configuration of the system is different from the latest configuration checkpoint.";
      }
      enum "system" {
        value 6;
        description
          "The client that generates a configuration checkpoint is system. A configuration checkpoint is generated because the current user information cannot be obtained.";
      }
      enum "mml" {
        value 7;
        description
          "The client that generates a configuration checkpoint is mml. A configuration checkpoint is generated because the startup configuration of the system is different from the latest configuration checkpoint.";
      }
      enum "inner" {
        value 8;
        description
          "The client that generates a configuration checkpoint is inner. A configuration checkpoint is generated because the startup configuration of the system is different from the latest configuration checkpoint.";
      }
    }
    description
      "Client type.";
  }

  typedef cfg-server-type {
    type enumeration {
      enum "ftp" {
        value 1;
        description
          "FTP protocol.";
      }
      enum "tftp" {
        value 2;
        description
          "TFTP protocol.";
      }
      enum "sftp" {
        value 3;
        description
          "SFTP protocol.";
      }
    }
    description
      "Server type.";
  }

  typedef cfg-operation-type {
    type enumeration {
      enum "running2net" {
        value 1;
        description
          "Back up the device configuration to a server.";
      }
      enum "net2startup" {
        value 2;
        description
          "Configure the configuration file on the server as the next startup configuration file.";
      }
    }
    description
      "Operation type.";
  }

  typedef cfg-operation-state {
    type enumeration {
      enum "running" {
        value 1;
        description
          "The operation is being processed.";
      }
      enum "success" {
        value 2;
        description
          "The operation is successful.";
      }
      enum "invalid-operation" {
        value 3;
        description
          "Invalid operation.";
      }
      enum "invalid-server-address" {
        value 4;
        description
          "Invalid server IP address.";
      }
      enum "invalid-source-name" {
        value 5;
        description
          "Invalid source file name.";
      }
      enum "invalid-dest-name" {
        value 6;
        description
          "Invalid destination file name.";
      }
      enum "device-busy" {
        value 7;
        description
          "The device is busy.";
      }
      enum "device-full" {
        value 8;
        description
          "The disk space of the device is full.";
      }
      enum "file-open-error" {
        value 9;
        description
          "The file fails to be opened.";
      }
      enum "file-transfer-error" {
        value 10;
        description
          "The file fails to be transferred.";
      }
      enum "auth-fail" {
        value 11;
        description
          "The server authentication fails.";
      }
      enum "timeout" {
        value 12;
        description
          "File transfer timeout.";
      }
      enum "startup-file-locked" {
        value 13;
        description
          "Startup file locked.";
      }
      enum "unknown-failure" {
        value 14;
        description
          "Unknown error.";
      }
    }
    description
      "Operation state.";
  }

  typedef command-result {
    type enumeration {
      enum "unknown-command" {
        value 0;
        description
          "The failed reason of a configuration command is unknown command.";
      }
      enum "execute-failed" {
        value 1;
        description
          "The failed reason of a configuration command is executed failed.";
      }
      enum "execute-timeout" {
        value 2;
        description
          "The failed reason of a configuration command is executed timeout.";
      }
    }
    description
      "Command result.";
  }

  typedef cfg-hwcm-operation-type {
    type enumeration {
      enum "running2startup" {
        value 1;
        description
          "Save the running configuration to the next startup configuration file.";
      }
      enum "startup2running" {
        value 2;
        description
          "Load the next startup configuration file to the device.";
      }
      enum "running2net" {
        value 3;
        description
          "Back up the device configuration to a server.";
      }
      enum "net2running" {
        value 4;
        description
          "Download the configuration file from the server to the device and run it.";
      }
      enum "net2startup" {
        value 5;
        description
          "Configure the configuration file on the server as the next startup configuration file.";
      }
      enum "startup2net" {
        value 6;
        description
          "Back up the next startup configuration file to a server.";
      }
      enum "delstartup" {
        value 7;
        description
          "Delete the next startup configuration file.";
      }
    }
    description
      "HWCM operation type.";
  }

  typedef cfg-service-type {
    type enumeration {
      enum "common" {
        value 0;
        description
          "Common service type.";
      }
      enum "cfg" {
        value 4;
        description
          "CFG service type.";
      }
    }
    description
      "File service type.";
  }

  typedef load-config-type {
    type enumeration {
      enum "merge" {
        value 0;
        description
          "Merge contents with existing configuration.";
      }
    }
    description
      "Load configuration type.";
  }

  augment "/ncs:devices/ncs:device/ncs:rpc" {
    container rpc-load-configuration-to-candidate-result {
      tailf:ncs-device-type "netconf";
      tailf:display-when "not(../../ncs:module) or ../../ncs:module[ncs:name='huawei-cfg']";
      tailf:action load-configuration-to-candidate-result {
        tailf:actionpoint ncsproxy {
          tailf:internal;
        }
        description
          "Operational state of loading configuration result.";
        output {
          anydata result {
            description
              "The result of loading configuration.";
          }
        }
      }
    }
  }
  augment "/ncs:devices/ncs:device-group/ncs:ned-id/ncs:rpc" {
    container rpc-load-configuration-to-candidate-result {
      tailf:ncs-device-type "netconf";
      tailf:display-when "/ncs:devices/ncs:device[ncs:name=current()/../../../ncs:member]/ncs:module[ncs:name='huawei-cfg']";
      tailf:action load-configuration-to-candidate-result {
        tailf:actionpoint ncsproxy {
          tailf:internal;
        }
        description
          "Operational state of loading configuration result.";
        output {
          container "device" {
            leaf "name" {
              type string;
            }
            leaf "info" {
              type string;
            }
            container "result" {
              anydata result {
                description
                  "The result of loading configuration.";
              }
            }
          }
        }
      }
    }
  }
  augment "/ncs:devices/ncs:device/ncs:rpc" {
    container rpc-load-configuration-to-candidate {
      tailf:ncs-device-type "netconf";
      tailf:display-when "not(../../ncs:module) or ../../ncs:module[ncs:name='huawei-cfg']";
      tailf:action load-configuration-to-candidate {
        tailf:actionpoint ncsproxy {
          tailf:internal;
        }
        description
          "Load local configuration file or the configuration file on a remote server and delivers configurations to the local device.";
        input {
          leaf config-type {
            type ncs_rpc_notif_load-config-type;
            description
              "Type of loading configuration.";
          }
          choice server-type {
            description
              "Type of the protocol for loading the file.";
            case local {
              description
                "Local system.";
              leaf local-filename {
                type string {
                  length "1..128";
                }
                description
                  "Configuration file name of the local system.";
              }
            }
            case ftp {
              description
                "FTP protocol.";
              leaf ftp-server-ip {
                type inet:ip-address-no-zone;
                description
                  "IP address of the remote FTP server.";
              }
              leaf ftp-username {
                type string {
                  length "1..64";
                }
                description
                  "User name for logging in to the remote FTP server.";
              }
              leaf ftp-password {
                type pub-type:ncs_rpc_notif_password-extend;
                description
                  "Password for logging in to the remote FTP server.";
              }
              leaf ftp-vpn-instance {
                type string {
                  length "1..31";
                }
                description
                  "VPN instance name of the remote FTP server.";
              }
              leaf ftp-filename {
                type string {
                  length "1..128";
                }
                description
                  "Configuration file name of the remote FTP server.";
              }
            }
            case sftp {
              description
                "SFTP protocol.";
              leaf sftp-server-ip {
                type inet:ip-address-no-zone;
                description
                  "IP address of the remote SFTP server.";
              }
              leaf sftp-username {
                type string {
                  length "1..64";
                }
                description
                  "User name for logging in to the remote SFTP server.";
              }
              leaf sftp-password {
                type pub-type:ncs_rpc_notif_password-extend;
                description
                  "Password for logging in to the remote SFTP server.";
              }
              leaf sftp-vpn-instance {
                type string {
                  length "1..31";
                }
                description
                  "VPN instance name of the remote SFTP server.";
              }
              leaf sftp-filename {
                type string {
                  length "1..128";
                }
                description
                  "Configuration file name of the remote SFTP server.";
              }
            }
            case http {
              description
                "HTTP protocol.";
              leaf http-url {
                type string {
                  length "1..255";
                }
                description
                  "The URL of the remote HTTP server.";
              }
              leaf http-vpn-instance {
                type string {
                  length "1..31";
                }
                description
                  "VPN instance name of the remote HTTP server.";
              }
            }
          }
        }
      }
    }
  }
  augment "/ncs:devices/ncs:device-group/ncs:ned-id/ncs:rpc" {
    container rpc-load-configuration-to-candidate {
      tailf:ncs-device-type "netconf";
      tailf:display-when "/ncs:devices/ncs:device[ncs:name=current()/../../../ncs:member]/ncs:module[ncs:name='huawei-cfg']";
      tailf:action load-configuration-to-candidate {
        tailf:actionpoint ncsproxy {
          tailf:internal;
        }
        description
          "Load local configuration file or the configuration file on a remote server and delivers configurations to the local device.";
        input {
          leaf config-type {
            type ncs_rpc_notif_load-config-type;
            description
              "Type of loading configuration.";
          }
          choice server-type {
            description
              "Type of the protocol for loading the file.";
            case local {
              description
                "Local system.";
              leaf local-filename {
                type string {
                  length "1..128";
                }
                description
                  "Configuration file name of the local system.";
              }
            }
            case ftp {
              description
                "FTP protocol.";
              leaf ftp-server-ip {
                type inet:ip-address-no-zone;
                description
                  "IP address of the remote FTP server.";
              }
              leaf ftp-username {
                type string {
                  length "1..64";
                }
                description
                  "User name for logging in to the remote FTP server.";
              }
              leaf ftp-password {
                type pub-type:ncs_rpc_notif_password-extend;
                description
                  "Password for logging in to the remote FTP server.";
              }
              leaf ftp-vpn-instance {
                type string {
                  length "1..31";
                }
                description
                  "VPN instance name of the remote FTP server.";
              }
              leaf ftp-filename {
                type string {
                  length "1..128";
                }
                description
                  "Configuration file name of the remote FTP server.";
              }
            }
            case sftp {
              description
                "SFTP protocol.";
              leaf sftp-server-ip {
                type inet:ip-address-no-zone;
                description
                  "IP address of the remote SFTP server.";
              }
              leaf sftp-username {
                type string {
                  length "1..64";
                }
                description
                  "User name for logging in to the remote SFTP server.";
              }
              leaf sftp-password {
                type pub-type:ncs_rpc_notif_password-extend;
                description
                  "Password for logging in to the remote SFTP server.";
              }
              leaf sftp-vpn-instance {
                type string {
                  length "1..31";
                }
                description
                  "VPN instance name of the remote SFTP server.";
              }
              leaf sftp-filename {
                type string {
                  length "1..128";
                }
                description
                  "Configuration file name of the remote SFTP server.";
              }
            }
            case http {
              description
                "HTTP protocol.";
              leaf http-url {
                type string {
                  length "1..255";
                }
                description
                  "The URL of the remote HTTP server.";
              }
              leaf http-vpn-instance {
                type string {
                  length "1..31";
                }
                description
                  "VPN instance name of the remote HTTP server.";
              }
            }
          }
        }
      }
    }
  }
  augment "/ncs:devices/ncs:device/ncs:rpc" {
    container rpc-delete-user-label-checkpoint {
      tailf:ncs-device-type "netconf";
      tailf:display-when "not(../../ncs:module) or ../../ncs:module[ncs:name='huawei-cfg']";
      tailf:action delete-user-label-checkpoint {
        tailf:actionpoint ncsproxy {
          tailf:internal;
        }
        description
          "Delete the checkpoint of a specified label.";
        ext:node-ref "/cfg/checkpoints/checkpoint";
        input {
          leaf commit-id {
            type string;
            description
              "ID of a configuration checkpoint.";
          }
        }
      }
    }
  }
  augment "/ncs:devices/ncs:device-group/ncs:ned-id/ncs:rpc" {
    container rpc-delete-user-label-checkpoint {
      tailf:ncs-device-type "netconf";
      tailf:display-when "/ncs:devices/ncs:device[ncs:name=current()/../../../ncs:member]/ncs:module[ncs:name='huawei-cfg']";
      tailf:action delete-user-label-checkpoint {
        tailf:actionpoint ncsproxy {
          tailf:internal;
        }
        description
          "Delete the checkpoint of a specified label.";
        ext:node-ref "/cfg/checkpoints/checkpoint";
        input {
          leaf commit-id {
            type string;
            description
              "ID of a configuration checkpoint.";
          }
        }
      }
    }
  }
  augment "/ncs:devices/ncs:device/ncs:rpc" {
    container rpc-create-user-label-checkpoint {
      tailf:ncs-device-type "netconf";
      tailf:display-when "not(../../ncs:module) or ../../ncs:module[ncs:name='huawei-cfg']";
      tailf:action create-user-label-checkpoint {
        tailf:actionpoint ncsproxy {
          tailf:internal;
        }
        description
          "Create the checkpoint of a specified label.";
        ext:node-ref "/cfg/checkpoints/checkpoint";
        input {
          leaf user-label {
            type string {
              length "1..256";
              pattern '.*[^\s]+.*';
            }
            mandatory true;
            description
              "Label of a configuration checkpoint.";
          }
          leaf description {
            type string {
              length "1..60";
            }
            description
              "Description of a configuration checkpoint.";
          }
        }
      }
    }
  }
  augment "/ncs:devices/ncs:device-group/ncs:ned-id/ncs:rpc" {
    container rpc-create-user-label-checkpoint {
      tailf:ncs-device-type "netconf";
      tailf:display-when "/ncs:devices/ncs:device[ncs:name=current()/../../../ncs:member]/ncs:module[ncs:name='huawei-cfg']";
      tailf:action create-user-label-checkpoint {
        tailf:actionpoint ncsproxy {
          tailf:internal;
        }
        description
          "Create the checkpoint of a specified label.";
        ext:node-ref "/cfg/checkpoints/checkpoint";
        input {
          leaf user-label {
            type string {
              length "1..256";
              pattern '.*[^\s]+.*';
            }
            mandatory true;
            description
              "Label of a configuration checkpoint.";
          }
          leaf description {
            type string {
              length "1..60";
            }
            description
              "Description of a configuration checkpoint.";
          }
        }
      }
    }
  }
  augment "/ncs:devices/ncs:device/ncs:rpc" {
    container rpc-set-user-label-by-commit-id {
      tailf:ncs-device-type "netconf";
      tailf:display-when "not(../../ncs:module) or ../../ncs:module[ncs:name='huawei-cfg']";
      tailf:action set-user-label-by-commit-id {
        tailf:actionpoint ncsproxy {
          tailf:internal;
        }
        description
          "Set the user label of a specified configuration checkpoint.";
        ext:node-ref "/cfg/checkpoints/checkpoint";
        input {
          leaf commit-id {
            type string;
            mandatory true;
            description
              "ID of a configuration checkpoint.";
          }
          leaf user-label {
            type string {
              length "1..256";
              pattern '.*[^\s]+.*';
            }
            mandatory true;
            description
              "Label of a configuration checkpoint.";
          }
        }
      }
    }
  }
  augment "/ncs:devices/ncs:device-group/ncs:ned-id/ncs:rpc" {
    container rpc-set-user-label-by-commit-id {
      tailf:ncs-device-type "netconf";
      tailf:display-when "/ncs:devices/ncs:device[ncs:name=current()/../../../ncs:member]/ncs:module[ncs:name='huawei-cfg']";
      tailf:action set-user-label-by-commit-id {
        tailf:actionpoint ncsproxy {
          tailf:internal;
        }
        description
          "Set the user label of a specified configuration checkpoint.";
        ext:node-ref "/cfg/checkpoints/checkpoint";
        input {
          leaf commit-id {
            type string;
            mandatory true;
            description
              "ID of a configuration checkpoint.";
          }
          leaf user-label {
            type string {
              length "1..256";
              pattern '.*[^\s]+.*';
            }
            mandatory true;
            description
              "Label of a configuration checkpoint.";
          }
        }
      }
    }
  }
  augment "/ncs:devices/ncs:device/ncs:rpc" {
    container rpc-set-startup {
      tailf:ncs-device-type "netconf";
      tailf:display-when "not(../../ncs:module) or ../../ncs:module[ncs:name='huawei-cfg']";
      tailf:action set-startup {
        tailf:actionpoint ncsproxy {
          tailf:internal;
        }
        description
          "Configure an existing configuration file as the startup file.";
        ext:node-ref "/cfg/cfg-files/cfg-file";
        input {
          leaf filename {
            type string;
            mandatory true;
            description
              "Name of a configuration file.";
          }
        }
      }
    }
  }
  augment "/ncs:devices/ncs:device-group/ncs:ned-id/ncs:rpc" {
    container rpc-set-startup {
      tailf:ncs-device-type "netconf";
      tailf:display-when "/ncs:devices/ncs:device[ncs:name=current()/../../../ncs:member]/ncs:module[ncs:name='huawei-cfg']";
      tailf:action set-startup {
        tailf:actionpoint ncsproxy {
          tailf:internal;
        }
        description
          "Configure an existing configuration file as the startup file.";
        ext:node-ref "/cfg/cfg-files/cfg-file";
        input {
          leaf filename {
            type string;
            mandatory true;
            description
              "Name of a configuration file.";
          }
        }
      }
    }
  }
  augment "/ncs:devices/ncs:device/ncs:rpc" {
    container rpc-save-all-virtual-systems {
      tailf:ncs-device-type "netconf";
      tailf:display-when "not(../../ncs:module) or ../../ncs:module[ncs:name='huawei-cfg']";
      tailf:action save-all-virtual-systems {
        tailf:actionpoint ncsproxy {
          tailf:internal;
        }
        description
          "Saving all virtual-systems to the next startup file.";
      }
    }
  }
  augment "/ncs:devices/ncs:device-group/ncs:ned-id/ncs:rpc" {
    container rpc-save-all-virtual-systems {
      tailf:ncs-device-type "netconf";
      tailf:display-when "/ncs:devices/ncs:device[ncs:name=current()/../../../ncs:member]/ncs:module[ncs:name='huawei-cfg']";
      tailf:action save-all-virtual-systems {
        tailf:actionpoint ncsproxy {
          tailf:internal;
        }
        description
          "Saving all virtual-systems to the next startup file.";
      }
    }
  }
  augment "/ncs:devices/ncs:device/ncs:rpc" {
    container rpc-rollback-by-file {
      tailf:ncs-device-type "netconf";
      tailf:display-when "not(../../ncs:module) or ../../ncs:module[ncs:name='huawei-cfg']";
      tailf:action rollback-by-file {
        tailf:actionpoint ncsproxy {
          tailf:internal;
        }
        description
          "Rollback the configuration with a specified configuration file.";
        ext:node-ref "/cfg/cfg-files/cfg-file";
        input {
          leaf filename {
            type string;
            mandatory true;
            description
              "Name of a configuration file.";
          }
        }
      }
    }
  }
  augment "/ncs:devices/ncs:device-group/ncs:ned-id/ncs:rpc" {
    container rpc-rollback-by-file {
      tailf:ncs-device-type "netconf";
      tailf:display-when "/ncs:devices/ncs:device[ncs:name=current()/../../../ncs:member]/ncs:module[ncs:name='huawei-cfg']";
      tailf:action rollback-by-file {
        tailf:actionpoint ncsproxy {
          tailf:internal;
        }
        description
          "Rollback the configuration with a specified configuration file.";
        ext:node-ref "/cfg/cfg-files/cfg-file";
        input {
          leaf filename {
            type string;
            mandatory true;
            description
              "Name of a configuration file.";
          }
        }
      }
    }
  }
  augment "/ncs:devices/ncs:device/ncs:rpc" {
    container rpc-rollback-by-last-num {
      tailf:ncs-device-type "netconf";
      tailf:display-when "not(../../ncs:module) or ../../ncs:module[ncs:name='huawei-cfg']";
      tailf:action rollback-by-last-num {
        tailf:actionpoint ncsproxy {
          tailf:internal;
        }
        description
          "Rollback the configurations of several checkpoints.";
        ext:node-ref "/cfg/checkpoints/checkpoint";
        input {
          leaf checkpoint-num {
            type uint8 {
              range "1..80";
            }
            description
              "Number of configuration checkpoints that are rolled back.";
          }
        }
      }
    }
  }
  augment "/ncs:devices/ncs:device-group/ncs:ned-id/ncs:rpc" {
    container rpc-rollback-by-last-num {
      tailf:ncs-device-type "netconf";
      tailf:display-when "/ncs:devices/ncs:device[ncs:name=current()/../../../ncs:member]/ncs:module[ncs:name='huawei-cfg']";
      tailf:action rollback-by-last-num {
        tailf:actionpoint ncsproxy {
          tailf:internal;
        }
        description
          "Rollback the configurations of several checkpoints.";
        ext:node-ref "/cfg/checkpoints/checkpoint";
        input {
          leaf checkpoint-num {
            type uint8 {
              range "1..80";
            }
            description
              "Number of configuration checkpoints that are rolled back.";
          }
        }
      }
    }
  }
  augment "/ncs:devices/ncs:device/ncs:rpc" {
    container rpc-rollback-by-user-label {
      tailf:ncs-device-type "netconf";
      tailf:display-when "not(../../ncs:module) or ../../ncs:module[ncs:name='huawei-cfg']";
      tailf:action rollback-by-user-label {
        tailf:actionpoint ncsproxy {
          tailf:internal;
        }
        description
          "Rollback the system configuration to a specified checkpoint by user label.";
        ext:node-ref "/cfg/checkpoints/checkpoint";
        input {
          leaf commit-id {
            type string;
            description
              "ID of a configuration checkpoint.";
          }
          leaf user-label {
            type string;
            description
              "Label of a configuration checkpoint.";
          }
        }
      }
    }
  }
  augment "/ncs:devices/ncs:device-group/ncs:ned-id/ncs:rpc" {
    container rpc-rollback-by-user-label {
      tailf:ncs-device-type "netconf";
      tailf:display-when "/ncs:devices/ncs:device[ncs:name=current()/../../../ncs:member]/ncs:module[ncs:name='huawei-cfg']";
      tailf:action rollback-by-user-label {
        tailf:actionpoint ncsproxy {
          tailf:internal;
        }
        description
          "Rollback the system configuration to a specified checkpoint by user label.";
        ext:node-ref "/cfg/checkpoints/checkpoint";
        input {
          leaf commit-id {
            type string;
            description
              "ID of a configuration checkpoint.";
          }
          leaf user-label {
            type string;
            description
              "Label of a configuration checkpoint.";
          }
        }
      }
    }
  }
  augment "/ncs:devices/ncs:device/ncs:rpc" {
    container rpc-rollback-by-commit-id {
      tailf:ncs-device-type "netconf";
      tailf:display-when "not(../../ncs:module) or ../../ncs:module[ncs:name='huawei-cfg']";
      tailf:action rollback-by-commit-id {
        tailf:actionpoint ncsproxy {
          tailf:internal;
        }
        description
          "Rollback the system configuration to a specified checkpoint.";
        ext:node-ref "/cfg/checkpoints/checkpoint";
        input {
          leaf commit-id {
            type string;
            description
              "ID of a configuration checkpoint.";
          }
        }
      }
    }
  }
  augment "/ncs:devices/ncs:device-group/ncs:ned-id/ncs:rpc" {
    container rpc-rollback-by-commit-id {
      tailf:ncs-device-type "netconf";
      tailf:display-when "/ncs:devices/ncs:device[ncs:name=current()/../../../ncs:member]/ncs:module[ncs:name='huawei-cfg']";
      tailf:action rollback-by-commit-id {
        tailf:actionpoint ncsproxy {
          tailf:internal;
        }
        description
          "Rollback the system configuration to a specified checkpoint.";
        ext:node-ref "/cfg/checkpoints/checkpoint";
        input {
          leaf commit-id {
            type string;
            description
              "ID of a configuration checkpoint.";
          }
        }
      }
    }
  }
  augment "/ncs:devices/ncs:device/ncs:rpc" {
    container rpc-delete-checkpoint-by-oldest-num {
      tailf:ncs-device-type "netconf";
      tailf:display-when "not(../../ncs:module) or ../../ncs:module[ncs:name='huawei-cfg']";
      tailf:action delete-checkpoint-by-oldest-num {
        tailf:actionpoint ncsproxy {
          tailf:internal;
        }
        description
          "Delete the oldest checkpoints.";
        ext:node-ref "/cfg/checkpoints/checkpoint";
        input {
          leaf checkpoint-num {
            type uint8 {
              range "1..80";
            }
            description
              "Number of configuration checkpoints that are deleted.";
          }
        }
      }
    }
  }
  augment "/ncs:devices/ncs:device-group/ncs:ned-id/ncs:rpc" {
    container rpc-delete-checkpoint-by-oldest-num {
      tailf:ncs-device-type "netconf";
      tailf:display-when "/ncs:devices/ncs:device[ncs:name=current()/../../../ncs:member]/ncs:module[ncs:name='huawei-cfg']";
      tailf:action delete-checkpoint-by-oldest-num {
        tailf:actionpoint ncsproxy {
          tailf:internal;
        }
        description
          "Delete the oldest checkpoints.";
        ext:node-ref "/cfg/checkpoints/checkpoint";
        input {
          leaf checkpoint-num {
            type uint8 {
              range "1..80";
            }
            description
              "Number of configuration checkpoints that are deleted.";
          }
        }
      }
    }
  }
  augment "/ncs:devices/ncs:device/ncs:rpc" {
    container rpc-clear-interface-config {
      tailf:ncs-device-type "netconf";
      tailf:display-when "not(../../ncs:module) or ../../ncs:module[ncs:name='huawei-cfg']";
      tailf:action clear-interface-config {
        tailf:actionpoint ncsproxy {
          tailf:internal;
        }
        description
          "Clear configurations on the interface.";
        input {
          leaf interface-name {
            type string;
            mandatory true;
            description
              "Interface name.";
          }
        }
      }
    }
  }
  augment "/ncs:devices/ncs:device-group/ncs:ned-id/ncs:rpc" {
    container rpc-clear-interface-config {
      tailf:ncs-device-type "netconf";
      tailf:display-when "/ncs:devices/ncs:device[ncs:name=current()/../../../ncs:member]/ncs:module[ncs:name='huawei-cfg']";
      tailf:action clear-interface-config {
        tailf:actionpoint ncsproxy {
          tailf:internal;
        }
        description
          "Clear configurations on the interface.";
        input {
          leaf interface-name {
            type string;
            mandatory true;
            description
              "Interface name.";
          }
        }
      }
    }
  }
  augment "/ncs:devices/ncs:device/ncs:rpc" {
    container rpc-clear-startup {
      tailf:ncs-device-type "netconf";
      tailf:display-when "not(../../ncs:module) or ../../ncs:module[ncs:name='huawei-cfg']";
      tailf:action clear-startup {
        tailf:actionpoint ncsproxy {
          tailf:internal;
        }
        description
          "Cancel the startup file settings. The current and next startup file settings will be empty.";
        ext:node-ref "/cfg/cfg-files/cfg-file";
      }
    }
  }
  augment "/ncs:devices/ncs:device-group/ncs:ned-id/ncs:rpc" {
    container rpc-clear-startup {
      tailf:ncs-device-type "netconf";
      tailf:display-when "/ncs:devices/ncs:device[ncs:name=current()/../../../ncs:member]/ncs:module[ncs:name='huawei-cfg']";
      tailf:action clear-startup {
        tailf:actionpoint ncsproxy {
          tailf:internal;
        }
        description
          "Cancel the startup file settings. The current and next startup file settings will be empty.";
        ext:node-ref "/cfg/cfg-files/cfg-file";
      }
    }
  }
  augment "/ncs:devices/ncs:device/ncs:rpc" {
    container rpc-cfg-file-backup-and-recovery {
      tailf:ncs-device-type "netconf";
      tailf:display-when "not(../../ncs:module) or ../../ncs:module[ncs:name='huawei-cfg']";
      tailf:action cfg-file-backup-and-recovery {
        tailf:actionpoint ncsproxy {
          tailf:internal;
        }
        description
          "Back up the device configuration to a server or restore the configuration from a server to the next startup configuration file of the device.";
        input {
          leaf index {
            type uint32 {
              range "1..2147483647";
            }
            mandatory true;
            description
              "Operation ID.";
          }
          leaf operation-type {
            type ncs_rpc_notif_cfg-operation-type;
            mandatory true;
            description
              "Back up the running configuration of the device to a specified server or restore the configuration from a specified server to the next startup file of the device.";
          }
          leaf filename {
            type string {
              length "5..128";
            }
            description
              "Name of a configuration file.";
          }
          leaf transport-type {
            type ncs_rpc_notif_cfg-server-type;
            mandatory true;
            description
              "Type of the protocol for transporting the backup file.";
          }
          leaf server-ip {
            type inet:ip-address-no-zone;
            mandatory true;
            description
              "Server IP address for backing up the configuration file.";
          }
          leaf username {
            when "not(../transport-type='tftp')" {
              tailf:xpath-root 3;
            }
            type string {
              length "1..85";
            }
            description
              "User name for connecting a server, for example, an FTP server.";
          }
          leaf password {
            when "not(../transport-type='tftp')" {
              tailf:xpath-root 3;
            }
            type pub-type:ncs_rpc_notif_password;
            description
              "Password for connecting a server, for example, an FTP server.";
          }
          leaf vpn-instance {
            type string {
              length "1..31";
            }
            description
              "Name of a VPN instance.";
          }
          leaf use-net-manager-vpn {
            type boolean;
            default "false";
            description
              "Whether a global VPN is used.";
          }
        }
      }
    }
  }
  augment "/ncs:devices/ncs:device-group/ncs:ned-id/ncs:rpc" {
    container rpc-cfg-file-backup-and-recovery {
      tailf:ncs-device-type "netconf";
      tailf:display-when "/ncs:devices/ncs:device[ncs:name=current()/../../../ncs:member]/ncs:module[ncs:name='huawei-cfg']";
      tailf:action cfg-file-backup-and-recovery {
        tailf:actionpoint ncsproxy {
          tailf:internal;
        }
        description
          "Back up the device configuration to a server or restore the configuration from a server to the next startup configuration file of the device.";
        input {
          leaf index {
            type uint32 {
              range "1..2147483647";
            }
            mandatory true;
            description
              "Operation ID.";
          }
          leaf operation-type {
            type ncs_rpc_notif_cfg-operation-type;
            mandatory true;
            description
              "Back up the running configuration of the device to a specified server or restore the configuration from a specified server to the next startup file of the device.";
          }
          leaf filename {
            type string {
              length "5..128";
            }
            description
              "Name of a configuration file.";
          }
          leaf transport-type {
            type ncs_rpc_notif_cfg-server-type;
            mandatory true;
            description
              "Type of the protocol for transporting the backup file.";
          }
          leaf server-ip {
            type inet:ip-address-no-zone;
            mandatory true;
            description
              "Server IP address for backing up the configuration file.";
          }
          leaf username {
            when "not(../transport-type='tftp')" {
              tailf:xpath-root 4;
            }
            type string {
              length "1..85";
            }
            description
              "User name for connecting a server, for example, an FTP server.";
          }
          leaf password {
            when "not(../transport-type='tftp')" {
              tailf:xpath-root 4;
            }
            type pub-type:ncs_rpc_notif_password;
            description
              "Password for connecting a server, for example, an FTP server.";
          }
          leaf vpn-instance {
            type string {
              length "1..31";
            }
            description
              "Name of a VPN instance.";
          }
          leaf use-net-manager-vpn {
            type boolean;
            default "false";
            description
              "Whether a global VPN is used.";
          }
        }
      }
    }
  }
  augment "/ncs:devices/ncs:device/ncs:rpc" {
    container rpc-save {
      tailf:ncs-device-type "netconf";
      tailf:display-when "not(../../ncs:module) or ../../ncs:module[ncs:name='huawei-cfg']";
      tailf:action save {
        tailf:actionpoint ncsproxy {
          tailf:internal;
        }
        description
          "Save the current configuration to file.";
        input {
          leaf filename {
            type string {
              length "5..64";
            }
            mandatory true;
            description
              "Name of a configuration file.";
          }
        }
      }
    }
  }
  augment "/ncs:devices/ncs:device-group/ncs:ned-id/ncs:rpc" {
    container rpc-save {
      tailf:ncs-device-type "netconf";
      tailf:display-when "/ncs:devices/ncs:device[ncs:name=current()/../../../ncs:member]/ncs:module[ncs:name='huawei-cfg']";
      tailf:action save {
        tailf:actionpoint ncsproxy {
          tailf:internal;
        }
        description
          "Save the current configuration to file.";
        input {
          leaf filename {
            type string {
              length "5..64";
            }
            mandatory true;
            description
              "Name of a configuration file.";
          }
        }
      }
    }
  }
  augment "/ncs:devices/ncs:device/ncs:config" {
    container cfg {
      tailf:ncs-device-type "netconf";
      tailf:display-when "not(../../ncs:module) or ../../ncs:module[ncs:name='huawei-cfg']";
      description
        "Configuration management module.";
      container autosave {
        presence "Enable autosave";
        description
          "Configure used for automatically saving configurations.";
        leaf interval-time {
          type uint32 {
            range "30..43200";
          }
          units "min";
          must '../interval-time > ../delay-time' {
            tailf:xpath-root 3;
            error-app-tag "The interval time must be more than the delay time.";
          }
          default "30";
          description
            "The system automatically saves configurations every a specified interval.";
        }
        leaf delay-time {
          type uint32 {
            range "1..60";
          }
          units "min";
          must '../interval-time > ../delay-time' {
            tailf:xpath-root 3;
            error-app-tag "The interval time must be more than the delay time.";
          }
          default "5";
          description
            "When the system configuration changes, the system automatically saves the configuration after a specified delay.";
        }
        leaf cpu-limit {
          type uint32 {
            range "1..100";
          }
          default "50";
          description
            "Upper limit of the CPU usage for automatically saving configurations.";
        }
      }
      container lock-by-users {
        description
          "List of lock configuration.";
        list lock-by-user {
          key "lock-username";
          max-elements 1;
          description
            "Configure lock configuration.";
          leaf lock-username {
            type string {
              length "1..253";
            }
            description
              "Name of a user who locks the configuration.";
          }
          // NCS drop config false leaf 'lock-time'
          // NCS drop config false leaf identifier
          // NCS drop config false leaf 'unlock-username'
          // NCS drop config false leaf 'unlock-time'
        }
      }
      // NCS drop config false container checkpoints
      container global-switch {
        description
          "Configure the globally configuration management feature.";
        leaf configuration-slave-detect-switch {
          type boolean;
          default "true";
          description
            "Enable/disable function to automatically verify the configurations of the master and slave main control boards.";
        }
        leaf appdata-detect-switch {
          type boolean;
          default "false";
          description
            "Enable/disable function to automatically verify application data.";
        }
        leaf checkpoint-switch {
          type boolean;
          default "true";
          description
            "Enable/disable switch of saving check ponit.";
        }
      }
      // NCS drop config false container 'backup-and-recovery-states'
      container autosave-checkpoint {
        description
          "Configure start-time for automatically saving checkpoint.";
        leaf start-time {
          type pub-type:time-hhmm {
            length "5";
            pattern '(([0-1][0-9])|(2[0-3])):[0-5][0-9]';
          }
          units "min";
          default "02:00";
          description
            "The system automatically save checkpoint at a specified time of the day.";
        }
      }
      container configuration-operation-cpu-limit {
        description
          "Configure the CPU supress on configuration operation.";
        leaf snmp-cpu-limit {
          when "../snmp-switch = 'true'" {
            tailf:xpath-root 3;
          }
          type uint32 {
            range "30..100";
          }
          default "100";
          description
            "CPU usage threshold that triggers rate limiting on users that access through SNMP.";
        }
        leaf snmp-switch {
          type boolean;
          default "false";
          description
            "Enable/disable function of CPU usage-based rate limiting for users that access through SNMP.";
        }
        leaf netconf-cpu-limit {
          when "../netconf-switch = 'true'" {
            tailf:xpath-root 3;
          }
          type uint32 {
            range "30..100";
          }
          default "100";
          description
            "CPU usage threshold that triggers rate limiting on users that access through NETCONF.";
        }
        leaf netconf-switch {
          type boolean;
          default "false";
          description
            "Enable/disable function of CPU usage-based rate limiting for users that access through NETCONF.";
        }
      }
      container backup-servers {
        description
          "List of backup servers. A maximum of five backup servers can be configured.";
        list backup-server {
          key "server-ip vpn-instance";
          max-elements 5;
          description
            "Configure backup server used for automatically saving uploaded files.";
          leaf server-ip {
            type inet:ip-address-no-zone;
            description
              "IP address of the backup server.";
          }
          leaf vpn-instance {
            type string {
              length "1..31";
            }
            description
              "Name of a VPN instance.";
          }
          leaf transport-type {
            type cfg-server-type;
            mandatory true;
            description
              "Type of the protocol for transporting the backup file.";
          }
          leaf username {
            when "not(../transport-type='tftp')" {
              tailf:xpath-root 3;
            }
            type string {
              length "1..64";
            }
            mandatory true;
            description
              "User name for connecting the backup server.";
          }
          leaf password {
            when "not(../transport-type='tftp')" {
              tailf:xpath-root 3;
            }
            type pub-type:password-extend {
              length "1..432";
            }
            mandatory true;
            description
              "Password for connecting the backup server.";
          }
          leaf path {
            type string {
              length "1..64";
            }
            description
              "Path for backing up the configuration file.";
          }
          leaf port {
            when "not(../transport-type='tftp')" {
              tailf:xpath-root 3;
            }
            type uint16 {
              range "1..65535";
            }
            description
              "Port of a backup server.";
          }
        }
      }
      // NCS drop config false container 'startup-infos'
      // NCS drop config false container 'cfg-files'
      // NCS drop config false container 'config-rollback-result'
      // NCS drop config false container 'config-recover-results'
      container configuration-backup-to-file {
        presence "Enable configuration-backup-to-file";
        description
          "Configure the start-time and interval for cycle backup the current configuration operation.";
        leaf interval-time {
          type uint32 {
            range "1..7";
          }
          default "1";
          description
            "The system automatically backups configurations every a specified interval day.";
        }
        leaf start-time {
          type pub-type:time-hhmm {
            length "5";
            pattern '(([0-1][0-9])|(2[0-3])):[0-5][0-9]';
          }
          units "min";
          default "05:00";
          description
            "The system automatically backups running configuration at a specified time of the day.";
        }
      }
      // NCS drop config false container 'config-change'
    }
  }
  augment "/ncs:devices/ncs:device/ncs:live-status" {
    container cfg {
      tailf:ncs-device-type "netconf";
      tailf:display-when "not(../../ncs:module) or ../../ncs:module[ncs:name='huawei-cfg'] or (../../ncs:live-status-protocol[not(ncs:capability)]) or (../../ncs:live-status-protocol/ncs:capability/ncs:module[.='huawei-cfg'])";
      description
        "Configuration management module.";
      container autosave {
        presence "Enable autosave";
        description
          "Configure used for automatically saving configurations.";
        leaf interval-time {
          type uint32 {
            range "30..43200";
          }
          units "min";
          // NCS drop must statement
          // NCS drop default statement
          description
            "The system automatically saves configurations every a specified interval.";
        }
        leaf delay-time {
          type uint32 {
            range "1..60";
          }
          units "min";
          // NCS drop must statement
          // NCS drop default statement
          description
            "When the system configuration changes, the system automatically saves the configuration after a specified delay.";
        }
        leaf cpu-limit {
          type uint32 {
            range "1..100";
          }
          // NCS drop default statement
          description
            "Upper limit of the CPU usage for automatically saving configurations.";
        }
      }
      container lock-by-users {
        description
          "List of lock configuration.";
        list lock-by-user {
          key "lock-username";
          // NCS drop max-elements statement
          description
            "Configure lock configuration.";
          leaf lock-username {
            type string {
              length "1..253";
            }
            description
              "Name of a user who locks the configuration.";
          }
          leaf lock-time {
            type yang:date-and-time;
            description
              "Time when the configuration is locked.";
          }
          leaf identifier {
            type uint32;
            description
              "Unique ID of a configuration lock.";
          }
          leaf unlock-username {
            type string {
              length "1..253";
            }
            description
              "Name of a user who unlocks the configuration.";
          }
          leaf unlock-time {
            type yang:date-and-time;
            description
              "Time when the configuration is unlocked.";
          }
        }
      }
      container checkpoints {
        description
          "List of all configuration checkpoints in the system.";
        list checkpoint {
          key "commit-id";
          // NCS drop max-elements statement
          description
            "Operational state of configuration checkpoints in the system.";
          leaf commit-id {
            type string {
              length "1..20";
            }
            description
              "Uniquely identify a configuration checkpoint.";
          }
          leaf user-label {
            type string {
              length "1..256";
            }
            description
              "Label for identifying a configuration checkpoint, which is a character string that does not start with a digit.";
          }
          leaf username {
            type string {
              length "1..253";
            }
            description
              "Name of the user who committed a configuration to trigger the generation of a configuration checkpoint.";
          }
          leaf line {
            type string {
              length "1..85";
            }
            description
              "Instance of the terminal accessed by the user who committed a configuration to trigger the generation of a configuration checkpoint.";
          }
          leaf client {
            type live_ncs_config-checkpoint-client;
            description
              "Type of the tool agent accessed by the user who committed a configuration to trigger the generation of a configuration checkpoint.";
          }
          leaf timestamp {
            type yang:date-and-time;
            description
              "Time when a configuration checkpoint was created.";
          }
          leaf description {
            type string {
              length "1..60";
            }
            description
              "Description of a configuration checkpoint. A user can set a description for a configuration checkpoint to be generated when committing a configuration.";
          }
          container current-point-changes {
            description
              "List of configuration change information recorded in all configuration checkpoints. List of the configuration change information recorded in each configuration checkpoint is separately displayed.";
            list current-point-change {
              key "index";
              description
                "Operational state of configuration change between a specified configuration checkpoint and the previous configuration checkpoint.";
              leaf index {
                type uint32;
                description
                  "Index of a configuration change. A configuration checkpoint records a configuration change after a configuration is committed. Each configuration change is identified by an index.";
              }
              leaf config-change {
                type string {
                  length "1..3200";
                }
                description
                  "Configuration change command.";
              }
            }
          }
          container since-point-changes {
            description
              "List of configuration changes between a specified configuration checkpoint and the current configuration.";
            list since-point-change {
              key "index";
              description
                "Operational state of configuration change between a specified configuration checkpoint and the current configuration.";
              leaf index {
                type uint32;
                description
                  "Index of a configuration change. A configuration checkpoint records a configuration change after a configuration is committed. Each configuration change is identified by an index.";
              }
              leaf config-change {
                type string {
                  length "1..3200";
                }
                description
                  "Configuration change command.";
              }
            }
          }
        }
      }
      container global-switch {
        description
          "Configure the globally configuration management feature.";
        leaf configuration-slave-detect-switch {
          type boolean;
          // NCS drop default statement
          description
            "Enable/disable function to automatically verify the configurations of the master and slave main control boards.";
        }
        leaf appdata-detect-switch {
          type boolean;
          // NCS drop default statement
          description
            "Enable/disable function to automatically verify application data.";
        }
        leaf checkpoint-switch {
          type boolean;
          // NCS drop default statement
          description
            "Enable/disable switch of saving check ponit.";
        }
      }
      container backup-and-recovery-states {
        description
          "List of operation states delivered by the NMS.";
        list backup-and-recovery-state {
          key "index";
          // NCS drop max-elements statement
          description
            "Operational state of a configuration file.";
          leaf index {
            type uint32 {
              range "1..2147483647";
            }
            description
              "Operation ID.";
          }
          leaf operation-type {
            type live_ncs_cfg-hwcm-operation-type;
            description
              "Operation type delivered by the NMS.";
          }
          leaf state {
            type live_ncs_cfg-operation-state;
            description
              "Operation result.";
          }
          leaf operate-progress {
            type uint32 {
              range "0..100";
            }
            description
              "Operation progress.";
          }
          leaf start-time {
            type yang:date-and-time;
            description
              "Operation start time.";
          }
          leaf last-time {
            type pub-type:live_ncs_time-tick;
            description
              "Operation end time.";
          }
          leaf filename {
            type string {
              length "5..64";
            }
            description
              "Name of a configuration file.";
          }
          leaf service-type {
            type live_ncs_cfg-service-type;
            description
              "File service type.";
          }
        }
      }
      container autosave-checkpoint {
        description
          "Configure start-time for automatically saving checkpoint.";
        leaf start-time {
          type pub-type:live_ncs_time-hhmm;
          units "min";
          // NCS drop default statement
          description
            "The system automatically save checkpoint at a specified time of the day.";
        }
      }
      container configuration-operation-cpu-limit {
        description
          "Configure the CPU supress on configuration operation.";
        leaf snmp-cpu-limit {
          // NCS drop when statement
          type uint32 {
            range "30..100";
          }
          // NCS drop default statement
          description
            "CPU usage threshold that triggers rate limiting on users that access through SNMP.";
        }
        leaf snmp-switch {
          type boolean;
          // NCS drop default statement
          description
            "Enable/disable function of CPU usage-based rate limiting for users that access through SNMP.";
        }
        leaf netconf-cpu-limit {
          // NCS drop when statement
          type uint32 {
            range "30..100";
          }
          // NCS drop default statement
          description
            "CPU usage threshold that triggers rate limiting on users that access through NETCONF.";
        }
        leaf netconf-switch {
          type boolean;
          // NCS drop default statement
          description
            "Enable/disable function of CPU usage-based rate limiting for users that access through NETCONF.";
        }
      }
      container backup-servers {
        description
          "List of backup servers. A maximum of five backup servers can be configured.";
        list backup-server {
          key "server-ip vpn-instance";
          // NCS drop max-elements statement
          description
            "Configure backup server used for automatically saving uploaded files.";
          leaf server-ip {
            type inet:ip-address-no-zone;
            description
              "IP address of the backup server.";
          }
          leaf vpn-instance {
            type string {
              length "1..31";
            }
            description
              "Name of a VPN instance.";
          }
          leaf transport-type {
            type live_ncs_cfg-server-type;
            // NCS drop mandatory statement
            description
              "Type of the protocol for transporting the backup file.";
          }
          leaf username {
            // NCS drop when statement
            type string {
              length "1..64";
            }
            // NCS drop mandatory statement
            description
              "User name for connecting the backup server.";
          }
          leaf password {
            // NCS drop when statement
            type pub-type:live_ncs_password-extend;
            // NCS drop mandatory statement
            description
              "Password for connecting the backup server.";
          }
          leaf path {
            type string {
              length "1..64";
            }
            description
              "Path for backing up the configuration file.";
          }
          leaf port {
            // NCS drop when statement
            type uint16 {
              range "1..65535";
            }
            description
              "Port of a backup server.";
          }
        }
      }
      container startup-infos {
        description
          "List of information about system startup.";
        list startup-info {
          key "position";
          description
            "Operational state of information about a system startup.";
          leaf position {
            type string {
              length "0..32";
            }
            description
              "Position of the device.";
          }
          leaf configed-system-software {
            type string {
              length "0..255";
            }
            description
              "File name of the system software that is set by users for the current startup.";
          }
          leaf current-system-software {
            type string {
              length "0..255";
            }
            description
              "File name of the system software that is applied for the current startup.";
          }
          leaf next-system-software {
            type string {
              length "0..255";
            }
            description
              "File name of the system software that is applied for the next startup.";
          }
          leaf current-cfg-file {
            type string {
              length "0..255";
            }
            description
              "Name of the configuration file that is applied for the current startup.";
          }
          leaf next-cfg-file {
            type string {
              length "0..255";
            }
            description
              "Name of the configuration file that is applied for the next startup.";
          }
          leaf current-patch-file {
            type string {
              length "0..255";
            }
            description
              "Name of the patch file that is applied for the current startup.";
          }
          leaf next-patch-file {
            type string {
              length "0..255";
            }
            description
              "Name of the patch file that is applied for the next startup.";
          }
        }
      }
      container cfg-files {
        description
          "List of configuration files.";
        list cfg-file {
          key "filename";
          description
            "Operational state of the specified configuration file that a user can set for the next startup or the information about the difference to current configuration.";
          leaf filename {
            type string {
              length "5..64";
            }
            description
              "Name of a configuration file.";
          }
          leaf size {
            type uint32;
            units "Byte";
            description
              "Size of a configuration file.";
          }
          leaf create-time {
            type yang:date-and-time;
            description
              "Time when a configuration file was created, for example, 2010-11-04 20:01:38 +08:00.";
          }
          container file-current-changes {
            description
              "List of differences between a specified configuration file and the current configuration.";
            list file-current-change {
              key "index";
              description
                "Operational state of a specified configuration file different with the current configuration.";
              leaf index {
                type uint32;
                description
                  "Index of the configuration difference. Each configuration difference has an index.";
              }
              leaf config-change {
                type string {
                  length "1..3200";
                }
                description
                  "Configuration difference command.";
              }
            }
          }
        }
      }
      container config-rollback-result {
        description
          "Operational state of rollbacking configuration result.";
        anydata result {
          description
            "The result of rollbacking configuration.";
        }
      }
      container config-recover-results {
        description
          "List of all configuration restoration results in the system.";
        list config-recover-result {
          key "index";
          description
            "Operational state of configuration restoration result in the system.";
          leaf index {
            type uint32;
            description
              "Index of a configuration command. Each failure command is identified by an index.";
          }
          leaf command {
            type string {
              length "1..2047";
            }
            description
              "Configure the command that fails to be restored.";
          }
          leaf view {
            type string {
              length "1..80";
            }
            description
              "View of a command that fails to be restored.";
          }
          leaf line {
            type uint32;
            description
              "Row number of a command that fails to be restored in a file.";
          }
          leaf reason {
            type live_ncs_command-result;
            description
              "Cause of the configuration restoration failure command.";
          }
          leaf time {
            type yang:date-and-time;
            description
              "The command failed to be executed during configuration restoration.";
          }
        }
      }
      container configuration-backup-to-file {
        presence "Enable configuration-backup-to-file";
        description
          "Configure the start-time and interval for cycle backup the current configuration operation.";
        leaf interval-time {
          type uint32 {
            range "1..7";
          }
          // NCS drop default statement
          description
            "The system automatically backups configurations every a specified interval day.";
        }
        leaf start-time {
          type pub-type:live_ncs_time-hhmm;
          units "min";
          // NCS drop default statement
          description
            "The system automatically backups running configuration at a specified time of the day.";
        }
      }
      container config-change {
        description
          "Operational state of SN of a configuration change. The SN increases by 1 for each configuration change.";
        leaf flow-id {
          type uint32;
          description
            "SN of the current configuration change of the system.";
        }
        leaf baseline-time {
          type yang:date-and-time;
          description
            "Time when the system configuration has a major change, for example, 2012-07-19 14:57:44 +08:00.";
        }
      }
    }
  }
  augment "/ncs:devices/ncs:template/ncs:ned-id/ncs:config" {
    container cfg {
      description
        "Configuration management module.";
      container autosave {
        presence "Enable autosave";
        description
          "Configure used for automatically saving configurations.";
        leaf interval-time {
          type string;
          units "min";
          // NCS drop must statement
          // NCS drop default statement
          description
            "The system automatically saves configurations every a specified interval.";
        }
        leaf delay-time {
          type string;
          units "min";
          // NCS drop must statement
          // NCS drop default statement
          description
            "When the system configuration changes, the system automatically saves the configuration after a specified delay.";
        }
        leaf cpu-limit {
          type string;
          // NCS drop default statement
          description
            "Upper limit of the CPU usage for automatically saving configurations.";
        }
      }
      container lock-by-users {
        description
          "List of lock configuration.";
        list lock-by-user {
          // NCS patched for predictable order
          ordered-by user;
          key "lock-username";
          // NCS drop max-elements statement
          description
            "Configure lock configuration.";
          leaf lock-username {
            type string;
            description
              "Name of a user who locks the configuration.";
          }
          // NCS drop config false leaf 'lock-time'
          // NCS drop config false leaf identifier
          // NCS drop config false leaf 'unlock-username'
          // NCS drop config false leaf 'unlock-time'
        }
      }
      // NCS drop config false container checkpoints
      container global-switch {
        description
          "Configure the globally configuration management feature.";
        leaf configuration-slave-detect-switch {
          type string;
          // NCS drop default statement
          description
            "Enable/disable function to automatically verify the configurations of the master and slave main control boards.";
        }
        leaf appdata-detect-switch {
          type string;
          // NCS drop default statement
          description
            "Enable/disable function to automatically verify application data.";
        }
        leaf checkpoint-switch {
          type string;
          // NCS drop default statement
          description
            "Enable/disable switch of saving check ponit.";
        }
      }
      // NCS drop config false container 'backup-and-recovery-states'
      container autosave-checkpoint {
        description
          "Configure start-time for automatically saving checkpoint.";
        leaf start-time {
          type pub-type:ncs_template_time-hhmm;
          units "min";
          // NCS drop default statement
          description
            "The system automatically save checkpoint at a specified time of the day.";
        }
      }
      container configuration-operation-cpu-limit {
        description
          "Configure the CPU supress on configuration operation.";
        leaf snmp-cpu-limit {
          // NCS drop when statement
          type string;
          // NCS drop default statement
          description
            "CPU usage threshold that triggers rate limiting on users that access through SNMP.";
        }
        leaf snmp-switch {
          type string;
          // NCS drop default statement
          description
            "Enable/disable function of CPU usage-based rate limiting for users that access through SNMP.";
        }
        leaf netconf-cpu-limit {
          // NCS drop when statement
          type string;
          // NCS drop default statement
          description
            "CPU usage threshold that triggers rate limiting on users that access through NETCONF.";
        }
        leaf netconf-switch {
          type string;
          // NCS drop default statement
          description
            "Enable/disable function of CPU usage-based rate limiting for users that access through NETCONF.";
        }
      }
      container backup-servers {
        description
          "List of backup servers. A maximum of five backup servers can be configured.";
        list backup-server {
          // NCS patched for predictable order
          ordered-by user;
          key "server-ip vpn-instance";
          // NCS drop max-elements statement
          description
            "Configure backup server used for automatically saving uploaded files.";
          leaf server-ip {
            type string;
            description
              "IP address of the backup server.";
          }
          leaf vpn-instance {
            type string;
            description
              "Name of a VPN instance.";
          }
          leaf transport-type {
            type ncs_template_cfg-server-type;
            // NCS drop mandatory statement
            description
              "Type of the protocol for transporting the backup file.";
          }
          leaf username {
            // NCS drop when statement
            type string;
            // NCS drop mandatory statement
            description
              "User name for connecting the backup server.";
          }
          leaf password {
            // NCS drop when statement
            type pub-type:ncs_template_password-extend;
            // NCS drop mandatory statement
            description
              "Password for connecting the backup server.";
          }
          leaf path {
            type string;
            description
              "Path for backing up the configuration file.";
          }
          leaf port {
            // NCS drop when statement
            type string;
            description
              "Port of a backup server.";
          }
        }
      }
      // NCS drop config false container 'startup-infos'
      // NCS drop config false container 'cfg-files'
      // NCS drop config false container 'config-rollback-result'
      // NCS drop config false container 'config-recover-results'
      container configuration-backup-to-file {
        presence "Enable configuration-backup-to-file";
        description
          "Configure the start-time and interval for cycle backup the current configuration operation.";
        leaf interval-time {
          type string;
          // NCS drop default statement
          description
            "The system automatically backups configurations every a specified interval day.";
        }
        leaf start-time {
          type pub-type:ncs_template_time-hhmm;
          units "min";
          // NCS drop default statement
          description
            "The system automatically backups running configuration at a specified time of the day.";
        }
      }
      // NCS drop config false container 'config-change'
    }
  }
}
