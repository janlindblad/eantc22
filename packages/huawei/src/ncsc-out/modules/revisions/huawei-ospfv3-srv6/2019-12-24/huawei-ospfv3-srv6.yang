module huawei-ospfv3-srv6 {
  // Generated by yanger -t ncs
  tailf:mount-id "huawei-nc-1.0:huawei-nc-1.0";
  tailf:ncs-device-type "netconf";

  namespace "urn:huawei:yang:huawei-ospfv3-srv6";
  prefix ospfv3-srv6;

  import huawei-network-instance {
    prefix ni;
  }
  import huawei-ospfv3 {
    prefix ospfv3;
  }
  import huawei-srv6 {
    prefix srv6;
  }
  import huawei-extension {
    prefix ext;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "The YANG module defines generic configuration model for IPv6 Segment Routing (SRv6) OSPFv3 extensions that are common across all of the vendor implementations.";

  revision 2019-12-24 {
    description
      "Initial revision.";
    reference "Huawei private.";
  }
  ext:task-name "ospf";

  augment "/ncs:devices/ncs:template/ncs:ned-id/ncs:config/ni:network-instance/ni:instances/ni:instance/ospfv3:ospfv3/ospfv3:sites/ospfv3:site" {
    description
      "This augments OSPFv3 protocol configuration with SRv6.";
    container srv6 {
      // NCS drop when statement
      description
        "Configure OSPFv3 IPv6 Segment Routing (SRv6).";
      container locators {
        description
          "List of the information about segment-routing IPv6 locators.";
        list locator {
          // NCS patched for predictable order
          ordered-by user;
          key "locator-name";
          description
            "Configure IPv6 Segment Routing (SRv6) locators.";
          leaf locator-name {
            type string;
            description
              "Enable OSPFv3 IPv6 Segment Routing (SRv6) with a specified locator.";
          }
          leaf auto-sid {
            type string;
            // NCS drop must statement
            // NCS drop mandatory statement
            description
              "Enable/disable dynamic SID allocation.";
          }
        }
      }
    }
  }
  augment "/ncs:devices/ncs:device/ncs:live-status/ni:network-instance/ni:instances/ni:instance/ospfv3:ospfv3/ospfv3:sites/ospfv3:site" {
    description
      "This augments OSPFv3 protocol configuration with SRv6.";
    container srv6 {
      tailf:ncs-device-type "netconf";
      tailf:display-when "not(../../../../../../../../ncs:module) or ../../../../../../../../ncs:module[ncs:name='huawei-ospfv3-srv6'] or (../../../../../../../../ncs:live-status-protocol[not(ncs:capability)]) or (../../../../../../../../ncs:live-status-protocol/ncs:capability/ncs:module[.='huawei-ospfv3-srv6'])";
      // NCS drop when statement
      description
        "Configure OSPFv3 IPv6 Segment Routing (SRv6).";
      container locators {
        description
          "List of the information about segment-routing IPv6 locators.";
        list locator {
          key "locator-name";
          description
            "Configure IPv6 Segment Routing (SRv6) locators.";
          leaf locator-name {
            type leafref {
              path "/ncs:devices/ncs:device/ncs:live-status/ni:network-instance/ni:instances/ni:instance/srv6:srv6/srv6:locators/srv6:locator/srv6:name" {
                tailf:xpath-root 3;
              }
            }
            description
              "Enable OSPFv3 IPv6 Segment Routing (SRv6) with a specified locator.";
          }
          leaf auto-sid {
            type boolean;
            // NCS drop must statement
            // NCS drop mandatory statement
            description
              "Enable/disable dynamic SID allocation.";
          }
        }
      }
    }
  }
  augment "/ncs:devices/ncs:device/ncs:config/ni:network-instance/ni:instances/ni:instance/ospfv3:ospfv3/ospfv3:sites/ospfv3:site" {
    description
      "This augments OSPFv3 protocol configuration with SRv6.";
    container srv6 {
      tailf:ncs-device-type "netconf";
      tailf:display-when "not(../../../../../../../../ncs:module) or ../../../../../../../../ncs:module[ncs:name='huawei-ospfv3-srv6']";
      when "../../../../ni:name='_public_'" {
        tailf:xpath-root 3;
      }
      description
        "Configure OSPFv3 IPv6 Segment Routing (SRv6).";
      container locators {
        description
          "List of the information about segment-routing IPv6 locators.";
        list locator {
          key "locator-name";
          description
            "Configure IPv6 Segment Routing (SRv6) locators.";
          leaf locator-name {
            type leafref {
              path "/ncs:devices/ncs:device/ncs:config/ni:network-instance/ni:instances/ni:instance/srv6:srv6/srv6:locators/srv6:locator/srv6:name" {
                tailf:xpath-root 3;
              }
            }
            description
              "Enable OSPFv3 IPv6 Segment Routing (SRv6) with a specified locator.";
          }
          leaf auto-sid {
            type boolean;
            must "../auto-sid='false'" {
              tailf:xpath-root 3;
            }
            mandatory true;
            description
              "Enable/disable dynamic SID allocation.";
          }
        }
      }
    }
  }
}
