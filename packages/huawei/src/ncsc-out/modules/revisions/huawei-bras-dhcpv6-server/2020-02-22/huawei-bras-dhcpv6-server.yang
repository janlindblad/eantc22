module huawei-bras-dhcpv6-server {
  // Generated by yanger -t ncs
  tailf:mount-id "huawei-nc-1.0:huawei-nc-1.0";
  tailf:ncs-device-type "netconf";

  namespace "urn:huawei:yang:huawei-bras-dhcpv6-server";
  prefix bras-dhcpv6-server;

  import huawei-ifm {
    prefix ifm;
  }
  import huawei-extension {
    prefix ext;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Configure the DHCPv6 server.";

  revision 2020-02-22 {
    description
      "Description modification.";
    reference "Huawei private.";
  }
  revision 2019-10-17 {
    description
      "Second revision.";
    reference "Huawei private.";
  }
  revision 2019-09-27 {
    description
      "Init revision.";
    reference "Huawei private.";
  }
  ext:task-name "ipv6pool";

  grouping ncs_template_dhcpv6-server-property {
    description
      "Configure a status (Up/Down) switchover for a DHCPv6 server.";
    leaf dead-count {
      type string;
      // NCS drop default statement
      description
        "Specify the maximum number of times at which the DHCPv6 server does not send response packets.";
    }
    leaf time-out {
      type string;
      units "s";
      // NCS drop default statement
      description
        "Specify a timeout period. If a device receives no response from the DHCPv6 server within the timeout period, it re-sends request packets.";
    }
    leaf dead-time {
      type string;
      units "min";
      // NCS drop default statement
      description
        "Specify a period within which the DHCPv6 server is down. After the dead-time, the DHCPv6 server is set to up.";
    }
  }

  grouping ncs_rpc_notif_dhcpv6-server-property {
    description
      "Configure a status (Up/Down) switchover for a DHCPv6 server.";
    leaf dead-count {
      type uint8 {
        range "1..64";
      }
      default "1";
      description
        "Specify the maximum number of times at which the DHCPv6 server does not send response packets.";
    }
    leaf time-out {
      type uint8 {
        range "1..60";
      }
      units "s";
      default "25";
      description
        "Specify a timeout period. If a device receives no response from the DHCPv6 server within the timeout period, it re-sends request packets.";
    }
    leaf dead-time {
      type uint16 {
        range "1..65535";
      }
      units "min";
      default "3";
      description
        "Specify a period within which the DHCPv6 server is down. After the dead-time, the DHCPv6 server is set to up.";
    }
  }

  grouping live_ncs_dhcpv6-server-property {
    description
      "Configure a status (Up/Down) switchover for a DHCPv6 server.";
    leaf dead-count {
      type uint8 {
        range "1..64";
      }
      // NCS drop default statement
      description
        "Specify the maximum number of times at which the DHCPv6 server does not send response packets.";
    }
    leaf time-out {
      type uint8 {
        range "1..60";
      }
      units "s";
      // NCS drop default statement
      description
        "Specify a timeout period. If a device receives no response from the DHCPv6 server within the timeout period, it re-sends request packets.";
    }
    leaf dead-time {
      type uint16 {
        range "1..65535";
      }
      units "min";
      // NCS drop default statement
      description
        "Specify a period within which the DHCPv6 server is down. After the dead-time, the DHCPv6 server is set to up.";
    }
  }

  grouping dhcpv6-server-property {
    description
      "Configure a status (Up/Down) switchover for a DHCPv6 server.";
    leaf dead-count {
      type uint8 {
        range "1..64";
      }
      default "1";
      description
        "Specify the maximum number of times at which the DHCPv6 server does not send response packets.";
    }
    leaf time-out {
      type uint8 {
        range "1..60";
      }
      units "s";
      default "25";
      description
        "Specify a timeout period. If a device receives no response from the DHCPv6 server within the timeout period, it re-sends request packets.";
    }
    leaf dead-time {
      type uint16 {
        range "1..65535";
      }
      units "min";
      default "3";
      description
        "Specify a period within which the DHCPv6 server is down. After the dead-time, the DHCPv6 server is set to up.";
    }
  }

  augment "/ncs:devices/ncs:device/ncs:config" {
    container bras-dhcpv6-server {
      tailf:ncs-device-type "netconf";
      tailf:display-when "not(../../ncs:module) or ../../ncs:module[ncs:name='huawei-bras-dhcpv6-server']";
      description
        "Configure the DHCPv6 server.";
      container dhcpv6-server-groups {
        description
          "List of DHCPv6 server groups.";
        list dhcpv6-server-group {
          key "name";
          max-elements 4096;
          description
            "Configure a DHCPv6 server group.";
          leaf name {
            type string {
              length "1..32";
              pattern '[a-z0-9._-]{1,32}';
            }
            must "../name != '-' and ../name != '--'" {
              tailf:xpath-root 3;
            }
            description
              "Specify the name of the DHCPv6 server group.";
            ext:case-sensitivity "lower-only";
          }
          container server-source {
            description
              "Configure the source address for packets to be sent to the DHCPv6 server group.";
            choice source-address {
              description
                "Configure the source address for packets to be sent to the DHCPv6 server group.";
              case link-address {
                description
                  "Configures the source address, which is a link address of the prefix pool bound to a remote address pool.";
                leaf link-address {
                  type empty;
                  description
                    "Indicate that the source address is a link address of the prefix pool bound to a remote address pool.";
                }
              }
              case if-name {
                description
                  "Configures the type and number of the interface whose address is the source address.";
                leaf if-name {
                  type leafref {
                    path "/ncs:devices/ncs:device/ncs:config/ifm:ifm/ifm:interfaces/ifm:interface/ifm:name" {
                      tailf:xpath-root 3;
                    }
                  }
                  must "/ifm:ifm/ifm:interfaces/ifm:interface[ifm:name=current()]/ifm:type='GigabitEthernet' or
/ifm:ifm/ifm:interfaces/ifm:interface[ifm:name=current()]/ifm:type='10GE' or
/ifm:ifm/ifm:interfaces/ifm:interface[ifm:name=current()]/ifm:type='XGigabitEthernet' or
/ifm:ifm/ifm:interfaces/ifm:interface[ifm:name=current()]/ifm:type='100GE' or
/ifm:ifm/ifm:interfaces/ifm:interface[ifm:name=current()]/ifm:type='Virtual-Ethernet' or
/ifm:ifm/ifm:interfaces/ifm:interface[ifm:name=current()]/ifm:type='50GE' or
/ifm:ifm/ifm:interfaces/ifm:interface[ifm:name=current()]/ifm:type='50|100GE' or
/ifm:ifm/ifm:interfaces/ifm:interface[ifm:name=current()]/ifm:type='FlexE' or
/ifm:ifm/ifm:interfaces/ifm:interface[ifm:name=current()]/ifm:type='25GE' or
/ifm:ifm/ifm:interfaces/ifm:interface[ifm:name=current()]/ifm:type='Ethernet' or
/ifm:ifm/ifm:interfaces/ifm:interface[ifm:name=current()]/ifm:type='Eth-Trunk' or
/ifm:ifm/ifm:interfaces/ifm:interface[ifm:name=current()]/ifm:type='LoopBack'" {
                    tailf:xpath-root 3;
                  }
                  description
                    "Indicate the type and number of the interface whose address is the source address.";
                }
              }
            }
          }
        }
      }
      container server-global-property {
        description
          "Configure a status (Up/Down) switchover for global DHCPv6 server.";
        uses dhcpv6-server-property;
      }
    }
  }
  augment "/ncs:devices/ncs:device/ncs:live-status" {
    container bras-dhcpv6-server {
      tailf:ncs-device-type "netconf";
      tailf:display-when "not(../../ncs:module) or ../../ncs:module[ncs:name='huawei-bras-dhcpv6-server'] or (../../ncs:live-status-protocol[not(ncs:capability)]) or (../../ncs:live-status-protocol/ncs:capability/ncs:module[.='huawei-bras-dhcpv6-server'])";
      description
        "Configure the DHCPv6 server.";
      container dhcpv6-server-groups {
        description
          "List of DHCPv6 server groups.";
        list dhcpv6-server-group {
          key "name";
          // NCS drop max-elements statement
          description
            "Configure a DHCPv6 server group.";
          leaf name {
            type string {
              length "1..32";
              pattern '[a-z0-9._-]{1,32}';
            }
            // NCS drop must statement
            description
              "Specify the name of the DHCPv6 server group.";
            ext:case-sensitivity "lower-only";
          }
          container server-source {
            description
              "Configure the source address for packets to be sent to the DHCPv6 server group.";
            choice source-address {
              description
                "Configure the source address for packets to be sent to the DHCPv6 server group.";
              case link-address {
                description
                  "Configures the source address, which is a link address of the prefix pool bound to a remote address pool.";
                leaf link-address {
                  type empty;
                  description
                    "Indicate that the source address is a link address of the prefix pool bound to a remote address pool.";
                }
              }
              case if-name {
                description
                  "Configures the type and number of the interface whose address is the source address.";
                leaf if-name {
                  type leafref {
                    path "/ncs:devices/ncs:device/ncs:live-status/ifm:ifm/ifm:interfaces/ifm:interface/ifm:name" {
                      tailf:xpath-root 3;
                    }
                  }
                  // NCS drop must statement
                  description
                    "Indicate the type and number of the interface whose address is the source address.";
                }
              }
            }
          }
        }
      }
      container server-global-property {
        description
          "Configure a status (Up/Down) switchover for global DHCPv6 server.";
        uses live_ncs_dhcpv6-server-property;
      }
    }
  }
  augment "/ncs:devices/ncs:template/ncs:ned-id/ncs:config" {
    container bras-dhcpv6-server {
      description
        "Configure the DHCPv6 server.";
      container dhcpv6-server-groups {
        description
          "List of DHCPv6 server groups.";
        list dhcpv6-server-group {
          // NCS patched for predictable order
          ordered-by user;
          key "name";
          // NCS drop max-elements statement
          description
            "Configure a DHCPv6 server group.";
          leaf name {
            type string;
            // NCS drop must statement
            description
              "Specify the name of the DHCPv6 server group.";
            ext:case-sensitivity "lower-only";
          }
          container server-source {
            description
              "Configure the source address for packets to be sent to the DHCPv6 server group.";
            choice source-address {
              description
                "Configure the source address for packets to be sent to the DHCPv6 server group.";
              case link-address {
                description
                  "Configures the source address, which is a link address of the prefix pool bound to a remote address pool.";
                leaf link-address {
                  type empty;
                  description
                    "Indicate that the source address is a link address of the prefix pool bound to a remote address pool.";
                }
              }
              case if-name {
                description
                  "Configures the type and number of the interface whose address is the source address.";
                leaf if-name {
                  type string;
                  // NCS drop must statement
                  description
                    "Indicate the type and number of the interface whose address is the source address.";
                }
              }
            }
          }
        }
      }
      container server-global-property {
        description
          "Configure a status (Up/Down) switchover for global DHCPv6 server.";
        uses ncs_template_dhcpv6-server-property;
      }
    }
  }
}
