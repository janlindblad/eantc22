submodule openconfig-aft-ethernet {
  // Generated by yanger -t ncs
  tailf:mount-id "huawei-nc-1.0:huawei-nc-1.0";

  belongs-to openconfig-aft {
    prefix oc-aft;
  }

  import openconfig-extensions {
    prefix oc-ext;
  }
  import openconfig-yang-types {
    prefix oc-yang;
  }
  include openconfig-aft-common;
  import tailf-common {
    prefix tailf;
  }
  import tailf-ncs {
    prefix ncs;
  }

  organization
    "OpenConfig working group";
  contact
    "OpenConfig working group
     www.openconfig.net";
  description
    "Submodule containing definitions of groupings for the abstract
     forwarding tables for Ethernet.";
  oc-ext:openconfig-version "0.4.0";

  revision 2019-08-02 {
    description
      "Add installing protocol for IPv[46] unicast entries.
       Add the ability to describe conditional next-hop groups
       outside of the policy forwarding module to allow for efficient
       handling of CBTS, where many prefixes may share the same next-hop
       criteria.";
    reference "0.4.0";
  }
  revision 2019-08-01 {
    description
      "Add lsp-name leaf to AFT next-hop.";
    reference "0.3.3";
  }
  revision 2018-11-21 {
    description
      "Add OpenConfig module metadata extensions.";
    reference "0.3.2";
  }
  revision 2017-08-24 {
    description
      "Formatting fixes";
    reference "0.3.1";
  }
  revision 2017-05-10 {
    description
      "Refactor to provide concretised per-AF schemas per AFT.";
    reference "0.3.0";
  }

  grouping ncs_template_aft-ethernet-structural {
    description
      "Structural grouping defining the schema for the Ethernet
       abstract forwarding table.";
    list mac-entry {
      // NCS patched for predictable order
      ordered-by user;
      key "mac-address";
      description
        "List of the Ethernet entries within the abstract
         forwarding table. This list is keyed by the outer MAC address
         of the Ethernet frame.";
      leaf mac-address {
        type string;
        description
          "Reference to the outer MAC address matched by the
           entry.";
      }
      container config {
        description
          "Configuration parameters for the Ethernet AFT entry.";
        uses ncs_template_aft-ethernet-entry-config;
      }
      // NCS drop config false container state
    }
  }

  grouping ncs_template_aft-ethernet-entry-config {
    description
      "Configuration parameters for the Ethernet AFT entry.";
    leaf mac-address {
      type oc-yang:ncs_template_mac-address;
      description
        "The outer MAC address of the Ethernet frame that must
         be matched for the AFT entry to be utilised.";
    }
  }

  grouping ncs_template_aft-ethernet-entry-state {
    description
      "Operational state parameters for the Ethernet AFT entry.";
    uses ncs_template_aft-common-entry-state;
  }

  grouping ncs_rpc_notif_aft-ethernet-structural {
    description
      "Structural grouping defining the schema for the Ethernet
       abstract forwarding table.";
    list mac-entry {
      key "mac-address";
      description
        "List of the Ethernet entries within the abstract
         forwarding table. This list is keyed by the outer MAC address
         of the Ethernet frame.";
      leaf mac-address {
        type leafref {
          path "../config/mac-address";
        }
        description
          "Reference to the outer MAC address matched by the
           entry.";
      }
      container config {
        description
          "Configuration parameters for the Ethernet AFT entry.";
        uses ncs_rpc_notif_aft-ethernet-entry-config;
      }
      container state {
        config false;
        description
          "Operational state parameters for the Ethernet AFT
           entry.";
        uses ncs_rpc_notif_aft-ethernet-entry-config;
        uses ncs_rpc_notif_aft-ethernet-entry-state;
      }
    }
  }

  grouping ncs_rpc_notif_aft-ethernet-entry-config {
    description
      "Configuration parameters for the Ethernet AFT entry.";
    leaf mac-address {
      type oc-yang:ncs_rpc_notif_mac-address;
      description
        "The outer MAC address of the Ethernet frame that must
         be matched for the AFT entry to be utilised.";
    }
  }

  grouping ncs_rpc_notif_aft-ethernet-entry-state {
    description
      "Operational state parameters for the Ethernet AFT entry.";
    uses ncs_rpc_notif_aft-common-entry-state;
  }

  grouping live_ncs_aft-ethernet-structural {
    description
      "Structural grouping defining the schema for the Ethernet
       abstract forwarding table.";
    list mac-entry {
      key "mac-address";
      description
        "List of the Ethernet entries within the abstract
         forwarding table. This list is keyed by the outer MAC address
         of the Ethernet frame.";
      leaf mac-address {
        type leafref {
          path "../config/mac-address";
        }
        description
          "Reference to the outer MAC address matched by the
           entry.";
      }
      container config {
        description
          "Configuration parameters for the Ethernet AFT entry.";
        uses live_ncs_aft-ethernet-entry-config;
      }
      container state {
        description
          "Operational state parameters for the Ethernet AFT
           entry.";
        uses live_ncs_aft-ethernet-entry-config;
        uses live_ncs_aft-ethernet-entry-state;
      }
    }
  }

  grouping live_ncs_aft-ethernet-entry-config {
    description
      "Configuration parameters for the Ethernet AFT entry.";
    leaf mac-address {
      type oc-yang:live_ncs_mac-address;
      description
        "The outer MAC address of the Ethernet frame that must
         be matched for the AFT entry to be utilised.";
    }
  }

  grouping live_ncs_aft-ethernet-entry-state {
    description
      "Operational state parameters for the Ethernet AFT entry.";
    uses live_ncs_aft-common-entry-state;
  }

  grouping aft-ethernet-structural {
    description
      "Structural grouping defining the schema for the Ethernet
       abstract forwarding table.";
    list mac-entry {
      key "mac-address";
      description
        "List of the Ethernet entries within the abstract
         forwarding table. This list is keyed by the outer MAC address
         of the Ethernet frame.";
      leaf mac-address {
        type leafref {
          path "../config/mac-address";
        }
        description
          "Reference to the outer MAC address matched by the
           entry.";
      }
      container config {
        description
          "Configuration parameters for the Ethernet AFT entry.";
        uses aft-ethernet-entry-config;
      }
      // NCS drop config false container state
    }
  }

  grouping aft-ethernet-entry-config {
    description
      "Configuration parameters for the Ethernet AFT entry.";
    leaf mac-address {
      type oc-yang:mac-address;
      description
        "The outer MAC address of the Ethernet frame that must
         be matched for the AFT entry to be utilised.";
    }
  }

  grouping aft-ethernet-entry-state {
    description
      "Operational state parameters for the Ethernet AFT entry.";
    uses aft-common-entry-state;
  }
}
