submodule openconfig-aft-ipv6 {
  // Generated by yanger -t ncs
  tailf:mount-id "huawei-nc-1.0:huawei-nc-1.0";

  belongs-to openconfig-aft {
    prefix oc-aft;
  }

  import openconfig-extensions {
    prefix oc-ext;
  }
  import openconfig-inet-types {
    prefix oc-inet;
  }
  include openconfig-aft-common;
  import tailf-common {
    prefix tailf;
  }
  import tailf-ncs {
    prefix ncs;
  }

  organization
    "OpenConfig working group";
  contact
    "OpenConfig working group
     www.openconfig.net";
  description
    "Submodule containing definitions of groupings for the abstract
     forwarding tables for IPv6.";
  oc-ext:openconfig-version "0.4.0";

  revision 2019-08-02 {
    description
      "Add installing protocol for IPv[46] unicast entries.
       Add the ability to describe conditional next-hop groups
       outside of the policy forwarding module to allow for efficient
       handling of CBTS, where many prefixes may share the same next-hop
       criteria.";
    reference "0.4.0";
  }
  revision 2019-08-01 {
    description
      "Add lsp-name leaf to AFT next-hop.";
    reference "0.3.3";
  }
  revision 2018-11-21 {
    description
      "Add OpenConfig module metadata extensions.";
    reference "0.3.2";
  }
  revision 2017-08-24 {
    description
      "Formatting fixes";
    reference "0.3.1";
  }
  revision 2017-05-10 {
    description
      "Refactor to provide concretised per-AF schemas per AFT.";
    reference "0.3.0";
  }

  grouping ncs_template_aft-ipv6-unicast-structural {
    description
      "Structural grouping defining the schema for the IPv6 unicast
       abstract forwarding table.";
    list ipv6-entry {
      // NCS patched for predictable order
      ordered-by user;
      key "prefix";
      description
        "List of the IPv6 unicast entries within the abstract
         forwarding table. This list is keyed by the destination IPv6
         prefix.";
      leaf prefix {
        type string;
        description
          "Reference to the IPv6 unicast destination prefix which
           must be matched to utilise the AFT entry.";
      }
      container config {
        description
          "Configuration parameters for the IPv6 unicast AFT entry.";
        uses ncs_template_aft-ipv6-unicast-entry-config;
      }
      // NCS drop config false container state
    }
  }

  grouping ncs_template_aft-ipv6-unicast-entry-config {
    description
      "Configuration parameters for the IPv6 unicast entry.";
    leaf prefix {
      type oc-inet:ncs_template_ipv6-prefix;
      description
        "The IPv6 destination prefix that should be matched to
         utilise the AFT entry.";
    }
  }

  grouping ncs_template_aft-ipv6-unicast-entry-state {
    description
      "Operational state parameters for the IPv6 unicast entry.";
    uses ncs_template_aft-common-entry-state;
    uses ncs_template_aft-common-ip-state;
  }

  grouping ncs_rpc_notif_aft-ipv6-unicast-structural {
    description
      "Structural grouping defining the schema for the IPv6 unicast
       abstract forwarding table.";
    list ipv6-entry {
      key "prefix";
      description
        "List of the IPv6 unicast entries within the abstract
         forwarding table. This list is keyed by the destination IPv6
         prefix.";
      leaf prefix {
        type leafref {
          path "../config/prefix";
        }
        description
          "Reference to the IPv6 unicast destination prefix which
           must be matched to utilise the AFT entry.";
      }
      container config {
        description
          "Configuration parameters for the IPv6 unicast AFT entry.";
        uses ncs_rpc_notif_aft-ipv6-unicast-entry-config;
      }
      container state {
        config false;
        description
          "Operational state parameters for the IPv6 unicast AFT
           entry.";
        uses ncs_rpc_notif_aft-ipv6-unicast-entry-config;
        uses ncs_rpc_notif_aft-ipv6-unicast-entry-state;
      }
    }
  }

  grouping ncs_rpc_notif_aft-ipv6-unicast-entry-config {
    description
      "Configuration parameters for the IPv6 unicast entry.";
    leaf prefix {
      type oc-inet:ncs_rpc_notif_ipv6-prefix;
      description
        "The IPv6 destination prefix that should be matched to
         utilise the AFT entry.";
    }
  }

  grouping ncs_rpc_notif_aft-ipv6-unicast-entry-state {
    description
      "Operational state parameters for the IPv6 unicast entry.";
    uses ncs_rpc_notif_aft-common-entry-state;
    uses ncs_rpc_notif_aft-common-ip-state;
  }

  grouping live_ncs_aft-ipv6-unicast-structural {
    description
      "Structural grouping defining the schema for the IPv6 unicast
       abstract forwarding table.";
    list ipv6-entry {
      key "prefix";
      description
        "List of the IPv6 unicast entries within the abstract
         forwarding table. This list is keyed by the destination IPv6
         prefix.";
      leaf prefix {
        type leafref {
          path "../config/prefix";
        }
        description
          "Reference to the IPv6 unicast destination prefix which
           must be matched to utilise the AFT entry.";
      }
      container config {
        description
          "Configuration parameters for the IPv6 unicast AFT entry.";
        uses live_ncs_aft-ipv6-unicast-entry-config;
      }
      container state {
        description
          "Operational state parameters for the IPv6 unicast AFT
           entry.";
        uses live_ncs_aft-ipv6-unicast-entry-config;
        uses live_ncs_aft-ipv6-unicast-entry-state;
      }
    }
  }

  grouping live_ncs_aft-ipv6-unicast-entry-config {
    description
      "Configuration parameters for the IPv6 unicast entry.";
    leaf prefix {
      type oc-inet:live_ncs_ipv6-prefix;
      description
        "The IPv6 destination prefix that should be matched to
         utilise the AFT entry.";
    }
  }

  grouping live_ncs_aft-ipv6-unicast-entry-state {
    description
      "Operational state parameters for the IPv6 unicast entry.";
    uses live_ncs_aft-common-entry-state;
    uses live_ncs_aft-common-ip-state;
  }

  grouping aft-ipv6-unicast-structural {
    description
      "Structural grouping defining the schema for the IPv6 unicast
       abstract forwarding table.";
    list ipv6-entry {
      key "prefix";
      description
        "List of the IPv6 unicast entries within the abstract
         forwarding table. This list is keyed by the destination IPv6
         prefix.";
      leaf prefix {
        type leafref {
          path "../config/prefix";
        }
        description
          "Reference to the IPv6 unicast destination prefix which
           must be matched to utilise the AFT entry.";
      }
      container config {
        description
          "Configuration parameters for the IPv6 unicast AFT entry.";
        uses aft-ipv6-unicast-entry-config;
      }
      // NCS drop config false container state
    }
  }

  grouping aft-ipv6-unicast-entry-config {
    description
      "Configuration parameters for the IPv6 unicast entry.";
    leaf prefix {
      type oc-inet:ipv6-prefix;
      description
        "The IPv6 destination prefix that should be matched to
         utilise the AFT entry.";
    }
  }

  grouping aft-ipv6-unicast-entry-state {
    description
      "Operational state parameters for the IPv6 unicast entry.";
    uses aft-common-entry-state;
    uses aft-common-ip-state;
  }
}
