module huawei-mplsoam {
  // Generated by yanger -t ncs
  tailf:mount-id "huawei-nc-1.0:huawei-nc-1.0";
  tailf:ncs-device-type "netconf";

  yang-version 1;
  namespace "urn:huawei:yang:huawei-mplsoam";
  prefix mplsoam;

  import huawei-l2vpn {
    prefix l2vpn;
  }
  import huawei-ifm {
    prefix ifm;
  }
  import huawei-tunnel-management {
    prefix tnlm;
  }
  import huawei-mpls-te {
    prefix mpls-te;
  }
  import huawei-pub-type {
    prefix pub-type;
  }
  import ietf-inet-types {
    prefix inet;
  }
  import huawei-extension {
    prefix ext;
  }
  import huawei-mpls {
    prefix mpls;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Multiprotocol Label Switching (MPLS) operations, administration and maintenance (OAM), provides the following functions: fault management, performance monitoring, and protection switching.";

  revision 2019-04-18 {
    description
      "Initial revision.";
    reference "Huawei private.";
  }
  ext:task-name "tpoam";

  typedef ncs_template_detect-pkt-type {
    type string;
    description
      "Detect pkt type.";
  }

  typedef ncs_template_detect-mode {
    type string;
    description
      "Detect type.";
  }

  typedef ncs_template_l2vc-type {
    type string;
    description
      "L2vc type.";
  }

  typedef ncs_template_detect-interval {
    type string;
    description
      "Detect interval.";
  }

  typedef ncs_template_defect-status-type {
    type string;
    description
      "Defect status type.";
  }

  typedef ncs_template_defect-type {
    type string;
    description
      "Defect type.";
  }

  typedef ncs_template_padding-value {
    type string;
    description
      "Delay measurement padding value.";
  }

  typedef ncs_template_active-type {
    type string;
    description
      "Active type.";
  }

  typedef ncs_template_bdi-frequency {
    type string;
    description
      "Bdi frequency.";
  }

  typedef ncs_template_compatibility-mode {
    type string;
    description
      "Compatibility mode.";
  }

  typedef ncs_template_reverse-mode {
    type string;
    description
      "Reverse mode.";
  }

  typedef ncs_template_defect-state {
    type string;
    description
      "Defect state.";
  }

  typedef ncs_template_available-state {
    type string;
    description
      "Available state.";
  }

  typedef ncs_template_lsp-type {
    type string;
    description
      "LSP type.";
  }

  typedef ncs_template_lsp-establish-type {
    type string;
    description
      "LSP establish type.";
  }

  typedef ncs_rpc_notif_detect-pkt-type {
    type enumeration {
      enum "cv" {
        value 0;
        description
          "The detection packet type is cv.";
      }
      enum "ffd" {
        value 1;
        description
          "The detection packet type is ffd.";
      }
    }
    description
      "Detect pkt type.";
  }

  typedef ncs_rpc_notif_detect-mode {
    type enumeration {
      enum "manual" {
        value 0;
        description
          "The detection mode is manual.";
      }
      enum "auto" {
        value 1;
        description
          "The detection mode is adaptive.";
      }
    }
    description
      "Detect type.";
  }

  typedef ncs_rpc_notif_l2vc-type {
    type enumeration {
      enum "atm-1to1-vcc" {
        value 0;
        description
          "The VC type is ATM-1to1-VCC.";
      }
      enum "atm-1to1-vpc" {
        value 1;
        description
          "The VC type is ATM-1to1-VPC.";
      }
      enum "atm-aal5-pdu" {
        value 2;
        description
          "The VC type is atm-aal5-pdu.";
      }
      enum "atm-aal5-sdu" {
        value 3;
        description
          "The VC type is atm-aal5-sdu.";
      }
      enum "atm-nto1-vcc" {
        value 4;
        description
          "The VC type is ATM-nto1-VCC.";
      }
      enum "atm-nto1-vpc" {
        value 5;
        description
          "The VC type is ATM-nto1-VPC.";
      }
      enum "atm-trans-cell" {
        value 6;
        description
          "The VC type is atm-trans-cell.";
      }
      enum "cep" {
        value 7;
        description
          "The VC type is CEP.";
      }
      enum "cesopsn-basic" {
        value 8;
        description
          "The VC type is CESoPSN-basic.";
      }
      enum "ethernet" {
        value 9;
        description
          "The VC type is Ethernet.";
      }
      enum "fr" {
        value 10;
        description
          "The VC type e is FR.";
      }
      enum "hdlc" {
        value 11;
        description
          "The VC type is HDLC.";
      }
      enum "ip-interworking" {
        value 12;
        description
          "The VC type is IP-interworking.";
      }
      enum "ip-layer2" {
        value 13;
        description
          "The VC type is IP-Layer 2.";
      }
      enum "ppp" {
        value 14;
        description
          "The VC type is PPP.";
      }
      enum "satop-e1" {
        value 15;
        description
          "The VC type is SAToP-E1.";
      }
      enum "satop-e3" {
        value 16;
        description
          "The VC type is SAToP-E3.";
      }
      enum "satop-t1" {
        value 17;
        description
          "The VC type is SAToP-T1.";
      }
      enum "vlan" {
        value 18;
        description
          "The VC type is VLAN.";
      }
    }
    description
      "L2vc type.";
  }

  typedef ncs_rpc_notif_detect-interval {
    type enumeration {
      enum "3ms" {
        value 0;
        description
          "Interval value of 3ms.";
      }
      enum "10ms" {
        value 1;
        description
          "Interval value of 10ms.";
      }
      enum "20ms" {
        value 2;
        description
          "Interval value of 20ms.";
      }
      enum "50ms" {
        value 3;
        description
          "Interval value of 50ms.";
      }
      enum "100ms" {
        value 4;
        description
          "Interval value of 100ms.";
      }
      enum "200ms" {
        value 5;
        description
          "Interval value of 200ms.";
      }
      enum "500ms" {
        value 6;
        description
          "Interval value of 500ms.";
      }
      enum "1000ms" {
        value 7;
        description
          "Interval value of 1000ms.";
      }
    }
    description
      "Detect interval.";
  }

  typedef ncs_rpc_notif_defect-status-type {
    type enumeration {
      enum "init" {
        value 0;
        description
          "The status of MPLS OAM is initial.";
      }
      enum "local-valid" {
        value 1;
        description
          "Local valid.";
      }
      enum "local-defect-valid" {
        value 2;
        description
          "Local defect valid.";
      }
      enum "local-defect-invalid" {
        value 3;
        description
          "Local defect invalid.";
      }
      enum "local-invalid" {
        value 4;
        description
          "Local invalid.";
      }
      enum "remote-valid" {
        value 5;
        description
          "Remote valid.";
      }
      enum "remote-defect-valid" {
        value 6;
        description
          "Remote defect valid.";
      }
      enum "remote-defect-invalid" {
        value 7;
        description
          "Remote defect invalid.";
      }
      enum "remote-invalid" {
        value 8;
        description
          "Remote invalid.";
      }
    }
    description
      "Defect status type.";
  }

  typedef ncs_rpc_notif_defect-type {
    type enumeration {
      enum "server" {
        value 0;
        description
          "The defect type is server.";
      }
      enum "peer-me" {
        value 1;
        description
          "The defect type is peerme.";
      }
      enum "locv" {
        value 2;
        description
          "The defect type is locv.";
      }
      enum "ttsi-mismatch" {
        value 3;
        description
          "The defect type is ttsi-mismatch.";
      }
      enum "ttsi-mismerge" {
        value 4;
        description
          "The defect type is ttsi-mismerge.";
      }
      enum "excess" {
        value 5;
        description
          "The defect type is excess.";
      }
      enum "unknown" {
        value 6;
        description
          "The defect type is unknown.";
      }
    }
    description
      "Defect type.";
  }

  typedef ncs_rpc_notif_padding-value {
    type enumeration {
      enum "0" {
        value 0;
        description
          "The padding value of delay measurement packet is 0.";
      }
      enum "1" {
        value 1;
        description
          "The padding value of delay measurement packet is 1.";
      }
    }
    description
      "Delay measurement padding value.";
  }

  typedef ncs_rpc_notif_active-type {
    type enumeration {
      enum "deactive" {
        value 0;
        description
          "Deactive the MPLS OAM.";
      }
      enum "active" {
        value 1;
        description
          "Active the MPLS OAM.";
      }
    }
    description
      "Active type.";
  }

  typedef ncs_rpc_notif_bdi-frequency {
    type enumeration {
      enum "per-second" {
        value 0;
        description
          "BDI frequency is per second.";
      }
      enum "detect-freq" {
        value 1;
        description
          "BDI frequency is detect-frequency.";
      }
    }
    description
      "Bdi frequency.";
  }

  typedef ncs_rpc_notif_compatibility-mode {
    type enumeration {
      enum "route-mode" {
        value 0;
        description
          "Compatibility mode is route mode.";
      }
      enum "ptn-mode" {
        value 1;
        description
          "Compatibility mode is PTN mode.";
      }
    }
    description
      "Compatibility mode.";
  }

  typedef ncs_rpc_notif_reverse-mode {
    type enumeration {
      enum "share" {
        value 0;
        description
          "The share Type is share.";
      }
      enum "private" {
        value 1;
        description
          "The share Type is private.";
      }
    }
    description
      "Reverse mode.";
  }

  typedef ncs_rpc_notif_defect-state {
    type enumeration {
      enum "non-defect" {
        value 0;
        description
          "The Defect State is non-defect.";
      }
      enum "in-defect" {
        value 1;
        description
          "The Defect State is in-defect.";
      }
    }
    description
      "Defect state.";
  }

  typedef ncs_rpc_notif_available-state {
    type enumeration {
      enum "available" {
        value 0;
        description
          "Available State.";
      }
      enum "unavailable" {
        value 1;
        description
          "Unavailable State.";
      }
    }
    description
      "Available state.";
  }

  typedef ncs_rpc_notif_lsp-type {
    type enumeration {
      enum "ingress" {
        value 0;
        description
          "The Service Type is ingress.";
      }
      enum "egress-lspname" {
        value 1;
        description
          "The Service Type is egress which Bind LSP Name.";
      }
      enum "egress-ttsi" {
        value 2;
        description
          "The Service Type is egress which Bind TTSI.";
      }
      enum "te-crlsp" {
        value 3;
        description
          "The Service Type is TE.";
      }
    }
    description
      "LSP type.";
  }

  typedef ncs_rpc_notif_lsp-establish-type {
    type enumeration {
      enum "rsvp-lsp" {
        value 0;
        description
          "RSVP LSP.";
      }
      enum "static-cr-lsp" {
        value 1;
        description
          "Static CR-LSP.";
      }
    }
    description
      "LSP establish type.";
  }

  typedef live_ncs_detect-pkt-type {
    type enumeration {
      enum "cv" {
        value 0;
        description
          "The detection packet type is cv.";
      }
      enum "ffd" {
        value 1;
        description
          "The detection packet type is ffd.";
      }
    }
    description
      "Detect pkt type.";
  }

  typedef live_ncs_detect-mode {
    type enumeration {
      enum "manual" {
        value 0;
        description
          "The detection mode is manual.";
      }
      enum "auto" {
        value 1;
        description
          "The detection mode is adaptive.";
      }
    }
    description
      "Detect type.";
  }

  typedef live_ncs_l2vc-type {
    type enumeration {
      enum "atm-1to1-vcc" {
        value 0;
        description
          "The VC type is ATM-1to1-VCC.";
      }
      enum "atm-1to1-vpc" {
        value 1;
        description
          "The VC type is ATM-1to1-VPC.";
      }
      enum "atm-aal5-pdu" {
        value 2;
        description
          "The VC type is atm-aal5-pdu.";
      }
      enum "atm-aal5-sdu" {
        value 3;
        description
          "The VC type is atm-aal5-sdu.";
      }
      enum "atm-nto1-vcc" {
        value 4;
        description
          "The VC type is ATM-nto1-VCC.";
      }
      enum "atm-nto1-vpc" {
        value 5;
        description
          "The VC type is ATM-nto1-VPC.";
      }
      enum "atm-trans-cell" {
        value 6;
        description
          "The VC type is atm-trans-cell.";
      }
      enum "cep" {
        value 7;
        description
          "The VC type is CEP.";
      }
      enum "cesopsn-basic" {
        value 8;
        description
          "The VC type is CESoPSN-basic.";
      }
      enum "ethernet" {
        value 9;
        description
          "The VC type is Ethernet.";
      }
      enum "fr" {
        value 10;
        description
          "The VC type e is FR.";
      }
      enum "hdlc" {
        value 11;
        description
          "The VC type is HDLC.";
      }
      enum "ip-interworking" {
        value 12;
        description
          "The VC type is IP-interworking.";
      }
      enum "ip-layer2" {
        value 13;
        description
          "The VC type is IP-Layer 2.";
      }
      enum "ppp" {
        value 14;
        description
          "The VC type is PPP.";
      }
      enum "satop-e1" {
        value 15;
        description
          "The VC type is SAToP-E1.";
      }
      enum "satop-e3" {
        value 16;
        description
          "The VC type is SAToP-E3.";
      }
      enum "satop-t1" {
        value 17;
        description
          "The VC type is SAToP-T1.";
      }
      enum "vlan" {
        value 18;
        description
          "The VC type is VLAN.";
      }
    }
    description
      "L2vc type.";
  }

  typedef live_ncs_detect-interval {
    type enumeration {
      enum "3ms" {
        value 0;
        description
          "Interval value of 3ms.";
      }
      enum "10ms" {
        value 1;
        description
          "Interval value of 10ms.";
      }
      enum "20ms" {
        value 2;
        description
          "Interval value of 20ms.";
      }
      enum "50ms" {
        value 3;
        description
          "Interval value of 50ms.";
      }
      enum "100ms" {
        value 4;
        description
          "Interval value of 100ms.";
      }
      enum "200ms" {
        value 5;
        description
          "Interval value of 200ms.";
      }
      enum "500ms" {
        value 6;
        description
          "Interval value of 500ms.";
      }
      enum "1000ms" {
        value 7;
        description
          "Interval value of 1000ms.";
      }
    }
    description
      "Detect interval.";
  }

  typedef live_ncs_defect-status-type {
    type enumeration {
      enum "init" {
        value 0;
        description
          "The status of MPLS OAM is initial.";
      }
      enum "local-valid" {
        value 1;
        description
          "Local valid.";
      }
      enum "local-defect-valid" {
        value 2;
        description
          "Local defect valid.";
      }
      enum "local-defect-invalid" {
        value 3;
        description
          "Local defect invalid.";
      }
      enum "local-invalid" {
        value 4;
        description
          "Local invalid.";
      }
      enum "remote-valid" {
        value 5;
        description
          "Remote valid.";
      }
      enum "remote-defect-valid" {
        value 6;
        description
          "Remote defect valid.";
      }
      enum "remote-defect-invalid" {
        value 7;
        description
          "Remote defect invalid.";
      }
      enum "remote-invalid" {
        value 8;
        description
          "Remote invalid.";
      }
    }
    description
      "Defect status type.";
  }

  typedef live_ncs_defect-type {
    type enumeration {
      enum "server" {
        value 0;
        description
          "The defect type is server.";
      }
      enum "peer-me" {
        value 1;
        description
          "The defect type is peerme.";
      }
      enum "locv" {
        value 2;
        description
          "The defect type is locv.";
      }
      enum "ttsi-mismatch" {
        value 3;
        description
          "The defect type is ttsi-mismatch.";
      }
      enum "ttsi-mismerge" {
        value 4;
        description
          "The defect type is ttsi-mismerge.";
      }
      enum "excess" {
        value 5;
        description
          "The defect type is excess.";
      }
      enum "unknown" {
        value 6;
        description
          "The defect type is unknown.";
      }
    }
    description
      "Defect type.";
  }

  typedef live_ncs_padding-value {
    type enumeration {
      enum "0" {
        value 0;
        description
          "The padding value of delay measurement packet is 0.";
      }
      enum "1" {
        value 1;
        description
          "The padding value of delay measurement packet is 1.";
      }
    }
    description
      "Delay measurement padding value.";
  }

  typedef live_ncs_active-type {
    type enumeration {
      enum "deactive" {
        value 0;
        description
          "Deactive the MPLS OAM.";
      }
      enum "active" {
        value 1;
        description
          "Active the MPLS OAM.";
      }
    }
    description
      "Active type.";
  }

  typedef live_ncs_bdi-frequency {
    type enumeration {
      enum "per-second" {
        value 0;
        description
          "BDI frequency is per second.";
      }
      enum "detect-freq" {
        value 1;
        description
          "BDI frequency is detect-frequency.";
      }
    }
    description
      "Bdi frequency.";
  }

  typedef live_ncs_compatibility-mode {
    type enumeration {
      enum "route-mode" {
        value 0;
        description
          "Compatibility mode is route mode.";
      }
      enum "ptn-mode" {
        value 1;
        description
          "Compatibility mode is PTN mode.";
      }
    }
    description
      "Compatibility mode.";
  }

  typedef live_ncs_reverse-mode {
    type enumeration {
      enum "share" {
        value 0;
        description
          "The share Type is share.";
      }
      enum "private" {
        value 1;
        description
          "The share Type is private.";
      }
    }
    description
      "Reverse mode.";
  }

  typedef live_ncs_defect-state {
    type enumeration {
      enum "non-defect" {
        value 0;
        description
          "The Defect State is non-defect.";
      }
      enum "in-defect" {
        value 1;
        description
          "The Defect State is in-defect.";
      }
    }
    description
      "Defect state.";
  }

  typedef live_ncs_available-state {
    type enumeration {
      enum "available" {
        value 0;
        description
          "Available State.";
      }
      enum "unavailable" {
        value 1;
        description
          "Unavailable State.";
      }
    }
    description
      "Available state.";
  }

  typedef live_ncs_lsp-type {
    type enumeration {
      enum "ingress" {
        value 0;
        description
          "The Service Type is ingress.";
      }
      enum "egress-lspname" {
        value 1;
        description
          "The Service Type is egress which Bind LSP Name.";
      }
      enum "egress-ttsi" {
        value 2;
        description
          "The Service Type is egress which Bind TTSI.";
      }
      enum "te-crlsp" {
        value 3;
        description
          "The Service Type is TE.";
      }
    }
    description
      "LSP type.";
  }

  typedef live_ncs_lsp-establish-type {
    type enumeration {
      enum "rsvp-lsp" {
        value 0;
        description
          "RSVP LSP.";
      }
      enum "static-cr-lsp" {
        value 1;
        description
          "Static CR-LSP.";
      }
    }
    description
      "LSP establish type.";
  }

  typedef detect-pkt-type {
    type enumeration {
      enum "cv" {
        value 0;
        description
          "The detection packet type is cv.";
      }
      enum "ffd" {
        value 1;
        description
          "The detection packet type is ffd.";
      }
    }
    description
      "Detect pkt type.";
  }

  typedef detect-mode {
    type enumeration {
      enum "manual" {
        value 0;
        description
          "The detection mode is manual.";
      }
      enum "auto" {
        value 1;
        description
          "The detection mode is adaptive.";
      }
    }
    description
      "Detect type.";
  }

  typedef l2vc-type {
    type enumeration {
      enum "atm-1to1-vcc" {
        value 0;
        description
          "The VC type is ATM-1to1-VCC.";
      }
      enum "atm-1to1-vpc" {
        value 1;
        description
          "The VC type is ATM-1to1-VPC.";
      }
      enum "atm-aal5-pdu" {
        value 2;
        description
          "The VC type is atm-aal5-pdu.";
      }
      enum "atm-aal5-sdu" {
        value 3;
        description
          "The VC type is atm-aal5-sdu.";
      }
      enum "atm-nto1-vcc" {
        value 4;
        description
          "The VC type is ATM-nto1-VCC.";
      }
      enum "atm-nto1-vpc" {
        value 5;
        description
          "The VC type is ATM-nto1-VPC.";
      }
      enum "atm-trans-cell" {
        value 6;
        description
          "The VC type is atm-trans-cell.";
      }
      enum "cep" {
        value 7;
        description
          "The VC type is CEP.";
      }
      enum "cesopsn-basic" {
        value 8;
        description
          "The VC type is CESoPSN-basic.";
      }
      enum "ethernet" {
        value 9;
        description
          "The VC type is Ethernet.";
      }
      enum "fr" {
        value 10;
        description
          "The VC type e is FR.";
      }
      enum "hdlc" {
        value 11;
        description
          "The VC type is HDLC.";
      }
      enum "ip-interworking" {
        value 12;
        description
          "The VC type is IP-interworking.";
      }
      enum "ip-layer2" {
        value 13;
        description
          "The VC type is IP-Layer 2.";
      }
      enum "ppp" {
        value 14;
        description
          "The VC type is PPP.";
      }
      enum "satop-e1" {
        value 15;
        description
          "The VC type is SAToP-E1.";
      }
      enum "satop-e3" {
        value 16;
        description
          "The VC type is SAToP-E3.";
      }
      enum "satop-t1" {
        value 17;
        description
          "The VC type is SAToP-T1.";
      }
      enum "vlan" {
        value 18;
        description
          "The VC type is VLAN.";
      }
    }
    description
      "L2vc type.";
  }

  typedef detect-interval {
    type enumeration {
      enum "3ms" {
        value 0;
        description
          "Interval value of 3ms.";
      }
      enum "10ms" {
        value 1;
        description
          "Interval value of 10ms.";
      }
      enum "20ms" {
        value 2;
        description
          "Interval value of 20ms.";
      }
      enum "50ms" {
        value 3;
        description
          "Interval value of 50ms.";
      }
      enum "100ms" {
        value 4;
        description
          "Interval value of 100ms.";
      }
      enum "200ms" {
        value 5;
        description
          "Interval value of 200ms.";
      }
      enum "500ms" {
        value 6;
        description
          "Interval value of 500ms.";
      }
      enum "1000ms" {
        value 7;
        description
          "Interval value of 1000ms.";
      }
    }
    description
      "Detect interval.";
  }

  typedef defect-status-type {
    type enumeration {
      enum "init" {
        value 0;
        description
          "The status of MPLS OAM is initial.";
      }
      enum "local-valid" {
        value 1;
        description
          "Local valid.";
      }
      enum "local-defect-valid" {
        value 2;
        description
          "Local defect valid.";
      }
      enum "local-defect-invalid" {
        value 3;
        description
          "Local defect invalid.";
      }
      enum "local-invalid" {
        value 4;
        description
          "Local invalid.";
      }
      enum "remote-valid" {
        value 5;
        description
          "Remote valid.";
      }
      enum "remote-defect-valid" {
        value 6;
        description
          "Remote defect valid.";
      }
      enum "remote-defect-invalid" {
        value 7;
        description
          "Remote defect invalid.";
      }
      enum "remote-invalid" {
        value 8;
        description
          "Remote invalid.";
      }
    }
    description
      "Defect status type.";
  }

  typedef defect-type {
    type enumeration {
      enum "server" {
        value 0;
        description
          "The defect type is server.";
      }
      enum "peer-me" {
        value 1;
        description
          "The defect type is peerme.";
      }
      enum "locv" {
        value 2;
        description
          "The defect type is locv.";
      }
      enum "ttsi-mismatch" {
        value 3;
        description
          "The defect type is ttsi-mismatch.";
      }
      enum "ttsi-mismerge" {
        value 4;
        description
          "The defect type is ttsi-mismerge.";
      }
      enum "excess" {
        value 5;
        description
          "The defect type is excess.";
      }
      enum "unknown" {
        value 6;
        description
          "The defect type is unknown.";
      }
    }
    description
      "Defect type.";
  }

  typedef padding-value {
    type enumeration {
      enum "0" {
        value 0;
        description
          "The padding value of delay measurement packet is 0.";
      }
      enum "1" {
        value 1;
        description
          "The padding value of delay measurement packet is 1.";
      }
    }
    description
      "Delay measurement padding value.";
  }

  typedef active-type {
    type enumeration {
      enum "deactive" {
        value 0;
        description
          "Deactive the MPLS OAM.";
      }
      enum "active" {
        value 1;
        description
          "Active the MPLS OAM.";
      }
    }
    description
      "Active type.";
  }

  typedef bdi-frequency {
    type enumeration {
      enum "per-second" {
        value 0;
        description
          "BDI frequency is per second.";
      }
      enum "detect-freq" {
        value 1;
        description
          "BDI frequency is detect-frequency.";
      }
    }
    description
      "Bdi frequency.";
  }

  typedef compatibility-mode {
    type enumeration {
      enum "route-mode" {
        value 0;
        description
          "Compatibility mode is route mode.";
      }
      enum "ptn-mode" {
        value 1;
        description
          "Compatibility mode is PTN mode.";
      }
    }
    description
      "Compatibility mode.";
  }

  typedef reverse-mode {
    type enumeration {
      enum "share" {
        value 0;
        description
          "The share Type is share.";
      }
      enum "private" {
        value 1;
        description
          "The share Type is private.";
      }
    }
    description
      "Reverse mode.";
  }

  typedef defect-state {
    type enumeration {
      enum "non-defect" {
        value 0;
        description
          "The Defect State is non-defect.";
      }
      enum "in-defect" {
        value 1;
        description
          "The Defect State is in-defect.";
      }
    }
    description
      "Defect state.";
  }

  typedef available-state {
    type enumeration {
      enum "available" {
        value 0;
        description
          "Available State.";
      }
      enum "unavailable" {
        value 1;
        description
          "Unavailable State.";
      }
    }
    description
      "Available state.";
  }

  typedef lsp-type {
    type enumeration {
      enum "ingress" {
        value 0;
        description
          "The Service Type is ingress.";
      }
      enum "egress-lspname" {
        value 1;
        description
          "The Service Type is egress which Bind LSP Name.";
      }
      enum "egress-ttsi" {
        value 2;
        description
          "The Service Type is egress which Bind TTSI.";
      }
      enum "te-crlsp" {
        value 3;
        description
          "The Service Type is TE.";
      }
    }
    description
      "LSP type.";
  }

  typedef lsp-establish-type {
    type enumeration {
      enum "rsvp-lsp" {
        value 0;
        description
          "RSVP LSP.";
      }
      enum "static-cr-lsp" {
        value 1;
        description
          "Static CR-LSP.";
      }
    }
    description
      "LSP establish type.";
  }

  grouping ncs_template_session-status {
    // NCS drop config false leaf 'bdi-defect-status'
    // NCS drop config false leaf 'bdi-defect-type'
    // NCS drop config false leaf 'available-status'
    // NCS drop config false leaf 'defect-type'
    // NCS drop config false leaf 'local-detect-status'
    // NCS drop config false leaf 'local-invalid-time'
    // NCS drop config false leaf 'local-defect-location'
    // NCS drop config false leaf 'local-defect-type'
    // NCS drop config false leaf 'remote-detect-status'
    // NCS drop config false leaf 'remote-invalid-time'
    // NCS drop config false leaf 'remote-defect-location'
    // NCS drop config false leaf 'remote-defect-type'
    description
      "Session status.";
  }

  grouping ncs_rpc_notif_session-status {
    leaf bdi-defect-status {
      type ncs_rpc_notif_defect-state;
      config false;
      description
        "BDI Defect Status.";
    }
    leaf bdi-defect-type {
      type ncs_rpc_notif_defect-type;
      config false;
      description
        "BDI Defect Type.";
    }
    leaf available-status {
      type ncs_rpc_notif_available-state;
      config false;
      description
        "Available Status.";
    }
    leaf defect-type {
      type ncs_rpc_notif_defect-type;
      config false;
      description
        "Defect Type.";
    }
    leaf local-detect-status {
      type ncs_rpc_notif_defect-status-type;
      default "init";
      config false;
      description
        "Local detection status.";
    }
    leaf local-invalid-time {
      type uint32 {
        range "0..4294967294";
      }
      config false;
      description
        "Local invalid time.";
    }
    leaf local-defect-location {
      type inet:ipv4-address-no-zone;
      config false;
      description
        "Local defect status.";
    }
    leaf local-defect-type {
      type ncs_rpc_notif_defect-type;
      config false;
      description
        "Local defect type.";
    }
    leaf remote-detect-status {
      type ncs_rpc_notif_defect-status-type;
      default "init";
      config false;
      description
        "Remote detection status.";
    }
    leaf remote-invalid-time {
      type uint32 {
        range "0..4294967294";
      }
      config false;
      description
        "Remote invalid time.";
    }
    leaf remote-defect-location {
      type inet:ipv4-address-no-zone;
      config false;
      description
        "Remote defect status.";
    }
    leaf remote-defect-type {
      type ncs_rpc_notif_defect-type;
      config false;
      description
        "Remote defect type.";
    }
    description
      "Session status.";
  }

  grouping live_ncs_session-status {
    leaf bdi-defect-status {
      type live_ncs_defect-state;
      description
        "BDI Defect Status.";
    }
    leaf bdi-defect-type {
      type live_ncs_defect-type;
      description
        "BDI Defect Type.";
    }
    leaf available-status {
      type live_ncs_available-state;
      description
        "Available Status.";
    }
    leaf defect-type {
      type live_ncs_defect-type;
      description
        "Defect Type.";
    }
    leaf local-detect-status {
      type live_ncs_defect-status-type;
      // NCS drop default statement
      description
        "Local detection status.";
    }
    leaf local-invalid-time {
      type uint32 {
        range "0..4294967294";
      }
      description
        "Local invalid time.";
    }
    leaf local-defect-location {
      type inet:ipv4-address-no-zone;
      description
        "Local defect status.";
    }
    leaf local-defect-type {
      type live_ncs_defect-type;
      description
        "Local defect type.";
    }
    leaf remote-detect-status {
      type live_ncs_defect-status-type;
      // NCS drop default statement
      description
        "Remote detection status.";
    }
    leaf remote-invalid-time {
      type uint32 {
        range "0..4294967294";
      }
      description
        "Remote invalid time.";
    }
    leaf remote-defect-location {
      type inet:ipv4-address-no-zone;
      description
        "Remote defect status.";
    }
    leaf remote-defect-type {
      type live_ncs_defect-type;
      description
        "Remote defect type.";
    }
    description
      "Session status.";
  }

  grouping session-status {
    // NCS drop config false leaf 'bdi-defect-status'
    // NCS drop config false leaf 'bdi-defect-type'
    // NCS drop config false leaf 'available-status'
    // NCS drop config false leaf 'defect-type'
    // NCS drop config false leaf 'local-detect-status'
    // NCS drop config false leaf 'local-invalid-time'
    // NCS drop config false leaf 'local-defect-location'
    // NCS drop config false leaf 'local-defect-type'
    // NCS drop config false leaf 'remote-detect-status'
    // NCS drop config false leaf 'remote-invalid-time'
    // NCS drop config false leaf 'remote-defect-location'
    // NCS drop config false leaf 'remote-defect-type'
    description
      "Session status.";
  }

  augment "/ncs:devices/ncs:device/ncs:rpc" {
    container rpc-disable-co-route-tunnel-lsp {
      tailf:ncs-device-type "netconf";
      tailf:display-when "not(../../ncs:module) or ../../ncs:module[ncs:name='huawei-mplsoam']";
      tailf:action disable-co-route-tunnel-lsp {
        tailf:actionpoint ncsproxy {
          tailf:internal;
        }
        description
          "Stop connectivity verification (cv) or fast failure detection (ffd).";
        ext:node-ref "/mplsoam/tunnels/co-route-tunnels";
        input {
          leaf tunnel-name {
            type string;
            description
              "Tunnel Name.";
          }
        }
      }
    }
  }
  augment "/ncs:devices/ncs:device-group/ncs:ned-id/ncs:rpc" {
    container rpc-disable-co-route-tunnel-lsp {
      tailf:ncs-device-type "netconf";
      tailf:display-when "/ncs:devices/ncs:device[ncs:name=current()/../../../ncs:member]/ncs:module[ncs:name='huawei-mplsoam']";
      tailf:action disable-co-route-tunnel-lsp {
        tailf:actionpoint ncsproxy {
          tailf:internal;
        }
        description
          "Stop connectivity verification (cv) or fast failure detection (ffd).";
        ext:node-ref "/mplsoam/tunnels/co-route-tunnels";
        input {
          leaf tunnel-name {
            type string;
            description
              "Tunnel Name.";
          }
        }
      }
    }
  }
  augment "/ncs:devices/ncs:device/ncs:rpc" {
    container rpc-enable-co-route-tunnel-lsp {
      tailf:ncs-device-type "netconf";
      tailf:display-when "not(../../ncs:module) or ../../ncs:module[ncs:name='huawei-mplsoam']";
      tailf:action enable-co-route-tunnel-lsp {
        tailf:actionpoint ncsproxy {
          tailf:internal;
        }
        description
          "Start connectivity verification (cv) or fast failure detection (ffd).";
        ext:node-ref "/mplsoam/tunnels/co-route-tunnels";
        input {
          leaf tunnel-name {
            type string;
            description
              "Tunnel Name.";
          }
        }
      }
    }
  }
  augment "/ncs:devices/ncs:device-group/ncs:ned-id/ncs:rpc" {
    container rpc-enable-co-route-tunnel-lsp {
      tailf:ncs-device-type "netconf";
      tailf:display-when "/ncs:devices/ncs:device[ncs:name=current()/../../../ncs:member]/ncs:module[ncs:name='huawei-mplsoam']";
      tailf:action enable-co-route-tunnel-lsp {
        tailf:actionpoint ncsproxy {
          tailf:internal;
        }
        description
          "Start connectivity verification (cv) or fast failure detection (ffd).";
        ext:node-ref "/mplsoam/tunnels/co-route-tunnels";
        input {
          leaf tunnel-name {
            type string;
            description
              "Tunnel Name.";
          }
        }
      }
    }
  }
  augment "/ncs:devices/ncs:device/ncs:rpc" {
    container rpc-disable-ingress-tunnel-lsp {
      tailf:ncs-device-type "netconf";
      tailf:display-when "not(../../ncs:module) or ../../ncs:module[ncs:name='huawei-mplsoam']";
      tailf:action disable-ingress-tunnel-lsp {
        tailf:actionpoint ncsproxy {
          tailf:internal;
        }
        description
          "Stop connectivity verification (cv) or fast failure detection (ffd).";
        ext:node-ref "/mplsoam/tunnels/ingress-tunnels";
        input {
          leaf tunnel-name {
            type string;
            description
              "Tunnel Name.";
          }
        }
      }
    }
  }
  augment "/ncs:devices/ncs:device-group/ncs:ned-id/ncs:rpc" {
    container rpc-disable-ingress-tunnel-lsp {
      tailf:ncs-device-type "netconf";
      tailf:display-when "/ncs:devices/ncs:device[ncs:name=current()/../../../ncs:member]/ncs:module[ncs:name='huawei-mplsoam']";
      tailf:action disable-ingress-tunnel-lsp {
        tailf:actionpoint ncsproxy {
          tailf:internal;
        }
        description
          "Stop connectivity verification (cv) or fast failure detection (ffd).";
        ext:node-ref "/mplsoam/tunnels/ingress-tunnels";
        input {
          leaf tunnel-name {
            type string;
            description
              "Tunnel Name.";
          }
        }
      }
    }
  }
  augment "/ncs:devices/ncs:device/ncs:rpc" {
    container rpc-enable-ingress-tunnel-lsp {
      tailf:ncs-device-type "netconf";
      tailf:display-when "not(../../ncs:module) or ../../ncs:module[ncs:name='huawei-mplsoam']";
      tailf:action enable-ingress-tunnel-lsp {
        tailf:actionpoint ncsproxy {
          tailf:internal;
        }
        description
          "Start connectivity verification (cv) or fast failure detection (ffd).";
        ext:node-ref "/mplsoam/tunnels/ingress-tunnels";
        input {
          leaf tunnel-name {
            type string;
            description
              "Tunnel Name.";
          }
        }
      }
    }
  }
  augment "/ncs:devices/ncs:device-group/ncs:ned-id/ncs:rpc" {
    container rpc-enable-ingress-tunnel-lsp {
      tailf:ncs-device-type "netconf";
      tailf:display-when "/ncs:devices/ncs:device[ncs:name=current()/../../../ncs:member]/ncs:module[ncs:name='huawei-mplsoam']";
      tailf:action enable-ingress-tunnel-lsp {
        tailf:actionpoint ncsproxy {
          tailf:internal;
        }
        description
          "Start connectivity verification (cv) or fast failure detection (ffd).";
        ext:node-ref "/mplsoam/tunnels/ingress-tunnels";
        input {
          leaf tunnel-name {
            type string;
            description
              "Tunnel Name.";
          }
        }
      }
    }
  }
  augment "/ncs:devices/ncs:device/ncs:rpc" {
    container rpc-disable-egress-name-tunnel-lsp {
      tailf:ncs-device-type "netconf";
      tailf:display-when "not(../../ncs:module) or ../../ncs:module[ncs:name='huawei-mplsoam']";
      tailf:action disable-egress-name-tunnel-lsp {
        tailf:actionpoint ncsproxy {
          tailf:internal;
        }
        description
          "Stop connectivity verification (cv) or fast failure detection (ffd).";
        ext:node-ref "/mplsoam/tunnels/egress-name-tunnels";
        input {
          leaf tunnel-name {
            type string;
            description
              "Tunnel Name.";
          }
        }
      }
    }
  }
  augment "/ncs:devices/ncs:device-group/ncs:ned-id/ncs:rpc" {
    container rpc-disable-egress-name-tunnel-lsp {
      tailf:ncs-device-type "netconf";
      tailf:display-when "/ncs:devices/ncs:device[ncs:name=current()/../../../ncs:member]/ncs:module[ncs:name='huawei-mplsoam']";
      tailf:action disable-egress-name-tunnel-lsp {
        tailf:actionpoint ncsproxy {
          tailf:internal;
        }
        description
          "Stop connectivity verification (cv) or fast failure detection (ffd).";
        ext:node-ref "/mplsoam/tunnels/egress-name-tunnels";
        input {
          leaf tunnel-name {
            type string;
            description
              "Tunnel Name.";
          }
        }
      }
    }
  }
  augment "/ncs:devices/ncs:device/ncs:rpc" {
    container rpc-enable-egress-name-tunnel-lsp {
      tailf:ncs-device-type "netconf";
      tailf:display-when "not(../../ncs:module) or ../../ncs:module[ncs:name='huawei-mplsoam']";
      tailf:action enable-egress-name-tunnel-lsp {
        tailf:actionpoint ncsproxy {
          tailf:internal;
        }
        description
          "Start connectivity verification (cv) or fast failure detection (ffd).";
        ext:node-ref "/mplsoam/tunnels/egress-name-tunnels";
        input {
          leaf tunnel-name {
            type string;
            description
              "Tunnel Name.";
          }
        }
      }
    }
  }
  augment "/ncs:devices/ncs:device-group/ncs:ned-id/ncs:rpc" {
    container rpc-enable-egress-name-tunnel-lsp {
      tailf:ncs-device-type "netconf";
      tailf:display-when "/ncs:devices/ncs:device[ncs:name=current()/../../../ncs:member]/ncs:module[ncs:name='huawei-mplsoam']";
      tailf:action enable-egress-name-tunnel-lsp {
        tailf:actionpoint ncsproxy {
          tailf:internal;
        }
        description
          "Start connectivity verification (cv) or fast failure detection (ffd).";
        ext:node-ref "/mplsoam/tunnels/egress-name-tunnels";
        input {
          leaf tunnel-name {
            type string;
            description
              "Tunnel Name.";
          }
        }
      }
    }
  }
  augment "/ncs:devices/ncs:device/ncs:rpc" {
    container rpc-disable-egress-id-tunnel-lsp {
      tailf:ncs-device-type "netconf";
      tailf:display-when "not(../../ncs:module) or ../../ncs:module[ncs:name='huawei-mplsoam']";
      tailf:action disable-egress-id-tunnel-lsp {
        tailf:actionpoint ncsproxy {
          tailf:internal;
        }
        description
          "Stop connectivity verification (cv) or fast failure detection (ffd).";
        ext:node-ref "/mplsoam/tunnels/egress-id-tunnels";
        input {
          leaf tunnel-id {
            type string;
            description
              "Configure the ID of tunnel.";
          }
          leaf ingress-lsr-id {
            type string;
            description
              "Configure the LSR ID.";
          }
        }
      }
    }
  }
  augment "/ncs:devices/ncs:device-group/ncs:ned-id/ncs:rpc" {
    container rpc-disable-egress-id-tunnel-lsp {
      tailf:ncs-device-type "netconf";
      tailf:display-when "/ncs:devices/ncs:device[ncs:name=current()/../../../ncs:member]/ncs:module[ncs:name='huawei-mplsoam']";
      tailf:action disable-egress-id-tunnel-lsp {
        tailf:actionpoint ncsproxy {
          tailf:internal;
        }
        description
          "Stop connectivity verification (cv) or fast failure detection (ffd).";
        ext:node-ref "/mplsoam/tunnels/egress-id-tunnels";
        input {
          leaf tunnel-id {
            type string;
            description
              "Configure the ID of tunnel.";
          }
          leaf ingress-lsr-id {
            type string;
            description
              "Configure the LSR ID.";
          }
        }
      }
    }
  }
  augment "/ncs:devices/ncs:device/ncs:rpc" {
    container rpc-enable-egress-id-tunnel-lsp {
      tailf:ncs-device-type "netconf";
      tailf:display-when "not(../../ncs:module) or ../../ncs:module[ncs:name='huawei-mplsoam']";
      tailf:action enable-egress-id-tunnel-lsp {
        tailf:actionpoint ncsproxy {
          tailf:internal;
        }
        description
          "Start connectivity verification (cv) or fast failure detection (ffd).";
        ext:node-ref "/mplsoam/tunnels/egress-id-tunnels";
        input {
          leaf tunnel-id {
            type string;
            description
              "Configure the ID of tunnel.";
          }
          leaf ingress-lsr-id {
            type string;
            description
              "Configure the LSR ID.";
          }
        }
      }
    }
  }
  augment "/ncs:devices/ncs:device-group/ncs:ned-id/ncs:rpc" {
    container rpc-enable-egress-id-tunnel-lsp {
      tailf:ncs-device-type "netconf";
      tailf:display-when "/ncs:devices/ncs:device[ncs:name=current()/../../../ncs:member]/ncs:module[ncs:name='huawei-mplsoam']";
      tailf:action enable-egress-id-tunnel-lsp {
        tailf:actionpoint ncsproxy {
          tailf:internal;
        }
        description
          "Start connectivity verification (cv) or fast failure detection (ffd).";
        ext:node-ref "/mplsoam/tunnels/egress-id-tunnels";
        input {
          leaf tunnel-id {
            type string;
            description
              "Configure the ID of tunnel.";
          }
          leaf ingress-lsr-id {
            type string;
            description
              "Configure the LSR ID.";
          }
        }
      }
    }
  }
  augment "/ncs:devices/ncs:device/ncs:rpc" {
    container rpc-disable-co-route-tunnel {
      tailf:ncs-device-type "netconf";
      tailf:display-when "not(../../ncs:module) or ../../ncs:module[ncs:name='huawei-mplsoam']";
      tailf:action disable-co-route-tunnel {
        tailf:actionpoint ncsproxy {
          tailf:internal;
        }
        description
          "Stop connectivity verification (cv) or fast failure detection (ffd).";
        ext:node-ref "/mplsoam/tunnels/co-route-tunnels";
        input {
          leaf tunnel-name {
            type string;
            description
              "Tunnel interface name.";
          }
        }
      }
    }
  }
  augment "/ncs:devices/ncs:device-group/ncs:ned-id/ncs:rpc" {
    container rpc-disable-co-route-tunnel {
      tailf:ncs-device-type "netconf";
      tailf:display-when "/ncs:devices/ncs:device[ncs:name=current()/../../../ncs:member]/ncs:module[ncs:name='huawei-mplsoam']";
      tailf:action disable-co-route-tunnel {
        tailf:actionpoint ncsproxy {
          tailf:internal;
        }
        description
          "Stop connectivity verification (cv) or fast failure detection (ffd).";
        ext:node-ref "/mplsoam/tunnels/co-route-tunnels";
        input {
          leaf tunnel-name {
            type string;
            description
              "Tunnel interface name.";
          }
        }
      }
    }
  }
  augment "/ncs:devices/ncs:device/ncs:rpc" {
    container rpc-enable-co-route-tunnel {
      tailf:ncs-device-type "netconf";
      tailf:display-when "not(../../ncs:module) or ../../ncs:module[ncs:name='huawei-mplsoam']";
      tailf:action enable-co-route-tunnel {
        tailf:actionpoint ncsproxy {
          tailf:internal;
        }
        description
          "Start connectivity verification (cv) or fast failure detection (ffd).";
        ext:node-ref "/mplsoam/tunnels/co-route-tunnels";
        input {
          leaf tunnel-name {
            type string;
            description
              "Tunnel interface name.";
          }
        }
      }
    }
  }
  augment "/ncs:devices/ncs:device-group/ncs:ned-id/ncs:rpc" {
    container rpc-enable-co-route-tunnel {
      tailf:ncs-device-type "netconf";
      tailf:display-when "/ncs:devices/ncs:device[ncs:name=current()/../../../ncs:member]/ncs:module[ncs:name='huawei-mplsoam']";
      tailf:action enable-co-route-tunnel {
        tailf:actionpoint ncsproxy {
          tailf:internal;
        }
        description
          "Start connectivity verification (cv) or fast failure detection (ffd).";
        ext:node-ref "/mplsoam/tunnels/co-route-tunnels";
        input {
          leaf tunnel-name {
            type string;
            description
              "Tunnel interface name.";
          }
        }
      }
    }
  }
  augment "/ncs:devices/ncs:device/ncs:config" {
    container mplsoam {
      tailf:ncs-device-type "netconf";
      tailf:display-when "not(../../ncs:module) or ../../ncs:module[ncs:name='huawei-mplsoam']";
      description
        "MPLS OAM.";
      container global {
        description
          "Configure global MPLS OAM attribute.";
        leaf oam-enable {
          when "/mpls:mpls/mpls:common/mpls:global/mpls:mpls-enable='true'" {
            tailf:xpath-root 3;
          }
          type boolean;
          default "false";
          description
            "Enable/disable global MPLS OAM.";
        }
        leaf fdi-enable {
          type boolean;
          default "false";
          description
            "Enable/disable MPLS OAM FDI.";
        }
        leaf itu-mode {
          when "../oam-enable='true'" {
            tailf:xpath-root 3;
          }
          type boolean;
          default "false";
          description
            "Enable/disable global mode of MPLS OAM.";
        }
        // NCS drop config false leaf 'oam-num'
      }
      container tunnels {
        when "../global/oam-enable='true'" {
          tailf:xpath-root 3;
        }
        description
          "Configure tunnels.";
        container egress-id-tunnels {
          description
            "List of MPLS OAM monitors egress LSP.";
          list egress-id-tunnel {
            key "id ingress-lsr-id";
            description
              "Configure MPLS OAM monitors egress LSP.";
            leaf id {
              type uint16 {
                range "0..65535";
              }
              description
                "Configure an ID of tunnel.";
            }
            leaf ingress-lsr-id {
              type inet:ipv4-address-no-zone;
              description
                "Configure an LSR ID.";
            }
            leaf reverse-name {
              type leafref {
                path "/ncs:devices/ncs:device/ncs:config/ifm:ifm/ifm:interfaces/ifm:interface/ifm:name" {
                  tailf:xpath-root 3;
                }
              }
              must '/ifm:ifm/ifm:interfaces/ifm:interface[ifm:name = current()]/tnlm:tunnel-protocol/mpls-te:te-tunnel' {
                tailf:xpath-root 3;
              }
              description
                "Configure a Backward Tunnel Name.";
            }
            leaf reverse-mode {
              type reverse-mode;
              default "share";
              description
                "Configure Backward Sharing Mode.";
            }
            leaf oam-loss-sd {
              type uint32 {
                range "0..100";
              }
              default "0";
              description
                "Configure the SD threshold of OAM loss measurement.";
            }
            leaf oam-loss-sf {
              type uint32 {
                range "0..100";
              }
              default "0";
              description
                "Configure the SF threshold of OAM loss measurement.";
            }
            leaf slm-threshold1 {
              type uint32 {
                range "1..1000000";
              }
              default "1";
              description
                "Configure threshold1 of proactive single-ended loss measurement. The default value is 1.";
            }
            leaf slm-threshold2 {
              type uint32 {
                range "1..1000000";
              }
              default "10";
              description
                "Configure threshold2 of proactive single-ended loss measurement. The default value is 10.";
            }
            leaf detect-mode {
              type detect-mode;
              default "auto";
              description
                "Configure a detection mode.";
            }
            leaf auto-mode-over-time {
              when "../detect-mode='auto'" {
                tailf:xpath-root 3;
              }
              type uint8 {
                range "0..255";
              }
              default "10";
              description
                "Configure a First Packet Timeout Coefficient, Step is 30s.";
            }
            leaf detect-pkt-type {
              type detect-pkt-type;
              default "cv";
              description
                "Configure a Type of Detected Packet.";
            }
            leaf detect-frequence {
              type detect-interval;
              must "(../detect-pkt-type='cv' and ../detect-frequence='1000ms') or (../detect-pkt-type='ffd' and ../detect-frequence!='1000ms')" {
                tailf:xpath-root 3;
              }
              mandatory true;
              description
                "Configure the detection packet frequency.";
            }
            leaf bdi-frequence {
              type bdi-frequency;
              default "detect-freq";
              description
                "BDI packet frequency, detect-freq indicate the same as frequency of detecting packet.";
            }
            leaf receive-enable {
              type boolean;
              default "false";
              description
                "Enable/disable MPLS OAM packets can be received.";
            }
            leaf oam-active-status {
              type active-type;
              default "deactive";
              description
                "Whether MPLS OAM detection is enabled. This function is disabled by default.";
            }
            // NCS drop config false leaf description
            // NCS drop config false leaf 'lsp-type'
            uses session-status;
          }
        }
        container egress-name-tunnels {
          description
            "List of MPLS OAM monitors egress static LSP.";
          list egress-name-tunnel {
            key "name";
            description
              "Configure MPLS OAM monitors egress LSP.";
            leaf name {
              type pub-type:if-name;
              description
                "Configure a tunnel interface name.";
            }
            leaf reverse-name {
              type leafref {
                path "/ncs:devices/ncs:device/ncs:config/ifm:ifm/ifm:interfaces/ifm:interface/ifm:name" {
                  tailf:xpath-root 3;
                }
              }
              must '/ifm:ifm/ifm:interfaces/ifm:interface[ifm:name = current()]/tnlm:tunnel-protocol/mpls-te:te-tunnel' {
                tailf:xpath-root 3;
              }
              description
                "Configure a Backward Tunnel Name.";
            }
            leaf reverse-mode {
              type reverse-mode;
              default "share";
              description
                "Configure Backward Sharing Mode.";
            }
            leaf oam-loss-sd {
              type uint32 {
                range "0..100";
              }
              default "0";
              description
                "Configure the SD threshold of OAM loss measurement.";
            }
            leaf oam-loss-sf {
              type uint32 {
                range "0..100";
              }
              default "0";
              description
                "Configure the SF threshold of OAM loss measurement.";
            }
            leaf slm-threshold1 {
              type uint32 {
                range "1..1000000";
              }
              default "1";
              description
                "Configure threshold1 of proactive single-ended loss measurement. The default value is 1.";
            }
            leaf slm-threshold2 {
              type uint32 {
                range "1..1000000";
              }
              default "10";
              description
                "Configure threshold2 of proactive single-ended loss measurement. The default value is 10.";
            }
            leaf detect-mode {
              type detect-mode;
              default "auto";
              description
                "Configure a detection mode.";
            }
            leaf auto-mode-over-time {
              when "../detect-mode='auto'" {
                tailf:xpath-root 3;
              }
              type uint8 {
                range "0..255";
              }
              default "10";
              description
                "Configure a First Packet Timeout Coefficient, Step is 30s.";
            }
            leaf detect-pkt-type {
              type detect-pkt-type;
              default "cv";
              description
                "Configure a Type of Detected Packet.";
            }
            leaf detect-frequence {
              type detect-interval;
              must "(../detect-pkt-type='cv' and ../detect-frequence='1000ms') or (../detect-pkt-type='ffd' and ../detect-frequence!='1000ms')" {
                tailf:xpath-root 3;
              }
              mandatory true;
              description
                "Configure the detection packet frequency.";
            }
            leaf bdi-frequence {
              type bdi-frequency;
              default "detect-freq";
              description
                "BDI packet frequency, detect-freq indicate the same as frequency of detecting packet.";
            }
            leaf receive-enable {
              type boolean;
              default "false";
              description
                "Enable/disable MPLS OAM packets can be received.";
            }
            leaf oam-active-status {
              type active-type;
              default "deactive";
              description
                "Whether MPLS OAM detection is enabled. This function is disabled by default.";
            }
            // NCS drop config false leaf description
            // NCS drop config false leaf 'lsp-type'
            uses session-status;
          }
        }
        container ingress-tunnels {
          description
            "List of MPLS OAM monitors ingress LSP.";
          list ingress-tunnel {
            key "name";
            description
              "Configure MPLS OAM monitors egress LSP.";
            leaf name {
              type leafref {
                path "/ncs:devices/ncs:device/ncs:config/ifm:ifm/ifm:interfaces/ifm:interface/ifm:name" {
                  tailf:xpath-root 3;
                }
              }
              must '/ifm:ifm/ifm:interfaces/ifm:interface[ifm:name = current()]/tnlm:tunnel-protocol/mpls-te:te-tunnel' {
                tailf:xpath-root 3;
              }
              description
                "Configure a tunnel interface name.";
            }
            choice reverse-lsp-name-or-id {
              description
                "Configure reverse lsp name or lsr id.";
              case lsp-name {
                description
                  "Configure reverse lsp name.";
                leaf reverse-name {
                  type pub-type:if-name;
                  description
                    "Configure the reverse tunnel name.";
                }
              }
              case lsp-id {
                description
                  "Configure reverse lsr id.";
                leaf reverse-id {
                  type uint16 {
                    range "1..65535";
                  }
                  description
                    "Configure the remote ID of tunnel.";
                }
                leaf reverse-lsr-id {
                  type inet:ipv4-address-no-zone;
                  description
                    "Configure the remote LSR ID.";
                }
              }
            }
            leaf reverse-mode {
              type reverse-mode;
              default "share";
              description
                "Configure Backward Sharing Mode.";
            }
            leaf oam-loss-sd {
              type uint32 {
                range "0..100";
              }
              default "0";
              description
                "Configure the SD threshold of OAM loss measurement.";
            }
            leaf oam-loss-sf {
              type uint32 {
                range "0..100";
              }
              default "0";
              description
                "Configure the SF threshold of OAM loss measurement.";
            }
            leaf slm-send-enable {
              type boolean;
              default "false";
              description
                "Enable/disable a device sends packets for proactive single-ended loss measurement. This function is disabled by default.";
            }
            leaf slm-threshold1 {
              type uint32 {
                range "1..1000000";
              }
              default "1";
              description
                "Configure threshold1 of proactive single-ended loss measurement. The default value is 1.";
            }
            leaf slm-threshold2 {
              type uint32 {
                range "1..1000000";
              }
              default "10";
              description
                "Configure threshold2 of proactive single-ended loss measurement. The default value is 10.";
            }
            leaf detect-pkt-type {
              type detect-pkt-type;
              default "cv";
              description
                "Configure a Type of Detected Packet.";
            }
            leaf detect-frequence {
              type detect-interval;
              must "(../detect-pkt-type='cv' and ../detect-frequence='1000ms') or (../detect-pkt-type='ffd' and ../detect-frequence!='1000ms')" {
                tailf:xpath-root 3;
              }
              mandatory true;
              description
                "Configure the detection packet frequency.";
            }
            leaf bdi-frequence {
              type bdi-frequency;
              default "detect-freq";
              description
                "BDI packet frequency, detect-freq indicate the same as frequency of detecting packet.";
            }
            leaf compatibility-mode {
              type compatibility-mode;
              default "route-mode";
              description
                "Configure Compatibility Mode.";
            }
            leaf send-enable {
              type boolean;
              default "false";
              description
                "Enable/disable the MPLS OAM packets can be sent.";
            }
            leaf cc-exp {
              type uint8 {
                range "0..7";
              }
              default "7";
              description
                "Configure the exp of packet.";
            }
            leaf oam-active-status {
              type active-type;
              default "deactive";
              description
                "Whether MPLS OAM detection is enabled. This function is disabled by default.";
            }
            leaf two-dm-send-enable {
              type boolean;
              default "false";
              description
                "Enable/disable a device sends packets for proactive two-way delay measurement. This function is disabled by default.";
            }
            leaf two-dm-packet-size {
              type uint32 {
                range "64..1500";
              }
              default "64";
              description
                "Configure the packet size of proactive two-way delay measurement.";
            }
            leaf two-dm-pad-value {
              type padding-value;
              default "0";
              description
                "Configure the padding value of proactive two-way delay measurement. The default value is 0.";
            }
            // NCS drop config false leaf description
            // NCS drop config false leaf 'lsp-type'
            uses session-status;
          }
        }
        container co-route-tunnels {
          description
            "List of MPLS OAM monitors cr static LSP.";
          list co-route-tunnel {
            key "name";
            description
              "Configure MPLS OAM monitors cr static LSP.";
            leaf name {
              type leafref {
                path "/ncs:devices/ncs:device/ncs:config/ifm:ifm/ifm:interfaces/ifm:interface/ifm:name" {
                  tailf:xpath-root 3;
                }
              }
              must '/ifm:ifm/ifm:interfaces/ifm:interface[ifm:name = current()]/tnlm:tunnel-protocol/mpls-te:te-tunnel' {
                tailf:xpath-root 3;
              }
              description
                "Configure a tunnel interface name.";
            }
            leaf oam-loss-sd {
              type uint32 {
                range "0..100";
              }
              default "0";
              description
                "Configure the SD threshold of OAM loss measurement.";
            }
            leaf oam-loss-sf {
              type uint32 {
                range "0..100";
              }
              default "0";
              description
                "Configure the SF threshold of OAM loss measurement.";
            }
            leaf slm-send-enable {
              type boolean;
              default "false";
              description
                "Enable/disable a device sends packets for proactive single-ended loss measurement.";
            }
            leaf slm-threshold1 {
              type uint32 {
                range "1..1000000";
              }
              default "1";
              description
                "Configure threshold1 of proactive single-ended loss measurement. The default value is 1.";
            }
            leaf slm-threshold2 {
              type uint32 {
                range "1..1000000";
              }
              default "10";
              description
                "Configure threshold2 of proactive single-ended loss measurement. The default value is 10.";
            }
            leaf detect-mode {
              type detect-mode;
              default "auto";
              description
                "Configure a detection mode.";
            }
            leaf auto-mode-over-time {
              when "../detect-mode='auto'" {
                tailf:xpath-root 3;
              }
              type uint8 {
                range "0..255";
              }
              default "10";
              description
                "Configure a First Packet Timeout Coefficient, Step is 30s.";
            }
            leaf detect-pkt-type {
              type detect-pkt-type;
              default "cv";
              description
                "Configure a Type of Detected Packet.";
            }
            leaf detect-frequence {
              type detect-interval;
              must "(../detect-pkt-type='cv' and ../detect-frequence='1000ms') or (../detect-pkt-type='ffd' and ../detect-frequence!='1000ms')" {
                tailf:xpath-root 3;
              }
              mandatory true;
              description
                "Configure the detection packet frequency.";
            }
            leaf bdi-frequence {
              type bdi-frequency;
              default "detect-freq";
              description
                "BDI packet frequency, detect-freq indicate the same as frequency of detecting packet.";
            }
            leaf compatibility-mode {
              type compatibility-mode;
              default "route-mode";
              description
                "Configure Compatibility Mode.";
            }
            leaf send-enable {
              type boolean;
              default "false";
              description
                "Enable/disable the MPLS OAM packets can be sent.";
            }
            leaf receive-enable {
              type boolean;
              default "false";
              description
                "Enable/disable MPLS OAM packets can be received.";
            }
            leaf cc-exp {
              type uint8 {
                range "0..7";
              }
              default "7";
              description
                "Configure the exp of packet.";
            }
            // NCS drop config false leaf description
            leaf oam-active-status {
              type active-type;
              default "deactive";
              description
                "Whether MPLS OAM detection is enabled. This function is disabled by default.";
            }
            leaf two-dm-send-enable {
              type boolean;
              default "false";
              description
                "Enable/disable a device sends packets for proactive two-way delay measurement.";
            }
            leaf two-dm-packet-size {
              type uint32 {
                range "64..1500";
              }
              default "64";
              description
                "Configure the packet size of proactive two-way delay measurement.";
            }
            leaf two-dm-pad-value {
              type padding-value;
              default "0";
              description
                "Configure the padding value of proactive two-way delay measurement. The default value is 0.";
            }
            // NCS drop config false leaf 'lsp-type'
            uses session-status;
          }
        }
      }
      container vll-pws {
        when "../global/oam-enable='true'" {
          tailf:xpath-root 3;
        }
        description
          "List of pseudo wire service (PWS).";
        list vll-pw {
          key "l2vpn-name l2vpn-type l2vpn-role";
          description
            "Configure MPLS OAM to monitor a VLL PW.";
          leaf l2vpn-name {
            type leafref {
              path "/ncs:devices/ncs:device/ncs:config/l2vpn:l2vpn/l2vpn:instances/l2vpn:instance/l2vpn:name" {
                tailf:xpath-root 3;
              }
            }
            description
              "Configure l2vpn name of MPLS OAM binded static PW.";
          }
          leaf l2vpn-type {
            type leafref {
              path "/ncs:devices/ncs:device/ncs:config/l2vpn:l2vpn/l2vpn:instances/l2vpn:instance/l2vpn:type" {
                tailf:xpath-root 3;
              }
            }
            description
              "Configure l2vpn name of MPLS OAM binded static PW.";
          }
          leaf l2vpn-role {
            type leafref {
              path "/ncs:devices/ncs:device/ncs:config/l2vpn:l2vpn/l2vpn:instances/l2vpn:instance[l2vpn:name = current()/../l2vpn-name][l2vpn:type = current()/../l2vpn-type]/l2vpn:vpws-ldp/l2vpn:pws/l2vpn:pw/l2vpn:role" {
                tailf:xpath-root 3;
              }
            }
            description
              "Configure pw role of MPLS OAM binded static PW.";
          }
          leaf remote-lsr-id {
            type inet:ipv4-address-no-zone;
            description
              "Configure a remote LSR ID.";
          }
          leaf remote-vc-id {
            type uint32 {
              range "0..4294967295";
            }
            description
              "Configure a remote VC ID of a static PW to which MPLS OAM is bound.";
          }
          leaf remote-vc-type {
            type l2vc-type;
            description
              "Configure a remote VC type of a static PW to which MPLS OAM is bound.";
          }
          leaf detect-pkt-type {
            type detect-pkt-type;
            default "cv";
            description
              "Configure a detection packet type.";
          }
          leaf detect-mode {
            type detect-mode;
            default "auto";
            description
              "Configure a detection mode.";
          }
          leaf auto-mode-over-time {
            when "../detect-mode='auto'" {
              tailf:xpath-root 3;
            }
            type uint8 {
              range "0..255";
            }
            default "10";
            description
              "Configure the Over Time.";
          }
          leaf detect-frequence {
            type detect-interval;
            must "(../detect-pkt-type='cv' and (../detect-frequence='1000ms') ) or not (../detect-pkt-type='ffd')" {
              tailf:xpath-root 3;
            }
            mandatory true;
            description
              "Configure the detection packet type.";
          }
          leaf bdi-frequence {
            type bdi-frequency;
            default "detect-freq";
            description
              "BDI packet frequency, detect-freq indicate the same as frequency of detecting packet.";
          }
          leaf compatibility-mode {
            type compatibility-mode;
            default "route-mode";
            description
              "Configure Compatibility Mode.";
          }
          leaf oam-active-status {
            type active-type;
            default "deactive";
            description
              "Whether MPLS OAM detection is enabled. This function is disabled by default.";
          }
          leaf send-enable {
            type boolean;
            default "false";
            description
              "Enable/disable the MPLS OAM packets can be sent.";
          }
          leaf receive-enable {
            type boolean;
            default "false";
            description
              "Enable/disable MPLS OAM packets can be received.";
          }
          leaf oam-loss-sd {
            type uint32 {
              range "0..100";
            }
            default "0";
            description
              "Configure the SD threshold of OAM loss measurement.";
          }
          leaf oam-loss-sf {
            type uint32 {
              range "0..100";
            }
            default "0";
            description
              "Configure the SF threshold of OAM Loss Measurement.";
          }
          leaf slm-send-enable {
            type boolean;
            default "false";
            description
              "Enable/disable a device sends packets for proactive single-ended loss measurement.";
          }
          leaf slm-threshold1 {
            type uint32 {
              range "1..1000000";
            }
            default "1";
            description
              "Configure threshold1 of proactive single-ended loss measurement. The default value is 1.";
          }
          leaf slm-threshold2 {
            type uint32 {
              range "1..1000000";
            }
            default "10";
            description
              "Configure threshold2 of proactive single-ended loss measurement. The default value is 10.";
          }
          leaf two-dm-send-enable {
            type boolean;
            default "false";
            description
              "Enable/disable a device sends packets for proactive two-way delay measurement.";
          }
          leaf two-dm-exp {
            type uint8 {
              range "0..7";
            }
            default "7";
            description
              "Configure the exp value of proactive two-way delay measurement. The default value is 7.";
          }
          leaf two-dm-packet-size {
            type uint32 {
              range "64..1500";
            }
            default "64";
            description
              "Configure the packet size of proactive two-way delay measurement.";
          }
          leaf two-dm-pad-value {
            type padding-value;
            default "0";
            description
              "Configure the padding value of proactive two-way delay measurement. The default value is 0.";
          }
          leaf cc-exp {
            type uint8 {
              range "0..7";
            }
            default "7";
            description
              "Configure the exp of packet.";
          }
          uses session-status;
        }
      }
      container vsi-pws {
        when "../global/oam-enable='true'" {
          tailf:xpath-root 3;
        }
        description
          "List of pseudo wire service (PWS).";
        list vsi-pw {
          key "peer-ip vc-id vc-type";
          description
            "Configure MPLS OAM to monitor a vsi PW.";
          leaf peer-ip {
            type leafref {
              path "/ncs:devices/ncs:device/ncs:config/l2vpn:l2vpn/l2vpn:instances/l2vpn:instance/l2vpn:vpls/l2vpn:ldp-signaling/l2vpn:pws/l2vpn:pw/l2vpn:peer-ip" {
                tailf:xpath-root 3;
              }
            }
            description
              "Configure peer IP of MPLS OAM binded static PW.";
          }
          leaf vc-id {
            type leafref {
              path "/ncs:devices/ncs:device/ncs:config/l2vpn:l2vpn/l2vpn:instances/l2vpn:instance/l2vpn:vpls/l2vpn:ldp-signaling/l2vpn:pws/l2vpn:pw/l2vpn:negotiation-vc-id" {
                tailf:xpath-root 3;
              }
            }
            description
              "Configure VC ID of MPLS OAM binded static PW.";
          }
          leaf vc-type {
            type leafref {
              path "/ncs:devices/ncs:device/ncs:config/l2vpn:l2vpn/l2vpn:instances/l2vpn:instance/l2vpn:vpls/l2vpn:ldp-signaling/l2vpn:pws/l2vpn:pw/l2vpn:encapsulation-type" {
                tailf:xpath-root 3;
              }
            }
            description
              "Configure remote VC Type of MPLS OAM binded static PW.";
          }
          leaf remote-lsr-id {
            type inet:ipv4-address-no-zone;
            description
              "Configure a remote LSR ID.";
          }
          leaf remote-vc-id {
            type uint32 {
              range "0..4294967295";
            }
            description
              "Configure a remote VC ID of a static PW to which MPLS OAM is bound.";
          }
          leaf remote-vc-type {
            type l2vc-type;
            description
              "Configure a remote VC type of a static PW to which MPLS OAM is bound.";
          }
          leaf detect-pkt-type {
            type detect-pkt-type;
            default "cv";
            description
              "Configure a detection packet type.";
          }
          leaf detect-mode {
            type detect-mode;
            default "auto";
            description
              "Configure a detection mode.";
          }
          leaf auto-mode-over-time {
            when "../detect-mode='auto'" {
              tailf:xpath-root 3;
            }
            type uint8 {
              range "0..255";
            }
            default "10";
            description
              "Configure the Over Time.";
          }
          leaf detect-frequence {
            type detect-interval;
            must "(../detect-pkt-type='cv' and (../detect-frequence='1000ms') ) or not (../detect-pkt-type='ffd')" {
              tailf:xpath-root 3;
            }
            mandatory true;
            description
              "Configure the detection packet type.";
          }
          leaf bdi-frequence {
            type bdi-frequency;
            default "detect-freq";
            description
              "BDI packet frequency, detect-freq indicate the same as frequency of detecting packet.";
          }
          leaf compatibility-mode {
            type compatibility-mode;
            default "route-mode";
            description
              "Configure Compatibility Mode.";
          }
          leaf oam-active-status {
            type active-type;
            default "deactive";
            description
              "Whether MPLS OAM detection is enabled. This function is disabled by default.";
          }
          leaf send-enable {
            type boolean;
            default "false";
            description
              "Enable/disable the MPLS OAM packets can be sent.";
          }
          leaf receive-enable {
            type boolean;
            default "false";
            description
              "Enable/disable MPLS OAM packets can be received.";
          }
          leaf oam-loss-sd {
            type uint32 {
              range "0..100";
            }
            default "0";
            description
              "Configure the SD threshold of OAM loss measurement.";
          }
          leaf oam-loss-sf {
            type uint32 {
              range "0..100";
            }
            default "0";
            description
              "Configure the SF threshold of OAM Loss Measurement.";
          }
          leaf slm-send-enable {
            type boolean;
            default "false";
            description
              "Enable/disable a device sends packets for proactive single-ended loss measurement.";
          }
          leaf slm-threshold1 {
            type uint32 {
              range "1..1000000";
            }
            default "1";
            description
              "Configure threshold1 of proactive single-ended loss measurement. The default value is 1.";
          }
          leaf slm-threshold2 {
            type uint32 {
              range "1..1000000";
            }
            default "10";
            description
              "Configure threshold2 of proactive single-ended loss measurement. The default value is 10.";
          }
          leaf two-dm-send-enable {
            type boolean;
            default "false";
            description
              "Enable/disable a device sends packets for proactive two-way delay measurement.";
          }
          leaf two-dm-exp {
            type uint8 {
              range "0..7";
            }
            default "7";
            description
              "Configure the exp value of proactive two-way delay measurement. The default value is 7.";
          }
          leaf two-dm-packet-size {
            type uint32 {
              range "64..1500";
            }
            default "64";
            description
              "Configure the packet size of proactive two-way delay measurement.";
          }
          leaf two-dm-pad-value {
            type padding-value;
            default "0";
            description
              "Configure the padding value of proactive two-way delay measurement. The default value is 0.";
          }
          leaf cc-exp {
            type uint8 {
              range "0..7";
            }
            default "7";
            description
              "Configure the exp of packet.";
          }
          uses session-status;
        }
      }
    }
  }
  augment "/ncs:devices/ncs:device/ncs:live-status" {
    container mplsoam {
      tailf:ncs-device-type "netconf";
      tailf:display-when "not(../../ncs:module) or ../../ncs:module[ncs:name='huawei-mplsoam'] or (../../ncs:live-status-protocol[not(ncs:capability)]) or (../../ncs:live-status-protocol/ncs:capability/ncs:module[.='huawei-mplsoam'])";
      description
        "MPLS OAM.";
      container global {
        description
          "Configure global MPLS OAM attribute.";
        leaf oam-enable {
          // NCS drop when statement
          type boolean;
          // NCS drop default statement
          description
            "Enable/disable global MPLS OAM.";
        }
        leaf fdi-enable {
          type boolean;
          // NCS drop default statement
          description
            "Enable/disable MPLS OAM FDI.";
        }
        leaf itu-mode {
          // NCS drop when statement
          type boolean;
          // NCS drop default statement
          description
            "Enable/disable global mode of MPLS OAM.";
        }
        leaf oam-num {
          type uint32;
          description
            "Total number of OAM instances, including MPLS OAM and MPLS-TP OAM instances.";
        }
      }
      container tunnels {
        // NCS drop when statement
        description
          "Configure tunnels.";
        container egress-id-tunnels {
          description
            "List of MPLS OAM monitors egress LSP.";
          list egress-id-tunnel {
            key "id ingress-lsr-id";
            description
              "Configure MPLS OAM monitors egress LSP.";
            leaf id {
              type uint16 {
                range "0..65535";
              }
              description
                "Configure an ID of tunnel.";
            }
            leaf ingress-lsr-id {
              type inet:ipv4-address-no-zone;
              description
                "Configure an LSR ID.";
            }
            leaf reverse-name {
              type leafref {
                path "/ncs:devices/ncs:device/ncs:live-status/ifm:ifm/ifm:interfaces/ifm:interface/ifm:name" {
                  tailf:xpath-root 3;
                }
              }
              // NCS drop must statement
              description
                "Configure a Backward Tunnel Name.";
            }
            leaf reverse-mode {
              type live_ncs_reverse-mode;
              // NCS drop default statement
              description
                "Configure Backward Sharing Mode.";
            }
            leaf oam-loss-sd {
              type uint32 {
                range "0..100";
              }
              // NCS drop default statement
              description
                "Configure the SD threshold of OAM loss measurement.";
            }
            leaf oam-loss-sf {
              type uint32 {
                range "0..100";
              }
              // NCS drop default statement
              description
                "Configure the SF threshold of OAM loss measurement.";
            }
            leaf slm-threshold1 {
              type uint32 {
                range "1..1000000";
              }
              // NCS drop default statement
              description
                "Configure threshold1 of proactive single-ended loss measurement. The default value is 1.";
            }
            leaf slm-threshold2 {
              type uint32 {
                range "1..1000000";
              }
              // NCS drop default statement
              description
                "Configure threshold2 of proactive single-ended loss measurement. The default value is 10.";
            }
            leaf detect-mode {
              type live_ncs_detect-mode;
              // NCS drop default statement
              description
                "Configure a detection mode.";
            }
            leaf auto-mode-over-time {
              // NCS drop when statement
              type uint8 {
                range "0..255";
              }
              // NCS drop default statement
              description
                "Configure a First Packet Timeout Coefficient, Step is 30s.";
            }
            leaf detect-pkt-type {
              type live_ncs_detect-pkt-type;
              // NCS drop default statement
              description
                "Configure a Type of Detected Packet.";
            }
            leaf detect-frequence {
              type live_ncs_detect-interval;
              // NCS drop must statement
              // NCS drop mandatory statement
              description
                "Configure the detection packet frequency.";
            }
            leaf bdi-frequence {
              type live_ncs_bdi-frequency;
              // NCS drop default statement
              description
                "BDI packet frequency, detect-freq indicate the same as frequency of detecting packet.";
            }
            leaf receive-enable {
              type boolean;
              // NCS drop default statement
              description
                "Enable/disable MPLS OAM packets can be received.";
            }
            leaf oam-active-status {
              type live_ncs_active-type;
              // NCS drop default statement
              description
                "Whether MPLS OAM detection is enabled. This function is disabled by default.";
            }
            leaf description {
              type string {
                length "0..64";
              }
              description
                "Description of a tunnel.";
            }
            leaf lsp-type {
              type live_ncs_lsp-establish-type;
              description
                "LSP Type.";
            }
            uses live_ncs_session-status;
          }
        }
        container egress-name-tunnels {
          description
            "List of MPLS OAM monitors egress static LSP.";
          list egress-name-tunnel {
            key "name";
            description
              "Configure MPLS OAM monitors egress LSP.";
            leaf name {
              type pub-type:live_ncs_if-name;
              description
                "Configure a tunnel interface name.";
            }
            leaf reverse-name {
              type leafref {
                path "/ncs:devices/ncs:device/ncs:live-status/ifm:ifm/ifm:interfaces/ifm:interface/ifm:name" {
                  tailf:xpath-root 3;
                }
              }
              // NCS drop must statement
              description
                "Configure a Backward Tunnel Name.";
            }
            leaf reverse-mode {
              type live_ncs_reverse-mode;
              // NCS drop default statement
              description
                "Configure Backward Sharing Mode.";
            }
            leaf oam-loss-sd {
              type uint32 {
                range "0..100";
              }
              // NCS drop default statement
              description
                "Configure the SD threshold of OAM loss measurement.";
            }
            leaf oam-loss-sf {
              type uint32 {
                range "0..100";
              }
              // NCS drop default statement
              description
                "Configure the SF threshold of OAM loss measurement.";
            }
            leaf slm-threshold1 {
              type uint32 {
                range "1..1000000";
              }
              // NCS drop default statement
              description
                "Configure threshold1 of proactive single-ended loss measurement. The default value is 1.";
            }
            leaf slm-threshold2 {
              type uint32 {
                range "1..1000000";
              }
              // NCS drop default statement
              description
                "Configure threshold2 of proactive single-ended loss measurement. The default value is 10.";
            }
            leaf detect-mode {
              type live_ncs_detect-mode;
              // NCS drop default statement
              description
                "Configure a detection mode.";
            }
            leaf auto-mode-over-time {
              // NCS drop when statement
              type uint8 {
                range "0..255";
              }
              // NCS drop default statement
              description
                "Configure a First Packet Timeout Coefficient, Step is 30s.";
            }
            leaf detect-pkt-type {
              type live_ncs_detect-pkt-type;
              // NCS drop default statement
              description
                "Configure a Type of Detected Packet.";
            }
            leaf detect-frequence {
              type live_ncs_detect-interval;
              // NCS drop must statement
              // NCS drop mandatory statement
              description
                "Configure the detection packet frequency.";
            }
            leaf bdi-frequence {
              type live_ncs_bdi-frequency;
              // NCS drop default statement
              description
                "BDI packet frequency, detect-freq indicate the same as frequency of detecting packet.";
            }
            leaf receive-enable {
              type boolean;
              // NCS drop default statement
              description
                "Enable/disable MPLS OAM packets can be received.";
            }
            leaf oam-active-status {
              type live_ncs_active-type;
              // NCS drop default statement
              description
                "Whether MPLS OAM detection is enabled. This function is disabled by default.";
            }
            leaf description {
              type string {
                length "0..64";
              }
              description
                "Description of a tunnel.";
            }
            leaf lsp-type {
              type live_ncs_lsp-establish-type;
              description
                "LSP Type.";
            }
            uses live_ncs_session-status;
          }
        }
        container ingress-tunnels {
          description
            "List of MPLS OAM monitors ingress LSP.";
          list ingress-tunnel {
            key "name";
            description
              "Configure MPLS OAM monitors egress LSP.";
            leaf name {
              type leafref {
                path "/ncs:devices/ncs:device/ncs:live-status/ifm:ifm/ifm:interfaces/ifm:interface/ifm:name" {
                  tailf:xpath-root 3;
                }
              }
              // NCS drop must statement
              description
                "Configure a tunnel interface name.";
            }
            choice reverse-lsp-name-or-id {
              description
                "Configure reverse lsp name or lsr id.";
              case lsp-name {
                description
                  "Configure reverse lsp name.";
                leaf reverse-name {
                  type pub-type:live_ncs_if-name;
                  description
                    "Configure the reverse tunnel name.";
                }
              }
              case lsp-id {
                description
                  "Configure reverse lsr id.";
                leaf reverse-id {
                  type uint16 {
                    range "1..65535";
                  }
                  description
                    "Configure the remote ID of tunnel.";
                }
                leaf reverse-lsr-id {
                  type inet:ipv4-address-no-zone;
                  description
                    "Configure the remote LSR ID.";
                }
              }
            }
            leaf reverse-mode {
              type live_ncs_reverse-mode;
              // NCS drop default statement
              description
                "Configure Backward Sharing Mode.";
            }
            leaf oam-loss-sd {
              type uint32 {
                range "0..100";
              }
              // NCS drop default statement
              description
                "Configure the SD threshold of OAM loss measurement.";
            }
            leaf oam-loss-sf {
              type uint32 {
                range "0..100";
              }
              // NCS drop default statement
              description
                "Configure the SF threshold of OAM loss measurement.";
            }
            leaf slm-send-enable {
              type boolean;
              // NCS drop default statement
              description
                "Enable/disable a device sends packets for proactive single-ended loss measurement. This function is disabled by default.";
            }
            leaf slm-threshold1 {
              type uint32 {
                range "1..1000000";
              }
              // NCS drop default statement
              description
                "Configure threshold1 of proactive single-ended loss measurement. The default value is 1.";
            }
            leaf slm-threshold2 {
              type uint32 {
                range "1..1000000";
              }
              // NCS drop default statement
              description
                "Configure threshold2 of proactive single-ended loss measurement. The default value is 10.";
            }
            leaf detect-pkt-type {
              type live_ncs_detect-pkt-type;
              // NCS drop default statement
              description
                "Configure a Type of Detected Packet.";
            }
            leaf detect-frequence {
              type live_ncs_detect-interval;
              // NCS drop must statement
              // NCS drop mandatory statement
              description
                "Configure the detection packet frequency.";
            }
            leaf bdi-frequence {
              type live_ncs_bdi-frequency;
              // NCS drop default statement
              description
                "BDI packet frequency, detect-freq indicate the same as frequency of detecting packet.";
            }
            leaf compatibility-mode {
              type live_ncs_compatibility-mode;
              // NCS drop default statement
              description
                "Configure Compatibility Mode.";
            }
            leaf send-enable {
              type boolean;
              // NCS drop default statement
              description
                "Enable/disable the MPLS OAM packets can be sent.";
            }
            leaf cc-exp {
              type uint8 {
                range "0..7";
              }
              // NCS drop default statement
              description
                "Configure the exp of packet.";
            }
            leaf oam-active-status {
              type live_ncs_active-type;
              // NCS drop default statement
              description
                "Whether MPLS OAM detection is enabled. This function is disabled by default.";
            }
            leaf two-dm-send-enable {
              type boolean;
              // NCS drop default statement
              description
                "Enable/disable a device sends packets for proactive two-way delay measurement. This function is disabled by default.";
            }
            leaf two-dm-packet-size {
              type uint32 {
                range "64..1500";
              }
              // NCS drop default statement
              description
                "Configure the packet size of proactive two-way delay measurement.";
            }
            leaf two-dm-pad-value {
              type live_ncs_padding-value;
              // NCS drop default statement
              description
                "Configure the padding value of proactive two-way delay measurement. The default value is 0.";
            }
            leaf description {
              type string {
                length "0..64";
              }
              description
                "Description of a tunnel.";
            }
            leaf lsp-type {
              type live_ncs_lsp-establish-type;
              description
                "LSP Type.";
            }
            uses live_ncs_session-status;
          }
        }
        container co-route-tunnels {
          description
            "List of MPLS OAM monitors cr static LSP.";
          list co-route-tunnel {
            key "name";
            description
              "Configure MPLS OAM monitors cr static LSP.";
            leaf name {
              type leafref {
                path "/ncs:devices/ncs:device/ncs:live-status/ifm:ifm/ifm:interfaces/ifm:interface/ifm:name" {
                  tailf:xpath-root 3;
                }
              }
              // NCS drop must statement
              description
                "Configure a tunnel interface name.";
            }
            leaf oam-loss-sd {
              type uint32 {
                range "0..100";
              }
              // NCS drop default statement
              description
                "Configure the SD threshold of OAM loss measurement.";
            }
            leaf oam-loss-sf {
              type uint32 {
                range "0..100";
              }
              // NCS drop default statement
              description
                "Configure the SF threshold of OAM loss measurement.";
            }
            leaf slm-send-enable {
              type boolean;
              // NCS drop default statement
              description
                "Enable/disable a device sends packets for proactive single-ended loss measurement.";
            }
            leaf slm-threshold1 {
              type uint32 {
                range "1..1000000";
              }
              // NCS drop default statement
              description
                "Configure threshold1 of proactive single-ended loss measurement. The default value is 1.";
            }
            leaf slm-threshold2 {
              type uint32 {
                range "1..1000000";
              }
              // NCS drop default statement
              description
                "Configure threshold2 of proactive single-ended loss measurement. The default value is 10.";
            }
            leaf detect-mode {
              type live_ncs_detect-mode;
              // NCS drop default statement
              description
                "Configure a detection mode.";
            }
            leaf auto-mode-over-time {
              // NCS drop when statement
              type uint8 {
                range "0..255";
              }
              // NCS drop default statement
              description
                "Configure a First Packet Timeout Coefficient, Step is 30s.";
            }
            leaf detect-pkt-type {
              type live_ncs_detect-pkt-type;
              // NCS drop default statement
              description
                "Configure a Type of Detected Packet.";
            }
            leaf detect-frequence {
              type live_ncs_detect-interval;
              // NCS drop must statement
              // NCS drop mandatory statement
              description
                "Configure the detection packet frequency.";
            }
            leaf bdi-frequence {
              type live_ncs_bdi-frequency;
              // NCS drop default statement
              description
                "BDI packet frequency, detect-freq indicate the same as frequency of detecting packet.";
            }
            leaf compatibility-mode {
              type live_ncs_compatibility-mode;
              // NCS drop default statement
              description
                "Configure Compatibility Mode.";
            }
            leaf send-enable {
              type boolean;
              // NCS drop default statement
              description
                "Enable/disable the MPLS OAM packets can be sent.";
            }
            leaf receive-enable {
              type boolean;
              // NCS drop default statement
              description
                "Enable/disable MPLS OAM packets can be received.";
            }
            leaf cc-exp {
              type uint8 {
                range "0..7";
              }
              // NCS drop default statement
              description
                "Configure the exp of packet.";
            }
            leaf description {
              type string {
                length "0..64";
              }
              description
                "Description of a tunnel.";
            }
            leaf oam-active-status {
              type live_ncs_active-type;
              // NCS drop default statement
              description
                "Whether MPLS OAM detection is enabled. This function is disabled by default.";
            }
            leaf two-dm-send-enable {
              type boolean;
              // NCS drop default statement
              description
                "Enable/disable a device sends packets for proactive two-way delay measurement.";
            }
            leaf two-dm-packet-size {
              type uint32 {
                range "64..1500";
              }
              // NCS drop default statement
              description
                "Configure the packet size of proactive two-way delay measurement.";
            }
            leaf two-dm-pad-value {
              type live_ncs_padding-value;
              // NCS drop default statement
              description
                "Configure the padding value of proactive two-way delay measurement. The default value is 0.";
            }
            leaf lsp-type {
              type live_ncs_lsp-establish-type;
              description
                "LSP Type.";
            }
            uses live_ncs_session-status;
          }
        }
      }
      container vll-pws {
        // NCS drop when statement
        description
          "List of pseudo wire service (PWS).";
        list vll-pw {
          key "l2vpn-name l2vpn-type l2vpn-role";
          description
            "Configure MPLS OAM to monitor a VLL PW.";
          leaf l2vpn-name {
            type leafref {
              path "/ncs:devices/ncs:device/ncs:live-status/l2vpn:l2vpn/l2vpn:instances/l2vpn:instance/l2vpn:name" {
                tailf:xpath-root 3;
              }
            }
            description
              "Configure l2vpn name of MPLS OAM binded static PW.";
          }
          leaf l2vpn-type {
            type leafref {
              path "/ncs:devices/ncs:device/ncs:live-status/l2vpn:l2vpn/l2vpn:instances/l2vpn:instance/l2vpn:type" {
                tailf:xpath-root 3;
              }
            }
            description
              "Configure l2vpn name of MPLS OAM binded static PW.";
          }
          leaf l2vpn-role {
            type leafref {
              path "/ncs:devices/ncs:device/ncs:live-status/l2vpn:l2vpn/l2vpn:instances/l2vpn:instance[l2vpn:name = current()/../l2vpn-name][l2vpn:type = current()/../l2vpn-type]/l2vpn:vpws-ldp/l2vpn:pws/l2vpn:pw/l2vpn:role" {
                tailf:xpath-root 3;
              }
            }
            description
              "Configure pw role of MPLS OAM binded static PW.";
          }
          leaf remote-lsr-id {
            type inet:ipv4-address-no-zone;
            description
              "Configure a remote LSR ID.";
          }
          leaf remote-vc-id {
            type uint32 {
              range "0..4294967295";
            }
            description
              "Configure a remote VC ID of a static PW to which MPLS OAM is bound.";
          }
          leaf remote-vc-type {
            type live_ncs_l2vc-type;
            description
              "Configure a remote VC type of a static PW to which MPLS OAM is bound.";
          }
          leaf detect-pkt-type {
            type live_ncs_detect-pkt-type;
            // NCS drop default statement
            description
              "Configure a detection packet type.";
          }
          leaf detect-mode {
            type live_ncs_detect-mode;
            // NCS drop default statement
            description
              "Configure a detection mode.";
          }
          leaf auto-mode-over-time {
            // NCS drop when statement
            type uint8 {
              range "0..255";
            }
            // NCS drop default statement
            description
              "Configure the Over Time.";
          }
          leaf detect-frequence {
            type live_ncs_detect-interval;
            // NCS drop must statement
            // NCS drop mandatory statement
            description
              "Configure the detection packet type.";
          }
          leaf bdi-frequence {
            type live_ncs_bdi-frequency;
            // NCS drop default statement
            description
              "BDI packet frequency, detect-freq indicate the same as frequency of detecting packet.";
          }
          leaf compatibility-mode {
            type live_ncs_compatibility-mode;
            // NCS drop default statement
            description
              "Configure Compatibility Mode.";
          }
          leaf oam-active-status {
            type live_ncs_active-type;
            // NCS drop default statement
            description
              "Whether MPLS OAM detection is enabled. This function is disabled by default.";
          }
          leaf send-enable {
            type boolean;
            // NCS drop default statement
            description
              "Enable/disable the MPLS OAM packets can be sent.";
          }
          leaf receive-enable {
            type boolean;
            // NCS drop default statement
            description
              "Enable/disable MPLS OAM packets can be received.";
          }
          leaf oam-loss-sd {
            type uint32 {
              range "0..100";
            }
            // NCS drop default statement
            description
              "Configure the SD threshold of OAM loss measurement.";
          }
          leaf oam-loss-sf {
            type uint32 {
              range "0..100";
            }
            // NCS drop default statement
            description
              "Configure the SF threshold of OAM Loss Measurement.";
          }
          leaf slm-send-enable {
            type boolean;
            // NCS drop default statement
            description
              "Enable/disable a device sends packets for proactive single-ended loss measurement.";
          }
          leaf slm-threshold1 {
            type uint32 {
              range "1..1000000";
            }
            // NCS drop default statement
            description
              "Configure threshold1 of proactive single-ended loss measurement. The default value is 1.";
          }
          leaf slm-threshold2 {
            type uint32 {
              range "1..1000000";
            }
            // NCS drop default statement
            description
              "Configure threshold2 of proactive single-ended loss measurement. The default value is 10.";
          }
          leaf two-dm-send-enable {
            type boolean;
            // NCS drop default statement
            description
              "Enable/disable a device sends packets for proactive two-way delay measurement.";
          }
          leaf two-dm-exp {
            type uint8 {
              range "0..7";
            }
            // NCS drop default statement
            description
              "Configure the exp value of proactive two-way delay measurement. The default value is 7.";
          }
          leaf two-dm-packet-size {
            type uint32 {
              range "64..1500";
            }
            // NCS drop default statement
            description
              "Configure the packet size of proactive two-way delay measurement.";
          }
          leaf two-dm-pad-value {
            type live_ncs_padding-value;
            // NCS drop default statement
            description
              "Configure the padding value of proactive two-way delay measurement. The default value is 0.";
          }
          leaf cc-exp {
            type uint8 {
              range "0..7";
            }
            // NCS drop default statement
            description
              "Configure the exp of packet.";
          }
          uses live_ncs_session-status;
        }
      }
      container vsi-pws {
        // NCS drop when statement
        description
          "List of pseudo wire service (PWS).";
        list vsi-pw {
          key "peer-ip vc-id vc-type";
          description
            "Configure MPLS OAM to monitor a vsi PW.";
          leaf peer-ip {
            type leafref {
              path "/ncs:devices/ncs:device/ncs:live-status/l2vpn:l2vpn/l2vpn:instances/l2vpn:instance/l2vpn:vpls/l2vpn:ldp-signaling/l2vpn:pws/l2vpn:pw/l2vpn:peer-ip" {
                tailf:xpath-root 3;
              }
            }
            description
              "Configure peer IP of MPLS OAM binded static PW.";
          }
          leaf vc-id {
            type leafref {
              path "/ncs:devices/ncs:device/ncs:live-status/l2vpn:l2vpn/l2vpn:instances/l2vpn:instance/l2vpn:vpls/l2vpn:ldp-signaling/l2vpn:pws/l2vpn:pw/l2vpn:negotiation-vc-id" {
                tailf:xpath-root 3;
              }
            }
            description
              "Configure VC ID of MPLS OAM binded static PW.";
          }
          leaf vc-type {
            type leafref {
              path "/ncs:devices/ncs:device/ncs:live-status/l2vpn:l2vpn/l2vpn:instances/l2vpn:instance/l2vpn:vpls/l2vpn:ldp-signaling/l2vpn:pws/l2vpn:pw/l2vpn:encapsulation-type" {
                tailf:xpath-root 3;
              }
            }
            description
              "Configure remote VC Type of MPLS OAM binded static PW.";
          }
          leaf remote-lsr-id {
            type inet:ipv4-address-no-zone;
            description
              "Configure a remote LSR ID.";
          }
          leaf remote-vc-id {
            type uint32 {
              range "0..4294967295";
            }
            description
              "Configure a remote VC ID of a static PW to which MPLS OAM is bound.";
          }
          leaf remote-vc-type {
            type live_ncs_l2vc-type;
            description
              "Configure a remote VC type of a static PW to which MPLS OAM is bound.";
          }
          leaf detect-pkt-type {
            type live_ncs_detect-pkt-type;
            // NCS drop default statement
            description
              "Configure a detection packet type.";
          }
          leaf detect-mode {
            type live_ncs_detect-mode;
            // NCS drop default statement
            description
              "Configure a detection mode.";
          }
          leaf auto-mode-over-time {
            // NCS drop when statement
            type uint8 {
              range "0..255";
            }
            // NCS drop default statement
            description
              "Configure the Over Time.";
          }
          leaf detect-frequence {
            type live_ncs_detect-interval;
            // NCS drop must statement
            // NCS drop mandatory statement
            description
              "Configure the detection packet type.";
          }
          leaf bdi-frequence {
            type live_ncs_bdi-frequency;
            // NCS drop default statement
            description
              "BDI packet frequency, detect-freq indicate the same as frequency of detecting packet.";
          }
          leaf compatibility-mode {
            type live_ncs_compatibility-mode;
            // NCS drop default statement
            description
              "Configure Compatibility Mode.";
          }
          leaf oam-active-status {
            type live_ncs_active-type;
            // NCS drop default statement
            description
              "Whether MPLS OAM detection is enabled. This function is disabled by default.";
          }
          leaf send-enable {
            type boolean;
            // NCS drop default statement
            description
              "Enable/disable the MPLS OAM packets can be sent.";
          }
          leaf receive-enable {
            type boolean;
            // NCS drop default statement
            description
              "Enable/disable MPLS OAM packets can be received.";
          }
          leaf oam-loss-sd {
            type uint32 {
              range "0..100";
            }
            // NCS drop default statement
            description
              "Configure the SD threshold of OAM loss measurement.";
          }
          leaf oam-loss-sf {
            type uint32 {
              range "0..100";
            }
            // NCS drop default statement
            description
              "Configure the SF threshold of OAM Loss Measurement.";
          }
          leaf slm-send-enable {
            type boolean;
            // NCS drop default statement
            description
              "Enable/disable a device sends packets for proactive single-ended loss measurement.";
          }
          leaf slm-threshold1 {
            type uint32 {
              range "1..1000000";
            }
            // NCS drop default statement
            description
              "Configure threshold1 of proactive single-ended loss measurement. The default value is 1.";
          }
          leaf slm-threshold2 {
            type uint32 {
              range "1..1000000";
            }
            // NCS drop default statement
            description
              "Configure threshold2 of proactive single-ended loss measurement. The default value is 10.";
          }
          leaf two-dm-send-enable {
            type boolean;
            // NCS drop default statement
            description
              "Enable/disable a device sends packets for proactive two-way delay measurement.";
          }
          leaf two-dm-exp {
            type uint8 {
              range "0..7";
            }
            // NCS drop default statement
            description
              "Configure the exp value of proactive two-way delay measurement. The default value is 7.";
          }
          leaf two-dm-packet-size {
            type uint32 {
              range "64..1500";
            }
            // NCS drop default statement
            description
              "Configure the packet size of proactive two-way delay measurement.";
          }
          leaf two-dm-pad-value {
            type live_ncs_padding-value;
            // NCS drop default statement
            description
              "Configure the padding value of proactive two-way delay measurement. The default value is 0.";
          }
          leaf cc-exp {
            type uint8 {
              range "0..7";
            }
            // NCS drop default statement
            description
              "Configure the exp of packet.";
          }
          uses live_ncs_session-status;
        }
      }
    }
  }
  augment "/ncs:devices/ncs:template/ncs:ned-id/ncs:config" {
    container mplsoam {
      description
        "MPLS OAM.";
      container global {
        description
          "Configure global MPLS OAM attribute.";
        leaf oam-enable {
          // NCS drop when statement
          type string;
          // NCS drop default statement
          description
            "Enable/disable global MPLS OAM.";
        }
        leaf fdi-enable {
          type string;
          // NCS drop default statement
          description
            "Enable/disable MPLS OAM FDI.";
        }
        leaf itu-mode {
          // NCS drop when statement
          type string;
          // NCS drop default statement
          description
            "Enable/disable global mode of MPLS OAM.";
        }
        // NCS drop config false leaf 'oam-num'
      }
      container tunnels {
        // NCS drop when statement
        description
          "Configure tunnels.";
        container egress-id-tunnels {
          description
            "List of MPLS OAM monitors egress LSP.";
          list egress-id-tunnel {
            // NCS patched for predictable order
            ordered-by user;
            key "id ingress-lsr-id";
            description
              "Configure MPLS OAM monitors egress LSP.";
            leaf id {
              type string;
              description
                "Configure an ID of tunnel.";
            }
            leaf ingress-lsr-id {
              type string;
              description
                "Configure an LSR ID.";
            }
            leaf reverse-name {
              type string;
              // NCS drop must statement
              description
                "Configure a Backward Tunnel Name.";
            }
            leaf reverse-mode {
              type ncs_template_reverse-mode;
              // NCS drop default statement
              description
                "Configure Backward Sharing Mode.";
            }
            leaf oam-loss-sd {
              type string;
              // NCS drop default statement
              description
                "Configure the SD threshold of OAM loss measurement.";
            }
            leaf oam-loss-sf {
              type string;
              // NCS drop default statement
              description
                "Configure the SF threshold of OAM loss measurement.";
            }
            leaf slm-threshold1 {
              type string;
              // NCS drop default statement
              description
                "Configure threshold1 of proactive single-ended loss measurement. The default value is 1.";
            }
            leaf slm-threshold2 {
              type string;
              // NCS drop default statement
              description
                "Configure threshold2 of proactive single-ended loss measurement. The default value is 10.";
            }
            leaf detect-mode {
              type ncs_template_detect-mode;
              // NCS drop default statement
              description
                "Configure a detection mode.";
            }
            leaf auto-mode-over-time {
              // NCS drop when statement
              type string;
              // NCS drop default statement
              description
                "Configure a First Packet Timeout Coefficient, Step is 30s.";
            }
            leaf detect-pkt-type {
              type ncs_template_detect-pkt-type;
              // NCS drop default statement
              description
                "Configure a Type of Detected Packet.";
            }
            leaf detect-frequence {
              type ncs_template_detect-interval;
              // NCS drop must statement
              // NCS drop mandatory statement
              description
                "Configure the detection packet frequency.";
            }
            leaf bdi-frequence {
              type ncs_template_bdi-frequency;
              // NCS drop default statement
              description
                "BDI packet frequency, detect-freq indicate the same as frequency of detecting packet.";
            }
            leaf receive-enable {
              type string;
              // NCS drop default statement
              description
                "Enable/disable MPLS OAM packets can be received.";
            }
            leaf oam-active-status {
              type ncs_template_active-type;
              // NCS drop default statement
              description
                "Whether MPLS OAM detection is enabled. This function is disabled by default.";
            }
            // NCS drop config false leaf description
            // NCS drop config false leaf 'lsp-type'
            uses ncs_template_session-status;
          }
        }
        container egress-name-tunnels {
          description
            "List of MPLS OAM monitors egress static LSP.";
          list egress-name-tunnel {
            // NCS patched for predictable order
            ordered-by user;
            key "name";
            description
              "Configure MPLS OAM monitors egress LSP.";
            leaf name {
              type pub-type:ncs_template_if-name;
              description
                "Configure a tunnel interface name.";
            }
            leaf reverse-name {
              type string;
              // NCS drop must statement
              description
                "Configure a Backward Tunnel Name.";
            }
            leaf reverse-mode {
              type ncs_template_reverse-mode;
              // NCS drop default statement
              description
                "Configure Backward Sharing Mode.";
            }
            leaf oam-loss-sd {
              type string;
              // NCS drop default statement
              description
                "Configure the SD threshold of OAM loss measurement.";
            }
            leaf oam-loss-sf {
              type string;
              // NCS drop default statement
              description
                "Configure the SF threshold of OAM loss measurement.";
            }
            leaf slm-threshold1 {
              type string;
              // NCS drop default statement
              description
                "Configure threshold1 of proactive single-ended loss measurement. The default value is 1.";
            }
            leaf slm-threshold2 {
              type string;
              // NCS drop default statement
              description
                "Configure threshold2 of proactive single-ended loss measurement. The default value is 10.";
            }
            leaf detect-mode {
              type ncs_template_detect-mode;
              // NCS drop default statement
              description
                "Configure a detection mode.";
            }
            leaf auto-mode-over-time {
              // NCS drop when statement
              type string;
              // NCS drop default statement
              description
                "Configure a First Packet Timeout Coefficient, Step is 30s.";
            }
            leaf detect-pkt-type {
              type ncs_template_detect-pkt-type;
              // NCS drop default statement
              description
                "Configure a Type of Detected Packet.";
            }
            leaf detect-frequence {
              type ncs_template_detect-interval;
              // NCS drop must statement
              // NCS drop mandatory statement
              description
                "Configure the detection packet frequency.";
            }
            leaf bdi-frequence {
              type ncs_template_bdi-frequency;
              // NCS drop default statement
              description
                "BDI packet frequency, detect-freq indicate the same as frequency of detecting packet.";
            }
            leaf receive-enable {
              type string;
              // NCS drop default statement
              description
                "Enable/disable MPLS OAM packets can be received.";
            }
            leaf oam-active-status {
              type ncs_template_active-type;
              // NCS drop default statement
              description
                "Whether MPLS OAM detection is enabled. This function is disabled by default.";
            }
            // NCS drop config false leaf description
            // NCS drop config false leaf 'lsp-type'
            uses ncs_template_session-status;
          }
        }
        container ingress-tunnels {
          description
            "List of MPLS OAM monitors ingress LSP.";
          list ingress-tunnel {
            // NCS patched for predictable order
            ordered-by user;
            key "name";
            description
              "Configure MPLS OAM monitors egress LSP.";
            leaf name {
              type string;
              // NCS drop must statement
              description
                "Configure a tunnel interface name.";
            }
            choice reverse-lsp-name-or-id {
              description
                "Configure reverse lsp name or lsr id.";
              case lsp-name {
                description
                  "Configure reverse lsp name.";
                leaf reverse-name {
                  type pub-type:ncs_template_if-name;
                  description
                    "Configure the reverse tunnel name.";
                }
              }
              case lsp-id {
                description
                  "Configure reverse lsr id.";
                leaf reverse-id {
                  type string;
                  description
                    "Configure the remote ID of tunnel.";
                }
                leaf reverse-lsr-id {
                  type string;
                  description
                    "Configure the remote LSR ID.";
                }
              }
            }
            leaf reverse-mode {
              type ncs_template_reverse-mode;
              // NCS drop default statement
              description
                "Configure Backward Sharing Mode.";
            }
            leaf oam-loss-sd {
              type string;
              // NCS drop default statement
              description
                "Configure the SD threshold of OAM loss measurement.";
            }
            leaf oam-loss-sf {
              type string;
              // NCS drop default statement
              description
                "Configure the SF threshold of OAM loss measurement.";
            }
            leaf slm-send-enable {
              type string;
              // NCS drop default statement
              description
                "Enable/disable a device sends packets for proactive single-ended loss measurement. This function is disabled by default.";
            }
            leaf slm-threshold1 {
              type string;
              // NCS drop default statement
              description
                "Configure threshold1 of proactive single-ended loss measurement. The default value is 1.";
            }
            leaf slm-threshold2 {
              type string;
              // NCS drop default statement
              description
                "Configure threshold2 of proactive single-ended loss measurement. The default value is 10.";
            }
            leaf detect-pkt-type {
              type ncs_template_detect-pkt-type;
              // NCS drop default statement
              description
                "Configure a Type of Detected Packet.";
            }
            leaf detect-frequence {
              type ncs_template_detect-interval;
              // NCS drop must statement
              // NCS drop mandatory statement
              description
                "Configure the detection packet frequency.";
            }
            leaf bdi-frequence {
              type ncs_template_bdi-frequency;
              // NCS drop default statement
              description
                "BDI packet frequency, detect-freq indicate the same as frequency of detecting packet.";
            }
            leaf compatibility-mode {
              type ncs_template_compatibility-mode;
              // NCS drop default statement
              description
                "Configure Compatibility Mode.";
            }
            leaf send-enable {
              type string;
              // NCS drop default statement
              description
                "Enable/disable the MPLS OAM packets can be sent.";
            }
            leaf cc-exp {
              type string;
              // NCS drop default statement
              description
                "Configure the exp of packet.";
            }
            leaf oam-active-status {
              type ncs_template_active-type;
              // NCS drop default statement
              description
                "Whether MPLS OAM detection is enabled. This function is disabled by default.";
            }
            leaf two-dm-send-enable {
              type string;
              // NCS drop default statement
              description
                "Enable/disable a device sends packets for proactive two-way delay measurement. This function is disabled by default.";
            }
            leaf two-dm-packet-size {
              type string;
              // NCS drop default statement
              description
                "Configure the packet size of proactive two-way delay measurement.";
            }
            leaf two-dm-pad-value {
              type ncs_template_padding-value;
              // NCS drop default statement
              description
                "Configure the padding value of proactive two-way delay measurement. The default value is 0.";
            }
            // NCS drop config false leaf description
            // NCS drop config false leaf 'lsp-type'
            uses ncs_template_session-status;
          }
        }
        container co-route-tunnels {
          description
            "List of MPLS OAM monitors cr static LSP.";
          list co-route-tunnel {
            // NCS patched for predictable order
            ordered-by user;
            key "name";
            description
              "Configure MPLS OAM monitors cr static LSP.";
            leaf name {
              type string;
              // NCS drop must statement
              description
                "Configure a tunnel interface name.";
            }
            leaf oam-loss-sd {
              type string;
              // NCS drop default statement
              description
                "Configure the SD threshold of OAM loss measurement.";
            }
            leaf oam-loss-sf {
              type string;
              // NCS drop default statement
              description
                "Configure the SF threshold of OAM loss measurement.";
            }
            leaf slm-send-enable {
              type string;
              // NCS drop default statement
              description
                "Enable/disable a device sends packets for proactive single-ended loss measurement.";
            }
            leaf slm-threshold1 {
              type string;
              // NCS drop default statement
              description
                "Configure threshold1 of proactive single-ended loss measurement. The default value is 1.";
            }
            leaf slm-threshold2 {
              type string;
              // NCS drop default statement
              description
                "Configure threshold2 of proactive single-ended loss measurement. The default value is 10.";
            }
            leaf detect-mode {
              type ncs_template_detect-mode;
              // NCS drop default statement
              description
                "Configure a detection mode.";
            }
            leaf auto-mode-over-time {
              // NCS drop when statement
              type string;
              // NCS drop default statement
              description
                "Configure a First Packet Timeout Coefficient, Step is 30s.";
            }
            leaf detect-pkt-type {
              type ncs_template_detect-pkt-type;
              // NCS drop default statement
              description
                "Configure a Type of Detected Packet.";
            }
            leaf detect-frequence {
              type ncs_template_detect-interval;
              // NCS drop must statement
              // NCS drop mandatory statement
              description
                "Configure the detection packet frequency.";
            }
            leaf bdi-frequence {
              type ncs_template_bdi-frequency;
              // NCS drop default statement
              description
                "BDI packet frequency, detect-freq indicate the same as frequency of detecting packet.";
            }
            leaf compatibility-mode {
              type ncs_template_compatibility-mode;
              // NCS drop default statement
              description
                "Configure Compatibility Mode.";
            }
            leaf send-enable {
              type string;
              // NCS drop default statement
              description
                "Enable/disable the MPLS OAM packets can be sent.";
            }
            leaf receive-enable {
              type string;
              // NCS drop default statement
              description
                "Enable/disable MPLS OAM packets can be received.";
            }
            leaf cc-exp {
              type string;
              // NCS drop default statement
              description
                "Configure the exp of packet.";
            }
            // NCS drop config false leaf description
            leaf oam-active-status {
              type ncs_template_active-type;
              // NCS drop default statement
              description
                "Whether MPLS OAM detection is enabled. This function is disabled by default.";
            }
            leaf two-dm-send-enable {
              type string;
              // NCS drop default statement
              description
                "Enable/disable a device sends packets for proactive two-way delay measurement.";
            }
            leaf two-dm-packet-size {
              type string;
              // NCS drop default statement
              description
                "Configure the packet size of proactive two-way delay measurement.";
            }
            leaf two-dm-pad-value {
              type ncs_template_padding-value;
              // NCS drop default statement
              description
                "Configure the padding value of proactive two-way delay measurement. The default value is 0.";
            }
            // NCS drop config false leaf 'lsp-type'
            uses ncs_template_session-status;
          }
        }
      }
      container vll-pws {
        // NCS drop when statement
        description
          "List of pseudo wire service (PWS).";
        list vll-pw {
          // NCS patched for predictable order
          ordered-by user;
          key "l2vpn-name l2vpn-type l2vpn-role";
          description
            "Configure MPLS OAM to monitor a VLL PW.";
          leaf l2vpn-name {
            type string;
            description
              "Configure l2vpn name of MPLS OAM binded static PW.";
          }
          leaf l2vpn-type {
            type string;
            description
              "Configure l2vpn name of MPLS OAM binded static PW.";
          }
          leaf l2vpn-role {
            type string;
            description
              "Configure pw role of MPLS OAM binded static PW.";
          }
          leaf remote-lsr-id {
            type string;
            description
              "Configure a remote LSR ID.";
          }
          leaf remote-vc-id {
            type string;
            description
              "Configure a remote VC ID of a static PW to which MPLS OAM is bound.";
          }
          leaf remote-vc-type {
            type ncs_template_l2vc-type;
            description
              "Configure a remote VC type of a static PW to which MPLS OAM is bound.";
          }
          leaf detect-pkt-type {
            type ncs_template_detect-pkt-type;
            // NCS drop default statement
            description
              "Configure a detection packet type.";
          }
          leaf detect-mode {
            type ncs_template_detect-mode;
            // NCS drop default statement
            description
              "Configure a detection mode.";
          }
          leaf auto-mode-over-time {
            // NCS drop when statement
            type string;
            // NCS drop default statement
            description
              "Configure the Over Time.";
          }
          leaf detect-frequence {
            type ncs_template_detect-interval;
            // NCS drop must statement
            // NCS drop mandatory statement
            description
              "Configure the detection packet type.";
          }
          leaf bdi-frequence {
            type ncs_template_bdi-frequency;
            // NCS drop default statement
            description
              "BDI packet frequency, detect-freq indicate the same as frequency of detecting packet.";
          }
          leaf compatibility-mode {
            type ncs_template_compatibility-mode;
            // NCS drop default statement
            description
              "Configure Compatibility Mode.";
          }
          leaf oam-active-status {
            type ncs_template_active-type;
            // NCS drop default statement
            description
              "Whether MPLS OAM detection is enabled. This function is disabled by default.";
          }
          leaf send-enable {
            type string;
            // NCS drop default statement
            description
              "Enable/disable the MPLS OAM packets can be sent.";
          }
          leaf receive-enable {
            type string;
            // NCS drop default statement
            description
              "Enable/disable MPLS OAM packets can be received.";
          }
          leaf oam-loss-sd {
            type string;
            // NCS drop default statement
            description
              "Configure the SD threshold of OAM loss measurement.";
          }
          leaf oam-loss-sf {
            type string;
            // NCS drop default statement
            description
              "Configure the SF threshold of OAM Loss Measurement.";
          }
          leaf slm-send-enable {
            type string;
            // NCS drop default statement
            description
              "Enable/disable a device sends packets for proactive single-ended loss measurement.";
          }
          leaf slm-threshold1 {
            type string;
            // NCS drop default statement
            description
              "Configure threshold1 of proactive single-ended loss measurement. The default value is 1.";
          }
          leaf slm-threshold2 {
            type string;
            // NCS drop default statement
            description
              "Configure threshold2 of proactive single-ended loss measurement. The default value is 10.";
          }
          leaf two-dm-send-enable {
            type string;
            // NCS drop default statement
            description
              "Enable/disable a device sends packets for proactive two-way delay measurement.";
          }
          leaf two-dm-exp {
            type string;
            // NCS drop default statement
            description
              "Configure the exp value of proactive two-way delay measurement. The default value is 7.";
          }
          leaf two-dm-packet-size {
            type string;
            // NCS drop default statement
            description
              "Configure the packet size of proactive two-way delay measurement.";
          }
          leaf two-dm-pad-value {
            type ncs_template_padding-value;
            // NCS drop default statement
            description
              "Configure the padding value of proactive two-way delay measurement. The default value is 0.";
          }
          leaf cc-exp {
            type string;
            // NCS drop default statement
            description
              "Configure the exp of packet.";
          }
          uses ncs_template_session-status;
        }
      }
      container vsi-pws {
        // NCS drop when statement
        description
          "List of pseudo wire service (PWS).";
        list vsi-pw {
          // NCS patched for predictable order
          ordered-by user;
          key "peer-ip vc-id vc-type";
          description
            "Configure MPLS OAM to monitor a vsi PW.";
          leaf peer-ip {
            type string;
            description
              "Configure peer IP of MPLS OAM binded static PW.";
          }
          leaf vc-id {
            type string;
            description
              "Configure VC ID of MPLS OAM binded static PW.";
          }
          leaf vc-type {
            type string;
            description
              "Configure remote VC Type of MPLS OAM binded static PW.";
          }
          leaf remote-lsr-id {
            type string;
            description
              "Configure a remote LSR ID.";
          }
          leaf remote-vc-id {
            type string;
            description
              "Configure a remote VC ID of a static PW to which MPLS OAM is bound.";
          }
          leaf remote-vc-type {
            type ncs_template_l2vc-type;
            description
              "Configure a remote VC type of a static PW to which MPLS OAM is bound.";
          }
          leaf detect-pkt-type {
            type ncs_template_detect-pkt-type;
            // NCS drop default statement
            description
              "Configure a detection packet type.";
          }
          leaf detect-mode {
            type ncs_template_detect-mode;
            // NCS drop default statement
            description
              "Configure a detection mode.";
          }
          leaf auto-mode-over-time {
            // NCS drop when statement
            type string;
            // NCS drop default statement
            description
              "Configure the Over Time.";
          }
          leaf detect-frequence {
            type ncs_template_detect-interval;
            // NCS drop must statement
            // NCS drop mandatory statement
            description
              "Configure the detection packet type.";
          }
          leaf bdi-frequence {
            type ncs_template_bdi-frequency;
            // NCS drop default statement
            description
              "BDI packet frequency, detect-freq indicate the same as frequency of detecting packet.";
          }
          leaf compatibility-mode {
            type ncs_template_compatibility-mode;
            // NCS drop default statement
            description
              "Configure Compatibility Mode.";
          }
          leaf oam-active-status {
            type ncs_template_active-type;
            // NCS drop default statement
            description
              "Whether MPLS OAM detection is enabled. This function is disabled by default.";
          }
          leaf send-enable {
            type string;
            // NCS drop default statement
            description
              "Enable/disable the MPLS OAM packets can be sent.";
          }
          leaf receive-enable {
            type string;
            // NCS drop default statement
            description
              "Enable/disable MPLS OAM packets can be received.";
          }
          leaf oam-loss-sd {
            type string;
            // NCS drop default statement
            description
              "Configure the SD threshold of OAM loss measurement.";
          }
          leaf oam-loss-sf {
            type string;
            // NCS drop default statement
            description
              "Configure the SF threshold of OAM Loss Measurement.";
          }
          leaf slm-send-enable {
            type string;
            // NCS drop default statement
            description
              "Enable/disable a device sends packets for proactive single-ended loss measurement.";
          }
          leaf slm-threshold1 {
            type string;
            // NCS drop default statement
            description
              "Configure threshold1 of proactive single-ended loss measurement. The default value is 1.";
          }
          leaf slm-threshold2 {
            type string;
            // NCS drop default statement
            description
              "Configure threshold2 of proactive single-ended loss measurement. The default value is 10.";
          }
          leaf two-dm-send-enable {
            type string;
            // NCS drop default statement
            description
              "Enable/disable a device sends packets for proactive two-way delay measurement.";
          }
          leaf two-dm-exp {
            type string;
            // NCS drop default statement
            description
              "Configure the exp value of proactive two-way delay measurement. The default value is 7.";
          }
          leaf two-dm-packet-size {
            type string;
            // NCS drop default statement
            description
              "Configure the packet size of proactive two-way delay measurement.";
          }
          leaf two-dm-pad-value {
            type ncs_template_padding-value;
            // NCS drop default statement
            description
              "Configure the padding value of proactive two-way delay measurement. The default value is 0.";
          }
          leaf cc-exp {
            type string;
            // NCS drop default statement
            description
              "Configure the exp of packet.";
          }
          uses ncs_template_session-status;
        }
      }
    }
  }
}
