module huawei-ifit {
  // Generated by yanger -t ncs
  tailf:mount-id "huawei-nc-1.0:huawei-nc-1.0";
  tailf:ncs-device-type "netconf";

  yang-version 1;
  namespace "urn:huawei:yang:huawei-ifit";
  prefix ifit;

  import huawei-extension {
    prefix ext;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "This module contains a collection of YANG definitions IFIT feature.";

  revision 2019-05-21 {
    description
      "Initial revision.";
    reference "Huawei private.";
  }
  ext:task-name "ifit";

  augment "/ncs:devices/ncs:device/ncs:config" {
    container ifit {
      tailf:ncs-device-type "netconf";
      tailf:display-when "not(../../ncs:module) or ../../ncs:module[ncs:name='huawei-ifit']";
      presence "IFIT Enable.";
      description
        "Inband flow information telemetry.";
    }
  }
  augment "/ncs:devices/ncs:device/ncs:live-status" {
    container ifit {
      tailf:ncs-device-type "netconf";
      tailf:display-when "not(../../ncs:module) or ../../ncs:module[ncs:name='huawei-ifit'] or (../../ncs:live-status-protocol[not(ncs:capability)]) or (../../ncs:live-status-protocol/ncs:capability/ncs:module[.='huawei-ifit'])";
      presence "IFIT Enable.";
      description
        "Inband flow information telemetry.";
    }
  }
  augment "/ncs:devices/ncs:template/ncs:ned-id/ncs:config" {
    container ifit {
      presence "IFIT Enable.";
      description
        "Inband flow information telemetry.";
    }
  }
}
