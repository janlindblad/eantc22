module huawei-clocksync-phy {
  // Generated by yanger -t ncs
  tailf:mount-id "huawei-nc-1.0:huawei-nc-1.0";
  tailf:ncs-device-type "netconf";

  namespace "urn:huawei:yang:huawei-clocksync-phy";
  prefix clocksync-phy;

  import huawei-pub-type {
    prefix pub-type;
  }
  import huawei-extension {
    prefix ext;
  }
  import huawei-ifm {
    prefix ifm;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Clkm data model define.";

  revision 2020-03-17 {
    description
      "Modify the node attribute.";
    reference "Huawei private.";
  }
  revision 2020-03-14 {
    description
      "Modify the node description.";
    reference "Huawei private.";
  }
  revision 2020-03-04 {
    description
      "Modify the node description.";
    reference "Huawei private.";
  }
  revision 2019-11-11 {
    description
      "Modify node must condition.";
    reference "Huawei private.";
  }
  revision 2019-03-01 {
    description
      "Initial revision.";
    reference "Huawei private.";
  }
  ext:task-name "clksync";

  typedef ncs_template_ssm-recovery-mode {
    type string;
    description
      "Configure SSM recovery mode as revertive mode or non-revertive mode.";
  }

  typedef ncs_template_ssm-level {
    type string;
    description
      "SSM level type.";
  }

  typedef ncs_template_sabit-type {
    type string;
    description
      "Sabit type.";
  }

  typedef ncs_template_source-state {
    type string;
    description
      "Status of a physical clock source.";
  }

  typedef ncs_template_pll-type {
    type string;
    description
      "PLL type.";
  }

  typedef ncs_template_source-selection-mode {
    type string;
    description
      "Clock source selection mode: forced clock source selection, manual clock source selection, and automatic clock source selection.";
  }

  typedef ncs_template_phy-source-state {
    type string;
    description
      "The physical layer interface status.";
  }

  typedef ncs_template_oam-profile-type {
    type string;
    description
      "Oam profile type.";
  }

  typedef ncs_template_bits-invalid-act {
    type string;
    description
      "Handling of 2M phase-locked source failure.";
  }

  typedef ncs_template_clock-bits-type {
    type string;
    description
      "BITS TYPE.";
  }

  typedef ncs_template_clock-run-mode {
    type string;
    description
      "Clock run mode type.";
  }

  typedef ncs_template_dev-clk-level-type {
    type string;
    description
      "The Clock Level of the current device.";
  }

  typedef ncs_rpc_notif_ssm-recovery-mode {
    type enumeration {
      enum "revertive" {
        value 0;
        description
          "Set the SSM selection mode to revertive mode to allow the system to always select the best physical clock source.";
      }
      enum "non-revertive" {
        value 1;
        description
          "Set the SSM mode of the physical clock to non-revertive mode to allow the system to select a physical clock source lower than or equal to the best one in current clock sources (QL is the highest). If there is no such source, the best clock source is selected.";
      }
    }
    description
      "Configure SSM recovery mode as revertive mode or non-revertive mode.";
  }

  typedef ncs_rpc_notif_ssm-level {
    type enumeration {
      enum "unk" {
        value 0;
        description
          "Unknown SSM level (UNK).";
      }
      enum "prc" {
        value 2;
        description
          "SSM level of the G.811 clock (PRC).";
      }
      enum "ssua" {
        value 4;
        description
          "G.812 transit clock (SSUA).";
      }
      enum "ssub" {
        value 8;
        description
          "G.812 local clock (SSUB).";
      }
      enum "sec" {
        value 11;
        description
          "SDH (sec).";
      }
      enum "dnu" {
        value 15;
        description
          "The quality level of the clock source is unavailable (DNU).";
      }
      enum "none" {
        value 16;
        description
          "Invalid SSM level.";
      }
      enum "prtc" {
        value 8194;
        description
          "G.8272 clock (PRTC).";
      }
      enum "eprtc" {
        value 8450;
        description
          "G.8272.1 clock (EPRTC).";
      }
      enum "esec" {
        value 8715;
        description
          "G.8262.1 clock (ESEC).";
      }
      enum "eprc" {
        value 8962;
        description
          "G.811.1 clock (EPRC).";
      }
    }
    description
      "SSM level type.";
  }

  typedef ncs_rpc_notif_sabit-type {
    type enumeration {
      enum "sa4" {
        value 4;
        description
          "Sa4 timeslot.";
      }
      enum "sa5" {
        value 5;
        description
          "Sa5 timeslot.";
      }
      enum "sa6" {
        value 6;
        description
          "Sa6 timeslot.";
      }
      enum "sa7" {
        value 7;
        description
          "Sa7 timeslot.";
      }
      enum "sa8" {
        value 8;
        description
          "Sa8 timeslot.";
      }
    }
    description
      "Sabit type.";
  }

  typedef ncs_rpc_notif_source-state {
    type enumeration {
      enum "initial" {
        value 0;
        description
          "The clock source is in the initialized state.";
      }
      enum "normal" {
        value 1;
        description
          "The physical source is normal.";
      }
      enum "abnormal" {
        value 2;
        description
          "The clock source is abnormal.";
      }
      enum "waitwtr" {
        value 3;
        description
          "The clock source is in the state of waiting for recovery.";
      }
      enum "holdoff" {
        value 4;
        description
          "The clock source is in the holdoff state.";
      }
    }
    description
      "Status of a physical clock source.";
  }

  typedef ncs_rpc_notif_pll-type {
    type enumeration {
      enum "system" {
        value 0;
        description
          "Select system PLL clock source.";
      }
      enum "sync2m-1" {
        value 1;
        description
          "Select 2M-1 PLL clock source.";
      }
      enum "sync2m-2" {
        value 2;
        description
          "Select 2M-2 PLL clock source.";
      }
    }
    description
      "PLL type.";
  }

  typedef ncs_rpc_notif_source-selection-mode {
    type enumeration {
      enum "auto" {
        value 0;
        description
          "The source selection mode is the auto mode.";
      }
      enum "manual" {
        value 1;
        description
          "The physical source selection mode is manual selection.";
      }
      enum "force" {
        value 2;
        description
          "The physical layer clock source selection mode is forcible selection.";
      }
    }
    description
      "Clock source selection mode: forced clock source selection, manual clock source selection, and automatic clock source selection.";
  }

  typedef ncs_rpc_notif_phy-source-state {
    type enumeration {
      enum "up" {
        value 1;
        description
          "The physical layer interface is Up.";
      }
      enum "down" {
        value 0;
        description
          "The physical layer interface is Down.";
      }
      enum "na" {
        value 2;
        description
          "The interface physical status is not involved.";
      }
    }
    description
      "The physical layer interface status.";
  }

  typedef ncs_rpc_notif_oam-profile-type {
    type enumeration {
      enum "none" {
        value 0;
        description
          "No OAM protocol is selected.";
      }
      enum "ccsa" {
        value 1;
        description
          "CCSA OAM technique requirements.";
      }
    }
    description
      "Oam profile type.";
  }

  typedef ncs_rpc_notif_bits-invalid-act {
    type enumeration {
      enum "shutdown" {
        value 0;
        description
          "When no tracing source is available for the 2M ring, the output signal action is shut down.";
      }
      enum "txdnu" {
        value 1;
        description
          "Set 2Mbps signal LTI action as sending DNU.";
      }
      enum "txais" {
        value 2;
        description
          "Set 2Mbps signal LTI action as sending the AIS alarm.";
      }
    }
    description
      "Handling of 2M phase-locked source failure.";
  }

  typedef ncs_rpc_notif_clock-bits-type {
    type enumeration {
      enum "1pps" {
        value 3;
        description
          "Bits type is 1PPS.";
      }
      enum "2mhz" {
        value 1;
        description
          "Bits type is 2MHZ.";
      }
      enum "2mbps" {
        value 0;
        description
          "Bits type is 2MBPS.";
      }
      enum "dcls" {
        value 2;
        description
          "Bits type is DCLS.";
      }
      enum "none" {
        value 255;
        description
          "NONE.";
      }
    }
    description
      "BITS TYPE.";
  }

  typedef ncs_rpc_notif_clock-run-mode {
    type enumeration {
      enum "free" {
        value 2;
        description
          "Free.";
      }
      enum "hold" {
        value 1;
        description
          "Hold.";
      }
      enum "normal" {
        value 0;
        description
          "Normal.";
      }
    }
    description
      "Clock run mode type.";
  }

  typedef ncs_rpc_notif_dev-clk-level-type {
    type enumeration {
      enum "SEC" {
        value 0;
        description
          "Level is SEC.";
      }
      enum "ESEC" {
        value 1;
        description
          "Level is eSEC.";
      }
    }
    description
      "The Clock Level of the current device.";
  }

  typedef live_ncs_ssm-recovery-mode {
    type enumeration {
      enum "revertive" {
        value 0;
        description
          "Set the SSM selection mode to revertive mode to allow the system to always select the best physical clock source.";
      }
      enum "non-revertive" {
        value 1;
        description
          "Set the SSM mode of the physical clock to non-revertive mode to allow the system to select a physical clock source lower than or equal to the best one in current clock sources (QL is the highest). If there is no such source, the best clock source is selected.";
      }
    }
    description
      "Configure SSM recovery mode as revertive mode or non-revertive mode.";
  }

  typedef live_ncs_ssm-level {
    type enumeration {
      enum "unk" {
        value 0;
        description
          "Unknown SSM level (UNK).";
      }
      enum "prc" {
        value 2;
        description
          "SSM level of the G.811 clock (PRC).";
      }
      enum "ssua" {
        value 4;
        description
          "G.812 transit clock (SSUA).";
      }
      enum "ssub" {
        value 8;
        description
          "G.812 local clock (SSUB).";
      }
      enum "sec" {
        value 11;
        description
          "SDH (sec).";
      }
      enum "dnu" {
        value 15;
        description
          "The quality level of the clock source is unavailable (DNU).";
      }
      enum "none" {
        value 16;
        description
          "Invalid SSM level.";
      }
      enum "prtc" {
        value 8194;
        description
          "G.8272 clock (PRTC).";
      }
      enum "eprtc" {
        value 8450;
        description
          "G.8272.1 clock (EPRTC).";
      }
      enum "esec" {
        value 8715;
        description
          "G.8262.1 clock (ESEC).";
      }
      enum "eprc" {
        value 8962;
        description
          "G.811.1 clock (EPRC).";
      }
    }
    description
      "SSM level type.";
  }

  typedef live_ncs_sabit-type {
    type enumeration {
      enum "sa4" {
        value 4;
        description
          "Sa4 timeslot.";
      }
      enum "sa5" {
        value 5;
        description
          "Sa5 timeslot.";
      }
      enum "sa6" {
        value 6;
        description
          "Sa6 timeslot.";
      }
      enum "sa7" {
        value 7;
        description
          "Sa7 timeslot.";
      }
      enum "sa8" {
        value 8;
        description
          "Sa8 timeslot.";
      }
    }
    description
      "Sabit type.";
  }

  typedef live_ncs_source-state {
    type enumeration {
      enum "initial" {
        value 0;
        description
          "The clock source is in the initialized state.";
      }
      enum "normal" {
        value 1;
        description
          "The physical source is normal.";
      }
      enum "abnormal" {
        value 2;
        description
          "The clock source is abnormal.";
      }
      enum "waitwtr" {
        value 3;
        description
          "The clock source is in the state of waiting for recovery.";
      }
      enum "holdoff" {
        value 4;
        description
          "The clock source is in the holdoff state.";
      }
    }
    description
      "Status of a physical clock source.";
  }

  typedef live_ncs_pll-type {
    type enumeration {
      enum "system" {
        value 0;
        description
          "Select system PLL clock source.";
      }
      enum "sync2m-1" {
        value 1;
        description
          "Select 2M-1 PLL clock source.";
      }
      enum "sync2m-2" {
        value 2;
        description
          "Select 2M-2 PLL clock source.";
      }
    }
    description
      "PLL type.";
  }

  typedef live_ncs_source-selection-mode {
    type enumeration {
      enum "auto" {
        value 0;
        description
          "The source selection mode is the auto mode.";
      }
      enum "manual" {
        value 1;
        description
          "The physical source selection mode is manual selection.";
      }
      enum "force" {
        value 2;
        description
          "The physical layer clock source selection mode is forcible selection.";
      }
    }
    description
      "Clock source selection mode: forced clock source selection, manual clock source selection, and automatic clock source selection.";
  }

  typedef live_ncs_phy-source-state {
    type enumeration {
      enum "up" {
        value 1;
        description
          "The physical layer interface is Up.";
      }
      enum "down" {
        value 0;
        description
          "The physical layer interface is Down.";
      }
      enum "na" {
        value 2;
        description
          "The interface physical status is not involved.";
      }
    }
    description
      "The physical layer interface status.";
  }

  typedef live_ncs_oam-profile-type {
    type enumeration {
      enum "none" {
        value 0;
        description
          "No OAM protocol is selected.";
      }
      enum "ccsa" {
        value 1;
        description
          "CCSA OAM technique requirements.";
      }
    }
    description
      "Oam profile type.";
  }

  typedef live_ncs_bits-invalid-act {
    type enumeration {
      enum "shutdown" {
        value 0;
        description
          "When no tracing source is available for the 2M ring, the output signal action is shut down.";
      }
      enum "txdnu" {
        value 1;
        description
          "Set 2Mbps signal LTI action as sending DNU.";
      }
      enum "txais" {
        value 2;
        description
          "Set 2Mbps signal LTI action as sending the AIS alarm.";
      }
    }
    description
      "Handling of 2M phase-locked source failure.";
  }

  typedef live_ncs_clock-bits-type {
    type enumeration {
      enum "1pps" {
        value 3;
        description
          "Bits type is 1PPS.";
      }
      enum "2mhz" {
        value 1;
        description
          "Bits type is 2MHZ.";
      }
      enum "2mbps" {
        value 0;
        description
          "Bits type is 2MBPS.";
      }
      enum "dcls" {
        value 2;
        description
          "Bits type is DCLS.";
      }
      enum "none" {
        value 255;
        description
          "NONE.";
      }
    }
    description
      "BITS TYPE.";
  }

  typedef live_ncs_clock-run-mode {
    type enumeration {
      enum "free" {
        value 2;
        description
          "Free.";
      }
      enum "hold" {
        value 1;
        description
          "Hold.";
      }
      enum "normal" {
        value 0;
        description
          "Normal.";
      }
    }
    description
      "Clock run mode type.";
  }

  typedef live_ncs_dev-clk-level-type {
    type enumeration {
      enum "SEC" {
        value 0;
        description
          "Level is SEC.";
      }
      enum "ESEC" {
        value 1;
        description
          "Level is eSEC.";
      }
    }
    description
      "The Clock Level of the current device.";
  }

  typedef ssm-recovery-mode {
    type enumeration {
      enum "revertive" {
        value 0;
        description
          "Set the SSM selection mode to revertive mode to allow the system to always select the best physical clock source.";
      }
      enum "non-revertive" {
        value 1;
        description
          "Set the SSM mode of the physical clock to non-revertive mode to allow the system to select a physical clock source lower than or equal to the best one in current clock sources (QL is the highest). If there is no such source, the best clock source is selected.";
      }
    }
    description
      "Configure SSM recovery mode as revertive mode or non-revertive mode.";
  }

  typedef ssm-level {
    type enumeration {
      enum "unk" {
        value 0;
        description
          "Unknown SSM level (UNK).";
      }
      enum "prc" {
        value 2;
        description
          "SSM level of the G.811 clock (PRC).";
      }
      enum "ssua" {
        value 4;
        description
          "G.812 transit clock (SSUA).";
      }
      enum "ssub" {
        value 8;
        description
          "G.812 local clock (SSUB).";
      }
      enum "sec" {
        value 11;
        description
          "SDH (sec).";
      }
      enum "dnu" {
        value 15;
        description
          "The quality level of the clock source is unavailable (DNU).";
      }
      enum "none" {
        value 16;
        description
          "Invalid SSM level.";
      }
      enum "prtc" {
        value 8194;
        description
          "G.8272 clock (PRTC).";
      }
      enum "eprtc" {
        value 8450;
        description
          "G.8272.1 clock (EPRTC).";
      }
      enum "esec" {
        value 8715;
        description
          "G.8262.1 clock (ESEC).";
      }
      enum "eprc" {
        value 8962;
        description
          "G.811.1 clock (EPRC).";
      }
    }
    description
      "SSM level type.";
  }

  typedef sabit-type {
    type enumeration {
      enum "sa4" {
        value 4;
        description
          "Sa4 timeslot.";
      }
      enum "sa5" {
        value 5;
        description
          "Sa5 timeslot.";
      }
      enum "sa6" {
        value 6;
        description
          "Sa6 timeslot.";
      }
      enum "sa7" {
        value 7;
        description
          "Sa7 timeslot.";
      }
      enum "sa8" {
        value 8;
        description
          "Sa8 timeslot.";
      }
    }
    description
      "Sabit type.";
  }

  typedef source-state {
    type enumeration {
      enum "initial" {
        value 0;
        description
          "The clock source is in the initialized state.";
      }
      enum "normal" {
        value 1;
        description
          "The physical source is normal.";
      }
      enum "abnormal" {
        value 2;
        description
          "The clock source is abnormal.";
      }
      enum "waitwtr" {
        value 3;
        description
          "The clock source is in the state of waiting for recovery.";
      }
      enum "holdoff" {
        value 4;
        description
          "The clock source is in the holdoff state.";
      }
    }
    description
      "Status of a physical clock source.";
  }

  typedef pll-type {
    type enumeration {
      enum "system" {
        value 0;
        description
          "Select system PLL clock source.";
      }
      enum "sync2m-1" {
        value 1;
        description
          "Select 2M-1 PLL clock source.";
      }
      enum "sync2m-2" {
        value 2;
        description
          "Select 2M-2 PLL clock source.";
      }
    }
    description
      "PLL type.";
  }

  typedef source-selection-mode {
    type enumeration {
      enum "auto" {
        value 0;
        description
          "The source selection mode is the auto mode.";
      }
      enum "manual" {
        value 1;
        description
          "The physical source selection mode is manual selection.";
      }
      enum "force" {
        value 2;
        description
          "The physical layer clock source selection mode is forcible selection.";
      }
    }
    description
      "Clock source selection mode: forced clock source selection, manual clock source selection, and automatic clock source selection.";
  }

  typedef phy-source-state {
    type enumeration {
      enum "up" {
        value 1;
        description
          "The physical layer interface is Up.";
      }
      enum "down" {
        value 0;
        description
          "The physical layer interface is Down.";
      }
      enum "na" {
        value 2;
        description
          "The interface physical status is not involved.";
      }
    }
    description
      "The physical layer interface status.";
  }

  typedef oam-profile-type {
    type enumeration {
      enum "none" {
        value 0;
        description
          "No OAM protocol is selected.";
      }
      enum "ccsa" {
        value 1;
        description
          "CCSA OAM technique requirements.";
      }
    }
    description
      "Oam profile type.";
  }

  typedef bits-invalid-act {
    type enumeration {
      enum "shutdown" {
        value 0;
        description
          "When no tracing source is available for the 2M ring, the output signal action is shut down.";
      }
      enum "txdnu" {
        value 1;
        description
          "Set 2Mbps signal LTI action as sending DNU.";
      }
      enum "txais" {
        value 2;
        description
          "Set 2Mbps signal LTI action as sending the AIS alarm.";
      }
    }
    description
      "Handling of 2M phase-locked source failure.";
  }

  typedef clock-bits-type {
    type enumeration {
      enum "1pps" {
        value 3;
        description
          "Bits type is 1PPS.";
      }
      enum "2mhz" {
        value 1;
        description
          "Bits type is 2MHZ.";
      }
      enum "2mbps" {
        value 0;
        description
          "Bits type is 2MBPS.";
      }
      enum "dcls" {
        value 2;
        description
          "Bits type is DCLS.";
      }
      enum "none" {
        value 255;
        description
          "NONE.";
      }
    }
    description
      "BITS TYPE.";
  }

  typedef clock-run-mode {
    type enumeration {
      enum "free" {
        value 2;
        description
          "Free.";
      }
      enum "hold" {
        value 1;
        description
          "Hold.";
      }
      enum "normal" {
        value 0;
        description
          "Normal.";
      }
    }
    description
      "Clock run mode type.";
  }

  typedef dev-clk-level-type {
    type enumeration {
      enum "SEC" {
        value 0;
        description
          "Level is SEC.";
      }
      enum "ESEC" {
        value 1;
        description
          "Level is eSEC.";
      }
    }
    description
      "The Clock Level of the current device.";
  }

  augment "/ncs:devices/ncs:device/ncs:rpc" {
    container rpc-recover-freq-deviation {
      tailf:ncs-device-type "netconf";
      tailf:display-when "not(../../ncs:module) or ../../ncs:module[ncs:name='huawei-clocksync-phy']";
      tailf:action recover-freq-deviation {
        tailf:actionpoint ncsproxy {
          tailf:internal;
        }
        description
          "Frequency offset status of the clock source to be recovered.";
        ext:node-ref "/clocksync-phy:clocksync-phy/clocksync-phy:detections/clocksync-phy:detection";
        input {
          leaf recover-src-name {
            type pub-type:ncs_rpc_notif_if-name;
            description
              "Interface name of the clock source to be recovered.";
          }
        }
      }
    }
  }
  augment "/ncs:devices/ncs:device-group/ncs:ned-id/ncs:rpc" {
    container rpc-recover-freq-deviation {
      tailf:ncs-device-type "netconf";
      tailf:display-when "/ncs:devices/ncs:device[ncs:name=current()/../../../ncs:member]/ncs:module[ncs:name='huawei-clocksync-phy']";
      tailf:action recover-freq-deviation {
        tailf:actionpoint ncsproxy {
          tailf:internal;
        }
        description
          "Frequency offset status of the clock source to be recovered.";
        ext:node-ref "/clocksync-phy:clocksync-phy/clocksync-phy:detections/clocksync-phy:detection";
        input {
          leaf recover-src-name {
            type pub-type:ncs_rpc_notif_if-name;
            description
              "Interface name of the clock source to be recovered.";
          }
        }
      }
    }
  }
  augment "/ncs:devices/ncs:device/ncs:config" {
    container clocksync-phy {
      tailf:ncs-device-type "netconf";
      tailf:display-when "not(../../ncs:module) or ../../ncs:module[ncs:name='huawei-clocksync-phy']";
      description
        "Physical layer clock synchronization management.";
      container common {
        description
          "Configure global information about the physical clock.";
        leaf system-clock-run-mode {
          type clock-run-mode;
          default "normal";
          description
            "Running mode of a system clock.";
        }
        leaf ssm-control-on {
          type boolean;
          default "false";
          description
            "Enable/disable the SSM level to participate in clock source selection.";
        }
        leaf ext-ssm-control-on {
          type boolean;
          default "false";
          description
            "Enable/disable the extended SSM level participates in clock source selection.";
        }
        leaf enh-ssm-control-on {
          type boolean;
          default "false";
          description
            "Enable/disable the enhanced SSM level to participate in clock source selection.";
        }
        leaf internal-clock-id {
          type uint32 {
            range "0..15";
          }
          default "0";
          description
            "Clock ID of an internal clock source used for extended SSM control.";
        }
        leaf internal-clock-ssm {
          type ssm-level;
          must "not (../internal-clock-ssm='none')" {
            tailf:xpath-root 3;
          }
          default "sec";
          description
            "Configure the SSM level of the internal clock source.";
        }
        leaf freq-check-enable {
          type boolean;
          default "false";
          description
            "Enable/disable frequency offset detection.";
        }
        leaf ssm-recovery-mode {
          type ssm-recovery-mode;
          default "revertive";
          description
            "Configure SSM recovery mode as revertive mode or non-revertive mode.";
        }
        leaf wtr-time {
          type uint32 {
            range "0..12";
          }
          units "min";
          default "5";
          description
            "WTR time for a Down interface.";
        }
        leaf freq-switch-enable {
          type boolean;
          default "false";
          description
            "Enable/disable frequency offset switchover. After switchover triggered by frequency offset is enabled, signals are switched to another slave source on the same interface board if the frequency offset is detected abnormal.";
        }
        leaf holdoff-time {
          type uint32 {
            range "300..1800";
          }
          units "ms";
          default "1000";
          description
            "Holdoff time of the clock source after an interface changes from normal to abnormal.";
        }
        leaf ssm-unk-map {
          type ssm-level;
          must "not (../ssm-unk-map='unk' or ../ssm-unk-map='none')" {
            tailf:xpath-root 3;
          }
          default "dnu";
          description
            "Map UNK to an SSM level so that the clock source with the unknown SSM level can be selected.";
        }
        leaf min-out-ssm-bits {
          type ssm-level;
          must "(../min-out-ssm-bits='dnu' or ../min-out-ssm-bits='prc' or ../min-out-ssm-bits='ssua' or ../min-out-ssm-bits='ssub' or ../min-out-ssm-bits='sec')" {
            tailf:xpath-root 3;
          }
          default "dnu";
          description
            "Lowest SSM level of the clock signals output by the BITS interface.";
        }
        leaf max-out-ssm-system {
          type ssm-level;
          must "not (../max-out-ssm-system='dnu' or ../max-out-ssm-system='unk')" {
            tailf:xpath-root 3;
          }
          default "none";
          description
            "Highest SSM level of the output system clock signals. If the SSM level of a system clock is greater than the set highest SSM level, the system clock signals are output based on the highest SSM level.";
        }
        leaf max-out-ssm-2m1 {
          type ssm-level;
          must "(../max-out-ssm-2m1='none' or ../max-out-ssm-2m1='prc' or ../max-out-ssm-2m1='ssua' or ../max-out-ssm-2m1='ssub' or ../max-out-ssm-2m1='sec')" {
            tailf:xpath-root 3;
          }
          default "none";
          description
            "Highest SSM level of the output 2M-1 clock signals. If the SSM level of a 2M-1 clock is greater than the set highest SSM level, the 2M-1 clock signals are output based on the highest SSM level.";
        }
        leaf max-out-ssm-2m2 {
          type ssm-level;
          must "(../max-out-ssm-2m2 ='none' or ../max-out-ssm-2m2 ='prc' or ../max-out-ssm-2m2 ='ssua' or ../max-out-ssm-2m2 ='ssub' or ../max-out-ssm-2m2 ='sec')" {
            tailf:xpath-root 3;
          }
          default "none";
          description
            "Highest SSM level of the output 2M-2 clock signals. If the SSM level of a 2M-2 clock is greater than the set highest SSM level, the 2M-2 clock signals are output based on the highest SSM level.";
        }
        leaf clock-oam-profile {
          type oam-profile-type;
          default "none";
          description
            "OAM protocol type.";
        }
        leaf freq-offset-alarm-threshold {
          type uint32 {
            range "10..92";
          }
          default "92";
          description
            "Alarm threshold for physical layer frequency offset.";
        }
        leaf input-ssm-alarm-threshold {
          type ssm-level;
          must "not (../input-ssm-alarm-threshold='none' or ../input-ssm-alarm-threshold='unk')" {
            tailf:xpath-root 3;
          }
          default "sec";
          description
            "Alarm threshold for input SSM.";
        }
        // NCS drop config false leaf 'device-clk-level'
      }
      container selection-sources {
        description
          "List of configure physical layer clock source selection.";
        list selection {
          ext:generated-by "system";
          ext:operation-exclude "create|delete";
          key "source-type";
          description
            "Configure physical layer clock source selection.";
          leaf source-type {
            type pll-type;
            description
              "PLL type.";
          }
          leaf source-name {
            when "not(../mode='auto')" {
              tailf:xpath-root 3;
            }
            type string {
              length "1..65";
            }
            mandatory true;
            description
              "Name of the selected clock source in forced clock source selection and manual clock source selection.";
          }
          leaf mode {
            type source-selection-mode;
            default "auto";
            description
              "Clock source selection mode: forced clock source selection, manual clock source selection, and automatic clock source selection.";
          }
          // NCS drop config false leaf 'trace-source-name'
        }
      }
      container external-clock-sources {
        description
          "List of configure physical layer clock source.";
        list source {
          ext:generated-by "system";
          ext:operation-exclude "create|delete";
          key "name";
          description
            "Configure physical clock source.";
          leaf name {
            type string {
              length "1..49";
              pattern 'bits[0-3]((/(c?)[0-9]{1,2}){1,2}){0,1}|ptp|CESACR([0-9]{1,2}/){2,3}[0-9]{1,2}';
            }
            description
              "Name of the physical clock source.";
          }
          // NCS drop config false leaf state
          leaf sync-enable {
            type boolean;
            default "false";
            description
              "Enable/disable clock synchronization for the physical clock source.";
          }
          // NCS drop config false leaf 'reference-enable'
          // NCS drop config false leaf 'phy-state'
          leaf system-priority {
            type int32 {
              range "0..255";
            }
            default "0";
            description
              "Priority of the physical source. In physical clock source selection, you must configure the priority of clock sources for the system PLL. Otherwise, the clock sources cannot participate in the selection of the system PLL clock source.";
          }
          container ssm-class {
            description
              "Configure information about the SSM level, including SSM selection mode, input SSM level, and output SSM level.";
            leaf ssm-configured {
              type ssm-level;
              default "none";
              description
                "Input SSM level of the physical clock source. If clock sources are configured with SSM levels, the configured SSM levels are used.";
            }
            // NCS drop config false leaf 'ssm-learn'
            // NCS drop config false leaf 'ssm-output'
          }
          container clock-id {
            description
              "Configure information about the Clock ID of extended SSM control, including the clock ID selection mode, input clock ID, and output clock ID.";
            leaf clock-id-configured {
              type uint32 {
                range "0..15";
              }
              default "0";
              description
                "Clock ID of the physical clock source in extended SSM control.";
            }
            // NCS drop config false leaf 'clock-id-learn'
            // NCS drop config false leaf 'clock-id-out'
          }
          container bits-sources {
            description
              "Configure physical BITS clock sources.";
            leaf sabit {
              type sabit-type;
              default "sa4";
              description
                "Sa timeslot used by the BITS interface to send or receive the SSM level.";
            }
            leaf signal-type {
              type clock-bits-type;
              default "2mbps";
              description
                "BITS signal type.";
            }
            leaf invalid-act {
              type bits-invalid-act;
              default "shutdown";
              description
                "2M phase-locked source failure handling.";
            }
            leaf force-cutoff-enable {
              type boolean;
              default "false";
              description
                "Enable/disable forcible cutoff for external clock output.";
            }
          }
        }
      }
      // NCS drop config false container detections
    }
  }
  augment "/ncs:devices/ncs:device/ncs:live-status" {
    container clocksync-phy {
      tailf:ncs-device-type "netconf";
      tailf:display-when "not(../../ncs:module) or ../../ncs:module[ncs:name='huawei-clocksync-phy'] or (../../ncs:live-status-protocol[not(ncs:capability)]) or (../../ncs:live-status-protocol/ncs:capability/ncs:module[.='huawei-clocksync-phy'])";
      description
        "Physical layer clock synchronization management.";
      container common {
        description
          "Configure global information about the physical clock.";
        leaf system-clock-run-mode {
          type live_ncs_clock-run-mode;
          // NCS drop default statement
          description
            "Running mode of a system clock.";
        }
        leaf ssm-control-on {
          type boolean;
          // NCS drop default statement
          description
            "Enable/disable the SSM level to participate in clock source selection.";
        }
        leaf ext-ssm-control-on {
          type boolean;
          // NCS drop default statement
          description
            "Enable/disable the extended SSM level participates in clock source selection.";
        }
        leaf enh-ssm-control-on {
          type boolean;
          // NCS drop default statement
          description
            "Enable/disable the enhanced SSM level to participate in clock source selection.";
        }
        leaf internal-clock-id {
          type uint32 {
            range "0..15";
          }
          // NCS drop default statement
          description
            "Clock ID of an internal clock source used for extended SSM control.";
        }
        leaf internal-clock-ssm {
          type live_ncs_ssm-level;
          // NCS drop must statement
          // NCS drop default statement
          description
            "Configure the SSM level of the internal clock source.";
        }
        leaf freq-check-enable {
          type boolean;
          // NCS drop default statement
          description
            "Enable/disable frequency offset detection.";
        }
        leaf ssm-recovery-mode {
          type live_ncs_ssm-recovery-mode;
          // NCS drop default statement
          description
            "Configure SSM recovery mode as revertive mode or non-revertive mode.";
        }
        leaf wtr-time {
          type uint32 {
            range "0..12";
          }
          units "min";
          // NCS drop default statement
          description
            "WTR time for a Down interface.";
        }
        leaf freq-switch-enable {
          type boolean;
          // NCS drop default statement
          description
            "Enable/disable frequency offset switchover. After switchover triggered by frequency offset is enabled, signals are switched to another slave source on the same interface board if the frequency offset is detected abnormal.";
        }
        leaf holdoff-time {
          type uint32 {
            range "300..1800";
          }
          units "ms";
          // NCS drop default statement
          description
            "Holdoff time of the clock source after an interface changes from normal to abnormal.";
        }
        leaf ssm-unk-map {
          type live_ncs_ssm-level;
          // NCS drop must statement
          // NCS drop default statement
          description
            "Map UNK to an SSM level so that the clock source with the unknown SSM level can be selected.";
        }
        leaf min-out-ssm-bits {
          type live_ncs_ssm-level;
          // NCS drop must statement
          // NCS drop default statement
          description
            "Lowest SSM level of the clock signals output by the BITS interface.";
        }
        leaf max-out-ssm-system {
          type live_ncs_ssm-level;
          // NCS drop must statement
          // NCS drop default statement
          description
            "Highest SSM level of the output system clock signals. If the SSM level of a system clock is greater than the set highest SSM level, the system clock signals are output based on the highest SSM level.";
        }
        leaf max-out-ssm-2m1 {
          type live_ncs_ssm-level;
          // NCS drop must statement
          // NCS drop default statement
          description
            "Highest SSM level of the output 2M-1 clock signals. If the SSM level of a 2M-1 clock is greater than the set highest SSM level, the 2M-1 clock signals are output based on the highest SSM level.";
        }
        leaf max-out-ssm-2m2 {
          type live_ncs_ssm-level;
          // NCS drop must statement
          // NCS drop default statement
          description
            "Highest SSM level of the output 2M-2 clock signals. If the SSM level of a 2M-2 clock is greater than the set highest SSM level, the 2M-2 clock signals are output based on the highest SSM level.";
        }
        leaf clock-oam-profile {
          type live_ncs_oam-profile-type;
          // NCS drop default statement
          description
            "OAM protocol type.";
        }
        leaf freq-offset-alarm-threshold {
          type uint32 {
            range "10..92";
          }
          // NCS drop default statement
          description
            "Alarm threshold for physical layer frequency offset.";
        }
        leaf input-ssm-alarm-threshold {
          type live_ncs_ssm-level;
          // NCS drop must statement
          // NCS drop default statement
          description
            "Alarm threshold for input SSM.";
        }
        leaf device-clk-level {
          type live_ncs_dev-clk-level-type;
          // NCS drop default statement
          description
            "The Clock Level of the current device.";
        }
      }
      container selection-sources {
        description
          "List of configure physical layer clock source selection.";
        list selection {
          ext:generated-by "system";
          ext:operation-exclude "create|delete";
          key "source-type";
          description
            "Configure physical layer clock source selection.";
          leaf source-type {
            type live_ncs_pll-type;
            description
              "PLL type.";
          }
          leaf source-name {
            // NCS drop when statement
            type string {
              length "1..65";
            }
            // NCS drop mandatory statement
            description
              "Name of the selected clock source in forced clock source selection and manual clock source selection.";
          }
          leaf mode {
            type live_ncs_source-selection-mode;
            // NCS drop default statement
            description
              "Clock source selection mode: forced clock source selection, manual clock source selection, and automatic clock source selection.";
          }
          leaf trace-source-name {
            type string {
              length "1..65";
            }
            description
              "Name of the traced clock source.";
          }
        }
      }
      container external-clock-sources {
        description
          "List of configure physical layer clock source.";
        list source {
          ext:generated-by "system";
          ext:operation-exclude "create|delete";
          key "name";
          description
            "Configure physical clock source.";
          leaf name {
            type string {
              length "1..49";
              pattern 'bits[0-3]((/(c?)[0-9]{1,2}){1,2}){0,1}|ptp|CESACR([0-9]{1,2}/){2,3}[0-9]{1,2}';
            }
            description
              "Name of the physical clock source.";
          }
          leaf state {
            type live_ncs_source-state;
            // NCS drop default statement
            description
              "Status of a physical clock source.";
          }
          leaf sync-enable {
            type boolean;
            // NCS drop default statement
            description
              "Enable/disable clock synchronization for the physical clock source.";
          }
          leaf reference-enable {
            type boolean;
            // NCS drop default statement
            description
              "Whether a clock source can serve as a reference clock source.";
          }
          leaf phy-state {
            type live_ncs_phy-source-state;
            // NCS drop default statement
            description
              "Physical status of the clock source.";
          }
          leaf system-priority {
            type int32 {
              range "0..255";
            }
            // NCS drop default statement
            description
              "Priority of the physical source. In physical clock source selection, you must configure the priority of clock sources for the system PLL. Otherwise, the clock sources cannot participate in the selection of the system PLL clock source.";
          }
          container ssm-class {
            description
              "Configure information about the SSM level, including SSM selection mode, input SSM level, and output SSM level.";
            leaf ssm-configured {
              type live_ncs_ssm-level;
              // NCS drop default statement
              description
                "Input SSM level of the physical clock source. If clock sources are configured with SSM levels, the configured SSM levels are used.";
            }
            leaf ssm-learn {
              type live_ncs_ssm-level;
              // NCS drop default statement
              description
                "Input SSM level of the physical clock source. If clock sources are configured with SSM levels, the configured SSM levels are used.";
            }
            leaf ssm-output {
              type live_ncs_ssm-level;
              description
                "Output SSM level of the physical clock source.";
            }
          }
          container clock-id {
            description
              "Configure information about the Clock ID of extended SSM control, including the clock ID selection mode, input clock ID, and output clock ID.";
            leaf clock-id-configured {
              type uint32 {
                range "0..15";
              }
              // NCS drop default statement
              description
                "Clock ID of the physical clock source in extended SSM control.";
            }
            leaf clock-id-learn {
              type uint32 {
                range "0..15";
              }
              // NCS drop default statement
              description
                "Clock ID of the physical clock source in extended SSM control.";
            }
            leaf clock-id-out {
              type uint32 {
                range "0..15";
              }
              // NCS drop default statement
              description
                "Output Clock ID of the physical clock source in extended SSM control.";
            }
          }
          container bits-sources {
            description
              "Configure physical BITS clock sources.";
            leaf sabit {
              type live_ncs_sabit-type;
              // NCS drop default statement
              description
                "Sa timeslot used by the BITS interface to send or receive the SSM level.";
            }
            leaf signal-type {
              type live_ncs_clock-bits-type;
              // NCS drop default statement
              description
                "BITS signal type.";
            }
            leaf invalid-act {
              type live_ncs_bits-invalid-act;
              // NCS drop default statement
              description
                "2M phase-locked source failure handling.";
            }
            leaf force-cutoff-enable {
              type boolean;
              // NCS drop default statement
              description
                "Enable/disable forcible cutoff for external clock output.";
            }
          }
        }
      }
      container detections {
        description
          "List of statistics of physical clock source detection.";
        list detection {
          key "source-name";
          description
            "Statistics of physical clock source detection.";
          leaf source-name {
            type string {
              length "1..65";
            }
            description
              "Physical clock source name.";
          }
          leaf freq-value {
            type string {
              length "1..65";
            }
            description
              "Detected frequency offset value of the clock source.";
          }
        }
      }
    }
  }
  augment "/ncs:devices/ncs:template/ncs:ned-id/ncs:config" {
    container clocksync-phy {
      description
        "Physical layer clock synchronization management.";
      container common {
        description
          "Configure global information about the physical clock.";
        leaf system-clock-run-mode {
          type ncs_template_clock-run-mode;
          // NCS drop default statement
          description
            "Running mode of a system clock.";
        }
        leaf ssm-control-on {
          type string;
          // NCS drop default statement
          description
            "Enable/disable the SSM level to participate in clock source selection.";
        }
        leaf ext-ssm-control-on {
          type string;
          // NCS drop default statement
          description
            "Enable/disable the extended SSM level participates in clock source selection.";
        }
        leaf enh-ssm-control-on {
          type string;
          // NCS drop default statement
          description
            "Enable/disable the enhanced SSM level to participate in clock source selection.";
        }
        leaf internal-clock-id {
          type string;
          // NCS drop default statement
          description
            "Clock ID of an internal clock source used for extended SSM control.";
        }
        leaf internal-clock-ssm {
          type ncs_template_ssm-level;
          // NCS drop must statement
          // NCS drop default statement
          description
            "Configure the SSM level of the internal clock source.";
        }
        leaf freq-check-enable {
          type string;
          // NCS drop default statement
          description
            "Enable/disable frequency offset detection.";
        }
        leaf ssm-recovery-mode {
          type ncs_template_ssm-recovery-mode;
          // NCS drop default statement
          description
            "Configure SSM recovery mode as revertive mode or non-revertive mode.";
        }
        leaf wtr-time {
          type string;
          units "min";
          // NCS drop default statement
          description
            "WTR time for a Down interface.";
        }
        leaf freq-switch-enable {
          type string;
          // NCS drop default statement
          description
            "Enable/disable frequency offset switchover. After switchover triggered by frequency offset is enabled, signals are switched to another slave source on the same interface board if the frequency offset is detected abnormal.";
        }
        leaf holdoff-time {
          type string;
          units "ms";
          // NCS drop default statement
          description
            "Holdoff time of the clock source after an interface changes from normal to abnormal.";
        }
        leaf ssm-unk-map {
          type ncs_template_ssm-level;
          // NCS drop must statement
          // NCS drop default statement
          description
            "Map UNK to an SSM level so that the clock source with the unknown SSM level can be selected.";
        }
        leaf min-out-ssm-bits {
          type ncs_template_ssm-level;
          // NCS drop must statement
          // NCS drop default statement
          description
            "Lowest SSM level of the clock signals output by the BITS interface.";
        }
        leaf max-out-ssm-system {
          type ncs_template_ssm-level;
          // NCS drop must statement
          // NCS drop default statement
          description
            "Highest SSM level of the output system clock signals. If the SSM level of a system clock is greater than the set highest SSM level, the system clock signals are output based on the highest SSM level.";
        }
        leaf max-out-ssm-2m1 {
          type ncs_template_ssm-level;
          // NCS drop must statement
          // NCS drop default statement
          description
            "Highest SSM level of the output 2M-1 clock signals. If the SSM level of a 2M-1 clock is greater than the set highest SSM level, the 2M-1 clock signals are output based on the highest SSM level.";
        }
        leaf max-out-ssm-2m2 {
          type ncs_template_ssm-level;
          // NCS drop must statement
          // NCS drop default statement
          description
            "Highest SSM level of the output 2M-2 clock signals. If the SSM level of a 2M-2 clock is greater than the set highest SSM level, the 2M-2 clock signals are output based on the highest SSM level.";
        }
        leaf clock-oam-profile {
          type ncs_template_oam-profile-type;
          // NCS drop default statement
          description
            "OAM protocol type.";
        }
        leaf freq-offset-alarm-threshold {
          type string;
          // NCS drop default statement
          description
            "Alarm threshold for physical layer frequency offset.";
        }
        leaf input-ssm-alarm-threshold {
          type ncs_template_ssm-level;
          // NCS drop must statement
          // NCS drop default statement
          description
            "Alarm threshold for input SSM.";
        }
        // NCS drop config false leaf 'device-clk-level'
      }
      container selection-sources {
        description
          "List of configure physical layer clock source selection.";
        list selection {
          // NCS patched for predictable order
          ordered-by user;
          ext:generated-by "system";
          ext:operation-exclude "create|delete";
          key "source-type";
          description
            "Configure physical layer clock source selection.";
          leaf source-type {
            type ncs_template_pll-type;
            description
              "PLL type.";
          }
          leaf source-name {
            // NCS drop when statement
            type string;
            // NCS drop mandatory statement
            description
              "Name of the selected clock source in forced clock source selection and manual clock source selection.";
          }
          leaf mode {
            type ncs_template_source-selection-mode;
            // NCS drop default statement
            description
              "Clock source selection mode: forced clock source selection, manual clock source selection, and automatic clock source selection.";
          }
          // NCS drop config false leaf 'trace-source-name'
        }
      }
      container external-clock-sources {
        description
          "List of configure physical layer clock source.";
        list source {
          // NCS patched for predictable order
          ordered-by user;
          ext:generated-by "system";
          ext:operation-exclude "create|delete";
          key "name";
          description
            "Configure physical clock source.";
          leaf name {
            type string;
            description
              "Name of the physical clock source.";
          }
          // NCS drop config false leaf state
          leaf sync-enable {
            type string;
            // NCS drop default statement
            description
              "Enable/disable clock synchronization for the physical clock source.";
          }
          // NCS drop config false leaf 'reference-enable'
          // NCS drop config false leaf 'phy-state'
          leaf system-priority {
            type string;
            // NCS drop default statement
            description
              "Priority of the physical source. In physical clock source selection, you must configure the priority of clock sources for the system PLL. Otherwise, the clock sources cannot participate in the selection of the system PLL clock source.";
          }
          container ssm-class {
            description
              "Configure information about the SSM level, including SSM selection mode, input SSM level, and output SSM level.";
            leaf ssm-configured {
              type ncs_template_ssm-level;
              // NCS drop default statement
              description
                "Input SSM level of the physical clock source. If clock sources are configured with SSM levels, the configured SSM levels are used.";
            }
            // NCS drop config false leaf 'ssm-learn'
            // NCS drop config false leaf 'ssm-output'
          }
          container clock-id {
            description
              "Configure information about the Clock ID of extended SSM control, including the clock ID selection mode, input clock ID, and output clock ID.";
            leaf clock-id-configured {
              type string;
              // NCS drop default statement
              description
                "Clock ID of the physical clock source in extended SSM control.";
            }
            // NCS drop config false leaf 'clock-id-learn'
            // NCS drop config false leaf 'clock-id-out'
          }
          container bits-sources {
            description
              "Configure physical BITS clock sources.";
            leaf sabit {
              type ncs_template_sabit-type;
              // NCS drop default statement
              description
                "Sa timeslot used by the BITS interface to send or receive the SSM level.";
            }
            leaf signal-type {
              type ncs_template_clock-bits-type;
              // NCS drop default statement
              description
                "BITS signal type.";
            }
            leaf invalid-act {
              type ncs_template_bits-invalid-act;
              // NCS drop default statement
              description
                "2M phase-locked source failure handling.";
            }
            leaf force-cutoff-enable {
              type string;
              // NCS drop default statement
              description
                "Enable/disable forcible cutoff for external clock output.";
            }
          }
        }
      }
      // NCS drop config false container detections
    }
  }
  augment "/ncs:devices/ncs:template/ncs:ned-id/ncs:config/ifm:ifm/ifm:interfaces/ifm:interface" {
    description
      "Interface.";
    container clock-port-sources {
      description
        "Configure physical layer clock source.";
      container source {
        presence "Create physical clock source.";
        description
          "Configure physical clock source node.";
        // NCS drop config false leaf state
        leaf sync-enable {
          type string;
          // NCS drop default statement
          description
            "Enable/disable clock synchronization for the physical clock source.";
        }
        leaf esmc-send-disable {
          // NCS drop when statement
          type string;
          // NCS drop default statement
          description
            "Enable/disable ESMC packet sending on interface.";
        }
        // NCS drop config false leaf 'reference-enable'
        leaf slave-nego-enable {
          type string;
          // NCS drop default statement
          description
            "Enable/disable the physical layer slave negotiation mode. Only GE electrical interfaces support this configuration.";
        }
        // NCS drop config false leaf 'phy-state'
        leaf e1-sabit {
          // NCS drop when statement
          type ncs_template_sabit-type;
          // NCS drop default statement
          description
            "Sa timeslot used by the E1 port to send or receive the SSM level.";
        }
        leaf e1-ais-enable {
          // NCS drop when statement
          type string;
          // NCS drop default statement
          description
            "Enable/disable association of AIS signals of E1 ports with the clock source status.";
        }
        leaf cpos-ais-enable {
          // NCS drop when statement
          type string;
          // NCS drop default statement
          description
            "Enable/disable Association of the clock source status with the MS-AIS signal alarm on the CPOS port.";
        }
        leaf cpos-exc-enable {
          // NCS drop when statement
          type string;
          // NCS drop default statement
          description
            "Enable/disable Association of the clock source status with the B2-EXC signal alarm on the CPOS port.";
        }
        container priority {
          description
            "Configure priority of the physical source.";
          leaf system {
            type string;
            // NCS drop default statement
            description
              "In physical clock source selection, you must configure the priority of clock sources for the system PLL. Otherwise, the clock sources cannot participate in the selection of the system PLL clock source.";
          }
          leaf sync2m1 {
            type string;
            // NCS drop default statement
            description
              "In physical clock source selection, you must configure the priority of clock sources for the 2M-1 PLL. Otherwise, the clock sources cannot participate in the selection of the 2M-1 PLL clock source.";
          }
          leaf sync2m2 {
            type string;
            // NCS drop default statement
            description
              "In physical clock source selection, you must configure the priority of clock sources for the 2M-2 PLL. Otherwise, the clock sources cannot participate in the selection of the 2M-2 PLL clock source.";
          }
        }
        container ssm-class {
          description
            "Configure information about the SSM level. Including SSM selection mode, input SSM level, and output SSM level.";
          leaf ssm-configured {
            type ncs_template_ssm-level;
            // NCS drop default statement
            description
              "Input SSM level of the physical clock source. If clock sources are configured with SSM levels, the configured SSM levels are used.";
          }
          // NCS drop config false leaf 'ssm-learn'
          // NCS drop config false leaf 'enh-ssm-learn'
          // NCS drop config false leaf 'ssm-output'
        }
        container clock-id {
          description
            "Configure information about the Clock ID of extended SSM control. Including the clock ID selection mode, input clock ID, and output clock ID.";
          leaf clock-id-configured {
            type string;
            // NCS drop default statement
            description
              "Clock ID of the physical clock source in extended SSM control.";
          }
          // NCS drop config false leaf 'clock-id-learn'
          // NCS drop config false leaf 'enh-clock-id-learn'
          // NCS drop config false leaf 'clock-id-out'
        }
        leaf bundle-group {
          type string;
          // NCS drop default statement
          description
            "Bundling group on a port.";
        }
        // NCS drop config false container 'enhanced-qltlv'
      }
    }
  }
  augment "/ncs:devices/ncs:device/ncs:live-status/ifm:ifm/ifm:interfaces/ifm:interface" {
    description
      "Interface.";
    container clock-port-sources {
      tailf:ncs-device-type "netconf";
      tailf:display-when "not(../../../../../ncs:module) or ../../../../../ncs:module[ncs:name='huawei-clocksync-phy'] or (../../../../../ncs:live-status-protocol[not(ncs:capability)]) or (../../../../../ncs:live-status-protocol/ncs:capability/ncs:module[.='huawei-clocksync-phy'])";
      description
        "Configure physical layer clock source.";
      container source {
        presence "Create physical clock source.";
        description
          "Configure physical clock source node.";
        leaf state {
          type live_ncs_source-state;
          // NCS drop default statement
          description
            "Status of a physical clock source.";
        }
        leaf sync-enable {
          type boolean;
          // NCS drop default statement
          description
            "Enable/disable clock synchronization for the physical clock source.";
        }
        leaf esmc-send-disable {
          // NCS drop when statement
          type boolean;
          // NCS drop default statement
          description
            "Enable/disable ESMC packet sending on interface.";
        }
        leaf reference-enable {
          type boolean;
          // NCS drop default statement
          description
            "Enable/disable a clock source can serve as a reference clock source.";
        }
        leaf slave-nego-enable {
          type boolean;
          // NCS drop default statement
          description
            "Enable/disable the physical layer slave negotiation mode. Only GE electrical interfaces support this configuration.";
        }
        leaf phy-state {
          type live_ncs_phy-source-state;
          // NCS drop default statement
          description
            "Physical status of the clock source.";
        }
        leaf e1-sabit {
          // NCS drop when statement
          type live_ncs_sabit-type;
          // NCS drop default statement
          description
            "Sa timeslot used by the E1 port to send or receive the SSM level.";
        }
        leaf e1-ais-enable {
          // NCS drop when statement
          type boolean;
          // NCS drop default statement
          description
            "Enable/disable association of AIS signals of E1 ports with the clock source status.";
        }
        leaf cpos-ais-enable {
          // NCS drop when statement
          type boolean;
          // NCS drop default statement
          description
            "Enable/disable Association of the clock source status with the MS-AIS signal alarm on the CPOS port.";
        }
        leaf cpos-exc-enable {
          // NCS drop when statement
          type boolean;
          // NCS drop default statement
          description
            "Enable/disable Association of the clock source status with the B2-EXC signal alarm on the CPOS port.";
        }
        container priority {
          description
            "Configure priority of the physical source.";
          leaf system {
            type int32 {
              range "0..255";
            }
            // NCS drop default statement
            description
              "In physical clock source selection, you must configure the priority of clock sources for the system PLL. Otherwise, the clock sources cannot participate in the selection of the system PLL clock source.";
          }
          leaf sync2m1 {
            type int32 {
              range "0..255";
            }
            // NCS drop default statement
            description
              "In physical clock source selection, you must configure the priority of clock sources for the 2M-1 PLL. Otherwise, the clock sources cannot participate in the selection of the 2M-1 PLL clock source.";
          }
          leaf sync2m2 {
            type int32 {
              range "0..255";
            }
            // NCS drop default statement
            description
              "In physical clock source selection, you must configure the priority of clock sources for the 2M-2 PLL. Otherwise, the clock sources cannot participate in the selection of the 2M-2 PLL clock source.";
          }
        }
        container ssm-class {
          description
            "Configure information about the SSM level. Including SSM selection mode, input SSM level, and output SSM level.";
          leaf ssm-configured {
            type live_ncs_ssm-level;
            // NCS drop default statement
            description
              "Input SSM level of the physical clock source. If clock sources are configured with SSM levels, the configured SSM levels are used.";
          }
          leaf ssm-learn {
            type live_ncs_ssm-level;
            // NCS drop default statement
            description
              "Input SSM level of the physical clock source. If clock sources are configured with SSM levels, the configured SSM levels are used.";
          }
          leaf enh-ssm-learn {
            type live_ncs_ssm-level;
            // NCS drop default statement
            description
              "Input SSM level of the physical clock source. If clock sources are configured with SSM levels, the configured SSM levels are used.";
          }
          leaf ssm-output {
            type live_ncs_ssm-level;
            description
              "Output SSM level of the physical clock source.";
          }
        }
        container clock-id {
          description
            "Configure information about the Clock ID of extended SSM control. Including the clock ID selection mode, input clock ID, and output clock ID.";
          leaf clock-id-configured {
            type uint32 {
              range "0..15";
            }
            // NCS drop default statement
            description
              "Clock ID of the physical clock source in extended SSM control.";
          }
          leaf clock-id-learn {
            type uint32 {
              range "0..15";
            }
            // NCS drop default statement
            description
              "Clock ID of the physical clock source in extended SSM control.";
          }
          leaf enh-clock-id-learn {
            type string {
              length "1..51";
            }
            description
              "Clock ID of the physical clock source in enhanced SSM control.";
          }
          leaf clock-id-out {
            type uint32 {
              range "0..15";
            }
            // NCS drop default statement
            description
              "Output Clock ID of the physical clock source in extended SSM control.";
          }
        }
        leaf bundle-group {
          type int32 {
            range "0..64";
          }
          // NCS drop default statement
          description
            "Bundling group on a port.";
        }
        container enhanced-qltlv {
          description
            "Statistics of enhanced quality level Tlv.";
          leaf flag {
            type uint32 {
              range "0..255";
            }
            // NCS drop default statement
            description
              "Enhanced flag.";
          }
          leaf cascade-esecs {
            type uint32 {
              range "0..255";
            }
            // NCS drop default statement
            description
              "Number of cascade eSECs.";
          }
          leaf cascade-secs {
            type uint32 {
              range "0..255";
            }
            // NCS drop default statement
            description
              "Number of cascade SECs.";
          }
        }
      }
    }
  }
  augment "/ncs:devices/ncs:device/ncs:config/ifm:ifm/ifm:interfaces/ifm:interface" {
    description
      "Interface.";
    container clock-port-sources {
      tailf:ncs-device-type "netconf";
      tailf:display-when "not(../../../../../ncs:module) or ../../../../../ncs:module[ncs:name='huawei-clocksync-phy']";
      description
        "Configure physical layer clock source.";
      container source {
        presence "Create physical clock source.";
        description
          "Configure physical clock source node.";
        // NCS drop config false leaf state
        leaf sync-enable {
          type boolean;
          default "false";
          description
            "Enable/disable clock synchronization for the physical clock source.";
        }
        leaf esmc-send-disable {
          when "not((../../../ifm:type='E1') or (../../../ifm:type='Pos') or (../../../ifm:type='Cpos') or (../../../ifm:type='T1'))" {
            tailf:xpath-root 3;
          }
          type boolean;
          default "false";
          description
            "Enable/disable ESMC packet sending on interface.";
        }
        // NCS drop config false leaf 'reference-enable'
        leaf slave-nego-enable {
          type boolean;
          default "false";
          description
            "Enable/disable the physical layer slave negotiation mode. Only GE electrical interfaces support this configuration.";
        }
        // NCS drop config false leaf 'phy-state'
        leaf e1-sabit {
          when "../../../ifm:type='E1'" {
            tailf:xpath-root 3;
          }
          type sabit-type;
          default "sa4";
          description
            "Sa timeslot used by the E1 port to send or receive the SSM level.";
        }
        leaf e1-ais-enable {
          when "../../../ifm:type='E1'" {
            tailf:xpath-root 3;
          }
          type boolean;
          default "false";
          description
            "Enable/disable association of AIS signals of E1 ports with the clock source status.";
        }
        leaf cpos-ais-enable {
          when "../../../ifm:type='Cpos'" {
            tailf:xpath-root 3;
          }
          type boolean;
          default "false";
          description
            "Enable/disable Association of the clock source status with the MS-AIS signal alarm on the CPOS port.";
        }
        leaf cpos-exc-enable {
          when "../../../ifm:type='Cpos'" {
            tailf:xpath-root 3;
          }
          type boolean;
          default "false";
          description
            "Enable/disable Association of the clock source status with the B2-EXC signal alarm on the CPOS port.";
        }
        container priority {
          description
            "Configure priority of the physical source.";
          leaf system {
            type int32 {
              range "0..255";
            }
            default "0";
            description
              "In physical clock source selection, you must configure the priority of clock sources for the system PLL. Otherwise, the clock sources cannot participate in the selection of the system PLL clock source.";
          }
          leaf sync2m1 {
            type int32 {
              range "0..255";
            }
            default "0";
            description
              "In physical clock source selection, you must configure the priority of clock sources for the 2M-1 PLL. Otherwise, the clock sources cannot participate in the selection of the 2M-1 PLL clock source.";
          }
          leaf sync2m2 {
            type int32 {
              range "0..255";
            }
            default "0";
            description
              "In physical clock source selection, you must configure the priority of clock sources for the 2M-2 PLL. Otherwise, the clock sources cannot participate in the selection of the 2M-2 PLL clock source.";
          }
        }
        container ssm-class {
          description
            "Configure information about the SSM level. Including SSM selection mode, input SSM level, and output SSM level.";
          leaf ssm-configured {
            type ssm-level;
            default "none";
            description
              "Input SSM level of the physical clock source. If clock sources are configured with SSM levels, the configured SSM levels are used.";
          }
          // NCS drop config false leaf 'ssm-learn'
          // NCS drop config false leaf 'enh-ssm-learn'
          // NCS drop config false leaf 'ssm-output'
        }
        container clock-id {
          description
            "Configure information about the Clock ID of extended SSM control. Including the clock ID selection mode, input clock ID, and output clock ID.";
          leaf clock-id-configured {
            type uint32 {
              range "0..15";
            }
            default "0";
            description
              "Clock ID of the physical clock source in extended SSM control.";
          }
          // NCS drop config false leaf 'clock-id-learn'
          // NCS drop config false leaf 'enh-clock-id-learn'
          // NCS drop config false leaf 'clock-id-out'
        }
        leaf bundle-group {
          type int32 {
            range "0..64";
          }
          default "0";
          description
            "Bundling group on a port.";
        }
        // NCS drop config false container 'enhanced-qltlv'
      }
    }
  }
}
