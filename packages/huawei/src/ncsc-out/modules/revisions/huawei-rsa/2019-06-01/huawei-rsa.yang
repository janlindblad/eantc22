module huawei-rsa {
  // Generated by yanger -t ncs
  tailf:mount-id "huawei-nc-1.0:huawei-nc-1.0";
  tailf:ncs-device-type "netconf";

  namespace "urn:huawei:yang:huawei-rsa";
  prefix rsa;

  import huawei-extension {
    prefix ext;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "RSA.";

  revision 2019-06-01 {
    description
      "Initial revision.";
    reference "Huawei private.";
  }
  ext:task-name "ssh-server";

  typedef ncs_template_encode-type {
    type string;
    description
      "RSA encode type list.";
  }

  typedef ncs_rpc_notif_encode-type {
    type enumeration {
      enum "der" {
        value 0;
        description
          "Der encode type.";
      }
      enum "pem" {
        value 1;
        description
          "Pem encode type.";
      }
      enum "openssh" {
        value 2;
        description
          "Openssh encode type.";
      }
    }
    description
      "RSA encode type list.";
  }

  typedef live_ncs_encode-type {
    type enumeration {
      enum "der" {
        value 0;
        description
          "Der encode type.";
      }
      enum "pem" {
        value 1;
        description
          "Pem encode type.";
      }
      enum "openssh" {
        value 2;
        description
          "Openssh encode type.";
      }
    }
    description
      "RSA encode type list.";
  }

  typedef encode-type {
    type enumeration {
      enum "der" {
        value 0;
        description
          "Der encode type.";
      }
      enum "pem" {
        value 1;
        description
          "Pem encode type.";
      }
      enum "openssh" {
        value 2;
        description
          "Openssh encode type.";
      }
    }
    description
      "RSA encode type list.";
  }

  augment "/ncs:devices/ncs:device/ncs:config" {
    container rsa {
      tailf:ncs-device-type "netconf";
      tailf:display-when "not(../../ncs:module) or ../../ncs:module[ncs:name='huawei-rsa']";
      description
        "RSA configuration.";
      container local-key {
        presence "create rsaLocalKey";
        description
          "Enable/disable Local key code.";
        leaf key-size {
          type uint32 {
            range "2048 | 3072";
          }
          default "3072";
          description
            "Key size.";
        }
        // NCS drop config false leaf 'host-key-name'
        // NCS drop config false leaf 'host-key-code'
        // NCS drop config false leaf 'host-key-ssh1'
        // NCS drop config false leaf 'host-key-pem'
        // NCS drop config false leaf 'host-key-openssh'
        // NCS drop config false leaf 'server-key-name'
        // NCS drop config false leaf 'server-key-code'
      }
      container peer-keys {
        description
          "List of Peer key table.";
        list peer-key {
          key "key-name";
          max-elements 20;
          description
            "Configure Peer key code. If the key code is bound, it cannot be deleted, you need to unbind and then delete.";
          leaf key-name {
            type string {
              length "1..40";
            }
            description
              "Key name.";
          }
          leaf key-code {
            type string {
              length "1..4096";
            }
            mandatory true;
            ext:support-filter "true";
            description
              "Key code conforming to PEM, OpenSSH or DER format.";
          }
          leaf encode-type {
            type encode-type;
            default "der";
            ext:support-filter "true";
            description
              "Encode type.";
          }
        }
      }
      container key-pairs {
        description
          "List of RSA key-pair label.";
        list key-pair {
          key "key-pair-label";
          max-elements 20;
          description
            "Configure RSA key-pair.";
          leaf key-pair-label {
            type string {
              length "1..35";
              pattern '[a-z0-9_]*';
            }
            description
              "Key-pair Label Name : It only contains underscores (_), lowercase letters and digits.";
          }
          leaf key-size {
            type uint32 {
              range "2048 | 3072";
            }
            default "3072";
            ext:support-filter "true";
            description
              "Size of Key-pair.";
          }
          // NCS drop config false leaf 'host-key-code'
        }
      }
      container rsa-global {
        description
          "Configure Global configuration.";
        leaf max-key-pair {
          type int32 {
            range "1..20";
          }
          default "20";
          description
            "Maximum key-pair value.";
        }
      }
    }
  }
  augment "/ncs:devices/ncs:device/ncs:live-status" {
    container rsa {
      tailf:ncs-device-type "netconf";
      tailf:display-when "not(../../ncs:module) or ../../ncs:module[ncs:name='huawei-rsa'] or (../../ncs:live-status-protocol[not(ncs:capability)]) or (../../ncs:live-status-protocol/ncs:capability/ncs:module[.='huawei-rsa'])";
      description
        "RSA configuration.";
      container local-key {
        presence "create rsaLocalKey";
        description
          "Enable/disable Local key code.";
        leaf key-size {
          type uint32 {
            range "2048 | 3072";
          }
          // NCS drop default statement
          description
            "Key size.";
        }
        leaf host-key-name {
          type string {
            length "0..264";
          }
          description
            "Hostkey name.";
        }
        leaf host-key-code {
          type string {
            length "0..1024";
          }
          description
            "Hostkey code.";
        }
        leaf host-key-ssh1 {
          type string {
            length "0..1024";
          }
          description
            "Hostkey code in SSH1 format.";
        }
        leaf host-key-pem {
          type string {
            length "0..1920";
          }
          description
            "Hostkey code in PEM format.";
        }
        leaf host-key-openssh {
          type string {
            length "0..1920";
          }
          description
            "Hostkey code in OpenSSH format.";
        }
        leaf server-key-name {
          type string {
            length "0..264";
          }
          description
            "Server key name.";
        }
        leaf server-key-code {
          type string {
            length "0..1024";
          }
          description
            "Server key code.";
        }
      }
      container peer-keys {
        description
          "List of Peer key table.";
        list peer-key {
          key "key-name";
          // NCS drop max-elements statement
          description
            "Configure Peer key code. If the key code is bound, it cannot be deleted, you need to unbind and then delete.";
          leaf key-name {
            type string {
              length "1..40";
            }
            description
              "Key name.";
          }
          leaf key-code {
            type string {
              length "1..4096";
            }
            // NCS drop mandatory statement
            ext:support-filter "true";
            description
              "Key code conforming to PEM, OpenSSH or DER format.";
          }
          leaf encode-type {
            type live_ncs_encode-type;
            // NCS drop default statement
            ext:support-filter "true";
            description
              "Encode type.";
          }
        }
      }
      container key-pairs {
        description
          "List of RSA key-pair label.";
        list key-pair {
          key "key-pair-label";
          // NCS drop max-elements statement
          description
            "Configure RSA key-pair.";
          leaf key-pair-label {
            type string {
              length "1..35";
              pattern '[a-z0-9_]*';
            }
            description
              "Key-pair Label Name : It only contains underscores (_), lowercase letters and digits.";
          }
          leaf key-size {
            type uint32 {
              range "2048 | 3072";
            }
            // NCS drop default statement
            ext:support-filter "true";
            description
              "Size of Key-pair.";
          }
          leaf host-key-code {
            type string {
              length "0..2048";
            }
            ext:support-filter "true";
            description
              "Hostkey code.";
          }
        }
      }
      container rsa-global {
        description
          "Configure Global configuration.";
        leaf max-key-pair {
          type int32 {
            range "1..20";
          }
          // NCS drop default statement
          description
            "Maximum key-pair value.";
        }
      }
    }
  }
  augment "/ncs:devices/ncs:template/ncs:ned-id/ncs:config" {
    container rsa {
      description
        "RSA configuration.";
      container local-key {
        presence "create rsaLocalKey";
        description
          "Enable/disable Local key code.";
        leaf key-size {
          type string;
          // NCS drop default statement
          description
            "Key size.";
        }
        // NCS drop config false leaf 'host-key-name'
        // NCS drop config false leaf 'host-key-code'
        // NCS drop config false leaf 'host-key-ssh1'
        // NCS drop config false leaf 'host-key-pem'
        // NCS drop config false leaf 'host-key-openssh'
        // NCS drop config false leaf 'server-key-name'
        // NCS drop config false leaf 'server-key-code'
      }
      container peer-keys {
        description
          "List of Peer key table.";
        list peer-key {
          // NCS patched for predictable order
          ordered-by user;
          key "key-name";
          // NCS drop max-elements statement
          description
            "Configure Peer key code. If the key code is bound, it cannot be deleted, you need to unbind and then delete.";
          leaf key-name {
            type string;
            description
              "Key name.";
          }
          leaf key-code {
            type string;
            // NCS drop mandatory statement
            ext:support-filter "true";
            description
              "Key code conforming to PEM, OpenSSH or DER format.";
          }
          leaf encode-type {
            type ncs_template_encode-type;
            // NCS drop default statement
            ext:support-filter "true";
            description
              "Encode type.";
          }
        }
      }
      container key-pairs {
        description
          "List of RSA key-pair label.";
        list key-pair {
          // NCS patched for predictable order
          ordered-by user;
          key "key-pair-label";
          // NCS drop max-elements statement
          description
            "Configure RSA key-pair.";
          leaf key-pair-label {
            type string;
            description
              "Key-pair Label Name : It only contains underscores (_), lowercase letters and digits.";
          }
          leaf key-size {
            type string;
            // NCS drop default statement
            ext:support-filter "true";
            description
              "Size of Key-pair.";
          }
          // NCS drop config false leaf 'host-key-code'
        }
      }
      container rsa-global {
        description
          "Configure Global configuration.";
        leaf max-key-pair {
          type string;
          // NCS drop default statement
          description
            "Maximum key-pair value.";
        }
      }
    }
  }
}
