module huawei-bier-fwd {
  // Generated by yanger -t ncs
  tailf:mount-id "huawei-nc-1.0:huawei-nc-1.0";
  tailf:ncs-device-type "netconf";

  namespace "urn:huawei:yang:huawei-bier-fwd";
  prefix bier-fwd;

  import huawei-bier {
    prefix bier;
  }
  import huawei-extension {
    prefix ext;
  }
  import huawei-devm {
    prefix devm;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Bier forward.";

  revision 2020-02-13 {
    description
      "Init revision.";
    reference "Huawei private.";
  }
  ext:task-name "bier";

  augment "/ncs:devices/ncs:device/ncs:config" {
    container bier-fwd {
      tailf:ncs-device-type "netconf";
      tailf:display-when "not(../../ncs:module) or ../../ncs:module[ncs:name='huawei-bier-fwd']";
      description
        "Global configuration of bier-fwd.";
      container select-boards {
        description
          "Configure boards selected for bier.";
        leaf-list slot {
          type leafref {
            path "/ncs:devices/ncs:device/ncs:config/devm:devm/devm:lpu-boards/devm:lpu-board/devm:position" {
              tailf:xpath-root 3;
            }
          }
          max-elements 20;
          description
            "Configure slot ID.";
        }
      }
    }
  }
  augment "/ncs:devices/ncs:device/ncs:live-status" {
    container bier-fwd {
      tailf:ncs-device-type "netconf";
      tailf:display-when "not(../../ncs:module) or ../../ncs:module[ncs:name='huawei-bier-fwd'] or (../../ncs:live-status-protocol[not(ncs:capability)]) or (../../ncs:live-status-protocol/ncs:capability/ncs:module[.='huawei-bier-fwd'])";
      description
        "Global configuration of bier-fwd.";
      container select-boards {
        description
          "Configure boards selected for bier.";
        leaf-list slot {
          type leafref {
            path "/ncs:devices/ncs:device/ncs:live-status/devm:devm/devm:lpu-boards/devm:lpu-board/devm:position" {
              tailf:xpath-root 3;
            }
          }
          // NCS drop max-elements statement
          description
            "Configure slot ID.";
        }
      }
    }
  }
  augment "/ncs:devices/ncs:template/ncs:ned-id/ncs:config" {
    container bier-fwd {
      description
        "Global configuration of bier-fwd.";
      container select-boards {
        description
          "Configure boards selected for bier.";
        leaf-list slot {
          // NCS patched for predictable order
          ordered-by user;
          type string;
          // NCS drop max-elements statement
          description
            "Configure slot ID.";
        }
      }
    }
  }
  augment "/ncs:devices/ncs:template/ncs:ned-id/ncs:config/bier:bier" {
    description
      "Configure global attributes to the BIER.";
    container forward {
      description
        "Configure global attributes to the BIER.";
      container reserve-interface-enhancement {
        description
          "Configure reserve-interface enhancement.";
        leaf enable {
          type string;
          // NCS drop default statement
          description
            "Enable/disable reserve-interface enhancement.";
        }
      }
    }
  }
  augment "/ncs:devices/ncs:device/ncs:live-status/bier:bier" {
    description
      "Configure global attributes to the BIER.";
    container forward {
      tailf:ncs-device-type "netconf";
      tailf:display-when "not(../../../ncs:module) or ../../../ncs:module[ncs:name='huawei-bier-fwd'] or (../../../ncs:live-status-protocol[not(ncs:capability)]) or (../../../ncs:live-status-protocol/ncs:capability/ncs:module[.='huawei-bier-fwd'])";
      description
        "Configure global attributes to the BIER.";
      container reserve-interface-enhancement {
        description
          "Configure reserve-interface enhancement.";
        leaf enable {
          type boolean;
          // NCS drop default statement
          description
            "Enable/disable reserve-interface enhancement.";
        }
      }
    }
  }
  augment "/ncs:devices/ncs:device/ncs:config/bier:bier" {
    description
      "Configure global attributes to the BIER.";
    container forward {
      tailf:ncs-device-type "netconf";
      tailf:display-when "not(../../../ncs:module) or ../../../ncs:module[ncs:name='huawei-bier-fwd']";
      description
        "Configure global attributes to the BIER.";
      container reserve-interface-enhancement {
        description
          "Configure reserve-interface enhancement.";
        leaf enable {
          type boolean;
          default "false";
          description
            "Enable/disable reserve-interface enhancement.";
        }
      }
    }
  }
  augment "/ncs:devices/ncs:template/ncs:ned-id/ncs:config/bier:bier/bier:sub-domains/bier:sub-domain" {
    description
      "Configure pipe mode ttl value.";
    container pipe-mode-ttl {
      description
        "Configure pipe mode ttl value.";
      leaf ttl-value {
        type string;
        // NCS drop default statement
        description
          "Bier pipe mode ttl value.";
      }
    }
  }
  augment "/ncs:devices/ncs:device/ncs:live-status/bier:bier/bier:sub-domains/bier:sub-domain" {
    description
      "Configure pipe mode ttl value.";
    container pipe-mode-ttl {
      tailf:ncs-device-type "netconf";
      tailf:display-when "not(../../../../../ncs:module) or ../../../../../ncs:module[ncs:name='huawei-bier-fwd'] or (../../../../../ncs:live-status-protocol[not(ncs:capability)]) or (../../../../../ncs:live-status-protocol/ncs:capability/ncs:module[.='huawei-bier-fwd'])";
      description
        "Configure pipe mode ttl value.";
      leaf ttl-value {
        type uint8 {
          range "1..255";
        }
        // NCS drop default statement
        description
          "Bier pipe mode ttl value.";
      }
    }
  }
  augment "/ncs:devices/ncs:device/ncs:config/bier:bier/bier:sub-domains/bier:sub-domain" {
    description
      "Configure pipe mode ttl value.";
    container pipe-mode-ttl {
      tailf:ncs-device-type "netconf";
      tailf:display-when "not(../../../../../ncs:module) or ../../../../../ncs:module[ncs:name='huawei-bier-fwd']";
      description
        "Configure pipe mode ttl value.";
      leaf ttl-value {
        type uint8 {
          range "1..255";
        }
        default "255";
        description
          "Bier pipe mode ttl value.";
      }
    }
  }
}
