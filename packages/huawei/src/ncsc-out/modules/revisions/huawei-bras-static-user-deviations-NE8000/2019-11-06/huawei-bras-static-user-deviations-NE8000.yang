module huawei-bras-static-user-deviations-NE8000 {
  // Generated by yanger -t ncs
  tailf:mount-id "huawei-nc-1.0:huawei-nc-1.0";
  tailf:ncs-device-type "netconf";

  namespace "urn:huawei:yang:huawei-bras-static-user-deviations-NE8000";
  prefix bras-static-user-devs-NE8000;

  import huawei-bras-static-user {
    prefix bras-static-user;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "This module defines deviation statements for huawei-bras-static-user module.";

  revision 2019-11-06 {
    description
      "Initial revision.";
    reference "Huawei private.";
  }

  deviation "/ncs:devices/ncs:template/ncs:ned-id/ncs:config/bras-static-user:bras-static-user/bras-static-user:ipv4-users/bras-static-user:ipv4-user/bras-static-user:up-backup-interface" {
    deviate not-supported;
  }
  deviation "/ncs:devices/ncs:device/ncs:live-status/bras-static-user:bras-static-user/bras-static-user:ipv4-users/bras-static-user:ipv4-user/bras-static-user:up-backup-interface" {
    deviate not-supported;
  }
  deviation "/ncs:devices/ncs:device/ncs:config/bras-static-user:bras-static-user/bras-static-user:ipv4-users/bras-static-user:ipv4-user/bras-static-user:up-backup-interface" {
    deviate not-supported;
  }
  deviation "/ncs:devices/ncs:template/ncs:ned-id/ncs:config/bras-static-user:bras-static-user/bras-static-user:ipv6-users/bras-static-user:ipv6-user/bras-static-user:up-backup-interface" {
    deviate not-supported;
  }
  deviation "/ncs:devices/ncs:device/ncs:live-status/bras-static-user:bras-static-user/bras-static-user:ipv6-users/bras-static-user:ipv6-user/bras-static-user:up-backup-interface" {
    deviate not-supported;
  }
  deviation "/ncs:devices/ncs:device/ncs:config/bras-static-user:bras-static-user/bras-static-user:ipv6-users/bras-static-user:ipv6-user/bras-static-user:up-backup-interface" {
    deviate not-supported;
  }
  deviation "/ncs:devices/ncs:template/ncs:ned-id/ncs:config/bras-static-user:bras-static-user/bras-static-user:dual-stack-users/bras-static-user:dual-stack-user/bras-static-user:up-backup-interface" {
    deviate not-supported;
  }
  deviation "/ncs:devices/ncs:device/ncs:live-status/bras-static-user:bras-static-user/bras-static-user:dual-stack-users/bras-static-user:dual-stack-user/bras-static-user:up-backup-interface" {
    deviate not-supported;
  }
  deviation "/ncs:devices/ncs:device/ncs:config/bras-static-user:bras-static-user/bras-static-user:dual-stack-users/bras-static-user:dual-stack-user/bras-static-user:up-backup-interface" {
    deviate not-supported;
  }
}
