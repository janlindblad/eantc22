module huawei-qppb {
  // Generated by yanger -t ncs
  tailf:mount-id "huawei-nc-1.0:huawei-nc-1.0";
  tailf:ncs-device-type "netconf";

  namespace "urn:huawei:yang:huawei-qppb";
  prefix qppb;

  import huawei-extension {
    prefix ext;
  }
  import huawei-qos {
    prefix qos;
  }
  import huawei-ifm {
    prefix ifm;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "QPPB module.";

  revision 2020-03-12 {
    description
      "Descriptive optimization.";
    reference "Huawei private.";
  }
  revision 2020-02-25 {
    description
      "The modifications in the schema file are synchronized to the YANG file.";
    reference "Huawei private.";
  }
  revision 2019-05-05 {
    description
      "Initial revision.";
    reference "Huawei private.";
  }
  ext:task-name "qos";

  typedef ncs_template_direction-type {
    type string;
    description
      "Direction type.";
  }

  typedef ncs_template_qppb-direction-type {
    type string;
    description
      "QPPB direction type.";
  }

  typedef ncs_template_behavior-state {
    type string;
    description
      "QPPB behavior state.";
  }

  typedef ncs_template_traffic-mode {
    type string;
    description
      "Traffic mode.";
  }

  typedef ncs_template_qppb-mode {
    type string;
    description
      "QPPB mode.";
  }

  typedef ncs_rpc_notif_direction-type {
    type enumeration {
      enum "inbound" {
        value 0;
        description
          "Inbound.";
      }
      enum "outbound" {
        value 1;
        description
          "Outbound.";
      }
    }
    description
      "Direction type.";
  }

  typedef ncs_rpc_notif_qppb-direction-type {
    type enumeration {
      enum "inbound" {
        value 2;
        description
          "Inbound.";
      }
      enum "outbound" {
        value 3;
        description
          "Outbound.";
      }
    }
    description
      "QPPB direction type.";
  }

  typedef ncs_rpc_notif_behavior-state {
    type enumeration {
      enum "active" {
        value 0;
        description
          "All active.";
      }
      enum "active-p" {
        value 1;
        description
          "Part active.";
      }
      enum "inactive" {
        value 2;
        description
          "Inactive.";
      }
    }
    description
      "QPPB behavior state.";
  }

  typedef ncs_rpc_notif_traffic-mode {
    type enumeration {
      enum "source" {
        value 0;
        description
          "Source address.";
      }
      enum "destination" {
        value 1;
        description
          "Destination address.";
      }
      enum "both" {
        value 2;
        description
          "Source and Destination address.";
      }
    }
    description
      "Traffic mode.";
  }

  typedef ncs_rpc_notif_qppb-mode {
    type enumeration {
      enum "source" {
        value 0;
        description
          "Source address.";
      }
      enum "destination" {
        value 1;
        description
          "Destination address.";
      }
    }
    description
      "QPPB mode.";
  }

  typedef live_ncs_direction-type {
    type enumeration {
      enum "inbound" {
        value 0;
        description
          "Inbound.";
      }
      enum "outbound" {
        value 1;
        description
          "Outbound.";
      }
    }
    description
      "Direction type.";
  }

  typedef live_ncs_qppb-direction-type {
    type enumeration {
      enum "inbound" {
        value 2;
        description
          "Inbound.";
      }
      enum "outbound" {
        value 3;
        description
          "Outbound.";
      }
    }
    description
      "QPPB direction type.";
  }

  typedef live_ncs_behavior-state {
    type enumeration {
      enum "active" {
        value 0;
        description
          "All active.";
      }
      enum "active-p" {
        value 1;
        description
          "Part active.";
      }
      enum "inactive" {
        value 2;
        description
          "Inactive.";
      }
    }
    description
      "QPPB behavior state.";
  }

  typedef live_ncs_traffic-mode {
    type enumeration {
      enum "source" {
        value 0;
        description
          "Source address.";
      }
      enum "destination" {
        value 1;
        description
          "Destination address.";
      }
      enum "both" {
        value 2;
        description
          "Source and Destination address.";
      }
    }
    description
      "Traffic mode.";
  }

  typedef live_ncs_qppb-mode {
    type enumeration {
      enum "source" {
        value 0;
        description
          "Source address.";
      }
      enum "destination" {
        value 1;
        description
          "Destination address.";
      }
    }
    description
      "QPPB mode.";
  }

  typedef direction-type {
    type enumeration {
      enum "inbound" {
        value 0;
        description
          "Inbound.";
      }
      enum "outbound" {
        value 1;
        description
          "Outbound.";
      }
    }
    description
      "Direction type.";
  }

  typedef qppb-direction-type {
    type enumeration {
      enum "inbound" {
        value 2;
        description
          "Inbound.";
      }
      enum "outbound" {
        value 3;
        description
          "Outbound.";
      }
    }
    description
      "QPPB direction type.";
  }

  typedef behavior-state {
    type enumeration {
      enum "active" {
        value 0;
        description
          "All active.";
      }
      enum "active-p" {
        value 1;
        description
          "Part active.";
      }
      enum "inactive" {
        value 2;
        description
          "Inactive.";
      }
    }
    description
      "QPPB behavior state.";
  }

  typedef traffic-mode {
    type enumeration {
      enum "source" {
        value 0;
        description
          "Source address.";
      }
      enum "destination" {
        value 1;
        description
          "Destination address.";
      }
      enum "both" {
        value 2;
        description
          "Source and Destination address.";
      }
    }
    description
      "Traffic mode.";
  }

  typedef qppb-mode {
    type enumeration {
      enum "source" {
        value 0;
        description
          "Source address.";
      }
      enum "destination" {
        value 1;
        description
          "Destination address.";
      }
    }
    description
      "QPPB mode.";
  }

  augment "/ncs:devices/ncs:device/ncs:rpc" {
    container rpc-reset-local-policy-statistics {
      tailf:ncs-device-type "netconf";
      tailf:display-when "not(../../ncs:module) or ../../ncs:module[ncs:name='huawei-qppb']";
      tailf:action reset-local-policy-statistics {
        tailf:actionpoint ncsproxy {
          tailf:internal;
        }
        description
          "To clear local policy statistics.";
        ext:node-ref "/qos:qos/qppb:qppb/qppb:query-statistics";
        input {
          leaf interface-name {
            type string;
            mandatory true;
            description
              "Interface name.";
          }
          leaf direction {
            type ncs_rpc_notif_qppb-direction-type;
            mandatory true;
            description
              "Direction.";
          }
          leaf local-id {
            type uint32 {
              range "1..255";
            }
            description
              "Local ID.";
          }
        }
      }
    }
  }
  augment "/ncs:devices/ncs:device-group/ncs:ned-id/ncs:rpc" {
    container rpc-reset-local-policy-statistics {
      tailf:ncs-device-type "netconf";
      tailf:display-when "/ncs:devices/ncs:device[ncs:name=current()/../../../ncs:member]/ncs:module[ncs:name='huawei-qppb']";
      tailf:action reset-local-policy-statistics {
        tailf:actionpoint ncsproxy {
          tailf:internal;
        }
        description
          "To clear local policy statistics.";
        ext:node-ref "/qos:qos/qppb:qppb/qppb:query-statistics";
        input {
          leaf interface-name {
            type string;
            mandatory true;
            description
              "Interface name.";
          }
          leaf direction {
            type ncs_rpc_notif_qppb-direction-type;
            mandatory true;
            description
              "Direction.";
          }
          leaf local-id {
            type uint32 {
              range "1..255";
            }
            description
              "Local ID.";
          }
        }
      }
    }
  }
  augment "/ncs:devices/ncs:template/ncs:ned-id/ncs:config/qos:qos" {
    description
      "QPPB.";
    container qppb {
      description
        "Configure QPPB.";
      container local-policys {
        description
          "List of QPPB local policy.";
        list local-policy {
          // NCS patched for predictable order
          ordered-by user;
          key "policy-name";
          description
            "Configure QPPB local policy.";
          leaf policy-name {
            type string;
            description
              "Local-policy name.";
          }
          leaf statistic-enable {
            type string;
            // NCS drop default statement
            description
              "Enable/disable statistics flag.";
          }
          leaf service-class-outbound {
            type string;
            // NCS drop default statement
            description
              "Enable/disable outbound service-class flag.";
          }
          container qos-local-ids {
            description
              "List of QoS local ID.";
            list qos-local-id {
              // NCS patched for predictable order
              ordered-by user;
              key "local-id";
              // NCS drop max-elements statement
              description
                "Configure local ID.";
              leaf local-id {
                type string;
                description
                  "Local ID value.";
              }
              leaf behavior-name {
                type string;
                // NCS drop mandatory statement
                description
                  "Behavior name.";
              }
            }
          }
        }
      }
      // NCS drop config false container 'query-policys'
      // NCS drop config false container 'query-statistics'
    }
  }
  augment "/ncs:devices/ncs:device/ncs:live-status/qos:qos" {
    description
      "QPPB.";
    container qppb {
      tailf:ncs-device-type "netconf";
      tailf:display-when "not(../../../ncs:module) or ../../../ncs:module[ncs:name='huawei-qppb'] or (../../../ncs:live-status-protocol[not(ncs:capability)]) or (../../../ncs:live-status-protocol/ncs:capability/ncs:module[.='huawei-qppb'])";
      description
        "Configure QPPB.";
      container local-policys {
        description
          "List of QPPB local policy.";
        list local-policy {
          key "policy-name";
          description
            "Configure QPPB local policy.";
          leaf policy-name {
            type string {
              length "1..31";
            }
            description
              "Local-policy name.";
          }
          leaf statistic-enable {
            type boolean;
            // NCS drop default statement
            description
              "Enable/disable statistics flag.";
          }
          leaf service-class-outbound {
            type boolean;
            // NCS drop default statement
            description
              "Enable/disable outbound service-class flag.";
          }
          container qos-local-ids {
            description
              "List of QoS local ID.";
            list qos-local-id {
              key "local-id";
              // NCS drop max-elements statement
              description
                "Configure local ID.";
              leaf local-id {
                type uint32 {
                  range "1..255";
                }
                description
                  "Local ID value.";
              }
              leaf behavior-name {
                type leafref {
                  path "/ncs:devices/ncs:device/ncs:live-status/qos:qos/qos:classifier-template/qos:traffic-behaviors/qos:traffic-behavior/qos:name" {
                    tailf:xpath-root 3;
                  }
                }
                // NCS drop mandatory statement
                description
                  "Behavior name.";
              }
            }
          }
        }
      }
      container query-policys {
        description
          "List of interface QPPB.";
        list query-policy {
          key "if-name direction";
          // NCS drop max-elements statement
          description
            "Interface QPPB state.";
          leaf if-name {
            type leafref {
              path "/ncs:devices/ncs:device/ncs:live-status/ifm:ifm/ifm:interfaces/ifm:interface/ifm:name" {
                tailf:xpath-root 3;
              }
            }
            description
              "Name of an interface.";
          }
          leaf direction {
            type live_ncs_direction-type;
            description
              "Direction.";
          }
          leaf policy-name {
            type leafref {
              path "/ncs:devices/ncs:device/ncs:live-status/qos:qos/qppb:qppb/qppb:local-policys/qppb:local-policy/qppb:policy-name" {
                tailf:xpath-root 3;
              }
            }
            description
              "Local-policy name.";
          }
          leaf local-id {
            type uint32 {
              range "1..255";
            }
            description
              "Local ID.";
          }
          leaf behavior-name {
            type leafref {
              path "/ncs:devices/ncs:device/ncs:live-status/qos:qos/qos:classifier-template/qos:traffic-behaviors/qos:traffic-behavior/qos:name" {
                tailf:xpath-root 3;
              }
            }
            description
              "Behavior name.";
          }
          leaf state {
            type live_ncs_behavior-state;
            description
              "QPPB Policy state.";
          }
        }
      }
      container query-statistics {
        description
          "List of QPPB statistics.";
        list query-statistic {
          key "if-name slot-id direction";
          description
            "QPPB statistics.";
          leaf if-name {
            type leafref {
              path "/ncs:devices/ncs:device/ncs:live-status/ifm:ifm/ifm:interfaces/ifm:interface/ifm:name" {
                tailf:xpath-root 3;
              }
            }
            description
              "Outbound interface name.";
          }
          leaf slot-id {
            type string {
              length "1..127";
              pattern '(c[cl]c\d+/)?\d+';
            }
            description
              "Slot ID.";
          }
          leaf direction {
            type live_ncs_qppb-direction-type;
            description
              "Direction.";
          }
          leaf local-id {
            type uint32 {
              range "1..255";
            }
            description
              "Local ID.";
          }
          leaf match-packets {
            type uint64;
            units "packet";
            description
              "Match packets.";
          }
          leaf match-bytes {
            type uint64;
            units "Byte";
            description
              "Match bytes.";
          }
          leaf match-packets-rate {
            type uint64;
            units "pps";
            description
              "Passed packets rate.";
          }
          leaf match-bytes-rate {
            type uint64;
            units "Byte/s";
            description
              "Passed bytes rate.";
          }
          leaf passed-car-packets {
            type uint64;
            units "packet";
            description
              "Passed packets by CAR.";
          }
          leaf passed-car-bytes {
            type uint64;
            units "Byte";
            description
              "Passed bytes by CAR.";
          }
          leaf dropped-car-packets {
            type uint64;
            units "packet";
            description
              "Dropped packets by CAR.";
          }
          leaf dropped-car-bytes {
            type uint64;
            units "Byte";
            description
              "Dropped bytes by CAR.";
          }
          leaf passed-car-packets-rate {
            type uint64;
            units "pps";
            description
              "Passed packets rate by CAR.";
          }
          leaf passed-car-bytes-rate {
            type uint64;
            units "Byte/s";
            description
              "Passed bytes rate by CAR.";
          }
          leaf dropped-car-packets-rate {
            type uint64;
            units "pps";
            description
              "Dropped packets rate by CAR.";
          }
          leaf dropped-car-bytes-rate {
            type uint64;
            units "Byte/s";
            description
              "Dropped bytes rate by CAR.";
          }
          leaf car-green-packets {
            type uint64;
            units "packet";
            description
              "CAR green packets.";
          }
          leaf car-green-bytes {
            type uint64;
            units "Byte";
            description
              "CAR green bytes.";
          }
          leaf car-green-packets-rate {
            type uint64;
            units "pps";
            description
              "CAR green packets rate.";
          }
          leaf car-green-bytes-rate {
            type uint64;
            units "Byte/s";
            description
              "CAR green bytes rate.";
          }
          leaf car-yellow-packets {
            type uint64;
            units "packet";
            description
              "CAR yellow packets.";
          }
          leaf car-yellow-bytes {
            type uint64;
            units "Byte";
            description
              "CAR yellow bytes.";
          }
          leaf car-yellow-packets-rate {
            type uint64;
            units "pps";
            description
              "CAR yellow packets rate.";
          }
          leaf car-yellow-bytes-rate {
            type uint64;
            units "Byte/s";
            description
              "CAR yellow bytes rate.";
          }
          leaf car-red-packets {
            type uint64;
            units "packet";
            description
              "CAR red packets.";
          }
          leaf car-red-bytes {
            type uint64;
            units "Byte";
            description
              "CAR red bytes.";
          }
          leaf car-red-packets-rate {
            type uint64;
            units "pps";
            description
              "CAR red packets rate.";
          }
          leaf car-red-bytes-rate {
            type uint64;
            units "Byte/s";
            description
              "CAR red bytes rate.";
          }
          leaf passed-sq-be-packets {
            type uint64;
            units "packet";
            description
              "BE Pass packets.";
          }
          leaf dropped-sq-be-packets {
            type uint64;
            units "packet";
            description
              "BE Drop packets.";
          }
          leaf passed-sq-af1-packets {
            type uint64;
            units "packet";
            description
              "AF1 Pass packets.";
          }
          leaf dropped-sq-af1-packets {
            type uint64;
            units "packet";
            description
              "AF1 Drop packets.";
          }
          leaf passed-sq-af2-packets {
            type uint64;
            units "packet";
            description
              "AF2 Pass packets.";
          }
          leaf dropped-sq-af2-packets {
            type uint64;
            units "packet";
            description
              "AF2 Drop packets.";
          }
          leaf passed-sq-af3-packets {
            type uint64;
            units "packet";
            description
              "AF3 Pass packets.";
          }
          leaf dropped-sq-af3-packets {
            type uint64;
            units "packet";
            description
              "AF3 Drop packets.";
          }
          leaf passed-sq-af4-packets {
            type uint64;
            units "packet";
            description
              "AF4 Pass packets.";
          }
          leaf dropped-sq-af4-packets {
            type uint64;
            units "packet";
            description
              "AF4 Drop packets.";
          }
          leaf passed-sq-ef-packets {
            type uint64;
            units "packet";
            description
              "EF Pass packets.";
          }
          leaf dropped-sq-ef-packets {
            type uint64;
            units "packet";
            description
              "EF Drop packets.";
          }
          leaf passed-sq-cs6-packets {
            type uint64;
            units "packet";
            description
              "CS6 Pass packets.";
          }
          leaf dropped-sq-cs6-packets {
            type uint64;
            units "packet";
            description
              "CS6 Drop packets.";
          }
          leaf passed-sq-cs7-packets {
            type uint64;
            units "packet";
            description
              "CS7 Pass packets.";
          }
          leaf dropped-sq-cs7-packets {
            type uint64;
            units "packet";
            description
              "CS7 Drop packets.";
          }
          leaf passed-sq-be-bytes {
            type uint64;
            units "Byte";
            description
              "BE Pass Bytes.";
          }
          leaf dropped-sq-be-bytes {
            type uint64;
            units "Byte";
            description
              "BE Drop Bytes.";
          }
          leaf passed-sq-af1-bytes {
            type uint64;
            units "Byte";
            description
              "AF1 Pass Bytes.";
          }
          leaf dropped-sq-af1-bytes {
            type uint64;
            units "Byte";
            description
              "AF1 Drop Bytes.";
          }
          leaf passed-sq-af2-bytes {
            type uint64;
            units "Byte";
            description
              "AF2 Pass Bytes.";
          }
          leaf dropped-sq-af2-bytes {
            type uint64;
            units "Byte";
            description
              "AF2 Drop Bytes.";
          }
          leaf passed-sq-af3-bytes {
            type uint64;
            units "Byte";
            description
              "AF3 Pass Bytes.";
          }
          leaf dropped-sq-af3-bytes {
            type uint64;
            units "Byte";
            description
              "AF3 Drop Bytes.";
          }
          leaf passed-sq-af4-bytes {
            type uint64;
            units "Byte";
            description
              "AF4 Pass Bytes.";
          }
          leaf dropped-sq-af4-bytes {
            type uint64;
            units "Byte";
            description
              "AF4 Drop Bytes.";
          }
          leaf passed-sq-ef-bytes {
            type uint64;
            units "Byte";
            description
              "EF Pass Bytes.";
          }
          leaf dropped-sq-ef-bytes {
            type uint64;
            units "Byte";
            description
              "EF Drop Bytes.";
          }
          leaf passed-sq-cs6-bytes {
            type uint64;
            units "Byte";
            description
              "CS6 Pass Bytes.";
          }
          leaf dropped-sq-cs6-bytes {
            type uint64;
            units "Byte";
            description
              "CS6 Drop Bytes.";
          }
          leaf passed-sq-cs7-bytes {
            type uint64;
            units "Byte";
            description
              "CS7 Pass Bytes.";
          }
          leaf dropped-sq-cs7-bytes {
            type uint64;
            units "Byte";
            description
              "CS7 Drop Bytes.";
          }
          leaf passed-sq-be-bytes-rate {
            type uint64;
            units "Byte/s";
            description
              "BE Pass Bytes.";
          }
          leaf dropped-sq-be-bytes-rate {
            type uint64;
            units "Byte/s";
            description
              "BE Drop Bytes.";
          }
          leaf passed-sq-af1-bytes-rate {
            type uint64;
            units "Byte/s";
            description
              "AF1 Pass Bytes.";
          }
          leaf dropped-sq-af1-bytes-rate {
            type uint64;
            units "Byte/s";
            description
              "AF1 Drop Bytes.";
          }
          leaf passed-sq-af2-bytes-rate {
            type uint64;
            units "Byte/s";
            description
              "AF2 Pass Bytes.";
          }
          leaf dropped-sq-af2-bytes-rate {
            type uint64;
            units "Byte/s";
            description
              "AF2 Drop Bytes.";
          }
          leaf passed-sq-af3-bytes-rate {
            type uint64;
            units "Byte/s";
            description
              "AF3 Pass Bytes.";
          }
          leaf dropped-sq-af3-bytes-rate {
            type uint64;
            units "Byte/s";
            description
              "AF3 Drop Bytes.";
          }
          leaf passed-sq-af4-bytes-rate {
            type uint64;
            units "Byte/s";
            description
              "AF4 Pass Bytes.";
          }
          leaf dropped-sq-af4-bytes-rate {
            type uint64;
            units "Byte/s";
            description
              "AF4 Drop Bytes.";
          }
          leaf passed-sq-ef-bytes-rate {
            type uint64;
            units "Byte/s";
            description
              "EF Pass Bytes.";
          }
          leaf dropped-sq-ef-bytes-rate {
            type uint64;
            units "Byte/s";
            description
              "EF Drop Bytes.";
          }
          leaf passed-sq-cs6-bytes-rate {
            type uint64;
            units "Byte/s";
            description
              "CS6 Pass Bytes.";
          }
          leaf dropped-sq-cs6-bytes-rate {
            type uint64;
            units "Byte/s";
            description
              "CS6 Drop Bytes.";
          }
          leaf passed-sq-cs7-bytes-rate {
            type uint64;
            units "Byte/s";
            description
              "CS7 Pass Bytes.";
          }
          leaf dropped-sq-cs7-bytes-rate {
            type uint64;
            units "Byte/s";
            description
              "CS7 Drop Bytes.";
          }
          leaf passed-sq-be-packets-rate {
            type uint64;
            units "pps";
            description
              "BE Pass packets.";
          }
          leaf dropped-sq-be-packets-rate {
            type uint64;
            units "pps";
            description
              "BE Drop packets.";
          }
          leaf passed-sq-af1-packets-rate {
            type uint64;
            units "pps";
            description
              "AF1 Pass packets.";
          }
          leaf dropped-sq-af1-packets-rate {
            type uint64;
            units "pps";
            description
              "AF1 Drop packets.";
          }
          leaf passed-sq-af2-packets-rate {
            type uint64;
            units "pps";
            description
              "AF2 Pass packets.";
          }
          leaf dropped-sq-af2-packets-rate {
            type uint64;
            units "pps";
            description
              "AF2 Drop packets.";
          }
          leaf passed-sq-af3-packets-rate {
            type uint64;
            units "pps";
            description
              "AF3 Pass packets.";
          }
          leaf dropped-sq-af3-packets-rate {
            type uint64;
            units "pps";
            description
              "AF3 Drop packets.";
          }
          leaf passed-sq-af4-packets-rate {
            type uint64;
            units "pps";
            description
              "AF4 Pass packets.";
          }
          leaf dropped-sq-af4-packets-rate {
            type uint64;
            units "pps";
            description
              "AF4 Drop packets.";
          }
          leaf passed-sq-ef-packets-rate {
            type uint64;
            units "pps";
            description
              "EF Pass packets.";
          }
          leaf dropped-sq-ef-packets-rate {
            type uint64;
            units "pps";
            description
              "EF Drop packets.";
          }
          leaf passed-sq-cs6-packets-rate {
            type uint64;
            units "pps";
            description
              "CS6 Pass packets.";
          }
          leaf dropped-sq-cs6-packets-rate {
            type uint64;
            units "pps";
            description
              "CS6 Drop packets.";
          }
          leaf passed-sq-cs7-packets-rate {
            type uint64;
            units "pps";
            description
              "CS7 Pass packets.";
          }
          leaf dropped-sq-cs7-packets-rate {
            type uint64;
            units "pps";
            description
              "CS7 Drop packets.";
          }
        }
      }
    }
  }
  augment "/ncs:devices/ncs:device/ncs:config/qos:qos" {
    description
      "QPPB.";
    container qppb {
      tailf:ncs-device-type "netconf";
      tailf:display-when "not(../../../ncs:module) or ../../../ncs:module[ncs:name='huawei-qppb']";
      description
        "Configure QPPB.";
      container local-policys {
        description
          "List of QPPB local policy.";
        list local-policy {
          key "policy-name";
          description
            "Configure QPPB local policy.";
          leaf policy-name {
            type string {
              length "1..31";
            }
            description
              "Local-policy name.";
          }
          leaf statistic-enable {
            type boolean;
            default "false";
            description
              "Enable/disable statistics flag.";
          }
          leaf service-class-outbound {
            type boolean;
            default "false";
            description
              "Enable/disable outbound service-class flag.";
          }
          container qos-local-ids {
            description
              "List of QoS local ID.";
            list qos-local-id {
              key "local-id";
              max-elements 255;
              description
                "Configure local ID.";
              leaf local-id {
                type uint32 {
                  range "1..255";
                }
                description
                  "Local ID value.";
              }
              leaf behavior-name {
                type leafref {
                  path "/ncs:devices/ncs:device/ncs:config/qos:qos/qos:classifier-template/qos:traffic-behaviors/qos:traffic-behavior/qos:name" {
                    tailf:xpath-root 3;
                  }
                }
                mandatory true;
                description
                  "Behavior name.";
              }
            }
          }
        }
      }
      // NCS drop config false container 'query-policys'
      // NCS drop config false container 'query-statistics'
    }
  }
  augment "/ncs:devices/ncs:template/ncs:ned-id/ncs:config/qos:qos/qos:global-config" {
    description
      "Global acl enable.";
    container local-id-enable {
      presence "create qos-local-id-enable";
      description
        "Enable/disable QoS-local-id.";
      leaf mode {
        type ncs_template_traffic-mode;
        // NCS drop mandatory statement
        description
          "The mode of traffic policy QoS-local-id enable.";
      }
    }
  }
  augment "/ncs:devices/ncs:device/ncs:live-status/qos:qos/qos:global-config" {
    description
      "Global acl enable.";
    container local-id-enable {
      tailf:ncs-device-type "netconf";
      tailf:display-when "not(../../../../ncs:module) or ../../../../ncs:module[ncs:name='huawei-qppb'] or (../../../../ncs:live-status-protocol[not(ncs:capability)]) or (../../../../ncs:live-status-protocol/ncs:capability/ncs:module[.='huawei-qppb'])";
      presence "create qos-local-id-enable";
      description
        "Enable/disable QoS-local-id.";
      leaf mode {
        type live_ncs_traffic-mode;
        // NCS drop mandatory statement
        description
          "The mode of traffic policy QoS-local-id enable.";
      }
    }
  }
  augment "/ncs:devices/ncs:device/ncs:config/qos:qos/qos:global-config" {
    description
      "Global acl enable.";
    container local-id-enable {
      tailf:ncs-device-type "netconf";
      tailf:display-when "not(../../../../ncs:module) or ../../../../ncs:module[ncs:name='huawei-qppb']";
      presence "create qos-local-id-enable";
      description
        "Enable/disable QoS-local-id.";
      leaf mode {
        type traffic-mode;
        mandatory true;
        description
          "The mode of traffic policy QoS-local-id enable.";
      }
    }
  }
  augment "/ncs:devices/ncs:template/ncs:ned-id/ncs:config/ifm:ifm/ifm:interfaces/ifm:interface/qos:qos" {
    description
      "QPPB.";
    container local-id-enable {
      description
        "Configure QoS-local-id enable.";
      leaf mode {
        type ncs_template_qppb-mode;
        // NCS drop must statement
        description
          "The mode of traffic policy and QPPB QoS-local-id enable.";
      }
      leaf both {
        type empty;
        description
          "The mode of traffic policy QoS-local-id both enable. Both has a higher priority than mode.";
      }
    }
    container qppb {
      description
        "Configure QPPB.";
      container policys {
        description
          "List of QPPB policies application.";
        list policy {
          // NCS patched for predictable order
          ordered-by user;
          // NCS drop must statement
          key "direction";
          description
            "Configure application of QPPB policy.";
          leaf direction {
            type ncs_template_qppb-direction-type;
            description
              "QPPB policy direction.";
          }
          leaf policy-name {
            type string;
            // NCS drop mandatory statement
            description
              "QPPB local policy name.";
          }
          leaf mode {
            // NCS drop when statement
            type ncs_template_qppb-mode;
            // NCS drop mandatory statement
            description
              "QPPB policy mode.";
          }
          leaf share-mode {
            type string;
            // NCS drop default statement
            description
              "Enable/disable share mode.";
          }
        }
      }
      container ip-precedence {
        presence "create ip-precedence";
        description
          "Enable/disable QPPB policy ip-precedence.";
        leaf mode {
          type ncs_template_qppb-mode;
          // NCS drop mandatory statement
          description
            "QPPB policy mode.";
        }
      }
    }
  }
  augment "/ncs:devices/ncs:device/ncs:live-status/ifm:ifm/ifm:interfaces/ifm:interface/qos:qos" {
    description
      "QPPB.";
    container local-id-enable {
      tailf:ncs-device-type "netconf";
      tailf:display-when "not(../../../../../../ncs:module) or ../../../../../../ncs:module[ncs:name='huawei-qppb'] or (../../../../../../ncs:live-status-protocol[not(ncs:capability)]) or (../../../../../../ncs:live-status-protocol/ncs:capability/ncs:module[.='huawei-qppb'])";
      description
        "Configure QoS-local-id enable.";
      leaf mode {
        type live_ncs_qppb-mode;
        // NCS drop must statement
        description
          "The mode of traffic policy and QPPB QoS-local-id enable.";
      }
      leaf both {
        type empty;
        description
          "The mode of traffic policy QoS-local-id both enable. Both has a higher priority than mode.";
      }
    }
    container qppb {
      tailf:ncs-device-type "netconf";
      tailf:display-when "not(../../../../../../ncs:module) or ../../../../../../ncs:module[ncs:name='huawei-qppb'] or (../../../../../../ncs:live-status-protocol[not(ncs:capability)]) or (../../../../../../ncs:live-status-protocol/ncs:capability/ncs:module[.='huawei-qppb'])";
      description
        "Configure QPPB.";
      container policys {
        description
          "List of QPPB policies application.";
        list policy {
          // NCS drop must statement
          key "direction";
          description
            "Configure application of QPPB policy.";
          leaf direction {
            type live_ncs_qppb-direction-type;
            description
              "QPPB policy direction.";
          }
          leaf policy-name {
            type leafref {
              path "/ncs:devices/ncs:device/ncs:live-status/qos:qos/qppb:qppb/qppb:local-policys/qppb:local-policy/qppb:policy-name" {
                tailf:xpath-root 3;
              }
            }
            // NCS drop mandatory statement
            description
              "QPPB local policy name.";
          }
          leaf mode {
            // NCS drop when statement
            type live_ncs_qppb-mode;
            // NCS drop mandatory statement
            description
              "QPPB policy mode.";
          }
          leaf share-mode {
            type boolean;
            // NCS drop default statement
            description
              "Enable/disable share mode.";
          }
        }
      }
      container ip-precedence {
        presence "create ip-precedence";
        description
          "Enable/disable QPPB policy ip-precedence.";
        leaf mode {
          type live_ncs_qppb-mode;
          // NCS drop mandatory statement
          description
            "QPPB policy mode.";
        }
      }
    }
  }
  augment "/ncs:devices/ncs:device/ncs:config/ifm:ifm/ifm:interfaces/ifm:interface/qos:qos" {
    description
      "QPPB.";
    container local-id-enable {
      tailf:ncs-device-type "netconf";
      tailf:display-when "not(../../../../../../ncs:module) or ../../../../../../ncs:module[ncs:name='huawei-qppb']";
      description
        "Configure QoS-local-id enable.";
      leaf mode {
        type qppb-mode;
        must "not(../../qppb:qppb/qppb:policys/qppb:policy[qppb:direction='inbound'])" {
          tailf:xpath-root 3;
        }
        description
          "The mode of traffic policy and QPPB QoS-local-id enable.";
      }
      leaf both {
        type empty;
        description
          "The mode of traffic policy QoS-local-id both enable. Both has a higher priority than mode.";
      }
    }
    container qppb {
      tailf:ncs-device-type "netconf";
      tailf:display-when "not(../../../../../../ncs:module) or ../../../../../../ncs:module[ncs:name='huawei-qppb']";
      description
        "Configure QPPB.";
      container policys {
        description
          "List of QPPB policies application.";
        list policy {
          must "(./direction='inbound' and ./policy-name and ./mode and not(../../../local-id-enable/mode)) or (./direction='outbound' and ./policy-name and not(./mode))" {
            tailf:xpath-root 3;
          }
          key "direction";
          description
            "Configure application of QPPB policy.";
          leaf direction {
            type qppb-direction-type;
            description
              "QPPB policy direction.";
          }
          leaf policy-name {
            type leafref {
              path "/ncs:devices/ncs:device/ncs:config/qos:qos/qppb:qppb/qppb:local-policys/qppb:local-policy/qppb:policy-name" {
                tailf:xpath-root 3;
              }
            }
            mandatory true;
            description
              "QPPB local policy name.";
          }
          leaf mode {
            when "../direction='inbound'" {
              tailf:xpath-root 3;
            }
            type qppb-mode;
            mandatory true;
            description
              "QPPB policy mode.";
          }
          leaf share-mode {
            type boolean;
            default "true";
            description
              "Enable/disable share mode.";
          }
        }
      }
      container ip-precedence {
        presence "create ip-precedence";
        description
          "Enable/disable QPPB policy ip-precedence.";
        leaf mode {
          type qppb-mode;
          mandatory true;
          description
            "QPPB policy mode.";
        }
      }
    }
  }
}
