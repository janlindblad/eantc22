submodule huawei-ospfv3-type {
  // Generated by yanger -t ncs
  tailf:mount-id "huawei-nc-1.0:huawei-nc-1.0";

  belongs-to huawei-ospfv3 {
    prefix ospfv3;
  }

  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "OSPFv3 type.";

  revision 2020-03-09 {
    description
      "Modify the description.";
    reference "Huawei private.";
  }
  revision 2020-02-27 {
    description
      "Modify the description.";
    reference "Huawei private.";
  }
  revision 2020-02-04 {
    description
      "Add spf-timer-type.";
    reference "Huawei private.";
  }
  revision 2019-12-19 {
    description
      "Reconstructing Yang file by yin mechanism.";
    reference "Huawei private.";
  }
  revision 2019-11-22 {
    description
      "Reconstructing Yang file by yin mechanism.";
    reference "Huawei private.";
  }
  revision 2019-11-15 {
    description
      "Reconstructing Yang file by yin mechanism.";
    reference "Huawei private.";
  }
  revision 2019-10-22 {
    description
      "Reconstructing Yang file by yin mechanism.";
    reference "Huawei private.";
  }
  revision 2019-04-04 {
    description
      "Initial revision.";
    reference "Huawei private.";
  }

  typedef ncs_template_domain-id-type {
    type string;
    description
      "OSPFv3 domain id type.";
  }

  typedef ncs_template_import-rt-protocol {
    type string;
    description
      "OSPFv3 import route protocol.";
  }

  typedef ncs_template_prefix-priority {
    type string;
    description
      "OSPFv3 prefix priority.";
  }

  typedef ncs_template_area-type {
    type string;
    description
      "OSPFv3 area type.";
  }

  typedef ncs_template_forwarding-address-type {
    type string;
    description
      "OSPFv3 forwarding address mode.";
  }

  typedef ncs_template_area-filter-mode {
    type string;
    description
      "OSPFv3 area filter mode.";
  }

  typedef ncs_template_external-route-type {
    type string;
    description
      "OSPFv3 external route type.";
  }

  typedef ncs_template_network-type {
    type string;
    description
      "OSPFv3 network type.";
  }

  typedef ncs_template_stub-router-flag {
    type string;
    description
      "OSPFv3 stub router flag.";
  }

  typedef ncs_template_ospf-route-type {
    type string;
    description
      "OSPFv3 ospf route type.";
  }

  typedef ncs_template_authen-mode {
    type string;
    description
      "OSPFv3 authencation mode.";
  }

  typedef ncs_template_filter-rt-protocol {
    type string;
    description
      "OSPFv3 filter router protocol.";
  }

  typedef ncs_template_spf-timer-type {
    type string;
    description
      "OSPFv3 SPF timer type.";
  }

  typedef ncs_template_nbr-state {
    type string;
    description
      "OSPFv3 nbr state.";
  }

  typedef ncs_template_interface-state {
    type string;
    description
      "OSPFv3 interface state.";
  }

  typedef ncs_template_auth-type {
    type string;
    description
      "OSPFv3 link protocol.";
  }

  typedef ncs_template_peer-flapping-suppress-type {
    type string;
    description
      "OSPFv3 peer suppress-flapping status.";
  }

  typedef ncs_rpc_notif_domain-id-type {
    type enumeration {
      enum "0x0005" {
        value 1;
        description
          "Domain id type is 0x0005.";
      }
      enum "0x0105" {
        value 2;
        description
          "Domain id type is 0x0105.";
      }
      enum "0x0205" {
        value 3;
        description
          "Domain id type is 0x0205.";
      }
      enum "0x8005" {
        value 4;
        description
          "Domain id type is 0x8005.";
      }
    }
    description
      "OSPFv3 domain id type.";
  }

  typedef ncs_rpc_notif_import-rt-protocol {
    type enumeration {
      enum "direct" {
        value 1;
        description
          "Direct route.";
      }
      enum "ospfv3" {
        value 7;
        description
          "OSPFv3 router.";
      }
      enum "isis" {
        value 3;
        description
          "ISIS protocol.";
      }
      enum "static" {
        value 4;
        description
          "Static route.";
      }
      enum "ripng" {
        value 8;
        description
          "RIPng routes.";
      }
      enum "bgp" {
        value 6;
        description
          "BGP protocol.";
      }
      enum "unr" {
        value 11;
        description
          "User Network routes.";
      }
      enum "opr" {
        value 14;
        description
          "Open programming routes.";
      }
    }
    description
      "OSPFv3 import route protocol.";
  }

  typedef ncs_rpc_notif_prefix-priority {
    type enumeration {
      enum "critical" {
        value 1;
        description
          "Critical.";
      }
      enum "high" {
        value 2;
        description
          "High.";
      }
      enum "medium" {
        value 3;
        description
          "Medium.";
      }
      enum "very-low" {
        value 5;
        description
          "Very low.";
      }
    }
    description
      "OSPFv3 prefix priority.";
  }

  typedef ncs_rpc_notif_area-type {
    type enumeration {
      enum "normal" {
        value 1;
        description
          "Normal area.";
      }
      enum "stub" {
        value 2;
        description
          "Stub area.";
      }
      enum "nssa" {
        value 3;
        description
          "Nssa area.";
      }
    }
    description
      "OSPFv3 area type.";
  }

  typedef ncs_rpc_notif_forwarding-address-type {
    type enumeration {
      enum "disable" {
        value 0;
        description
          "Disable mode.";
      }
      enum "standard" {
        value 1;
        description
          "Standard mode.";
      }
      enum "zero-translate" {
        value 2;
        description
          "Zero translate mode.";
      }
    }
    description
      "OSPFv3 forwarding address mode.";
  }

  typedef ncs_rpc_notif_area-filter-mode {
    type enumeration {
      enum "filter-import" {
        value 0;
        description
          "Filter incoming summary LSAs.";
      }
      enum "filter-export" {
        value 1;
        description
          "Filter outgoing summary LSAs.";
      }
    }
    description
      "OSPFv3 area filter mode.";
  }

  typedef ncs_rpc_notif_external-route-type {
    type enumeration {
      enum "type1" {
        value 1;
        description
          "External route type 1.";
      }
      enum "type2" {
        value 2;
        description
          "External route type 2.";
      }
    }
    description
      "OSPFv3 external route type.";
  }

  typedef ncs_rpc_notif_network-type {
    type enumeration {
      enum "broadcast" {
        value 1;
        description
          "The network type of an interface is set to broadcast.";
      }
      enum "nbma" {
        value 2;
        description
          "The network type of an interface is set to NBMA.";
      }
      enum "p2mp" {
        value 5;
        description
          "The network type of an interface is set to P2MP.";
      }
      enum "p2p" {
        value 3;
        description
          "The network type of an interface is set to P2P.";
      }
      enum "p2mp-nonbroadcast" {
        value 7;
        description
          "The network type of an interface is set to p2mp-nonbroadcast.";
      }
      enum "loopback" {
        value 22;
        description
          "The network type of an interface is set to Loopback.";
      }
    }
    description
      "OSPFv3 network type.";
  }

  typedef ncs_rpc_notif_stub-router-flag {
    type enumeration {
      enum "no-config" {
        value 0;
        description
          "No config.";
      }
      enum "stub-on-hand" {
        value 1;
        description
          "To configure a stub router.";
      }
      enum "stub-on-boot" {
        value 2;
        description
          "To remain as the stub router during the active/standby switchover of a router.";
      }
    }
    description
      "OSPFv3 stub router flag.";
  }

  typedef ncs_rpc_notif_ospf-route-type {
    type enumeration {
      enum "default" {
        value 1;
        description
          "Intra and inter route.";
      }
      enum "ase" {
        value 2;
        description
          "AS external route.";
      }
    }
    description
      "OSPFv3 ospf route type.";
  }

  typedef ncs_rpc_notif_authen-mode {
    type enumeration {
      enum "none" {
        value 0;
        description
          "To cancel authentication.";
      }
      enum "hmac-sha256" {
        value 2;
        description
          "Cipher text authentication mode.";
      }
    }
    description
      "OSPFv3 authencation mode.";
  }

  typedef ncs_rpc_notif_filter-rt-protocol {
    type enumeration {
      enum "default" {
        value 9;
        description
          "None config.";
      }
      enum "direct" {
        value 1;
        description
          "Direct route.";
      }
      enum "ospfv3" {
        value 7;
        description
          "OSPFv3 protocol.";
      }
      enum "isis" {
        value 3;
        description
          "ISIS protocol.";
      }
      enum "static" {
        value 4;
        description
          "Static route.";
      }
      enum "ripng" {
        value 8;
        description
          "RIPng protocol.";
      }
      enum "bgp" {
        value 6;
        description
          "BGP protocol.";
      }
      enum "unr" {
        value 11;
        description
          "User Network Routes.";
      }
      enum "opr" {
        value 14;
        description
          "Open programming routes.";
      }
    }
    description
      "OSPFv3 filter router protocol.";
  }

  typedef ncs_rpc_notif_spf-timer-type {
    type enumeration {
      enum "normal" {
        value 3;
        description
          "SPF normal timer.";
      }
      enum "intelligent" {
        value 4;
        description
          "SPF intelligent timer.";
      }
    }
    description
      "OSPFv3 SPF timer type.";
  }

  typedef ncs_rpc_notif_nbr-state {
    type enumeration {
      enum "down" {
        value 0;
        description
          "Initial status of a neighbor, which indicates that no neighbor receive any message. In an NBMA network, Hello packets can still be received and sent at poll intervals. The poll interval is longer than the Hello interval.";
      }
      enum "init" {
        value 1;
        description
          "Hello packet is received from the neighbor.";
      }
      enum "attempt" {
        value 2;
        description
          "The neighbor relationship is being set up, which exists on only an NBMA network. The period of sending and receiving Hello packets is Hello interval. Hello interval is shorter than the poll interval.";
      }
      enum "2-way" {
        value 3;
        description
          "The Hello packet is received from the neighbor and the neighbor list of the Hello packet contains the local ID, that is, the two ends can interwork.";
      }
      enum "exstart" {
        value 4;
        description
          "The neighbor relationship is set up. The master and slave relationship and DD sequence number are negotiated.";
      }
      enum "exchange" {
        value 5;
        description
          "LSDBs are synchronized. DD packets, LSR packets, and LSU packets are exchanged during LSDB synchronization.";
      }
      enum "loading" {
        value 6;
        description
          "LSDBs are being synchronized. LSR packets and LSU packets are exchanged during LSBD synchronization.";
      }
      enum "full" {
        value 7;
        description
          "LSDBs of neighbors have been synchronized. Both sides set up the adjacency and they are in Full state.";
      }
    }
    description
      "OSPFv3 nbr state.";
  }

  typedef ncs_rpc_notif_interface-state {
    type enumeration {
      enum "down" {
        value 0;
        description
          "Down.";
      }
      enum "waiting" {
        value 1;
        description
          "Waiting.";
      }
      enum "p-2-p" {
        value 2;
        description
          "P-2-P.";
      }
      enum "dr" {
        value 3;
        description
          "DR.";
      }
      enum "bdr" {
        value 4;
        description
          "BDR.";
      }
      enum "dr-other" {
        value 5;
        description
          "DROTHER.";
      }
      enum "loopback" {
        value 6;
        description
          "Loopback.";
      }
      enum "point-to-point" {
        value 18;
        description
          "Point-To-Point.";
      }
      enum "backup" {
        value 20;
        description
          "Backup.";
      }
    }
    description
      "OSPFv3 interface state.";
  }

  typedef ncs_rpc_notif_auth-type {
    type enumeration {
      enum "none" {
        value 0;
        description
          "None.";
      }
      enum "hmac-sha256" {
        value 1;
        description
          "HMAC-SHA256.";
      }
      enum "hmac-sha256-inherited" {
        value 2;
        description
          "HMAC-SHA256 [Inherited].";
      }
    }
    description
      "OSPFv3 link protocol.";
  }

  typedef ncs_rpc_notif_peer-flapping-suppress-type {
    type enumeration {
      enum "disable" {
        value 0;
        description
          "None.";
      }
      enum "enable" {
        value 1;
        description
          "Enable.";
      }
      enum "hold-max-cost" {
        value 2;
        description
          "Hold max cost.";
      }
      enum "hold-down" {
        value 3;
        description
          "Hold down.";
      }
    }
    description
      "OSPFv3 peer suppress-flapping status.";
  }

  typedef live_ncs_domain-id-type {
    type enumeration {
      enum "0x0005" {
        value 1;
        description
          "Domain id type is 0x0005.";
      }
      enum "0x0105" {
        value 2;
        description
          "Domain id type is 0x0105.";
      }
      enum "0x0205" {
        value 3;
        description
          "Domain id type is 0x0205.";
      }
      enum "0x8005" {
        value 4;
        description
          "Domain id type is 0x8005.";
      }
    }
    description
      "OSPFv3 domain id type.";
  }

  typedef live_ncs_import-rt-protocol {
    type enumeration {
      enum "direct" {
        value 1;
        description
          "Direct route.";
      }
      enum "ospfv3" {
        value 7;
        description
          "OSPFv3 router.";
      }
      enum "isis" {
        value 3;
        description
          "ISIS protocol.";
      }
      enum "static" {
        value 4;
        description
          "Static route.";
      }
      enum "ripng" {
        value 8;
        description
          "RIPng routes.";
      }
      enum "bgp" {
        value 6;
        description
          "BGP protocol.";
      }
      enum "unr" {
        value 11;
        description
          "User Network routes.";
      }
      enum "opr" {
        value 14;
        description
          "Open programming routes.";
      }
    }
    description
      "OSPFv3 import route protocol.";
  }

  typedef live_ncs_prefix-priority {
    type enumeration {
      enum "critical" {
        value 1;
        description
          "Critical.";
      }
      enum "high" {
        value 2;
        description
          "High.";
      }
      enum "medium" {
        value 3;
        description
          "Medium.";
      }
      enum "very-low" {
        value 5;
        description
          "Very low.";
      }
    }
    description
      "OSPFv3 prefix priority.";
  }

  typedef live_ncs_area-type {
    type enumeration {
      enum "normal" {
        value 1;
        description
          "Normal area.";
      }
      enum "stub" {
        value 2;
        description
          "Stub area.";
      }
      enum "nssa" {
        value 3;
        description
          "Nssa area.";
      }
    }
    description
      "OSPFv3 area type.";
  }

  typedef live_ncs_forwarding-address-type {
    type enumeration {
      enum "disable" {
        value 0;
        description
          "Disable mode.";
      }
      enum "standard" {
        value 1;
        description
          "Standard mode.";
      }
      enum "zero-translate" {
        value 2;
        description
          "Zero translate mode.";
      }
    }
    description
      "OSPFv3 forwarding address mode.";
  }

  typedef live_ncs_area-filter-mode {
    type enumeration {
      enum "filter-import" {
        value 0;
        description
          "Filter incoming summary LSAs.";
      }
      enum "filter-export" {
        value 1;
        description
          "Filter outgoing summary LSAs.";
      }
    }
    description
      "OSPFv3 area filter mode.";
  }

  typedef live_ncs_external-route-type {
    type enumeration {
      enum "type1" {
        value 1;
        description
          "External route type 1.";
      }
      enum "type2" {
        value 2;
        description
          "External route type 2.";
      }
    }
    description
      "OSPFv3 external route type.";
  }

  typedef live_ncs_network-type {
    type enumeration {
      enum "broadcast" {
        value 1;
        description
          "The network type of an interface is set to broadcast.";
      }
      enum "nbma" {
        value 2;
        description
          "The network type of an interface is set to NBMA.";
      }
      enum "p2mp" {
        value 5;
        description
          "The network type of an interface is set to P2MP.";
      }
      enum "p2p" {
        value 3;
        description
          "The network type of an interface is set to P2P.";
      }
      enum "p2mp-nonbroadcast" {
        value 7;
        description
          "The network type of an interface is set to p2mp-nonbroadcast.";
      }
      enum "loopback" {
        value 22;
        description
          "The network type of an interface is set to Loopback.";
      }
    }
    description
      "OSPFv3 network type.";
  }

  typedef live_ncs_stub-router-flag {
    type enumeration {
      enum "no-config" {
        value 0;
        description
          "No config.";
      }
      enum "stub-on-hand" {
        value 1;
        description
          "To configure a stub router.";
      }
      enum "stub-on-boot" {
        value 2;
        description
          "To remain as the stub router during the active/standby switchover of a router.";
      }
    }
    description
      "OSPFv3 stub router flag.";
  }

  typedef live_ncs_ospf-route-type {
    type enumeration {
      enum "default" {
        value 1;
        description
          "Intra and inter route.";
      }
      enum "ase" {
        value 2;
        description
          "AS external route.";
      }
    }
    description
      "OSPFv3 ospf route type.";
  }

  typedef live_ncs_authen-mode {
    type enumeration {
      enum "none" {
        value 0;
        description
          "To cancel authentication.";
      }
      enum "hmac-sha256" {
        value 2;
        description
          "Cipher text authentication mode.";
      }
    }
    description
      "OSPFv3 authencation mode.";
  }

  typedef live_ncs_filter-rt-protocol {
    type enumeration {
      enum "default" {
        value 9;
        description
          "None config.";
      }
      enum "direct" {
        value 1;
        description
          "Direct route.";
      }
      enum "ospfv3" {
        value 7;
        description
          "OSPFv3 protocol.";
      }
      enum "isis" {
        value 3;
        description
          "ISIS protocol.";
      }
      enum "static" {
        value 4;
        description
          "Static route.";
      }
      enum "ripng" {
        value 8;
        description
          "RIPng protocol.";
      }
      enum "bgp" {
        value 6;
        description
          "BGP protocol.";
      }
      enum "unr" {
        value 11;
        description
          "User Network Routes.";
      }
      enum "opr" {
        value 14;
        description
          "Open programming routes.";
      }
    }
    description
      "OSPFv3 filter router protocol.";
  }

  typedef live_ncs_spf-timer-type {
    type enumeration {
      enum "normal" {
        value 3;
        description
          "SPF normal timer.";
      }
      enum "intelligent" {
        value 4;
        description
          "SPF intelligent timer.";
      }
    }
    description
      "OSPFv3 SPF timer type.";
  }

  typedef live_ncs_nbr-state {
    type enumeration {
      enum "down" {
        value 0;
        description
          "Initial status of a neighbor, which indicates that no neighbor receive any message. In an NBMA network, Hello packets can still be received and sent at poll intervals. The poll interval is longer than the Hello interval.";
      }
      enum "init" {
        value 1;
        description
          "Hello packet is received from the neighbor.";
      }
      enum "attempt" {
        value 2;
        description
          "The neighbor relationship is being set up, which exists on only an NBMA network. The period of sending and receiving Hello packets is Hello interval. Hello interval is shorter than the poll interval.";
      }
      enum "2-way" {
        value 3;
        description
          "The Hello packet is received from the neighbor and the neighbor list of the Hello packet contains the local ID, that is, the two ends can interwork.";
      }
      enum "exstart" {
        value 4;
        description
          "The neighbor relationship is set up. The master and slave relationship and DD sequence number are negotiated.";
      }
      enum "exchange" {
        value 5;
        description
          "LSDBs are synchronized. DD packets, LSR packets, and LSU packets are exchanged during LSDB synchronization.";
      }
      enum "loading" {
        value 6;
        description
          "LSDBs are being synchronized. LSR packets and LSU packets are exchanged during LSBD synchronization.";
      }
      enum "full" {
        value 7;
        description
          "LSDBs of neighbors have been synchronized. Both sides set up the adjacency and they are in Full state.";
      }
    }
    description
      "OSPFv3 nbr state.";
  }

  typedef live_ncs_interface-state {
    type enumeration {
      enum "down" {
        value 0;
        description
          "Down.";
      }
      enum "waiting" {
        value 1;
        description
          "Waiting.";
      }
      enum "p-2-p" {
        value 2;
        description
          "P-2-P.";
      }
      enum "dr" {
        value 3;
        description
          "DR.";
      }
      enum "bdr" {
        value 4;
        description
          "BDR.";
      }
      enum "dr-other" {
        value 5;
        description
          "DROTHER.";
      }
      enum "loopback" {
        value 6;
        description
          "Loopback.";
      }
      enum "point-to-point" {
        value 18;
        description
          "Point-To-Point.";
      }
      enum "backup" {
        value 20;
        description
          "Backup.";
      }
    }
    description
      "OSPFv3 interface state.";
  }

  typedef live_ncs_auth-type {
    type enumeration {
      enum "none" {
        value 0;
        description
          "None.";
      }
      enum "hmac-sha256" {
        value 1;
        description
          "HMAC-SHA256.";
      }
      enum "hmac-sha256-inherited" {
        value 2;
        description
          "HMAC-SHA256 [Inherited].";
      }
    }
    description
      "OSPFv3 link protocol.";
  }

  typedef live_ncs_peer-flapping-suppress-type {
    type enumeration {
      enum "disable" {
        value 0;
        description
          "None.";
      }
      enum "enable" {
        value 1;
        description
          "Enable.";
      }
      enum "hold-max-cost" {
        value 2;
        description
          "Hold max cost.";
      }
      enum "hold-down" {
        value 3;
        description
          "Hold down.";
      }
    }
    description
      "OSPFv3 peer suppress-flapping status.";
  }

  typedef domain-id-type {
    type enumeration {
      enum "0x0005" {
        value 1;
        description
          "Domain id type is 0x0005.";
      }
      enum "0x0105" {
        value 2;
        description
          "Domain id type is 0x0105.";
      }
      enum "0x0205" {
        value 3;
        description
          "Domain id type is 0x0205.";
      }
      enum "0x8005" {
        value 4;
        description
          "Domain id type is 0x8005.";
      }
    }
    description
      "OSPFv3 domain id type.";
  }

  typedef import-rt-protocol {
    type enumeration {
      enum "direct" {
        value 1;
        description
          "Direct route.";
      }
      enum "ospfv3" {
        value 7;
        description
          "OSPFv3 router.";
      }
      enum "isis" {
        value 3;
        description
          "ISIS protocol.";
      }
      enum "static" {
        value 4;
        description
          "Static route.";
      }
      enum "ripng" {
        value 8;
        description
          "RIPng routes.";
      }
      enum "bgp" {
        value 6;
        description
          "BGP protocol.";
      }
      enum "unr" {
        value 11;
        description
          "User Network routes.";
      }
      enum "opr" {
        value 14;
        description
          "Open programming routes.";
      }
    }
    description
      "OSPFv3 import route protocol.";
  }

  typedef prefix-priority {
    type enumeration {
      enum "critical" {
        value 1;
        description
          "Critical.";
      }
      enum "high" {
        value 2;
        description
          "High.";
      }
      enum "medium" {
        value 3;
        description
          "Medium.";
      }
      enum "very-low" {
        value 5;
        description
          "Very low.";
      }
    }
    description
      "OSPFv3 prefix priority.";
  }

  typedef area-type {
    type enumeration {
      enum "normal" {
        value 1;
        description
          "Normal area.";
      }
      enum "stub" {
        value 2;
        description
          "Stub area.";
      }
      enum "nssa" {
        value 3;
        description
          "Nssa area.";
      }
    }
    description
      "OSPFv3 area type.";
  }

  typedef forwarding-address-type {
    type enumeration {
      enum "disable" {
        value 0;
        description
          "Disable mode.";
      }
      enum "standard" {
        value 1;
        description
          "Standard mode.";
      }
      enum "zero-translate" {
        value 2;
        description
          "Zero translate mode.";
      }
    }
    description
      "OSPFv3 forwarding address mode.";
  }

  typedef area-filter-mode {
    type enumeration {
      enum "filter-import" {
        value 0;
        description
          "Filter incoming summary LSAs.";
      }
      enum "filter-export" {
        value 1;
        description
          "Filter outgoing summary LSAs.";
      }
    }
    description
      "OSPFv3 area filter mode.";
  }

  typedef external-route-type {
    type enumeration {
      enum "type1" {
        value 1;
        description
          "External route type 1.";
      }
      enum "type2" {
        value 2;
        description
          "External route type 2.";
      }
    }
    description
      "OSPFv3 external route type.";
  }

  typedef network-type {
    type enumeration {
      enum "broadcast" {
        value 1;
        description
          "The network type of an interface is set to broadcast.";
      }
      enum "nbma" {
        value 2;
        description
          "The network type of an interface is set to NBMA.";
      }
      enum "p2mp" {
        value 5;
        description
          "The network type of an interface is set to P2MP.";
      }
      enum "p2p" {
        value 3;
        description
          "The network type of an interface is set to P2P.";
      }
      enum "p2mp-nonbroadcast" {
        value 7;
        description
          "The network type of an interface is set to p2mp-nonbroadcast.";
      }
      enum "loopback" {
        value 22;
        description
          "The network type of an interface is set to Loopback.";
      }
    }
    description
      "OSPFv3 network type.";
  }

  typedef stub-router-flag {
    type enumeration {
      enum "no-config" {
        value 0;
        description
          "No config.";
      }
      enum "stub-on-hand" {
        value 1;
        description
          "To configure a stub router.";
      }
      enum "stub-on-boot" {
        value 2;
        description
          "To remain as the stub router during the active/standby switchover of a router.";
      }
    }
    description
      "OSPFv3 stub router flag.";
  }

  typedef ospf-route-type {
    type enumeration {
      enum "default" {
        value 1;
        description
          "Intra and inter route.";
      }
      enum "ase" {
        value 2;
        description
          "AS external route.";
      }
    }
    description
      "OSPFv3 ospf route type.";
  }

  typedef authen-mode {
    type enumeration {
      enum "none" {
        value 0;
        description
          "To cancel authentication.";
      }
      enum "hmac-sha256" {
        value 2;
        description
          "Cipher text authentication mode.";
      }
    }
    description
      "OSPFv3 authencation mode.";
  }

  typedef filter-rt-protocol {
    type enumeration {
      enum "default" {
        value 9;
        description
          "None config.";
      }
      enum "direct" {
        value 1;
        description
          "Direct route.";
      }
      enum "ospfv3" {
        value 7;
        description
          "OSPFv3 protocol.";
      }
      enum "isis" {
        value 3;
        description
          "ISIS protocol.";
      }
      enum "static" {
        value 4;
        description
          "Static route.";
      }
      enum "ripng" {
        value 8;
        description
          "RIPng protocol.";
      }
      enum "bgp" {
        value 6;
        description
          "BGP protocol.";
      }
      enum "unr" {
        value 11;
        description
          "User Network Routes.";
      }
      enum "opr" {
        value 14;
        description
          "Open programming routes.";
      }
    }
    description
      "OSPFv3 filter router protocol.";
  }

  typedef spf-timer-type {
    type enumeration {
      enum "normal" {
        value 3;
        description
          "SPF normal timer.";
      }
      enum "intelligent" {
        value 4;
        description
          "SPF intelligent timer.";
      }
    }
    description
      "OSPFv3 SPF timer type.";
  }

  typedef nbr-state {
    type enumeration {
      enum "down" {
        value 0;
        description
          "Initial status of a neighbor, which indicates that no neighbor receive any message. In an NBMA network, Hello packets can still be received and sent at poll intervals. The poll interval is longer than the Hello interval.";
      }
      enum "init" {
        value 1;
        description
          "Hello packet is received from the neighbor.";
      }
      enum "attempt" {
        value 2;
        description
          "The neighbor relationship is being set up, which exists on only an NBMA network. The period of sending and receiving Hello packets is Hello interval. Hello interval is shorter than the poll interval.";
      }
      enum "2-way" {
        value 3;
        description
          "The Hello packet is received from the neighbor and the neighbor list of the Hello packet contains the local ID, that is, the two ends can interwork.";
      }
      enum "exstart" {
        value 4;
        description
          "The neighbor relationship is set up. The master and slave relationship and DD sequence number are negotiated.";
      }
      enum "exchange" {
        value 5;
        description
          "LSDBs are synchronized. DD packets, LSR packets, and LSU packets are exchanged during LSDB synchronization.";
      }
      enum "loading" {
        value 6;
        description
          "LSDBs are being synchronized. LSR packets and LSU packets are exchanged during LSBD synchronization.";
      }
      enum "full" {
        value 7;
        description
          "LSDBs of neighbors have been synchronized. Both sides set up the adjacency and they are in Full state.";
      }
    }
    description
      "OSPFv3 nbr state.";
  }

  typedef interface-state {
    type enumeration {
      enum "down" {
        value 0;
        description
          "Down.";
      }
      enum "waiting" {
        value 1;
        description
          "Waiting.";
      }
      enum "p-2-p" {
        value 2;
        description
          "P-2-P.";
      }
      enum "dr" {
        value 3;
        description
          "DR.";
      }
      enum "bdr" {
        value 4;
        description
          "BDR.";
      }
      enum "dr-other" {
        value 5;
        description
          "DROTHER.";
      }
      enum "loopback" {
        value 6;
        description
          "Loopback.";
      }
      enum "point-to-point" {
        value 18;
        description
          "Point-To-Point.";
      }
      enum "backup" {
        value 20;
        description
          "Backup.";
      }
    }
    description
      "OSPFv3 interface state.";
  }

  typedef auth-type {
    type enumeration {
      enum "none" {
        value 0;
        description
          "None.";
      }
      enum "hmac-sha256" {
        value 1;
        description
          "HMAC-SHA256.";
      }
      enum "hmac-sha256-inherited" {
        value 2;
        description
          "HMAC-SHA256 [Inherited].";
      }
    }
    description
      "OSPFv3 link protocol.";
  }

  typedef peer-flapping-suppress-type {
    type enumeration {
      enum "disable" {
        value 0;
        description
          "None.";
      }
      enum "enable" {
        value 1;
        description
          "Enable.";
      }
      enum "hold-max-cost" {
        value 2;
        description
          "Hold max cost.";
      }
      enum "hold-down" {
        value 3;
        description
          "Hold down.";
      }
    }
    description
      "OSPFv3 peer suppress-flapping status.";
  }
}
