module huawei-openconfig-mpls-types-ext {
  // Generated by yanger -t ncs
  tailf:mount-id "huawei-nc-1.0:huawei-nc-1.0";
  tailf:ncs-device-type "netconf";

  namespace "urn:huawei:yang:huawei-openconfig-mpls-types-ext";
  prefix hw-oc-mplst-ext;

  import openconfig-mpls-types {
    prefix oc-mplst;
  }
  import huawei-extension {
    prefix ext;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com
    ";
  description
    "GRPC.";

  revision 2019-03-01 {
    description
      "Initial revision.";
    reference "Huawei private.";
  }
  ext:task-name "mpls-base";

  identity NONNULL {
    base oc-mplst:NULL_LABEL_TYPE;
    description
      "Non-null label is used.";
  }
}
