module huawei-bgp-mvpn-deviations-NE8000 {
  // Generated by yanger -t ncs
  tailf:mount-id "huawei-nc-1.0:huawei-nc-1.0";
  tailf:ncs-device-type "netconf";

  namespace "urn:huawei:yang:huawei-bgp-mvpn-deviations-NE8000";
  prefix bgp-mvpn-devs-NE8000;

  import huawei-bgp {
    prefix bgp;
  }
  import huawei-network-instance {
    prefix ni;
  }
  import huawei-bgp-mvpn {
    prefix bgp-mvpn;
  }
  import tailf-common {
    prefix tailf;
  }
  import tailf-ncs {
    prefix ncs;
  }

  organization
    "Huawei Technologies Co., Ltd.";
  contact
    "Huawei Industrial Base
     Bantian, Longgang
     Shenzhen 518129
     People's Republic of China
     Website: http://www.huawei.com
     Email: support@huawei.com";
  description
    "Inter-AS routing protocol that exchanges Network Layer Reachability Information (NLRI) with other BGP systems.";

  revision 2019-03-22 {
    description
      "Initial revision.";
    reference "Huawei private.";
  }

  deviation "/ncs:devices/ncs:template/ncs:ned-id/ncs:config/ni:network-instance/ni:instances/ni:instance/bgp:bgp/bgp:base-process/bgp:peers/bgp:peer/bgp:afs/bgp:af/bgp-mvpn:ipv4-mvpn/bgp-mvpn:add-path-mode" {
    deviate not-supported;
  }
  deviation "/ncs:devices/ncs:device/ncs:live-status/ni:network-instance/ni:instances/ni:instance/bgp:bgp/bgp:base-process/bgp:peers/bgp:peer/bgp:afs/bgp:af/bgp-mvpn:ipv4-mvpn/bgp-mvpn:add-path-mode" {
    deviate not-supported;
  }
  deviation "/ncs:devices/ncs:device/ncs:config/ni:network-instance/ni:instances/ni:instance/bgp:bgp/bgp:base-process/bgp:peers/bgp:peer/bgp:afs/bgp:af/bgp-mvpn:ipv4-mvpn/bgp-mvpn:add-path-mode" {
    deviate not-supported;
  }
  deviation "/ncs:devices/ncs:template/ncs:ned-id/ncs:config/ni:network-instance/ni:instances/ni:instance/bgp:bgp/bgp:base-process/bgp:peer-groups/bgp:peer-group/bgp:afs/bgp:af/bgp-mvpn:ipv4-mvpn/bgp-mvpn:add-path-mode" {
    deviate not-supported;
  }
  deviation "/ncs:devices/ncs:device/ncs:live-status/ni:network-instance/ni:instances/ni:instance/bgp:bgp/bgp:base-process/bgp:peer-groups/bgp:peer-group/bgp:afs/bgp:af/bgp-mvpn:ipv4-mvpn/bgp-mvpn:add-path-mode" {
    deviate not-supported;
  }
  deviation "/ncs:devices/ncs:device/ncs:config/ni:network-instance/ni:instances/ni:instance/bgp:bgp/bgp:base-process/bgp:peer-groups/bgp:peer-group/bgp:afs/bgp:af/bgp-mvpn:ipv4-mvpn/bgp-mvpn:add-path-mode" {
    deviate not-supported;
  }
  deviation "/ncs:devices/ncs:template/ncs:ned-id/ncs:config/ni:network-instance/ni:instances/ni:instance/bgp:bgp/bgp:base-process/bgp:afs/bgp:af/bgp-mvpn:ipv4-mvpn/bgp-mvpn:common/bgp-mvpn:add-path-select-num" {
    deviate not-supported;
  }
  deviation "/ncs:devices/ncs:device/ncs:live-status/ni:network-instance/ni:instances/ni:instance/bgp:bgp/bgp:base-process/bgp:afs/bgp:af/bgp-mvpn:ipv4-mvpn/bgp-mvpn:common/bgp-mvpn:add-path-select-num" {
    deviate not-supported;
  }
  deviation "/ncs:devices/ncs:device/ncs:config/ni:network-instance/ni:instances/ni:instance/bgp:bgp/bgp:base-process/bgp:afs/bgp:af/bgp-mvpn:ipv4-mvpn/bgp-mvpn:common/bgp-mvpn:add-path-select-num" {
    deviate not-supported;
  }
  deviation "/ncs:devices/ncs:template/ncs:ned-id/ncs:config/ni:network-instance/ni:instances/ni:instance/bgp:bgp/bgp:base-process/bgp:peers/bgp:peer/bgp:afs/bgp:af/bgp-mvpn:ipv6-mvpn/bgp-mvpn:add-path-mode" {
    deviate not-supported;
  }
  deviation "/ncs:devices/ncs:device/ncs:live-status/ni:network-instance/ni:instances/ni:instance/bgp:bgp/bgp:base-process/bgp:peers/bgp:peer/bgp:afs/bgp:af/bgp-mvpn:ipv6-mvpn/bgp-mvpn:add-path-mode" {
    deviate not-supported;
  }
  deviation "/ncs:devices/ncs:device/ncs:config/ni:network-instance/ni:instances/ni:instance/bgp:bgp/bgp:base-process/bgp:peers/bgp:peer/bgp:afs/bgp:af/bgp-mvpn:ipv6-mvpn/bgp-mvpn:add-path-mode" {
    deviate not-supported;
  }
  deviation "/ncs:devices/ncs:template/ncs:ned-id/ncs:config/ni:network-instance/ni:instances/ni:instance/bgp:bgp/bgp:base-process/bgp:peer-groups/bgp:peer-group/bgp:afs/bgp:af/bgp-mvpn:ipv6-mvpn/bgp-mvpn:add-path-mode" {
    deviate not-supported;
  }
  deviation "/ncs:devices/ncs:device/ncs:live-status/ni:network-instance/ni:instances/ni:instance/bgp:bgp/bgp:base-process/bgp:peer-groups/bgp:peer-group/bgp:afs/bgp:af/bgp-mvpn:ipv6-mvpn/bgp-mvpn:add-path-mode" {
    deviate not-supported;
  }
  deviation "/ncs:devices/ncs:device/ncs:config/ni:network-instance/ni:instances/ni:instance/bgp:bgp/bgp:base-process/bgp:peer-groups/bgp:peer-group/bgp:afs/bgp:af/bgp-mvpn:ipv6-mvpn/bgp-mvpn:add-path-mode" {
    deviate not-supported;
  }
  deviation "/ncs:devices/ncs:template/ncs:ned-id/ncs:config/ni:network-instance/ni:instances/ni:instance/bgp:bgp/bgp:base-process/bgp:afs/bgp:af/bgp-mvpn:ipv6-mvpn/bgp-mvpn:common/bgp-mvpn:add-path-select-num" {
    deviate not-supported;
  }
  deviation "/ncs:devices/ncs:device/ncs:live-status/ni:network-instance/ni:instances/ni:instance/bgp:bgp/bgp:base-process/bgp:afs/bgp:af/bgp-mvpn:ipv6-mvpn/bgp-mvpn:common/bgp-mvpn:add-path-select-num" {
    deviate not-supported;
  }
  deviation "/ncs:devices/ncs:device/ncs:config/ni:network-instance/ni:instances/ni:instance/bgp:bgp/bgp:base-process/bgp:afs/bgp:af/bgp-mvpn:ipv6-mvpn/bgp-mvpn:common/bgp-mvpn:add-path-select-num" {
    deviate not-supported;
  }
}
